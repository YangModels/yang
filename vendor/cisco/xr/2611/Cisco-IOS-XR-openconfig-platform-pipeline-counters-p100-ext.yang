module Cisco-IOS-XR-openconfig-platform-pipeline-counters-p100-ext {
  yang-version 1;
  namespace "http://cisco.com/ns/yang/Cisco-IOS-XR-openconfig-platform-pipeline-counters-p100-ext";
  prefix p100;

  import openconfig-yang-types {
    prefix oc-yang;
  }
  import openconfig-extensions {
    prefix oc-ext;
  }
  import openconfig-platform {
    prefix oc-platform;
  }
  import openconfig-platform-pipeline-counters {
    prefix oc-ppc;
  }
  import Cisco-IOS-XR-openconfig-platform-pipeline-counters-ext {
    prefix cisco;
  }

  organization
    "Cisco Systems, Inc";
  contact
    "Cisco Systems
     Customer Service
     Postal: 170 West Tasman Drive
     San Jose, CA 95134
     
     Tel: +1 800 553-NETS
     
     E-mail: cs-yang@cisco.com";
  description
    "Adding augments to oc-ppc yang for providing vendor based counters for the p100 asic";

  revision 2024-08-20 {
    description
      "Updated leaf information";
  }
  revision 2024-07-20 {
    description
      "Initial revision to support vendor drop counters";
  }

  grouping cisco-p100-adverse-drop-counters {
    description
      "Adverse Drop leafs grouping for the p100 asic";
    leaf counters_mmu_errors_drop_dbd_rcvd {
      type oc-yang:counter64;
      description
        "Count DBD with drop bit set";
    }
    leaf counters_npu_host_in_packets_in_with_errors {
      type oc-yang:counter64;
      description
        "Number of packets arrived from npu with errors";
    }
    leaf counters_slice0_ifg0_ifgb_rx_protection_errors {
      type oc-yang:counter64;
      description
        "RXPP interface protection errors counter.";
    }
    leaf counters_slice0_ifg0_ifgb_tx_protection_dropped_packets {
      type oc-yang:counter64;
      description
        "TXPP interface protection packet drop counter. Number of invalid packets arrived to TX.";
    }
    leaf counters_slice0_ifg0_ifgb_tx_protection_dropped_words {
      type oc-yang:counter64;
      description
        "TXPP interface protection words drop counter. Number of invalid words arrived to TX.";
    }
    leaf counters_slice0_ifg0_ifgb_tx_protection_errors {
      type oc-yang:counter64;
      description
        "TXPP interface protection errors counter.";
    }
    leaf counters_slice0_ifg0_ifgbi_pif_sequence_number_error {
      type oc-yang:counter64;
      description
        "PIF Sequence Number Error Count";
    }
    leaf counters_slice0_ifg0_ifgbi_rx_context_allocation_errors {
      type oc-yang:counter64;
      description
        "The amount of RXPP backpressure assertion events.";
    }
    leaf counters_slice0_ifg0_ifgbi_dash0_hp_dropped_full_packet {
      type oc-yang:counter64;
      description
        "SOP Drop Pkt Count - Full High Priority packet drops based on WrSopThd";
    }
    leaf counters_slice0_ifg0_ifgbi_dash0_hp_dropped_packets {
      type oc-yang:counter64;
      description
        "FIFO Full Pkt Count - Partial High Priority packet drops due to no space in FIFO";
    }
    leaf counters_slice0_ifg0_ifgbi_dash0_hp_dropped_words {
      type oc-yang:counter64;
      description
        "Word Drop Count - Partial High Priority word drops due to no space in FIFO";
    }
    leaf counters_slice0_ifg0_ifgbi_dash0_lp_dropped_full_packet {
      type oc-yang:counter64;
      description
        "SOP Drop Pkt Count - Full Low Priority packet drops based on WrSopThd";
    }
    leaf counters_slice0_ifg0_ifgbi_dash0_lp_dropped_packets {
      type oc-yang:counter64;
      description
        "FIFO Full Pkt Count - Partial Low Priority packet drops due to no space in FIFO";
    }
    leaf counters_slice0_ifg0_ifgbi_dash0_lp_dropped_words {
      type oc-yang:counter64;
      description
        "Word Drop Count - Partial Low Priority word drops due to no space in FIFO";
    }
    leaf counters_slice0_ifg0_ifgbi_dash1_hp_dropped_full_packet {
      type oc-yang:counter64;
      description
        "SOP Drop Pkt Count - Full High Priority packet drops based on WrSopThd";
    }
    leaf counters_slice0_ifg0_ifgbi_dash1_hp_dropped_packets {
      type oc-yang:counter64;
      description
        "FIFO Full Pkt Count - Partial High Priority packet drops due to no space in FIFO";
    }
    leaf counters_slice0_ifg0_ifgbi_dash1_hp_dropped_words {
      type oc-yang:counter64;
      description
        "Word Drop Count - Partial High Priority word drops due to no space in FIFO";
    }
    leaf counters_slice0_ifg0_ifgbi_dash1_lp_dropped_full_packet {
      type oc-yang:counter64;
      description
        "SOP Drop Pkt Count - Full Low Priority packet drops based on WrSopThd";
    }
    leaf counters_slice0_ifg0_ifgbi_dash1_lp_dropped_packets {
      type oc-yang:counter64;
      description
        "FIFO Full Pkt Count - Partial Low Priority packet drops due to no space in FIFO";
    }
    leaf counters_slice0_ifg0_ifgbi_dash1_lp_dropped_words {
      type oc-yang:counter64;
      description
        "Word Drop Count - Partial Low Priority word drops due to no space in FIFO";
    }
    leaf counters_slice0_ifg0_ifgbi_inband_extract_nph_errored_packets {
      type oc-yang:counter64;
      description
        "Inband Extract Bad packet extracted";
    }
    leaf counters_slice0_ifg0_ifgbi_inband_extract_pdm_errored_packets {
      type oc-yang:counter64;
      description
        "Inband Extract Bad packet extracted";
    }
    leaf counters_slice0_ifg0_ifgbi_inband_inject_nph_errored_packets {
      type oc-yang:counter64;
      description
        "Inband Inject Bad packet injected";
    }
    leaf counters_slice0_ifg0_ifgbi_inband_inject_pdm_errored_packets {
      type oc-yang:counter64;
      description
        "Inband Inject Bad packet injected";
    }
    leaf counters_slice0_ifg0_ifgbi_oobi_csms_dropped_packets {
      type oc-yang:counter64;
      description
        "Injected CSMS pkt drop cnt across all links";
    }
    leaf counters_slice0_ifg0_ifgbi_oobi_frm_dropped_packets {
      type oc-yang:counter64;
      description
        "Injected FRM pkt drop cnt across all links";
    }
    leaf counters_slice0_ifg0_ifgbi_oobi_fte_fts_dropped_packets {
      type oc-yang:counter64;
      description
        "Injected FTE Fabric Time Sync pkt drop cnt across all links";
    }
    leaf counters_slice0_ifg0_ifgbi_oobi_fte_pd_req_dropped_packets {
      type oc-yang:counter64;
      description
        "Injected FTE Peer Delay Request pkt drop cnt across all links";
    }
    leaf counters_slice0_ifg0_ifgbi_oobi_fte_pd_res_dropped_packets {
      type oc-yang:counter64;
      description
        "Injected FTE Peer Delay Response pkt drop cnt across all links";
    }
    leaf counters_slice0_ifg0_ifgbi_recycle_recycle_drop_on_port0 {
      type oc-yang:counter64;
      description
        "IFG recycling drop counter. Increments based on the RcyDropCntrsCfg.";
    }
    leaf counters_slice0_ifg0_ifgbi_recycle_recycle_drop_on_port1 {
      type oc-yang:counter64;
      description
        "IFG recycling drop counter. Increments based on the RcyDropCntrsCfg.";
    }
    leaf counters_slice0_ifg0_ifgbi_recycle_recycle_drop_on_port10 {
      type oc-yang:counter64;
      description
        "IFG recycling drop counter. Increments based on the RcyDropCntrsCfg.";
    }
    leaf counters_slice0_ifg0_ifgbi_recycle_recycle_drop_on_port11 {
      type oc-yang:counter64;
      description
        "IFG recycling drop counter. Increments based on the RcyDropCntrsCfg.";
    }
    leaf counters_slice0_ifg0_ifgbi_recycle_recycle_drop_on_port12 {
      type oc-yang:counter64;
      description
        "IFG recycling drop counter. Increments based on the RcyDropCntrsCfg.";
    }
    leaf counters_slice0_ifg0_ifgbi_recycle_recycle_drop_on_port13 {
      type oc-yang:counter64;
      description
        "IFG recycling drop counter. Increments based on the RcyDropCntrsCfg.";
    }
    leaf counters_slice0_ifg0_ifgbi_recycle_recycle_drop_on_port14 {
      type oc-yang:counter64;
      description
        "IFG recycling drop counter. Increments based on the RcyDropCntrsCfg.";
    }
    leaf counters_slice0_ifg0_ifgbi_recycle_recycle_drop_on_port15 {
      type oc-yang:counter64;
      description
        "IFG recycling drop counter. Increments based on the RcyDropCntrsCfg.";
    }
    leaf counters_slice0_ifg0_ifgbi_recycle_recycle_drop_on_port16 {
      type oc-yang:counter64;
      description
        "IFG recycling drop counter. Increments based on the RcyDropCntrsCfg.";
    }
    leaf counters_slice0_ifg0_ifgbi_recycle_recycle_drop_on_port17 {
      type oc-yang:counter64;
      description
        "IFG recycling drop counter. Increments based on the RcyDropCntrsCfg.";
    }
    leaf counters_slice0_ifg0_ifgbi_recycle_recycle_drop_on_port18 {
      type oc-yang:counter64;
      description
        "IFG recycling drop counter. Increments based on the RcyDropCntrsCfg.";
    }
    leaf counters_slice0_ifg0_ifgbi_recycle_recycle_drop_on_port19 {
      type oc-yang:counter64;
      description
        "IFG recycling drop counter. Increments based on the RcyDropCntrsCfg.";
    }
    leaf counters_slice0_ifg0_ifgbi_recycle_recycle_drop_on_port2 {
      type oc-yang:counter64;
      description
        "IFG recycling drop counter. Increments based on the RcyDropCntrsCfg.";
    }
    leaf counters_slice0_ifg0_ifgbi_recycle_recycle_drop_on_port20 {
      type oc-yang:counter64;
      description
        "IFG recycling drop counter. Increments based on the RcyDropCntrsCfg.";
    }
    leaf counters_slice0_ifg0_ifgbi_recycle_recycle_drop_on_port21 {
      type oc-yang:counter64;
      description
        "IFG recycling drop counter. Increments based on the RcyDropCntrsCfg.";
    }
    leaf counters_slice0_ifg0_ifgbi_recycle_recycle_drop_on_port22 {
      type oc-yang:counter64;
      description
        "IFG recycling drop counter. Increments based on the RcyDropCntrsCfg.";
    }
    leaf counters_slice0_ifg0_ifgbi_recycle_recycle_drop_on_port23 {
      type oc-yang:counter64;
      description
        "IFG recycling drop counter. Increments based on the RcyDropCntrsCfg.";
    }
    leaf counters_slice0_ifg0_ifgbi_recycle_recycle_drop_on_port24 {
      type oc-yang:counter64;
      description
        "IFG recycling drop counter. Increments based on the RcyDropCntrsCfg.";
    }
    leaf counters_slice0_ifg0_ifgbi_recycle_recycle_drop_on_port25 {
      type oc-yang:counter64;
      description
        "IFG recycling drop counter. Increments based on the RcyDropCntrsCfg.";
    }
    leaf counters_slice0_ifg0_ifgbi_recycle_recycle_drop_on_port26 {
      type oc-yang:counter64;
      description
        "IFG recycling drop counter. Increments based on the RcyDropCntrsCfg.";
    }
    leaf counters_slice0_ifg0_ifgbi_recycle_recycle_drop_on_port27 {
      type oc-yang:counter64;
      description
        "IFG recycling drop counter. Increments based on the RcyDropCntrsCfg.";
    }
    leaf counters_slice0_ifg0_ifgbi_recycle_recycle_drop_on_port28 {
      type oc-yang:counter64;
      description
        "IFG recycling drop counter. Increments based on the RcyDropCntrsCfg.";
    }
    leaf counters_slice0_ifg0_ifgbi_recycle_recycle_drop_on_port29 {
      type oc-yang:counter64;
      description
        "IFG recycling drop counter. Increments based on the RcyDropCntrsCfg.";
    }
    leaf counters_slice0_ifg0_ifgbi_recycle_recycle_drop_on_port3 {
      type oc-yang:counter64;
      description
        "IFG recycling drop counter. Increments based on the RcyDropCntrsCfg.";
    }
    leaf counters_slice0_ifg0_ifgbi_recycle_recycle_drop_on_port30 {
      type oc-yang:counter64;
      description
        "IFG recycling drop counter. Increments based on the RcyDropCntrsCfg.";
    }
    leaf counters_slice0_ifg0_ifgbi_recycle_recycle_drop_on_port31 {
      type oc-yang:counter64;
      description
        "IFG recycling drop counter. Increments based on the RcyDropCntrsCfg.";
    }
    leaf counters_slice0_ifg0_ifgbi_recycle_recycle_drop_on_port4 {
      type oc-yang:counter64;
      description
        "IFG recycling drop counter. Increments based on the RcyDropCntrsCfg.";
    }
    leaf counters_slice0_ifg0_ifgbi_recycle_recycle_drop_on_port5 {
      type oc-yang:counter64;
      description
        "IFG recycling drop counter. Increments based on the RcyDropCntrsCfg.";
    }
    leaf counters_slice0_ifg0_ifgbi_recycle_recycle_drop_on_port6 {
      type oc-yang:counter64;
      description
        "IFG recycling drop counter. Increments based on the RcyDropCntrsCfg.";
    }
    leaf counters_slice0_ifg0_ifgbi_recycle_recycle_drop_on_port7 {
      type oc-yang:counter64;
      description
        "IFG recycling drop counter. Increments based on the RcyDropCntrsCfg.";
    }
    leaf counters_slice0_ifg0_ifgbi_recycle_recycle_drop_on_port8 {
      type oc-yang:counter64;
      description
        "IFG recycling drop counter. Increments based on the RcyDropCntrsCfg.";
    }
    leaf counters_slice0_ifg0_ifgbi_recycle_recycle_drop_on_port9 {
      type oc-yang:counter64;
      description
        "IFG recycling drop counter. Increments based on the RcyDropCntrsCfg.";
    }
    leaf counters_slice0_ifg0_ifgbi_rx_protection_abnormally_terminated_packets {
      type oc-yang:counter64;
      description
        "RXPP interface protection packets termiante abnormally counter";
    }
    leaf counters_slice0_ifg0_mac_pool80_port0_rx_oob_mac_type_errors {
      type oc-yang:counter64;
      description
        "Counts in interleaving mode OOB packets that are received with none OOB packet type.";
    }
    leaf counters_slice0_ifg0_mac_pool80_port1_rx_oob_mac_type_errors {
      type oc-yang:counter64;
      description
        "Counts in interleaving mode OOB packets that are received with none OOB packet type.";
    }
    leaf counters_slice0_ifg0_mac_pool80_port2_rx_oob_mac_type_errors {
      type oc-yang:counter64;
      description
        "Counts in interleaving mode OOB packets that are received with none OOB packet type.";
    }
    leaf counters_slice0_ifg0_mac_pool80_port3_rx_oob_mac_type_errors {
      type oc-yang:counter64;
      description
        "Counts in interleaving mode OOB packets that are received with none OOB packet type.";
    }
    leaf counters_slice0_ifg0_mac_pool81_port0_rx_oob_mac_type_errors {
      type oc-yang:counter64;
      description
        "Counts in interleaving mode OOB packets that are received with none OOB packet type.";
    }
    leaf counters_slice0_ifg0_mac_pool81_port1_rx_oob_mac_type_errors {
      type oc-yang:counter64;
      description
        "Counts in interleaving mode OOB packets that are received with none OOB packet type.";
    }
    leaf counters_slice0_ifg0_mac_pool81_port2_rx_oob_mac_type_errors {
      type oc-yang:counter64;
      description
        "Counts in interleaving mode OOB packets that are received with none OOB packet type.";
    }
    leaf counters_slice0_ifg0_mac_pool81_port3_rx_oob_mac_type_errors {
      type oc-yang:counter64;
      description
        "Counts in interleaving mode OOB packets that are received with none OOB packet type.";
    }
    leaf counters_slice0_ifg0_mac_pool82_port0_rx_oob_mac_type_errors {
      type oc-yang:counter64;
      description
        "Counts in interleaving mode OOB packets that are received with none OOB packet type.";
    }
    leaf counters_slice0_ifg0_mac_pool82_port1_rx_oob_mac_type_errors {
      type oc-yang:counter64;
      description
        "Counts in interleaving mode OOB packets that are received with none OOB packet type.";
    }
    leaf counters_slice0_ifg0_mac_pool82_port2_rx_oob_mac_type_errors {
      type oc-yang:counter64;
      description
        "Counts in interleaving mode OOB packets that are received with none OOB packet type.";
    }
    leaf counters_slice0_ifg0_mac_pool82_port3_rx_oob_mac_type_errors {
      type oc-yang:counter64;
      description
        "Counts in interleaving mode OOB packets that are received with none OOB packet type.";
    }
    leaf counters_slice0_ifg0_mac_pool83_port0_rx_oob_mac_type_errors {
      type oc-yang:counter64;
      description
        "Counts in interleaving mode OOB packets that are received with none OOB packet type.";
    }
    leaf counters_slice0_ifg0_mac_pool83_port1_rx_oob_mac_type_errors {
      type oc-yang:counter64;
      description
        "Counts in interleaving mode OOB packets that are received with none OOB packet type.";
    }
    leaf counters_slice0_ifg0_mac_pool83_port2_rx_oob_mac_type_errors {
      type oc-yang:counter64;
      description
        "Counts in interleaving mode OOB packets that are received with none OOB packet type.";
    }
    leaf counters_slice0_ifg0_mac_pool83_port3_rx_oob_mac_type_errors {
      type oc-yang:counter64;
      description
        "Counts in interleaving mode OOB packets that are received with none OOB packet type.";
    }
    leaf counters_slice0_ifg0_npu_txpp_ifc_cluster_dropped_bad_packets {
      type oc-yang:counter64;
      description
        "Counts bad packets arrived to txpp Number of packet drops at the output of TxPP on IFG <i>";
    }
    leaf counters_slice0_ifg1_ifgb_rx_protection_errors {
      type oc-yang:counter64;
      description
        "RXPP interface protection errors counter.";
    }
    leaf counters_slice0_ifg1_ifgb_tx_protection_dropped_packets {
      type oc-yang:counter64;
      description
        "TXPP interface protection packet drop counter. Number of invalid packets arrived to TX.";
    }
    leaf counters_slice0_ifg1_ifgb_tx_protection_dropped_words {
      type oc-yang:counter64;
      description
        "TXPP interface protection words drop counter. Number of invalid words arrived to TX.";
    }
    leaf counters_slice0_ifg1_ifgb_tx_protection_errors {
      type oc-yang:counter64;
      description
        "TXPP interface protection errors counter.";
    }
    leaf counters_slice0_ifg1_ifgbi_pif_sequence_number_error {
      type oc-yang:counter64;
      description
        "PIF Sequence Number Error Count";
    }
    leaf counters_slice0_ifg1_ifgbi_rx_context_allocation_errors {
      type oc-yang:counter64;
      description
        "The amount of RXPP backpressure assertion events.";
    }
    leaf counters_slice0_ifg1_ifgbi_dash0_hp_dropped_full_packet {
      type oc-yang:counter64;
      description
        "SOP Drop Pkt Count - Full High Priority packet drops based on WrSopThd";
    }
    leaf counters_slice0_ifg1_ifgbi_dash0_hp_dropped_packets {
      type oc-yang:counter64;
      description
        "FIFO Full Pkt Count - Partial High Priority packet drops due to no space in FIFO";
    }
    leaf counters_slice0_ifg1_ifgbi_dash0_hp_dropped_words {
      type oc-yang:counter64;
      description
        "Word Drop Count - Partial High Priority word drops due to no space in FIFO";
    }
    leaf counters_slice0_ifg1_ifgbi_dash0_lp_dropped_full_packet {
      type oc-yang:counter64;
      description
        "SOP Drop Pkt Count - Full Low Priority packet drops based on WrSopThd";
    }
    leaf counters_slice0_ifg1_ifgbi_dash0_lp_dropped_packets {
      type oc-yang:counter64;
      description
        "FIFO Full Pkt Count - Partial Low Priority packet drops due to no space in FIFO";
    }
    leaf counters_slice0_ifg1_ifgbi_dash0_lp_dropped_words {
      type oc-yang:counter64;
      description
        "Word Drop Count - Partial Low Priority word drops due to no space in FIFO";
    }
    leaf counters_slice0_ifg1_ifgbi_dash1_hp_dropped_full_packet {
      type oc-yang:counter64;
      description
        "SOP Drop Pkt Count - Full High Priority packet drops based on WrSopThd";
    }
    leaf counters_slice0_ifg1_ifgbi_dash1_hp_dropped_packets {
      type oc-yang:counter64;
      description
        "FIFO Full Pkt Count - Partial High Priority packet drops due to no space in FIFO";
    }
    leaf counters_slice0_ifg1_ifgbi_dash1_hp_dropped_words {
      type oc-yang:counter64;
      description
        "Word Drop Count - Partial High Priority word drops due to no space in FIFO";
    }
    leaf counters_slice0_ifg1_ifgbi_dash1_lp_dropped_full_packet {
      type oc-yang:counter64;
      description
        "SOP Drop Pkt Count - Full Low Priority packet drops based on WrSopThd";
    }
    leaf counters_slice0_ifg1_ifgbi_dash1_lp_dropped_packets {
      type oc-yang:counter64;
      description
        "FIFO Full Pkt Count - Partial Low Priority packet drops due to no space in FIFO";
    }
    leaf counters_slice0_ifg1_ifgbi_dash1_lp_dropped_words {
      type oc-yang:counter64;
      description
        "Word Drop Count - Partial Low Priority word drops due to no space in FIFO";
    }
    leaf counters_slice0_ifg1_ifgbi_inband_extract_nph_errored_packets {
      type oc-yang:counter64;
      description
        "Inband Extract Bad packet extracted";
    }
    leaf counters_slice0_ifg1_ifgbi_inband_extract_pdm_errored_packets {
      type oc-yang:counter64;
      description
        "Inband Extract Bad packet extracted";
    }
    leaf counters_slice0_ifg1_ifgbi_inband_inject_nph_errored_packets {
      type oc-yang:counter64;
      description
        "Inband Inject Bad packet injected";
    }
    leaf counters_slice0_ifg1_ifgbi_inband_inject_pdm_errored_packets {
      type oc-yang:counter64;
      description
        "Inband Inject Bad packet injected";
    }
    leaf counters_slice0_ifg1_ifgbi_oobi_csms_dropped_packets {
      type oc-yang:counter64;
      description
        "Injected CSMS pkt drop cnt across all links";
    }
    leaf counters_slice0_ifg1_ifgbi_oobi_frm_dropped_packets {
      type oc-yang:counter64;
      description
        "Injected FRM pkt drop cnt across all links";
    }
    leaf counters_slice0_ifg1_ifgbi_oobi_fte_fts_dropped_packets {
      type oc-yang:counter64;
      description
        "Injected FTE Fabric Time Sync pkt drop cnt across all links";
    }
    leaf counters_slice0_ifg1_ifgbi_oobi_fte_pd_req_dropped_packets {
      type oc-yang:counter64;
      description
        "Injected FTE Peer Delay Request pkt drop cnt across all links";
    }
    leaf counters_slice0_ifg1_ifgbi_oobi_fte_pd_res_dropped_packets {
      type oc-yang:counter64;
      description
        "Injected FTE Peer Delay Response pkt drop cnt across all links";
    }
    leaf counters_slice0_ifg1_ifgbi_recycle_recycle_drop_on_port0 {
      type oc-yang:counter64;
      description
        "IFG recycling drop counter. Increments based on the RcyDropCntrsCfg.";
    }
    leaf counters_slice0_ifg1_ifgbi_recycle_recycle_drop_on_port1 {
      type oc-yang:counter64;
      description
        "IFG recycling drop counter. Increments based on the RcyDropCntrsCfg.";
    }
    leaf counters_slice0_ifg1_ifgbi_recycle_recycle_drop_on_port10 {
      type oc-yang:counter64;
      description
        "IFG recycling drop counter. Increments based on the RcyDropCntrsCfg.";
    }
    leaf counters_slice0_ifg1_ifgbi_recycle_recycle_drop_on_port11 {
      type oc-yang:counter64;
      description
        "IFG recycling drop counter. Increments based on the RcyDropCntrsCfg.";
    }
    leaf counters_slice0_ifg1_ifgbi_recycle_recycle_drop_on_port12 {
      type oc-yang:counter64;
      description
        "IFG recycling drop counter. Increments based on the RcyDropCntrsCfg.";
    }
    leaf counters_slice0_ifg1_ifgbi_recycle_recycle_drop_on_port13 {
      type oc-yang:counter64;
      description
        "IFG recycling drop counter. Increments based on the RcyDropCntrsCfg.";
    }
    leaf counters_slice0_ifg1_ifgbi_recycle_recycle_drop_on_port14 {
      type oc-yang:counter64;
      description
        "IFG recycling drop counter. Increments based on the RcyDropCntrsCfg.";
    }
    leaf counters_slice0_ifg1_ifgbi_recycle_recycle_drop_on_port15 {
      type oc-yang:counter64;
      description
        "IFG recycling drop counter. Increments based on the RcyDropCntrsCfg.";
    }
    leaf counters_slice0_ifg1_ifgbi_recycle_recycle_drop_on_port16 {
      type oc-yang:counter64;
      description
        "IFG recycling drop counter. Increments based on the RcyDropCntrsCfg.";
    }
    leaf counters_slice0_ifg1_ifgbi_recycle_recycle_drop_on_port17 {
      type oc-yang:counter64;
      description
        "IFG recycling drop counter. Increments based on the RcyDropCntrsCfg.";
    }
    leaf counters_slice0_ifg1_ifgbi_recycle_recycle_drop_on_port18 {
      type oc-yang:counter64;
      description
        "IFG recycling drop counter. Increments based on the RcyDropCntrsCfg.";
    }
    leaf counters_slice0_ifg1_ifgbi_recycle_recycle_drop_on_port19 {
      type oc-yang:counter64;
      description
        "IFG recycling drop counter. Increments based on the RcyDropCntrsCfg.";
    }
    leaf counters_slice0_ifg1_ifgbi_recycle_recycle_drop_on_port2 {
      type oc-yang:counter64;
      description
        "IFG recycling drop counter. Increments based on the RcyDropCntrsCfg.";
    }
    leaf counters_slice0_ifg1_ifgbi_recycle_recycle_drop_on_port20 {
      type oc-yang:counter64;
      description
        "IFG recycling drop counter. Increments based on the RcyDropCntrsCfg.";
    }
    leaf counters_slice0_ifg1_ifgbi_recycle_recycle_drop_on_port21 {
      type oc-yang:counter64;
      description
        "IFG recycling drop counter. Increments based on the RcyDropCntrsCfg.";
    }
    leaf counters_slice0_ifg1_ifgbi_recycle_recycle_drop_on_port22 {
      type oc-yang:counter64;
      description
        "IFG recycling drop counter. Increments based on the RcyDropCntrsCfg.";
    }
    leaf counters_slice0_ifg1_ifgbi_recycle_recycle_drop_on_port23 {
      type oc-yang:counter64;
      description
        "IFG recycling drop counter. Increments based on the RcyDropCntrsCfg.";
    }
    leaf counters_slice0_ifg1_ifgbi_recycle_recycle_drop_on_port24 {
      type oc-yang:counter64;
      description
        "IFG recycling drop counter. Increments based on the RcyDropCntrsCfg.";
    }
    leaf counters_slice0_ifg1_ifgbi_recycle_recycle_drop_on_port25 {
      type oc-yang:counter64;
      description
        "IFG recycling drop counter. Increments based on the RcyDropCntrsCfg.";
    }
    leaf counters_slice0_ifg1_ifgbi_recycle_recycle_drop_on_port26 {
      type oc-yang:counter64;
      description
        "IFG recycling drop counter. Increments based on the RcyDropCntrsCfg.";
    }
    leaf counters_slice0_ifg1_ifgbi_recycle_recycle_drop_on_port27 {
      type oc-yang:counter64;
      description
        "IFG recycling drop counter. Increments based on the RcyDropCntrsCfg.";
    }
    leaf counters_slice0_ifg1_ifgbi_recycle_recycle_drop_on_port28 {
      type oc-yang:counter64;
      description
        "IFG recycling drop counter. Increments based on the RcyDropCntrsCfg.";
    }
    leaf counters_slice0_ifg1_ifgbi_recycle_recycle_drop_on_port29 {
      type oc-yang:counter64;
      description
        "IFG recycling drop counter. Increments based on the RcyDropCntrsCfg.";
    }
    leaf counters_slice0_ifg1_ifgbi_recycle_recycle_drop_on_port3 {
      type oc-yang:counter64;
      description
        "IFG recycling drop counter. Increments based on the RcyDropCntrsCfg.";
    }
    leaf counters_slice0_ifg1_ifgbi_recycle_recycle_drop_on_port30 {
      type oc-yang:counter64;
      description
        "IFG recycling drop counter. Increments based on the RcyDropCntrsCfg.";
    }
    leaf counters_slice0_ifg1_ifgbi_recycle_recycle_drop_on_port31 {
      type oc-yang:counter64;
      description
        "IFG recycling drop counter. Increments based on the RcyDropCntrsCfg.";
    }
    leaf counters_slice0_ifg1_ifgbi_recycle_recycle_drop_on_port4 {
      type oc-yang:counter64;
      description
        "IFG recycling drop counter. Increments based on the RcyDropCntrsCfg.";
    }
    leaf counters_slice0_ifg1_ifgbi_recycle_recycle_drop_on_port5 {
      type oc-yang:counter64;
      description
        "IFG recycling drop counter. Increments based on the RcyDropCntrsCfg.";
    }
    leaf counters_slice0_ifg1_ifgbi_recycle_recycle_drop_on_port6 {
      type oc-yang:counter64;
      description
        "IFG recycling drop counter. Increments based on the RcyDropCntrsCfg.";
    }
    leaf counters_slice0_ifg1_ifgbi_recycle_recycle_drop_on_port7 {
      type oc-yang:counter64;
      description
        "IFG recycling drop counter. Increments based on the RcyDropCntrsCfg.";
    }
    leaf counters_slice0_ifg1_ifgbi_recycle_recycle_drop_on_port8 {
      type oc-yang:counter64;
      description
        "IFG recycling drop counter. Increments based on the RcyDropCntrsCfg.";
    }
    leaf counters_slice0_ifg1_ifgbi_recycle_recycle_drop_on_port9 {
      type oc-yang:counter64;
      description
        "IFG recycling drop counter. Increments based on the RcyDropCntrsCfg.";
    }
    leaf counters_slice0_ifg1_ifgbi_rx_protection_abnormally_terminated_packets {
      type oc-yang:counter64;
      description
        "RXPP interface protection packets termiante abnormally counter";
    }
    leaf counters_slice0_ifg1_mac_pool80_port0_rx_oob_mac_type_errors {
      type oc-yang:counter64;
      description
        "Counts in interleaving mode OOB packets that are received with none OOB packet type.";
    }
    leaf counters_slice0_ifg1_mac_pool80_port1_rx_oob_mac_type_errors {
      type oc-yang:counter64;
      description
        "Counts in interleaving mode OOB packets that are received with none OOB packet type.";
    }
    leaf counters_slice0_ifg1_mac_pool80_port2_rx_oob_mac_type_errors {
      type oc-yang:counter64;
      description
        "Counts in interleaving mode OOB packets that are received with none OOB packet type.";
    }
    leaf counters_slice0_ifg1_mac_pool80_port3_rx_oob_mac_type_errors {
      type oc-yang:counter64;
      description
        "Counts in interleaving mode OOB packets that are received with none OOB packet type.";
    }
    leaf counters_slice0_ifg1_mac_pool81_port0_rx_oob_mac_type_errors {
      type oc-yang:counter64;
      description
        "Counts in interleaving mode OOB packets that are received with none OOB packet type.";
    }
    leaf counters_slice0_ifg1_mac_pool81_port1_rx_oob_mac_type_errors {
      type oc-yang:counter64;
      description
        "Counts in interleaving mode OOB packets that are received with none OOB packet type.";
    }
    leaf counters_slice0_ifg1_mac_pool81_port2_rx_oob_mac_type_errors {
      type oc-yang:counter64;
      description
        "Counts in interleaving mode OOB packets that are received with none OOB packet type.";
    }
    leaf counters_slice0_ifg1_mac_pool81_port3_rx_oob_mac_type_errors {
      type oc-yang:counter64;
      description
        "Counts in interleaving mode OOB packets that are received with none OOB packet type.";
    }
    leaf counters_slice0_ifg1_mac_pool82_port0_rx_oob_mac_type_errors {
      type oc-yang:counter64;
      description
        "Counts in interleaving mode OOB packets that are received with none OOB packet type.";
    }
    leaf counters_slice0_ifg1_mac_pool82_port1_rx_oob_mac_type_errors {
      type oc-yang:counter64;
      description
        "Counts in interleaving mode OOB packets that are received with none OOB packet type.";
    }
    leaf counters_slice0_ifg1_mac_pool82_port2_rx_oob_mac_type_errors {
      type oc-yang:counter64;
      description
        "Counts in interleaving mode OOB packets that are received with none OOB packet type.";
    }
    leaf counters_slice0_ifg1_mac_pool82_port3_rx_oob_mac_type_errors {
      type oc-yang:counter64;
      description
        "Counts in interleaving mode OOB packets that are received with none OOB packet type.";
    }
    leaf counters_slice0_ifg1_mac_pool83_port0_rx_oob_mac_type_errors {
      type oc-yang:counter64;
      description
        "Counts in interleaving mode OOB packets that are received with none OOB packet type.";
    }
    leaf counters_slice0_ifg1_mac_pool83_port1_rx_oob_mac_type_errors {
      type oc-yang:counter64;
      description
        "Counts in interleaving mode OOB packets that are received with none OOB packet type.";
    }
    leaf counters_slice0_ifg1_mac_pool83_port2_rx_oob_mac_type_errors {
      type oc-yang:counter64;
      description
        "Counts in interleaving mode OOB packets that are received with none OOB packet type.";
    }
    leaf counters_slice0_ifg1_mac_pool83_port3_rx_oob_mac_type_errors {
      type oc-yang:counter64;
      description
        "Counts in interleaving mode OOB packets that are received with none OOB packet type.";
    }
    leaf counters_slice0_ifg1_npu_txpp_ifc_cluster_dropped_bad_packets {
      type oc-yang:counter64;
      description
        "Counts bad packets arrived to txpp Number of packet drops at the output of TxPP on IFG <i>";
    }
    leaf counters_slice1_ifg0_ifgb_rx_protection_errors {
      type oc-yang:counter64;
      description
        "RXPP interface protection errors counter.";
    }
    leaf counters_slice1_ifg0_ifgb_tx_protection_dropped_packets {
      type oc-yang:counter64;
      description
        "TXPP interface protection packet drop counter. Number of invalid packets arrived to TX.";
    }
    leaf counters_slice1_ifg0_ifgb_tx_protection_dropped_words {
      type oc-yang:counter64;
      description
        "TXPP interface protection words drop counter. Number of invalid words arrived to TX.";
    }
    leaf counters_slice1_ifg0_ifgb_tx_protection_errors {
      type oc-yang:counter64;
      description
        "TXPP interface protection errors counter.";
    }
    leaf counters_slice1_ifg0_ifgbi_pif_sequence_number_error {
      type oc-yang:counter64;
      description
        "PIF Sequence Number Error Count";
    }
    leaf counters_slice1_ifg0_ifgbi_rx_context_allocation_errors {
      type oc-yang:counter64;
      description
        "The amount of RXPP backpressure assertion events.";
    }
    leaf counters_slice1_ifg0_ifgbi_dash0_hp_dropped_full_packet {
      type oc-yang:counter64;
      description
        "SOP Drop Pkt Count - Full High Priority packet drops based on WrSopThd";
    }
    leaf counters_slice1_ifg0_ifgbi_dash0_hp_dropped_packets {
      type oc-yang:counter64;
      description
        "FIFO Full Pkt Count - Partial High Priority packet drops due to no space in FIFO";
    }
    leaf counters_slice1_ifg0_ifgbi_dash0_hp_dropped_words {
      type oc-yang:counter64;
      description
        "Word Drop Count - Partial High Priority word drops due to no space in FIFO";
    }
    leaf counters_slice1_ifg0_ifgbi_dash0_lp_dropped_full_packet {
      type oc-yang:counter64;
      description
        "SOP Drop Pkt Count - Full Low Priority packet drops based on WrSopThd";
    }
    leaf counters_slice1_ifg0_ifgbi_dash0_lp_dropped_packets {
      type oc-yang:counter64;
      description
        "FIFO Full Pkt Count - Partial Low Priority packet drops due to no space in FIFO";
    }
    leaf counters_slice1_ifg0_ifgbi_dash0_lp_dropped_words {
      type oc-yang:counter64;
      description
        "Word Drop Count - Partial Low Priority word drops due to no space in FIFO";
    }
    leaf counters_slice1_ifg0_ifgbi_dash1_hp_dropped_full_packet {
      type oc-yang:counter64;
      description
        "SOP Drop Pkt Count - Full High Priority packet drops based on WrSopThd";
    }
    leaf counters_slice1_ifg0_ifgbi_dash1_hp_dropped_packets {
      type oc-yang:counter64;
      description
        "FIFO Full Pkt Count - Partial High Priority packet drops due to no space in FIFO";
    }
    leaf counters_slice1_ifg0_ifgbi_dash1_hp_dropped_words {
      type oc-yang:counter64;
      description
        "Word Drop Count - Partial High Priority word drops due to no space in FIFO";
    }
    leaf counters_slice1_ifg0_ifgbi_dash1_lp_dropped_full_packet {
      type oc-yang:counter64;
      description
        "SOP Drop Pkt Count - Full Low Priority packet drops based on WrSopThd";
    }
    leaf counters_slice1_ifg0_ifgbi_dash1_lp_dropped_packets {
      type oc-yang:counter64;
      description
        "FIFO Full Pkt Count - Partial Low Priority packet drops due to no space in FIFO";
    }
    leaf counters_slice1_ifg0_ifgbi_dash1_lp_dropped_words {
      type oc-yang:counter64;
      description
        "Word Drop Count - Partial Low Priority word drops due to no space in FIFO";
    }
    leaf counters_slice1_ifg0_ifgbi_inband_extract_nph_errored_packets {
      type oc-yang:counter64;
      description
        "Inband Extract Bad packet extracted";
    }
    leaf counters_slice1_ifg0_ifgbi_inband_extract_pdm_errored_packets {
      type oc-yang:counter64;
      description
        "Inband Extract Bad packet extracted";
    }
    leaf counters_slice1_ifg0_ifgbi_inband_inject_nph_errored_packets {
      type oc-yang:counter64;
      description
        "Inband Inject Bad packet injected";
    }
    leaf counters_slice1_ifg0_ifgbi_inband_inject_pdm_errored_packets {
      type oc-yang:counter64;
      description
        "Inband Inject Bad packet injected";
    }
    leaf counters_slice1_ifg0_ifgbi_oobi_csms_dropped_packets {
      type oc-yang:counter64;
      description
        "Injected CSMS pkt drop cnt across all links";
    }
    leaf counters_slice1_ifg0_ifgbi_oobi_frm_dropped_packets {
      type oc-yang:counter64;
      description
        "Injected FRM pkt drop cnt across all links";
    }
    leaf counters_slice1_ifg0_ifgbi_oobi_fte_fts_dropped_packets {
      type oc-yang:counter64;
      description
        "Injected FTE Fabric Time Sync pkt drop cnt across all links";
    }
    leaf counters_slice1_ifg0_ifgbi_oobi_fte_pd_req_dropped_packets {
      type oc-yang:counter64;
      description
        "Injected FTE Peer Delay Request pkt drop cnt across all links";
    }
    leaf counters_slice1_ifg0_ifgbi_oobi_fte_pd_res_dropped_packets {
      type oc-yang:counter64;
      description
        "Injected FTE Peer Delay Response pkt drop cnt across all links";
    }
    leaf counters_slice1_ifg0_ifgbi_recycle_recycle_drop_on_port0 {
      type oc-yang:counter64;
      description
        "IFG recycling drop counter. Increments based on the RcyDropCntrsCfg.";
    }
    leaf counters_slice1_ifg0_ifgbi_recycle_recycle_drop_on_port1 {
      type oc-yang:counter64;
      description
        "IFG recycling drop counter. Increments based on the RcyDropCntrsCfg.";
    }
    leaf counters_slice1_ifg0_ifgbi_recycle_recycle_drop_on_port10 {
      type oc-yang:counter64;
      description
        "IFG recycling drop counter. Increments based on the RcyDropCntrsCfg.";
    }
    leaf counters_slice1_ifg0_ifgbi_recycle_recycle_drop_on_port11 {
      type oc-yang:counter64;
      description
        "IFG recycling drop counter. Increments based on the RcyDropCntrsCfg.";
    }
    leaf counters_slice1_ifg0_ifgbi_recycle_recycle_drop_on_port12 {
      type oc-yang:counter64;
      description
        "IFG recycling drop counter. Increments based on the RcyDropCntrsCfg.";
    }
    leaf counters_slice1_ifg0_ifgbi_recycle_recycle_drop_on_port13 {
      type oc-yang:counter64;
      description
        "IFG recycling drop counter. Increments based on the RcyDropCntrsCfg.";
    }
    leaf counters_slice1_ifg0_ifgbi_recycle_recycle_drop_on_port14 {
      type oc-yang:counter64;
      description
        "IFG recycling drop counter. Increments based on the RcyDropCntrsCfg.";
    }
    leaf counters_slice1_ifg0_ifgbi_recycle_recycle_drop_on_port15 {
      type oc-yang:counter64;
      description
        "IFG recycling drop counter. Increments based on the RcyDropCntrsCfg.";
    }
    leaf counters_slice1_ifg0_ifgbi_recycle_recycle_drop_on_port16 {
      type oc-yang:counter64;
      description
        "IFG recycling drop counter. Increments based on the RcyDropCntrsCfg.";
    }
    leaf counters_slice1_ifg0_ifgbi_recycle_recycle_drop_on_port17 {
      type oc-yang:counter64;
      description
        "IFG recycling drop counter. Increments based on the RcyDropCntrsCfg.";
    }
    leaf counters_slice1_ifg0_ifgbi_recycle_recycle_drop_on_port18 {
      type oc-yang:counter64;
      description
        "IFG recycling drop counter. Increments based on the RcyDropCntrsCfg.";
    }
    leaf counters_slice1_ifg0_ifgbi_recycle_recycle_drop_on_port19 {
      type oc-yang:counter64;
      description
        "IFG recycling drop counter. Increments based on the RcyDropCntrsCfg.";
    }
    leaf counters_slice1_ifg0_ifgbi_recycle_recycle_drop_on_port2 {
      type oc-yang:counter64;
      description
        "IFG recycling drop counter. Increments based on the RcyDropCntrsCfg.";
    }
    leaf counters_slice1_ifg0_ifgbi_recycle_recycle_drop_on_port20 {
      type oc-yang:counter64;
      description
        "IFG recycling drop counter. Increments based on the RcyDropCntrsCfg.";
    }
    leaf counters_slice1_ifg0_ifgbi_recycle_recycle_drop_on_port21 {
      type oc-yang:counter64;
      description
        "IFG recycling drop counter. Increments based on the RcyDropCntrsCfg.";
    }
    leaf counters_slice1_ifg0_ifgbi_recycle_recycle_drop_on_port22 {
      type oc-yang:counter64;
      description
        "IFG recycling drop counter. Increments based on the RcyDropCntrsCfg.";
    }
    leaf counters_slice1_ifg0_ifgbi_recycle_recycle_drop_on_port23 {
      type oc-yang:counter64;
      description
        "IFG recycling drop counter. Increments based on the RcyDropCntrsCfg.";
    }
    leaf counters_slice1_ifg0_ifgbi_recycle_recycle_drop_on_port24 {
      type oc-yang:counter64;
      description
        "IFG recycling drop counter. Increments based on the RcyDropCntrsCfg.";
    }
    leaf counters_slice1_ifg0_ifgbi_recycle_recycle_drop_on_port25 {
      type oc-yang:counter64;
      description
        "IFG recycling drop counter. Increments based on the RcyDropCntrsCfg.";
    }
    leaf counters_slice1_ifg0_ifgbi_recycle_recycle_drop_on_port26 {
      type oc-yang:counter64;
      description
        "IFG recycling drop counter. Increments based on the RcyDropCntrsCfg.";
    }
    leaf counters_slice1_ifg0_ifgbi_recycle_recycle_drop_on_port27 {
      type oc-yang:counter64;
      description
        "IFG recycling drop counter. Increments based on the RcyDropCntrsCfg.";
    }
    leaf counters_slice1_ifg0_ifgbi_recycle_recycle_drop_on_port28 {
      type oc-yang:counter64;
      description
        "IFG recycling drop counter. Increments based on the RcyDropCntrsCfg.";
    }
    leaf counters_slice1_ifg0_ifgbi_recycle_recycle_drop_on_port29 {
      type oc-yang:counter64;
      description
        "IFG recycling drop counter. Increments based on the RcyDropCntrsCfg.";
    }
    leaf counters_slice1_ifg0_ifgbi_recycle_recycle_drop_on_port3 {
      type oc-yang:counter64;
      description
        "IFG recycling drop counter. Increments based on the RcyDropCntrsCfg.";
    }
    leaf counters_slice1_ifg0_ifgbi_recycle_recycle_drop_on_port30 {
      type oc-yang:counter64;
      description
        "IFG recycling drop counter. Increments based on the RcyDropCntrsCfg.";
    }
    leaf counters_slice1_ifg0_ifgbi_recycle_recycle_drop_on_port31 {
      type oc-yang:counter64;
      description
        "IFG recycling drop counter. Increments based on the RcyDropCntrsCfg.";
    }
    leaf counters_slice1_ifg0_ifgbi_recycle_recycle_drop_on_port4 {
      type oc-yang:counter64;
      description
        "IFG recycling drop counter. Increments based on the RcyDropCntrsCfg.";
    }
    leaf counters_slice1_ifg0_ifgbi_recycle_recycle_drop_on_port5 {
      type oc-yang:counter64;
      description
        "IFG recycling drop counter. Increments based on the RcyDropCntrsCfg.";
    }
    leaf counters_slice1_ifg0_ifgbi_recycle_recycle_drop_on_port6 {
      type oc-yang:counter64;
      description
        "IFG recycling drop counter. Increments based on the RcyDropCntrsCfg.";
    }
    leaf counters_slice1_ifg0_ifgbi_recycle_recycle_drop_on_port7 {
      type oc-yang:counter64;
      description
        "IFG recycling drop counter. Increments based on the RcyDropCntrsCfg.";
    }
    leaf counters_slice1_ifg0_ifgbi_recycle_recycle_drop_on_port8 {
      type oc-yang:counter64;
      description
        "IFG recycling drop counter. Increments based on the RcyDropCntrsCfg.";
    }
    leaf counters_slice1_ifg0_ifgbi_recycle_recycle_drop_on_port9 {
      type oc-yang:counter64;
      description
        "IFG recycling drop counter. Increments based on the RcyDropCntrsCfg.";
    }
    leaf counters_slice1_ifg0_ifgbi_rx_protection_abnormally_terminated_packets {
      type oc-yang:counter64;
      description
        "RXPP interface protection packets termiante abnormally counter";
    }
    leaf counters_slice1_ifg0_mac_pool80_port0_rx_oob_mac_type_errors {
      type oc-yang:counter64;
      description
        "Counts in interleaving mode OOB packets that are received with none OOB packet type.";
    }
    leaf counters_slice1_ifg0_mac_pool80_port1_rx_oob_mac_type_errors {
      type oc-yang:counter64;
      description
        "Counts in interleaving mode OOB packets that are received with none OOB packet type.";
    }
    leaf counters_slice1_ifg0_mac_pool80_port2_rx_oob_mac_type_errors {
      type oc-yang:counter64;
      description
        "Counts in interleaving mode OOB packets that are received with none OOB packet type.";
    }
    leaf counters_slice1_ifg0_mac_pool80_port3_rx_oob_mac_type_errors {
      type oc-yang:counter64;
      description
        "Counts in interleaving mode OOB packets that are received with none OOB packet type.";
    }
    leaf counters_slice1_ifg0_mac_pool81_port0_rx_oob_mac_type_errors {
      type oc-yang:counter64;
      description
        "Counts in interleaving mode OOB packets that are received with none OOB packet type.";
    }
    leaf counters_slice1_ifg0_mac_pool81_port1_rx_oob_mac_type_errors {
      type oc-yang:counter64;
      description
        "Counts in interleaving mode OOB packets that are received with none OOB packet type.";
    }
    leaf counters_slice1_ifg0_mac_pool81_port2_rx_oob_mac_type_errors {
      type oc-yang:counter64;
      description
        "Counts in interleaving mode OOB packets that are received with none OOB packet type.";
    }
    leaf counters_slice1_ifg0_mac_pool81_port3_rx_oob_mac_type_errors {
      type oc-yang:counter64;
      description
        "Counts in interleaving mode OOB packets that are received with none OOB packet type.";
    }
    leaf counters_slice1_ifg0_mac_pool82_port0_rx_oob_mac_type_errors {
      type oc-yang:counter64;
      description
        "Counts in interleaving mode OOB packets that are received with none OOB packet type.";
    }
    leaf counters_slice1_ifg0_mac_pool82_port1_rx_oob_mac_type_errors {
      type oc-yang:counter64;
      description
        "Counts in interleaving mode OOB packets that are received with none OOB packet type.";
    }
    leaf counters_slice1_ifg0_mac_pool82_port2_rx_oob_mac_type_errors {
      type oc-yang:counter64;
      description
        "Counts in interleaving mode OOB packets that are received with none OOB packet type.";
    }
    leaf counters_slice1_ifg0_mac_pool82_port3_rx_oob_mac_type_errors {
      type oc-yang:counter64;
      description
        "Counts in interleaving mode OOB packets that are received with none OOB packet type.";
    }
    leaf counters_slice1_ifg0_mac_pool83_port0_rx_oob_mac_type_errors {
      type oc-yang:counter64;
      description
        "Counts in interleaving mode OOB packets that are received with none OOB packet type.";
    }
    leaf counters_slice1_ifg0_mac_pool83_port1_rx_oob_mac_type_errors {
      type oc-yang:counter64;
      description
        "Counts in interleaving mode OOB packets that are received with none OOB packet type.";
    }
    leaf counters_slice1_ifg0_mac_pool83_port2_rx_oob_mac_type_errors {
      type oc-yang:counter64;
      description
        "Counts in interleaving mode OOB packets that are received with none OOB packet type.";
    }
    leaf counters_slice1_ifg0_mac_pool83_port3_rx_oob_mac_type_errors {
      type oc-yang:counter64;
      description
        "Counts in interleaving mode OOB packets that are received with none OOB packet type.";
    }
    leaf counters_slice1_ifg0_npu_txpp_ifc_cluster_dropped_bad_packets {
      type oc-yang:counter64;
      description
        "Counts bad packets arrived to txpp Number of packet drops at the output of TxPP on IFG <i>";
    }
    leaf counters_slice1_ifg1_ifgb_rx_protection_errors {
      type oc-yang:counter64;
      description
        "RXPP interface protection errors counter.";
    }
    leaf counters_slice1_ifg1_ifgb_tx_protection_dropped_packets {
      type oc-yang:counter64;
      description
        "TXPP interface protection packet drop counter. Number of invalid packets arrived to TX.";
    }
    leaf counters_slice1_ifg1_ifgb_tx_protection_dropped_words {
      type oc-yang:counter64;
      description
        "TXPP interface protection words drop counter. Number of invalid words arrived to TX.";
    }
    leaf counters_slice1_ifg1_ifgb_tx_protection_errors {
      type oc-yang:counter64;
      description
        "TXPP interface protection errors counter.";
    }
    leaf counters_slice1_ifg1_ifgbi_pif_sequence_number_error {
      type oc-yang:counter64;
      description
        "PIF Sequence Number Error Count";
    }
    leaf counters_slice1_ifg1_ifgbi_rx_context_allocation_errors {
      type oc-yang:counter64;
      description
        "The amount of RXPP backpressure assertion events.";
    }
    leaf counters_slice1_ifg1_ifgbi_dash0_hp_dropped_full_packet {
      type oc-yang:counter64;
      description
        "SOP Drop Pkt Count - Full High Priority packet drops based on WrSopThd";
    }
    leaf counters_slice1_ifg1_ifgbi_dash0_hp_dropped_packets {
      type oc-yang:counter64;
      description
        "FIFO Full Pkt Count - Partial High Priority packet drops due to no space in FIFO";
    }
    leaf counters_slice1_ifg1_ifgbi_dash0_hp_dropped_words {
      type oc-yang:counter64;
      description
        "Word Drop Count - Partial High Priority word drops due to no space in FIFO";
    }
    leaf counters_slice1_ifg1_ifgbi_dash0_lp_dropped_full_packet {
      type oc-yang:counter64;
      description
        "SOP Drop Pkt Count - Full Low Priority packet drops based on WrSopThd";
    }
    leaf counters_slice1_ifg1_ifgbi_dash0_lp_dropped_packets {
      type oc-yang:counter64;
      description
        "FIFO Full Pkt Count - Partial Low Priority packet drops due to no space in FIFO";
    }
    leaf counters_slice1_ifg1_ifgbi_dash0_lp_dropped_words {
      type oc-yang:counter64;
      description
        "Word Drop Count - Partial Low Priority word drops due to no space in FIFO";
    }
    leaf counters_slice1_ifg1_ifgbi_dash1_hp_dropped_full_packet {
      type oc-yang:counter64;
      description
        "SOP Drop Pkt Count - Full High Priority packet drops based on WrSopThd";
    }
    leaf counters_slice1_ifg1_ifgbi_dash1_hp_dropped_packets {
      type oc-yang:counter64;
      description
        "FIFO Full Pkt Count - Partial High Priority packet drops due to no space in FIFO";
    }
    leaf counters_slice1_ifg1_ifgbi_dash1_hp_dropped_words {
      type oc-yang:counter64;
      description
        "Word Drop Count - Partial High Priority word drops due to no space in FIFO";
    }
    leaf counters_slice1_ifg1_ifgbi_dash1_lp_dropped_full_packet {
      type oc-yang:counter64;
      description
        "SOP Drop Pkt Count - Full Low Priority packet drops based on WrSopThd";
    }
    leaf counters_slice1_ifg1_ifgbi_dash1_lp_dropped_packets {
      type oc-yang:counter64;
      description
        "FIFO Full Pkt Count - Partial Low Priority packet drops due to no space in FIFO";
    }
    leaf counters_slice1_ifg1_ifgbi_dash1_lp_dropped_words {
      type oc-yang:counter64;
      description
        "Word Drop Count - Partial Low Priority word drops due to no space in FIFO";
    }
    leaf counters_slice1_ifg1_ifgbi_inband_extract_nph_errored_packets {
      type oc-yang:counter64;
      description
        "Inband Extract Bad packet extracted";
    }
    leaf counters_slice1_ifg1_ifgbi_inband_extract_pdm_errored_packets {
      type oc-yang:counter64;
      description
        "Inband Extract Bad packet extracted";
    }
    leaf counters_slice1_ifg1_ifgbi_inband_inject_nph_errored_packets {
      type oc-yang:counter64;
      description
        "Inband Inject Bad packet injected";
    }
    leaf counters_slice1_ifg1_ifgbi_inband_inject_pdm_errored_packets {
      type oc-yang:counter64;
      description
        "Inband Inject Bad packet injected";
    }
    leaf counters_slice1_ifg1_ifgbi_oobi_csms_dropped_packets {
      type oc-yang:counter64;
      description
        "Injected CSMS pkt drop cnt across all links";
    }
    leaf counters_slice1_ifg1_ifgbi_oobi_frm_dropped_packets {
      type oc-yang:counter64;
      description
        "Injected FRM pkt drop cnt across all links";
    }
    leaf counters_slice1_ifg1_ifgbi_oobi_fte_fts_dropped_packets {
      type oc-yang:counter64;
      description
        "Injected FTE Fabric Time Sync pkt drop cnt across all links";
    }
    leaf counters_slice1_ifg1_ifgbi_oobi_fte_pd_req_dropped_packets {
      type oc-yang:counter64;
      description
        "Injected FTE Peer Delay Request pkt drop cnt across all links";
    }
    leaf counters_slice1_ifg1_ifgbi_oobi_fte_pd_res_dropped_packets {
      type oc-yang:counter64;
      description
        "Injected FTE Peer Delay Response pkt drop cnt across all links";
    }
    leaf counters_slice1_ifg1_ifgbi_recycle_recycle_drop_on_port0 {
      type oc-yang:counter64;
      description
        "IFG recycling drop counter. Increments based on the RcyDropCntrsCfg.";
    }
    leaf counters_slice1_ifg1_ifgbi_recycle_recycle_drop_on_port1 {
      type oc-yang:counter64;
      description
        "IFG recycling drop counter. Increments based on the RcyDropCntrsCfg.";
    }
    leaf counters_slice1_ifg1_ifgbi_recycle_recycle_drop_on_port10 {
      type oc-yang:counter64;
      description
        "IFG recycling drop counter. Increments based on the RcyDropCntrsCfg.";
    }
    leaf counters_slice1_ifg1_ifgbi_recycle_recycle_drop_on_port11 {
      type oc-yang:counter64;
      description
        "IFG recycling drop counter. Increments based on the RcyDropCntrsCfg.";
    }
    leaf counters_slice1_ifg1_ifgbi_recycle_recycle_drop_on_port12 {
      type oc-yang:counter64;
      description
        "IFG recycling drop counter. Increments based on the RcyDropCntrsCfg.";
    }
    leaf counters_slice1_ifg1_ifgbi_recycle_recycle_drop_on_port13 {
      type oc-yang:counter64;
      description
        "IFG recycling drop counter. Increments based on the RcyDropCntrsCfg.";
    }
    leaf counters_slice1_ifg1_ifgbi_recycle_recycle_drop_on_port14 {
      type oc-yang:counter64;
      description
        "IFG recycling drop counter. Increments based on the RcyDropCntrsCfg.";
    }
    leaf counters_slice1_ifg1_ifgbi_recycle_recycle_drop_on_port15 {
      type oc-yang:counter64;
      description
        "IFG recycling drop counter. Increments based on the RcyDropCntrsCfg.";
    }
    leaf counters_slice1_ifg1_ifgbi_recycle_recycle_drop_on_port16 {
      type oc-yang:counter64;
      description
        "IFG recycling drop counter. Increments based on the RcyDropCntrsCfg.";
    }
    leaf counters_slice1_ifg1_ifgbi_recycle_recycle_drop_on_port17 {
      type oc-yang:counter64;
      description
        "IFG recycling drop counter. Increments based on the RcyDropCntrsCfg.";
    }
    leaf counters_slice1_ifg1_ifgbi_recycle_recycle_drop_on_port18 {
      type oc-yang:counter64;
      description
        "IFG recycling drop counter. Increments based on the RcyDropCntrsCfg.";
    }
    leaf counters_slice1_ifg1_ifgbi_recycle_recycle_drop_on_port19 {
      type oc-yang:counter64;
      description
        "IFG recycling drop counter. Increments based on the RcyDropCntrsCfg.";
    }
    leaf counters_slice1_ifg1_ifgbi_recycle_recycle_drop_on_port2 {
      type oc-yang:counter64;
      description
        "IFG recycling drop counter. Increments based on the RcyDropCntrsCfg.";
    }
    leaf counters_slice1_ifg1_ifgbi_recycle_recycle_drop_on_port20 {
      type oc-yang:counter64;
      description
        "IFG recycling drop counter. Increments based on the RcyDropCntrsCfg.";
    }
    leaf counters_slice1_ifg1_ifgbi_recycle_recycle_drop_on_port21 {
      type oc-yang:counter64;
      description
        "IFG recycling drop counter. Increments based on the RcyDropCntrsCfg.";
    }
    leaf counters_slice1_ifg1_ifgbi_recycle_recycle_drop_on_port22 {
      type oc-yang:counter64;
      description
        "IFG recycling drop counter. Increments based on the RcyDropCntrsCfg.";
    }
    leaf counters_slice1_ifg1_ifgbi_recycle_recycle_drop_on_port23 {
      type oc-yang:counter64;
      description
        "IFG recycling drop counter. Increments based on the RcyDropCntrsCfg.";
    }
    leaf counters_slice1_ifg1_ifgbi_recycle_recycle_drop_on_port24 {
      type oc-yang:counter64;
      description
        "IFG recycling drop counter. Increments based on the RcyDropCntrsCfg.";
    }
    leaf counters_slice1_ifg1_ifgbi_recycle_recycle_drop_on_port25 {
      type oc-yang:counter64;
      description
        "IFG recycling drop counter. Increments based on the RcyDropCntrsCfg.";
    }
    leaf counters_slice1_ifg1_ifgbi_recycle_recycle_drop_on_port26 {
      type oc-yang:counter64;
      description
        "IFG recycling drop counter. Increments based on the RcyDropCntrsCfg.";
    }
    leaf counters_slice1_ifg1_ifgbi_recycle_recycle_drop_on_port27 {
      type oc-yang:counter64;
      description
        "IFG recycling drop counter. Increments based on the RcyDropCntrsCfg.";
    }
    leaf counters_slice1_ifg1_ifgbi_recycle_recycle_drop_on_port28 {
      type oc-yang:counter64;
      description
        "IFG recycling drop counter. Increments based on the RcyDropCntrsCfg.";
    }
    leaf counters_slice1_ifg1_ifgbi_recycle_recycle_drop_on_port29 {
      type oc-yang:counter64;
      description
        "IFG recycling drop counter. Increments based on the RcyDropCntrsCfg.";
    }
    leaf counters_slice1_ifg1_ifgbi_recycle_recycle_drop_on_port3 {
      type oc-yang:counter64;
      description
        "IFG recycling drop counter. Increments based on the RcyDropCntrsCfg.";
    }
    leaf counters_slice1_ifg1_ifgbi_recycle_recycle_drop_on_port30 {
      type oc-yang:counter64;
      description
        "IFG recycling drop counter. Increments based on the RcyDropCntrsCfg.";
    }
    leaf counters_slice1_ifg1_ifgbi_recycle_recycle_drop_on_port31 {
      type oc-yang:counter64;
      description
        "IFG recycling drop counter. Increments based on the RcyDropCntrsCfg.";
    }
    leaf counters_slice1_ifg1_ifgbi_recycle_recycle_drop_on_port4 {
      type oc-yang:counter64;
      description
        "IFG recycling drop counter. Increments based on the RcyDropCntrsCfg.";
    }
    leaf counters_slice1_ifg1_ifgbi_recycle_recycle_drop_on_port5 {
      type oc-yang:counter64;
      description
        "IFG recycling drop counter. Increments based on the RcyDropCntrsCfg.";
    }
    leaf counters_slice1_ifg1_ifgbi_recycle_recycle_drop_on_port6 {
      type oc-yang:counter64;
      description
        "IFG recycling drop counter. Increments based on the RcyDropCntrsCfg.";
    }
    leaf counters_slice1_ifg1_ifgbi_recycle_recycle_drop_on_port7 {
      type oc-yang:counter64;
      description
        "IFG recycling drop counter. Increments based on the RcyDropCntrsCfg.";
    }
    leaf counters_slice1_ifg1_ifgbi_recycle_recycle_drop_on_port8 {
      type oc-yang:counter64;
      description
        "IFG recycling drop counter. Increments based on the RcyDropCntrsCfg.";
    }
    leaf counters_slice1_ifg1_ifgbi_recycle_recycle_drop_on_port9 {
      type oc-yang:counter64;
      description
        "IFG recycling drop counter. Increments based on the RcyDropCntrsCfg.";
    }
    leaf counters_slice1_ifg1_ifgbi_rx_protection_abnormally_terminated_packets {
      type oc-yang:counter64;
      description
        "RXPP interface protection packets termiante abnormally counter";
    }
    leaf counters_slice1_ifg1_mac_pool80_port0_rx_oob_mac_type_errors {
      type oc-yang:counter64;
      description
        "Counts in interleaving mode OOB packets that are received with none OOB packet type.";
    }
    leaf counters_slice1_ifg1_mac_pool80_port1_rx_oob_mac_type_errors {
      type oc-yang:counter64;
      description
        "Counts in interleaving mode OOB packets that are received with none OOB packet type.";
    }
    leaf counters_slice1_ifg1_mac_pool80_port2_rx_oob_mac_type_errors {
      type oc-yang:counter64;
      description
        "Counts in interleaving mode OOB packets that are received with none OOB packet type.";
    }
    leaf counters_slice1_ifg1_mac_pool80_port3_rx_oob_mac_type_errors {
      type oc-yang:counter64;
      description
        "Counts in interleaving mode OOB packets that are received with none OOB packet type.";
    }
    leaf counters_slice1_ifg1_mac_pool81_port0_rx_oob_mac_type_errors {
      type oc-yang:counter64;
      description
        "Counts in interleaving mode OOB packets that are received with none OOB packet type.";
    }
    leaf counters_slice1_ifg1_mac_pool81_port1_rx_oob_mac_type_errors {
      type oc-yang:counter64;
      description
        "Counts in interleaving mode OOB packets that are received with none OOB packet type.";
    }
    leaf counters_slice1_ifg1_mac_pool81_port2_rx_oob_mac_type_errors {
      type oc-yang:counter64;
      description
        "Counts in interleaving mode OOB packets that are received with none OOB packet type.";
    }
    leaf counters_slice1_ifg1_mac_pool81_port3_rx_oob_mac_type_errors {
      type oc-yang:counter64;
      description
        "Counts in interleaving mode OOB packets that are received with none OOB packet type.";
    }
    leaf counters_slice1_ifg1_mac_pool82_port0_rx_oob_mac_type_errors {
      type oc-yang:counter64;
      description
        "Counts in interleaving mode OOB packets that are received with none OOB packet type.";
    }
    leaf counters_slice1_ifg1_mac_pool82_port1_rx_oob_mac_type_errors {
      type oc-yang:counter64;
      description
        "Counts in interleaving mode OOB packets that are received with none OOB packet type.";
    }
    leaf counters_slice1_ifg1_mac_pool82_port2_rx_oob_mac_type_errors {
      type oc-yang:counter64;
      description
        "Counts in interleaving mode OOB packets that are received with none OOB packet type.";
    }
    leaf counters_slice1_ifg1_mac_pool82_port3_rx_oob_mac_type_errors {
      type oc-yang:counter64;
      description
        "Counts in interleaving mode OOB packets that are received with none OOB packet type.";
    }
    leaf counters_slice1_ifg1_mac_pool83_port0_rx_oob_mac_type_errors {
      type oc-yang:counter64;
      description
        "Counts in interleaving mode OOB packets that are received with none OOB packet type.";
    }
    leaf counters_slice1_ifg1_mac_pool83_port1_rx_oob_mac_type_errors {
      type oc-yang:counter64;
      description
        "Counts in interleaving mode OOB packets that are received with none OOB packet type.";
    }
    leaf counters_slice1_ifg1_mac_pool83_port2_rx_oob_mac_type_errors {
      type oc-yang:counter64;
      description
        "Counts in interleaving mode OOB packets that are received with none OOB packet type.";
    }
    leaf counters_slice1_ifg1_mac_pool83_port3_rx_oob_mac_type_errors {
      type oc-yang:counter64;
      description
        "Counts in interleaving mode OOB packets that are received with none OOB packet type.";
    }
    leaf counters_slice1_ifg1_npu_txpp_ifc_cluster_dropped_bad_packets {
      type oc-yang:counter64;
      description
        "Counts bad packets arrived to txpp Number of packet drops at the output of TxPP on IFG <i>";
    }
    leaf counters_slice2_ifg0_ifgb_rx_protection_errors {
      type oc-yang:counter64;
      description
        "RXPP interface protection errors counter.";
    }
    leaf counters_slice2_ifg0_ifgb_tx_protection_dropped_packets {
      type oc-yang:counter64;
      description
        "TXPP interface protection packet drop counter. Number of invalid packets arrived to TX.";
    }
    leaf counters_slice2_ifg0_ifgb_tx_protection_dropped_words {
      type oc-yang:counter64;
      description
        "TXPP interface protection words drop counter. Number of invalid words arrived to TX.";
    }
    leaf counters_slice2_ifg0_ifgb_tx_protection_errors {
      type oc-yang:counter64;
      description
        "TXPP interface protection errors counter.";
    }
    leaf counters_slice2_ifg0_ifgbi_pif_sequence_number_error {
      type oc-yang:counter64;
      description
        "PIF Sequence Number Error Count";
    }
    leaf counters_slice2_ifg0_ifgbi_rx_context_allocation_errors {
      type oc-yang:counter64;
      description
        "The amount of RXPP backpressure assertion events.";
    }
    leaf counters_slice2_ifg0_ifgbi_dash0_hp_dropped_full_packet {
      type oc-yang:counter64;
      description
        "SOP Drop Pkt Count - Full High Priority packet drops based on WrSopThd";
    }
    leaf counters_slice2_ifg0_ifgbi_dash0_hp_dropped_packets {
      type oc-yang:counter64;
      description
        "FIFO Full Pkt Count - Partial High Priority packet drops due to no space in FIFO";
    }
    leaf counters_slice2_ifg0_ifgbi_dash0_hp_dropped_words {
      type oc-yang:counter64;
      description
        "Word Drop Count - Partial High Priority word drops due to no space in FIFO";
    }
    leaf counters_slice2_ifg0_ifgbi_dash0_lp_dropped_full_packet {
      type oc-yang:counter64;
      description
        "SOP Drop Pkt Count - Full Low Priority packet drops based on WrSopThd";
    }
    leaf counters_slice2_ifg0_ifgbi_dash0_lp_dropped_packets {
      type oc-yang:counter64;
      description
        "FIFO Full Pkt Count - Partial Low Priority packet drops due to no space in FIFO";
    }
    leaf counters_slice2_ifg0_ifgbi_dash0_lp_dropped_words {
      type oc-yang:counter64;
      description
        "Word Drop Count - Partial Low Priority word drops due to no space in FIFO";
    }
    leaf counters_slice2_ifg0_ifgbi_dash1_hp_dropped_full_packet {
      type oc-yang:counter64;
      description
        "SOP Drop Pkt Count - Full High Priority packet drops based on WrSopThd";
    }
    leaf counters_slice2_ifg0_ifgbi_dash1_hp_dropped_packets {
      type oc-yang:counter64;
      description
        "FIFO Full Pkt Count - Partial High Priority packet drops due to no space in FIFO";
    }
    leaf counters_slice2_ifg0_ifgbi_dash1_hp_dropped_words {
      type oc-yang:counter64;
      description
        "Word Drop Count - Partial High Priority word drops due to no space in FIFO";
    }
    leaf counters_slice2_ifg0_ifgbi_dash1_lp_dropped_full_packet {
      type oc-yang:counter64;
      description
        "SOP Drop Pkt Count - Full Low Priority packet drops based on WrSopThd";
    }
    leaf counters_slice2_ifg0_ifgbi_dash1_lp_dropped_packets {
      type oc-yang:counter64;
      description
        "FIFO Full Pkt Count - Partial Low Priority packet drops due to no space in FIFO";
    }
    leaf counters_slice2_ifg0_ifgbi_dash1_lp_dropped_words {
      type oc-yang:counter64;
      description
        "Word Drop Count - Partial Low Priority word drops due to no space in FIFO";
    }
    leaf counters_slice2_ifg0_ifgbi_inband_extract_nph_errored_packets {
      type oc-yang:counter64;
      description
        "Inband Extract Bad packet extracted";
    }
    leaf counters_slice2_ifg0_ifgbi_inband_extract_pdm_errored_packets {
      type oc-yang:counter64;
      description
        "Inband Extract Bad packet extracted";
    }
    leaf counters_slice2_ifg0_ifgbi_inband_inject_nph_errored_packets {
      type oc-yang:counter64;
      description
        "Inband Inject Bad packet injected";
    }
    leaf counters_slice2_ifg0_ifgbi_inband_inject_pdm_errored_packets {
      type oc-yang:counter64;
      description
        "Inband Inject Bad packet injected";
    }
    leaf counters_slice2_ifg0_ifgbi_oobi_csms_dropped_packets {
      type oc-yang:counter64;
      description
        "Injected CSMS pkt drop cnt across all links";
    }
    leaf counters_slice2_ifg0_ifgbi_oobi_frm_dropped_packets {
      type oc-yang:counter64;
      description
        "Injected FRM pkt drop cnt across all links";
    }
    leaf counters_slice2_ifg0_ifgbi_oobi_fte_fts_dropped_packets {
      type oc-yang:counter64;
      description
        "Injected FTE Fabric Time Sync pkt drop cnt across all links";
    }
    leaf counters_slice2_ifg0_ifgbi_oobi_fte_pd_req_dropped_packets {
      type oc-yang:counter64;
      description
        "Injected FTE Peer Delay Request pkt drop cnt across all links";
    }
    leaf counters_slice2_ifg0_ifgbi_oobi_fte_pd_res_dropped_packets {
      type oc-yang:counter64;
      description
        "Injected FTE Peer Delay Response pkt drop cnt across all links";
    }
    leaf counters_slice2_ifg0_ifgbi_recycle_recycle_drop_on_port0 {
      type oc-yang:counter64;
      description
        "IFG recycling drop counter. Increments based on the RcyDropCntrsCfg.";
    }
    leaf counters_slice2_ifg0_ifgbi_recycle_recycle_drop_on_port1 {
      type oc-yang:counter64;
      description
        "IFG recycling drop counter. Increments based on the RcyDropCntrsCfg.";
    }
    leaf counters_slice2_ifg0_ifgbi_recycle_recycle_drop_on_port10 {
      type oc-yang:counter64;
      description
        "IFG recycling drop counter. Increments based on the RcyDropCntrsCfg.";
    }
    leaf counters_slice2_ifg0_ifgbi_recycle_recycle_drop_on_port11 {
      type oc-yang:counter64;
      description
        "IFG recycling drop counter. Increments based on the RcyDropCntrsCfg.";
    }
    leaf counters_slice2_ifg0_ifgbi_recycle_recycle_drop_on_port12 {
      type oc-yang:counter64;
      description
        "IFG recycling drop counter. Increments based on the RcyDropCntrsCfg.";
    }
    leaf counters_slice2_ifg0_ifgbi_recycle_recycle_drop_on_port13 {
      type oc-yang:counter64;
      description
        "IFG recycling drop counter. Increments based on the RcyDropCntrsCfg.";
    }
    leaf counters_slice2_ifg0_ifgbi_recycle_recycle_drop_on_port14 {
      type oc-yang:counter64;
      description
        "IFG recycling drop counter. Increments based on the RcyDropCntrsCfg.";
    }
    leaf counters_slice2_ifg0_ifgbi_recycle_recycle_drop_on_port15 {
      type oc-yang:counter64;
      description
        "IFG recycling drop counter. Increments based on the RcyDropCntrsCfg.";
    }
    leaf counters_slice2_ifg0_ifgbi_recycle_recycle_drop_on_port16 {
      type oc-yang:counter64;
      description
        "IFG recycling drop counter. Increments based on the RcyDropCntrsCfg.";
    }
    leaf counters_slice2_ifg0_ifgbi_recycle_recycle_drop_on_port17 {
      type oc-yang:counter64;
      description
        "IFG recycling drop counter. Increments based on the RcyDropCntrsCfg.";
    }
    leaf counters_slice2_ifg0_ifgbi_recycle_recycle_drop_on_port18 {
      type oc-yang:counter64;
      description
        "IFG recycling drop counter. Increments based on the RcyDropCntrsCfg.";
    }
    leaf counters_slice2_ifg0_ifgbi_recycle_recycle_drop_on_port19 {
      type oc-yang:counter64;
      description
        "IFG recycling drop counter. Increments based on the RcyDropCntrsCfg.";
    }
    leaf counters_slice2_ifg0_ifgbi_recycle_recycle_drop_on_port2 {
      type oc-yang:counter64;
      description
        "IFG recycling drop counter. Increments based on the RcyDropCntrsCfg.";
    }
    leaf counters_slice2_ifg0_ifgbi_recycle_recycle_drop_on_port20 {
      type oc-yang:counter64;
      description
        "IFG recycling drop counter. Increments based on the RcyDropCntrsCfg.";
    }
    leaf counters_slice2_ifg0_ifgbi_recycle_recycle_drop_on_port21 {
      type oc-yang:counter64;
      description
        "IFG recycling drop counter. Increments based on the RcyDropCntrsCfg.";
    }
    leaf counters_slice2_ifg0_ifgbi_recycle_recycle_drop_on_port22 {
      type oc-yang:counter64;
      description
        "IFG recycling drop counter. Increments based on the RcyDropCntrsCfg.";
    }
    leaf counters_slice2_ifg0_ifgbi_recycle_recycle_drop_on_port23 {
      type oc-yang:counter64;
      description
        "IFG recycling drop counter. Increments based on the RcyDropCntrsCfg.";
    }
    leaf counters_slice2_ifg0_ifgbi_recycle_recycle_drop_on_port24 {
      type oc-yang:counter64;
      description
        "IFG recycling drop counter. Increments based on the RcyDropCntrsCfg.";
    }
    leaf counters_slice2_ifg0_ifgbi_recycle_recycle_drop_on_port25 {
      type oc-yang:counter64;
      description
        "IFG recycling drop counter. Increments based on the RcyDropCntrsCfg.";
    }
    leaf counters_slice2_ifg0_ifgbi_recycle_recycle_drop_on_port26 {
      type oc-yang:counter64;
      description
        "IFG recycling drop counter. Increments based on the RcyDropCntrsCfg.";
    }
    leaf counters_slice2_ifg0_ifgbi_recycle_recycle_drop_on_port27 {
      type oc-yang:counter64;
      description
        "IFG recycling drop counter. Increments based on the RcyDropCntrsCfg.";
    }
    leaf counters_slice2_ifg0_ifgbi_recycle_recycle_drop_on_port28 {
      type oc-yang:counter64;
      description
        "IFG recycling drop counter. Increments based on the RcyDropCntrsCfg.";
    }
    leaf counters_slice2_ifg0_ifgbi_recycle_recycle_drop_on_port29 {
      type oc-yang:counter64;
      description
        "IFG recycling drop counter. Increments based on the RcyDropCntrsCfg.";
    }
    leaf counters_slice2_ifg0_ifgbi_recycle_recycle_drop_on_port3 {
      type oc-yang:counter64;
      description
        "IFG recycling drop counter. Increments based on the RcyDropCntrsCfg.";
    }
    leaf counters_slice2_ifg0_ifgbi_recycle_recycle_drop_on_port30 {
      type oc-yang:counter64;
      description
        "IFG recycling drop counter. Increments based on the RcyDropCntrsCfg.";
    }
    leaf counters_slice2_ifg0_ifgbi_recycle_recycle_drop_on_port31 {
      type oc-yang:counter64;
      description
        "IFG recycling drop counter. Increments based on the RcyDropCntrsCfg.";
    }
    leaf counters_slice2_ifg0_ifgbi_recycle_recycle_drop_on_port4 {
      type oc-yang:counter64;
      description
        "IFG recycling drop counter. Increments based on the RcyDropCntrsCfg.";
    }
    leaf counters_slice2_ifg0_ifgbi_recycle_recycle_drop_on_port5 {
      type oc-yang:counter64;
      description
        "IFG recycling drop counter. Increments based on the RcyDropCntrsCfg.";
    }
    leaf counters_slice2_ifg0_ifgbi_recycle_recycle_drop_on_port6 {
      type oc-yang:counter64;
      description
        "IFG recycling drop counter. Increments based on the RcyDropCntrsCfg.";
    }
    leaf counters_slice2_ifg0_ifgbi_recycle_recycle_drop_on_port7 {
      type oc-yang:counter64;
      description
        "IFG recycling drop counter. Increments based on the RcyDropCntrsCfg.";
    }
    leaf counters_slice2_ifg0_ifgbi_recycle_recycle_drop_on_port8 {
      type oc-yang:counter64;
      description
        "IFG recycling drop counter. Increments based on the RcyDropCntrsCfg.";
    }
    leaf counters_slice2_ifg0_ifgbi_recycle_recycle_drop_on_port9 {
      type oc-yang:counter64;
      description
        "IFG recycling drop counter. Increments based on the RcyDropCntrsCfg.";
    }
    leaf counters_slice2_ifg0_ifgbi_rx_protection_abnormally_terminated_packets {
      type oc-yang:counter64;
      description
        "RXPP interface protection packets termiante abnormally counter";
    }
    leaf counters_slice2_ifg0_mac_pool80_port0_rx_oob_mac_type_errors {
      type oc-yang:counter64;
      description
        "Counts in interleaving mode OOB packets that are received with none OOB packet type.";
    }
    leaf counters_slice2_ifg0_mac_pool80_port1_rx_oob_mac_type_errors {
      type oc-yang:counter64;
      description
        "Counts in interleaving mode OOB packets that are received with none OOB packet type.";
    }
    leaf counters_slice2_ifg0_mac_pool80_port2_rx_oob_mac_type_errors {
      type oc-yang:counter64;
      description
        "Counts in interleaving mode OOB packets that are received with none OOB packet type.";
    }
    leaf counters_slice2_ifg0_mac_pool80_port3_rx_oob_mac_type_errors {
      type oc-yang:counter64;
      description
        "Counts in interleaving mode OOB packets that are received with none OOB packet type.";
    }
    leaf counters_slice2_ifg0_mac_pool81_port0_rx_oob_mac_type_errors {
      type oc-yang:counter64;
      description
        "Counts in interleaving mode OOB packets that are received with none OOB packet type.";
    }
    leaf counters_slice2_ifg0_mac_pool81_port1_rx_oob_mac_type_errors {
      type oc-yang:counter64;
      description
        "Counts in interleaving mode OOB packets that are received with none OOB packet type.";
    }
    leaf counters_slice2_ifg0_mac_pool81_port2_rx_oob_mac_type_errors {
      type oc-yang:counter64;
      description
        "Counts in interleaving mode OOB packets that are received with none OOB packet type.";
    }
    leaf counters_slice2_ifg0_mac_pool81_port3_rx_oob_mac_type_errors {
      type oc-yang:counter64;
      description
        "Counts in interleaving mode OOB packets that are received with none OOB packet type.";
    }
    leaf counters_slice2_ifg0_mac_pool82_port0_rx_oob_mac_type_errors {
      type oc-yang:counter64;
      description
        "Counts in interleaving mode OOB packets that are received with none OOB packet type.";
    }
    leaf counters_slice2_ifg0_mac_pool82_port1_rx_oob_mac_type_errors {
      type oc-yang:counter64;
      description
        "Counts in interleaving mode OOB packets that are received with none OOB packet type.";
    }
    leaf counters_slice2_ifg0_mac_pool82_port2_rx_oob_mac_type_errors {
      type oc-yang:counter64;
      description
        "Counts in interleaving mode OOB packets that are received with none OOB packet type.";
    }
    leaf counters_slice2_ifg0_mac_pool82_port3_rx_oob_mac_type_errors {
      type oc-yang:counter64;
      description
        "Counts in interleaving mode OOB packets that are received with none OOB packet type.";
    }
    leaf counters_slice2_ifg0_mac_pool83_port0_rx_oob_mac_type_errors {
      type oc-yang:counter64;
      description
        "Counts in interleaving mode OOB packets that are received with none OOB packet type.";
    }
    leaf counters_slice2_ifg0_mac_pool83_port1_rx_oob_mac_type_errors {
      type oc-yang:counter64;
      description
        "Counts in interleaving mode OOB packets that are received with none OOB packet type.";
    }
    leaf counters_slice2_ifg0_mac_pool83_port2_rx_oob_mac_type_errors {
      type oc-yang:counter64;
      description
        "Counts in interleaving mode OOB packets that are received with none OOB packet type.";
    }
    leaf counters_slice2_ifg0_mac_pool83_port3_rx_oob_mac_type_errors {
      type oc-yang:counter64;
      description
        "Counts in interleaving mode OOB packets that are received with none OOB packet type.";
    }
    leaf counters_slice2_ifg0_npu_txpp_ifc_cluster_dropped_bad_packets {
      type oc-yang:counter64;
      description
        "Counts bad packets arrived to txpp Number of packet drops at the output of TxPP on IFG <i>";
    }
    leaf counters_slice2_ifg1_ifgb_rx_protection_errors {
      type oc-yang:counter64;
      description
        "RXPP interface protection errors counter.";
    }
    leaf counters_slice2_ifg1_ifgb_tx_protection_dropped_packets {
      type oc-yang:counter64;
      description
        "TXPP interface protection packet drop counter. Number of invalid packets arrived to TX.";
    }
    leaf counters_slice2_ifg1_ifgb_tx_protection_dropped_words {
      type oc-yang:counter64;
      description
        "TXPP interface protection words drop counter. Number of invalid words arrived to TX.";
    }
    leaf counters_slice2_ifg1_ifgb_tx_protection_errors {
      type oc-yang:counter64;
      description
        "TXPP interface protection errors counter.";
    }
    leaf counters_slice2_ifg1_ifgbi_pif_sequence_number_error {
      type oc-yang:counter64;
      description
        "PIF Sequence Number Error Count";
    }
    leaf counters_slice2_ifg1_ifgbi_rx_context_allocation_errors {
      type oc-yang:counter64;
      description
        "The amount of RXPP backpressure assertion events.";
    }
    leaf counters_slice2_ifg1_ifgbi_dash0_hp_dropped_full_packet {
      type oc-yang:counter64;
      description
        "SOP Drop Pkt Count - Full High Priority packet drops based on WrSopThd";
    }
    leaf counters_slice2_ifg1_ifgbi_dash0_hp_dropped_packets {
      type oc-yang:counter64;
      description
        "FIFO Full Pkt Count - Partial High Priority packet drops due to no space in FIFO";
    }
    leaf counters_slice2_ifg1_ifgbi_dash0_hp_dropped_words {
      type oc-yang:counter64;
      description
        "Word Drop Count - Partial High Priority word drops due to no space in FIFO";
    }
    leaf counters_slice2_ifg1_ifgbi_dash0_lp_dropped_full_packet {
      type oc-yang:counter64;
      description
        "SOP Drop Pkt Count - Full Low Priority packet drops based on WrSopThd";
    }
    leaf counters_slice2_ifg1_ifgbi_dash0_lp_dropped_packets {
      type oc-yang:counter64;
      description
        "FIFO Full Pkt Count - Partial Low Priority packet drops due to no space in FIFO";
    }
    leaf counters_slice2_ifg1_ifgbi_dash0_lp_dropped_words {
      type oc-yang:counter64;
      description
        "Word Drop Count - Partial Low Priority word drops due to no space in FIFO";
    }
    leaf counters_slice2_ifg1_ifgbi_dash1_hp_dropped_full_packet {
      type oc-yang:counter64;
      description
        "SOP Drop Pkt Count - Full High Priority packet drops based on WrSopThd";
    }
    leaf counters_slice2_ifg1_ifgbi_dash1_hp_dropped_packets {
      type oc-yang:counter64;
      description
        "FIFO Full Pkt Count - Partial High Priority packet drops due to no space in FIFO";
    }
    leaf counters_slice2_ifg1_ifgbi_dash1_hp_dropped_words {
      type oc-yang:counter64;
      description
        "Word Drop Count - Partial High Priority word drops due to no space in FIFO";
    }
    leaf counters_slice2_ifg1_ifgbi_dash1_lp_dropped_full_packet {
      type oc-yang:counter64;
      description
        "SOP Drop Pkt Count - Full Low Priority packet drops based on WrSopThd";
    }
    leaf counters_slice2_ifg1_ifgbi_dash1_lp_dropped_packets {
      type oc-yang:counter64;
      description
        "FIFO Full Pkt Count - Partial Low Priority packet drops due to no space in FIFO";
    }
    leaf counters_slice2_ifg1_ifgbi_dash1_lp_dropped_words {
      type oc-yang:counter64;
      description
        "Word Drop Count - Partial Low Priority word drops due to no space in FIFO";
    }
    leaf counters_slice2_ifg1_ifgbi_inband_extract_nph_errored_packets {
      type oc-yang:counter64;
      description
        "Inband Extract Bad packet extracted";
    }
    leaf counters_slice2_ifg1_ifgbi_inband_extract_pdm_errored_packets {
      type oc-yang:counter64;
      description
        "Inband Extract Bad packet extracted";
    }
    leaf counters_slice2_ifg1_ifgbi_inband_inject_nph_errored_packets {
      type oc-yang:counter64;
      description
        "Inband Inject Bad packet injected";
    }
    leaf counters_slice2_ifg1_ifgbi_inband_inject_pdm_errored_packets {
      type oc-yang:counter64;
      description
        "Inband Inject Bad packet injected";
    }
    leaf counters_slice2_ifg1_ifgbi_oobi_csms_dropped_packets {
      type oc-yang:counter64;
      description
        "Injected CSMS pkt drop cnt across all links";
    }
    leaf counters_slice2_ifg1_ifgbi_oobi_frm_dropped_packets {
      type oc-yang:counter64;
      description
        "Injected FRM pkt drop cnt across all links";
    }
    leaf counters_slice2_ifg1_ifgbi_oobi_fte_fts_dropped_packets {
      type oc-yang:counter64;
      description
        "Injected FTE Fabric Time Sync pkt drop cnt across all links";
    }
    leaf counters_slice2_ifg1_ifgbi_oobi_fte_pd_req_dropped_packets {
      type oc-yang:counter64;
      description
        "Injected FTE Peer Delay Request pkt drop cnt across all links";
    }
    leaf counters_slice2_ifg1_ifgbi_oobi_fte_pd_res_dropped_packets {
      type oc-yang:counter64;
      description
        "Injected FTE Peer Delay Response pkt drop cnt across all links";
    }
    leaf counters_slice2_ifg1_ifgbi_recycle_recycle_drop_on_port0 {
      type oc-yang:counter64;
      description
        "IFG recycling drop counter. Increments based on the RcyDropCntrsCfg.";
    }
    leaf counters_slice2_ifg1_ifgbi_recycle_recycle_drop_on_port1 {
      type oc-yang:counter64;
      description
        "IFG recycling drop counter. Increments based on the RcyDropCntrsCfg.";
    }
    leaf counters_slice2_ifg1_ifgbi_recycle_recycle_drop_on_port10 {
      type oc-yang:counter64;
      description
        "IFG recycling drop counter. Increments based on the RcyDropCntrsCfg.";
    }
    leaf counters_slice2_ifg1_ifgbi_recycle_recycle_drop_on_port11 {
      type oc-yang:counter64;
      description
        "IFG recycling drop counter. Increments based on the RcyDropCntrsCfg.";
    }
    leaf counters_slice2_ifg1_ifgbi_recycle_recycle_drop_on_port12 {
      type oc-yang:counter64;
      description
        "IFG recycling drop counter. Increments based on the RcyDropCntrsCfg.";
    }
    leaf counters_slice2_ifg1_ifgbi_recycle_recycle_drop_on_port13 {
      type oc-yang:counter64;
      description
        "IFG recycling drop counter. Increments based on the RcyDropCntrsCfg.";
    }
    leaf counters_slice2_ifg1_ifgbi_recycle_recycle_drop_on_port14 {
      type oc-yang:counter64;
      description
        "IFG recycling drop counter. Increments based on the RcyDropCntrsCfg.";
    }
    leaf counters_slice2_ifg1_ifgbi_recycle_recycle_drop_on_port15 {
      type oc-yang:counter64;
      description
        "IFG recycling drop counter. Increments based on the RcyDropCntrsCfg.";
    }
    leaf counters_slice2_ifg1_ifgbi_recycle_recycle_drop_on_port16 {
      type oc-yang:counter64;
      description
        "IFG recycling drop counter. Increments based on the RcyDropCntrsCfg.";
    }
    leaf counters_slice2_ifg1_ifgbi_recycle_recycle_drop_on_port17 {
      type oc-yang:counter64;
      description
        "IFG recycling drop counter. Increments based on the RcyDropCntrsCfg.";
    }
    leaf counters_slice2_ifg1_ifgbi_recycle_recycle_drop_on_port18 {
      type oc-yang:counter64;
      description
        "IFG recycling drop counter. Increments based on the RcyDropCntrsCfg.";
    }
    leaf counters_slice2_ifg1_ifgbi_recycle_recycle_drop_on_port19 {
      type oc-yang:counter64;
      description
        "IFG recycling drop counter. Increments based on the RcyDropCntrsCfg.";
    }
    leaf counters_slice2_ifg1_ifgbi_recycle_recycle_drop_on_port2 {
      type oc-yang:counter64;
      description
        "IFG recycling drop counter. Increments based on the RcyDropCntrsCfg.";
    }
    leaf counters_slice2_ifg1_ifgbi_recycle_recycle_drop_on_port20 {
      type oc-yang:counter64;
      description
        "IFG recycling drop counter. Increments based on the RcyDropCntrsCfg.";
    }
    leaf counters_slice2_ifg1_ifgbi_recycle_recycle_drop_on_port21 {
      type oc-yang:counter64;
      description
        "IFG recycling drop counter. Increments based on the RcyDropCntrsCfg.";
    }
    leaf counters_slice2_ifg1_ifgbi_recycle_recycle_drop_on_port22 {
      type oc-yang:counter64;
      description
        "IFG recycling drop counter. Increments based on the RcyDropCntrsCfg.";
    }
    leaf counters_slice2_ifg1_ifgbi_recycle_recycle_drop_on_port23 {
      type oc-yang:counter64;
      description
        "IFG recycling drop counter. Increments based on the RcyDropCntrsCfg.";
    }
    leaf counters_slice2_ifg1_ifgbi_recycle_recycle_drop_on_port24 {
      type oc-yang:counter64;
      description
        "IFG recycling drop counter. Increments based on the RcyDropCntrsCfg.";
    }
    leaf counters_slice2_ifg1_ifgbi_recycle_recycle_drop_on_port25 {
      type oc-yang:counter64;
      description
        "IFG recycling drop counter. Increments based on the RcyDropCntrsCfg.";
    }
    leaf counters_slice2_ifg1_ifgbi_recycle_recycle_drop_on_port26 {
      type oc-yang:counter64;
      description
        "IFG recycling drop counter. Increments based on the RcyDropCntrsCfg.";
    }
    leaf counters_slice2_ifg1_ifgbi_recycle_recycle_drop_on_port27 {
      type oc-yang:counter64;
      description
        "IFG recycling drop counter. Increments based on the RcyDropCntrsCfg.";
    }
    leaf counters_slice2_ifg1_ifgbi_recycle_recycle_drop_on_port28 {
      type oc-yang:counter64;
      description
        "IFG recycling drop counter. Increments based on the RcyDropCntrsCfg.";
    }
    leaf counters_slice2_ifg1_ifgbi_recycle_recycle_drop_on_port29 {
      type oc-yang:counter64;
      description
        "IFG recycling drop counter. Increments based on the RcyDropCntrsCfg.";
    }
    leaf counters_slice2_ifg1_ifgbi_recycle_recycle_drop_on_port3 {
      type oc-yang:counter64;
      description
        "IFG recycling drop counter. Increments based on the RcyDropCntrsCfg.";
    }
    leaf counters_slice2_ifg1_ifgbi_recycle_recycle_drop_on_port30 {
      type oc-yang:counter64;
      description
        "IFG recycling drop counter. Increments based on the RcyDropCntrsCfg.";
    }
    leaf counters_slice2_ifg1_ifgbi_recycle_recycle_drop_on_port31 {
      type oc-yang:counter64;
      description
        "IFG recycling drop counter. Increments based on the RcyDropCntrsCfg.";
    }
    leaf counters_slice2_ifg1_ifgbi_recycle_recycle_drop_on_port4 {
      type oc-yang:counter64;
      description
        "IFG recycling drop counter. Increments based on the RcyDropCntrsCfg.";
    }
    leaf counters_slice2_ifg1_ifgbi_recycle_recycle_drop_on_port5 {
      type oc-yang:counter64;
      description
        "IFG recycling drop counter. Increments based on the RcyDropCntrsCfg.";
    }
    leaf counters_slice2_ifg1_ifgbi_recycle_recycle_drop_on_port6 {
      type oc-yang:counter64;
      description
        "IFG recycling drop counter. Increments based on the RcyDropCntrsCfg.";
    }
    leaf counters_slice2_ifg1_ifgbi_recycle_recycle_drop_on_port7 {
      type oc-yang:counter64;
      description
        "IFG recycling drop counter. Increments based on the RcyDropCntrsCfg.";
    }
    leaf counters_slice2_ifg1_ifgbi_recycle_recycle_drop_on_port8 {
      type oc-yang:counter64;
      description
        "IFG recycling drop counter. Increments based on the RcyDropCntrsCfg.";
    }
    leaf counters_slice2_ifg1_ifgbi_recycle_recycle_drop_on_port9 {
      type oc-yang:counter64;
      description
        "IFG recycling drop counter. Increments based on the RcyDropCntrsCfg.";
    }
    leaf counters_slice2_ifg1_ifgbi_rx_protection_abnormally_terminated_packets {
      type oc-yang:counter64;
      description
        "RXPP interface protection packets termiante abnormally counter";
    }
    leaf counters_slice2_ifg1_mac_pool80_port0_rx_oob_mac_type_errors {
      type oc-yang:counter64;
      description
        "Counts in interleaving mode OOB packets that are received with none OOB packet type.";
    }
    leaf counters_slice2_ifg1_mac_pool80_port1_rx_oob_mac_type_errors {
      type oc-yang:counter64;
      description
        "Counts in interleaving mode OOB packets that are received with none OOB packet type.";
    }
    leaf counters_slice2_ifg1_mac_pool80_port2_rx_oob_mac_type_errors {
      type oc-yang:counter64;
      description
        "Counts in interleaving mode OOB packets that are received with none OOB packet type.";
    }
    leaf counters_slice2_ifg1_mac_pool80_port3_rx_oob_mac_type_errors {
      type oc-yang:counter64;
      description
        "Counts in interleaving mode OOB packets that are received with none OOB packet type.";
    }
    leaf counters_slice2_ifg1_mac_pool81_port0_rx_oob_mac_type_errors {
      type oc-yang:counter64;
      description
        "Counts in interleaving mode OOB packets that are received with none OOB packet type.";
    }
    leaf counters_slice2_ifg1_mac_pool81_port1_rx_oob_mac_type_errors {
      type oc-yang:counter64;
      description
        "Counts in interleaving mode OOB packets that are received with none OOB packet type.";
    }
    leaf counters_slice2_ifg1_mac_pool81_port2_rx_oob_mac_type_errors {
      type oc-yang:counter64;
      description
        "Counts in interleaving mode OOB packets that are received with none OOB packet type.";
    }
    leaf counters_slice2_ifg1_mac_pool81_port3_rx_oob_mac_type_errors {
      type oc-yang:counter64;
      description
        "Counts in interleaving mode OOB packets that are received with none OOB packet type.";
    }
    leaf counters_slice2_ifg1_mac_pool82_port0_rx_oob_mac_type_errors {
      type oc-yang:counter64;
      description
        "Counts in interleaving mode OOB packets that are received with none OOB packet type.";
    }
    leaf counters_slice2_ifg1_mac_pool82_port1_rx_oob_mac_type_errors {
      type oc-yang:counter64;
      description
        "Counts in interleaving mode OOB packets that are received with none OOB packet type.";
    }
    leaf counters_slice2_ifg1_mac_pool82_port2_rx_oob_mac_type_errors {
      type oc-yang:counter64;
      description
        "Counts in interleaving mode OOB packets that are received with none OOB packet type.";
    }
    leaf counters_slice2_ifg1_mac_pool82_port3_rx_oob_mac_type_errors {
      type oc-yang:counter64;
      description
        "Counts in interleaving mode OOB packets that are received with none OOB packet type.";
    }
    leaf counters_slice2_ifg1_mac_pool83_port0_rx_oob_mac_type_errors {
      type oc-yang:counter64;
      description
        "Counts in interleaving mode OOB packets that are received with none OOB packet type.";
    }
    leaf counters_slice2_ifg1_mac_pool83_port1_rx_oob_mac_type_errors {
      type oc-yang:counter64;
      description
        "Counts in interleaving mode OOB packets that are received with none OOB packet type.";
    }
    leaf counters_slice2_ifg1_mac_pool83_port2_rx_oob_mac_type_errors {
      type oc-yang:counter64;
      description
        "Counts in interleaving mode OOB packets that are received with none OOB packet type.";
    }
    leaf counters_slice2_ifg1_mac_pool83_port3_rx_oob_mac_type_errors {
      type oc-yang:counter64;
      description
        "Counts in interleaving mode OOB packets that are received with none OOB packet type.";
    }
    leaf counters_slice2_ifg1_npu_txpp_ifc_cluster_dropped_bad_packets {
      type oc-yang:counter64;
      description
        "Counts bad packets arrived to txpp Number of packet drops at the output of TxPP on IFG <i>";
    }
    leaf counters_slice3_ifg0_ifgb_rx_protection_errors {
      type oc-yang:counter64;
      description
        "RXPP interface protection errors counter.";
    }
    leaf counters_slice3_ifg0_ifgb_tx_protection_dropped_packets {
      type oc-yang:counter64;
      description
        "TXPP interface protection packet drop counter. Number of invalid packets arrived to TX.";
    }
    leaf counters_slice3_ifg0_ifgb_tx_protection_dropped_words {
      type oc-yang:counter64;
      description
        "TXPP interface protection words drop counter. Number of invalid words arrived to TX.";
    }
    leaf counters_slice3_ifg0_ifgb_tx_protection_errors {
      type oc-yang:counter64;
      description
        "TXPP interface protection errors counter.";
    }
    leaf counters_slice3_ifg0_ifgbi_pif_sequence_number_error {
      type oc-yang:counter64;
      description
        "PIF Sequence Number Error Count";
    }
    leaf counters_slice3_ifg0_ifgbi_rx_context_allocation_errors {
      type oc-yang:counter64;
      description
        "The amount of RXPP backpressure assertion events.";
    }
    leaf counters_slice3_ifg0_ifgbi_dash0_hp_dropped_full_packet {
      type oc-yang:counter64;
      description
        "SOP Drop Pkt Count - Full High Priority packet drops based on WrSopThd";
    }
    leaf counters_slice3_ifg0_ifgbi_dash0_hp_dropped_packets {
      type oc-yang:counter64;
      description
        "FIFO Full Pkt Count - Partial High Priority packet drops due to no space in FIFO";
    }
    leaf counters_slice3_ifg0_ifgbi_dash0_hp_dropped_words {
      type oc-yang:counter64;
      description
        "Word Drop Count - Partial High Priority word drops due to no space in FIFO";
    }
    leaf counters_slice3_ifg0_ifgbi_dash0_lp_dropped_full_packet {
      type oc-yang:counter64;
      description
        "SOP Drop Pkt Count - Full Low Priority packet drops based on WrSopThd";
    }
    leaf counters_slice3_ifg0_ifgbi_dash0_lp_dropped_packets {
      type oc-yang:counter64;
      description
        "FIFO Full Pkt Count - Partial Low Priority packet drops due to no space in FIFO";
    }
    leaf counters_slice3_ifg0_ifgbi_dash0_lp_dropped_words {
      type oc-yang:counter64;
      description
        "Word Drop Count - Partial Low Priority word drops due to no space in FIFO";
    }
    leaf counters_slice3_ifg0_ifgbi_dash1_hp_dropped_full_packet {
      type oc-yang:counter64;
      description
        "SOP Drop Pkt Count - Full High Priority packet drops based on WrSopThd";
    }
    leaf counters_slice3_ifg0_ifgbi_dash1_hp_dropped_packets {
      type oc-yang:counter64;
      description
        "FIFO Full Pkt Count - Partial High Priority packet drops due to no space in FIFO";
    }
    leaf counters_slice3_ifg0_ifgbi_dash1_hp_dropped_words {
      type oc-yang:counter64;
      description
        "Word Drop Count - Partial High Priority word drops due to no space in FIFO";
    }
    leaf counters_slice3_ifg0_ifgbi_dash1_lp_dropped_full_packet {
      type oc-yang:counter64;
      description
        "SOP Drop Pkt Count - Full Low Priority packet drops based on WrSopThd";
    }
    leaf counters_slice3_ifg0_ifgbi_dash1_lp_dropped_packets {
      type oc-yang:counter64;
      description
        "FIFO Full Pkt Count - Partial Low Priority packet drops due to no space in FIFO";
    }
    leaf counters_slice3_ifg0_ifgbi_dash1_lp_dropped_words {
      type oc-yang:counter64;
      description
        "Word Drop Count - Partial Low Priority word drops due to no space in FIFO";
    }
    leaf counters_slice3_ifg0_ifgbi_inband_extract_nph_errored_packets {
      type oc-yang:counter64;
      description
        "Inband Extract Bad packet extracted";
    }
    leaf counters_slice3_ifg0_ifgbi_inband_extract_pdm_errored_packets {
      type oc-yang:counter64;
      description
        "Inband Extract Bad packet extracted";
    }
    leaf counters_slice3_ifg0_ifgbi_inband_inject_nph_errored_packets {
      type oc-yang:counter64;
      description
        "Inband Inject Bad packet injected";
    }
    leaf counters_slice3_ifg0_ifgbi_inband_inject_pdm_errored_packets {
      type oc-yang:counter64;
      description
        "Inband Inject Bad packet injected";
    }
    leaf counters_slice3_ifg0_ifgbi_oobi_csms_dropped_packets {
      type oc-yang:counter64;
      description
        "Injected CSMS pkt drop cnt across all links";
    }
    leaf counters_slice3_ifg0_ifgbi_oobi_frm_dropped_packets {
      type oc-yang:counter64;
      description
        "Injected FRM pkt drop cnt across all links";
    }
    leaf counters_slice3_ifg0_ifgbi_oobi_fte_fts_dropped_packets {
      type oc-yang:counter64;
      description
        "Injected FTE Fabric Time Sync pkt drop cnt across all links";
    }
    leaf counters_slice3_ifg0_ifgbi_oobi_fte_pd_req_dropped_packets {
      type oc-yang:counter64;
      description
        "Injected FTE Peer Delay Request pkt drop cnt across all links";
    }
    leaf counters_slice3_ifg0_ifgbi_oobi_fte_pd_res_dropped_packets {
      type oc-yang:counter64;
      description
        "Injected FTE Peer Delay Response pkt drop cnt across all links";
    }
    leaf counters_slice3_ifg0_ifgbi_recycle_recycle_drop_on_port0 {
      type oc-yang:counter64;
      description
        "IFG recycling drop counter. Increments based on the RcyDropCntrsCfg.";
    }
    leaf counters_slice3_ifg0_ifgbi_recycle_recycle_drop_on_port1 {
      type oc-yang:counter64;
      description
        "IFG recycling drop counter. Increments based on the RcyDropCntrsCfg.";
    }
    leaf counters_slice3_ifg0_ifgbi_recycle_recycle_drop_on_port10 {
      type oc-yang:counter64;
      description
        "IFG recycling drop counter. Increments based on the RcyDropCntrsCfg.";
    }
    leaf counters_slice3_ifg0_ifgbi_recycle_recycle_drop_on_port11 {
      type oc-yang:counter64;
      description
        "IFG recycling drop counter. Increments based on the RcyDropCntrsCfg.";
    }
    leaf counters_slice3_ifg0_ifgbi_recycle_recycle_drop_on_port12 {
      type oc-yang:counter64;
      description
        "IFG recycling drop counter. Increments based on the RcyDropCntrsCfg.";
    }
    leaf counters_slice3_ifg0_ifgbi_recycle_recycle_drop_on_port13 {
      type oc-yang:counter64;
      description
        "IFG recycling drop counter. Increments based on the RcyDropCntrsCfg.";
    }
    leaf counters_slice3_ifg0_ifgbi_recycle_recycle_drop_on_port14 {
      type oc-yang:counter64;
      description
        "IFG recycling drop counter. Increments based on the RcyDropCntrsCfg.";
    }
    leaf counters_slice3_ifg0_ifgbi_recycle_recycle_drop_on_port15 {
      type oc-yang:counter64;
      description
        "IFG recycling drop counter. Increments based on the RcyDropCntrsCfg.";
    }
    leaf counters_slice3_ifg0_ifgbi_recycle_recycle_drop_on_port16 {
      type oc-yang:counter64;
      description
        "IFG recycling drop counter. Increments based on the RcyDropCntrsCfg.";
    }
    leaf counters_slice3_ifg0_ifgbi_recycle_recycle_drop_on_port17 {
      type oc-yang:counter64;
      description
        "IFG recycling drop counter. Increments based on the RcyDropCntrsCfg.";
    }
    leaf counters_slice3_ifg0_ifgbi_recycle_recycle_drop_on_port18 {
      type oc-yang:counter64;
      description
        "IFG recycling drop counter. Increments based on the RcyDropCntrsCfg.";
    }
    leaf counters_slice3_ifg0_ifgbi_recycle_recycle_drop_on_port19 {
      type oc-yang:counter64;
      description
        "IFG recycling drop counter. Increments based on the RcyDropCntrsCfg.";
    }
    leaf counters_slice3_ifg0_ifgbi_recycle_recycle_drop_on_port2 {
      type oc-yang:counter64;
      description
        "IFG recycling drop counter. Increments based on the RcyDropCntrsCfg.";
    }
    leaf counters_slice3_ifg0_ifgbi_recycle_recycle_drop_on_port20 {
      type oc-yang:counter64;
      description
        "IFG recycling drop counter. Increments based on the RcyDropCntrsCfg.";
    }
    leaf counters_slice3_ifg0_ifgbi_recycle_recycle_drop_on_port21 {
      type oc-yang:counter64;
      description
        "IFG recycling drop counter. Increments based on the RcyDropCntrsCfg.";
    }
    leaf counters_slice3_ifg0_ifgbi_recycle_recycle_drop_on_port22 {
      type oc-yang:counter64;
      description
        "IFG recycling drop counter. Increments based on the RcyDropCntrsCfg.";
    }
    leaf counters_slice3_ifg0_ifgbi_recycle_recycle_drop_on_port23 {
      type oc-yang:counter64;
      description
        "IFG recycling drop counter. Increments based on the RcyDropCntrsCfg.";
    }
    leaf counters_slice3_ifg0_ifgbi_recycle_recycle_drop_on_port24 {
      type oc-yang:counter64;
      description
        "IFG recycling drop counter. Increments based on the RcyDropCntrsCfg.";
    }
    leaf counters_slice3_ifg0_ifgbi_recycle_recycle_drop_on_port25 {
      type oc-yang:counter64;
      description
        "IFG recycling drop counter. Increments based on the RcyDropCntrsCfg.";
    }
    leaf counters_slice3_ifg0_ifgbi_recycle_recycle_drop_on_port26 {
      type oc-yang:counter64;
      description
        "IFG recycling drop counter. Increments based on the RcyDropCntrsCfg.";
    }
    leaf counters_slice3_ifg0_ifgbi_recycle_recycle_drop_on_port27 {
      type oc-yang:counter64;
      description
        "IFG recycling drop counter. Increments based on the RcyDropCntrsCfg.";
    }
    leaf counters_slice3_ifg0_ifgbi_recycle_recycle_drop_on_port28 {
      type oc-yang:counter64;
      description
        "IFG recycling drop counter. Increments based on the RcyDropCntrsCfg.";
    }
    leaf counters_slice3_ifg0_ifgbi_recycle_recycle_drop_on_port29 {
      type oc-yang:counter64;
      description
        "IFG recycling drop counter. Increments based on the RcyDropCntrsCfg.";
    }
    leaf counters_slice3_ifg0_ifgbi_recycle_recycle_drop_on_port3 {
      type oc-yang:counter64;
      description
        "IFG recycling drop counter. Increments based on the RcyDropCntrsCfg.";
    }
    leaf counters_slice3_ifg0_ifgbi_recycle_recycle_drop_on_port30 {
      type oc-yang:counter64;
      description
        "IFG recycling drop counter. Increments based on the RcyDropCntrsCfg.";
    }
    leaf counters_slice3_ifg0_ifgbi_recycle_recycle_drop_on_port31 {
      type oc-yang:counter64;
      description
        "IFG recycling drop counter. Increments based on the RcyDropCntrsCfg.";
    }
    leaf counters_slice3_ifg0_ifgbi_recycle_recycle_drop_on_port4 {
      type oc-yang:counter64;
      description
        "IFG recycling drop counter. Increments based on the RcyDropCntrsCfg.";
    }
    leaf counters_slice3_ifg0_ifgbi_recycle_recycle_drop_on_port5 {
      type oc-yang:counter64;
      description
        "IFG recycling drop counter. Increments based on the RcyDropCntrsCfg.";
    }
    leaf counters_slice3_ifg0_ifgbi_recycle_recycle_drop_on_port6 {
      type oc-yang:counter64;
      description
        "IFG recycling drop counter. Increments based on the RcyDropCntrsCfg.";
    }
    leaf counters_slice3_ifg0_ifgbi_recycle_recycle_drop_on_port7 {
      type oc-yang:counter64;
      description
        "IFG recycling drop counter. Increments based on the RcyDropCntrsCfg.";
    }
    leaf counters_slice3_ifg0_ifgbi_recycle_recycle_drop_on_port8 {
      type oc-yang:counter64;
      description
        "IFG recycling drop counter. Increments based on the RcyDropCntrsCfg.";
    }
    leaf counters_slice3_ifg0_ifgbi_recycle_recycle_drop_on_port9 {
      type oc-yang:counter64;
      description
        "IFG recycling drop counter. Increments based on the RcyDropCntrsCfg.";
    }
    leaf counters_slice3_ifg0_ifgbi_rx_protection_abnormally_terminated_packets {
      type oc-yang:counter64;
      description
        "RXPP interface protection packets termiante abnormally counter";
    }
    leaf counters_slice3_ifg0_mac_pool80_port0_rx_oob_mac_type_errors {
      type oc-yang:counter64;
      description
        "Counts in interleaving mode OOB packets that are received with none OOB packet type.";
    }
    leaf counters_slice3_ifg0_mac_pool80_port1_rx_oob_mac_type_errors {
      type oc-yang:counter64;
      description
        "Counts in interleaving mode OOB packets that are received with none OOB packet type.";
    }
    leaf counters_slice3_ifg0_mac_pool80_port2_rx_oob_mac_type_errors {
      type oc-yang:counter64;
      description
        "Counts in interleaving mode OOB packets that are received with none OOB packet type.";
    }
    leaf counters_slice3_ifg0_mac_pool80_port3_rx_oob_mac_type_errors {
      type oc-yang:counter64;
      description
        "Counts in interleaving mode OOB packets that are received with none OOB packet type.";
    }
    leaf counters_slice3_ifg0_mac_pool81_port0_rx_oob_mac_type_errors {
      type oc-yang:counter64;
      description
        "Counts in interleaving mode OOB packets that are received with none OOB packet type.";
    }
    leaf counters_slice3_ifg0_mac_pool81_port1_rx_oob_mac_type_errors {
      type oc-yang:counter64;
      description
        "Counts in interleaving mode OOB packets that are received with none OOB packet type.";
    }
    leaf counters_slice3_ifg0_mac_pool81_port2_rx_oob_mac_type_errors {
      type oc-yang:counter64;
      description
        "Counts in interleaving mode OOB packets that are received with none OOB packet type.";
    }
    leaf counters_slice3_ifg0_mac_pool81_port3_rx_oob_mac_type_errors {
      type oc-yang:counter64;
      description
        "Counts in interleaving mode OOB packets that are received with none OOB packet type.";
    }
    leaf counters_slice3_ifg0_mac_pool82_port0_rx_oob_mac_type_errors {
      type oc-yang:counter64;
      description
        "Counts in interleaving mode OOB packets that are received with none OOB packet type.";
    }
    leaf counters_slice3_ifg0_mac_pool82_port1_rx_oob_mac_type_errors {
      type oc-yang:counter64;
      description
        "Counts in interleaving mode OOB packets that are received with none OOB packet type.";
    }
    leaf counters_slice3_ifg0_mac_pool82_port2_rx_oob_mac_type_errors {
      type oc-yang:counter64;
      description
        "Counts in interleaving mode OOB packets that are received with none OOB packet type.";
    }
    leaf counters_slice3_ifg0_mac_pool82_port3_rx_oob_mac_type_errors {
      type oc-yang:counter64;
      description
        "Counts in interleaving mode OOB packets that are received with none OOB packet type.";
    }
    leaf counters_slice3_ifg0_mac_pool83_port0_rx_oob_mac_type_errors {
      type oc-yang:counter64;
      description
        "Counts in interleaving mode OOB packets that are received with none OOB packet type.";
    }
    leaf counters_slice3_ifg0_mac_pool83_port1_rx_oob_mac_type_errors {
      type oc-yang:counter64;
      description
        "Counts in interleaving mode OOB packets that are received with none OOB packet type.";
    }
    leaf counters_slice3_ifg0_mac_pool83_port2_rx_oob_mac_type_errors {
      type oc-yang:counter64;
      description
        "Counts in interleaving mode OOB packets that are received with none OOB packet type.";
    }
    leaf counters_slice3_ifg0_mac_pool83_port3_rx_oob_mac_type_errors {
      type oc-yang:counter64;
      description
        "Counts in interleaving mode OOB packets that are received with none OOB packet type.";
    }
    leaf counters_slice3_ifg0_npu_txpp_ifc_cluster_dropped_bad_packets {
      type oc-yang:counter64;
      description
        "Counts bad packets arrived to txpp Number of packet drops at the output of TxPP on IFG <i>";
    }
    leaf counters_slice3_ifg1_ifgb_rx_protection_errors {
      type oc-yang:counter64;
      description
        "RXPP interface protection errors counter.";
    }
    leaf counters_slice3_ifg1_ifgb_tx_protection_dropped_packets {
      type oc-yang:counter64;
      description
        "TXPP interface protection packet drop counter. Number of invalid packets arrived to TX.";
    }
    leaf counters_slice3_ifg1_ifgb_tx_protection_dropped_words {
      type oc-yang:counter64;
      description
        "TXPP interface protection words drop counter. Number of invalid words arrived to TX.";
    }
    leaf counters_slice3_ifg1_ifgb_tx_protection_errors {
      type oc-yang:counter64;
      description
        "TXPP interface protection errors counter.";
    }
    leaf counters_slice3_ifg1_ifgbi_pif_sequence_number_error {
      type oc-yang:counter64;
      description
        "PIF Sequence Number Error Count";
    }
    leaf counters_slice3_ifg1_ifgbi_rx_context_allocation_errors {
      type oc-yang:counter64;
      description
        "The amount of RXPP backpressure assertion events.";
    }
    leaf counters_slice3_ifg1_ifgbi_dash0_hp_dropped_full_packet {
      type oc-yang:counter64;
      description
        "SOP Drop Pkt Count - Full High Priority packet drops based on WrSopThd";
    }
    leaf counters_slice3_ifg1_ifgbi_dash0_hp_dropped_packets {
      type oc-yang:counter64;
      description
        "FIFO Full Pkt Count - Partial High Priority packet drops due to no space in FIFO";
    }
    leaf counters_slice3_ifg1_ifgbi_dash0_hp_dropped_words {
      type oc-yang:counter64;
      description
        "Word Drop Count - Partial High Priority word drops due to no space in FIFO";
    }
    leaf counters_slice3_ifg1_ifgbi_dash0_lp_dropped_full_packet {
      type oc-yang:counter64;
      description
        "SOP Drop Pkt Count - Full Low Priority packet drops based on WrSopThd";
    }
    leaf counters_slice3_ifg1_ifgbi_dash0_lp_dropped_packets {
      type oc-yang:counter64;
      description
        "FIFO Full Pkt Count - Partial Low Priority packet drops due to no space in FIFO";
    }
    leaf counters_slice3_ifg1_ifgbi_dash0_lp_dropped_words {
      type oc-yang:counter64;
      description
        "Word Drop Count - Partial Low Priority word drops due to no space in FIFO";
    }
    leaf counters_slice3_ifg1_ifgbi_dash1_hp_dropped_full_packet {
      type oc-yang:counter64;
      description
        "SOP Drop Pkt Count - Full High Priority packet drops based on WrSopThd";
    }
    leaf counters_slice3_ifg1_ifgbi_dash1_hp_dropped_packets {
      type oc-yang:counter64;
      description
        "FIFO Full Pkt Count - Partial High Priority packet drops due to no space in FIFO";
    }
    leaf counters_slice3_ifg1_ifgbi_dash1_hp_dropped_words {
      type oc-yang:counter64;
      description
        "Word Drop Count - Partial High Priority word drops due to no space in FIFO";
    }
    leaf counters_slice3_ifg1_ifgbi_dash1_lp_dropped_full_packet {
      type oc-yang:counter64;
      description
        "SOP Drop Pkt Count - Full Low Priority packet drops based on WrSopThd";
    }
    leaf counters_slice3_ifg1_ifgbi_dash1_lp_dropped_packets {
      type oc-yang:counter64;
      description
        "FIFO Full Pkt Count - Partial Low Priority packet drops due to no space in FIFO";
    }
    leaf counters_slice3_ifg1_ifgbi_dash1_lp_dropped_words {
      type oc-yang:counter64;
      description
        "Word Drop Count - Partial Low Priority word drops due to no space in FIFO";
    }
    leaf counters_slice3_ifg1_ifgbi_inband_extract_nph_errored_packets {
      type oc-yang:counter64;
      description
        "Inband Extract Bad packet extracted";
    }
    leaf counters_slice3_ifg1_ifgbi_inband_extract_pdm_errored_packets {
      type oc-yang:counter64;
      description
        "Inband Extract Bad packet extracted";
    }
    leaf counters_slice3_ifg1_ifgbi_inband_inject_nph_errored_packets {
      type oc-yang:counter64;
      description
        "Inband Inject Bad packet injected";
    }
    leaf counters_slice3_ifg1_ifgbi_inband_inject_pdm_errored_packets {
      type oc-yang:counter64;
      description
        "Inband Inject Bad packet injected";
    }
    leaf counters_slice3_ifg1_ifgbi_oobi_csms_dropped_packets {
      type oc-yang:counter64;
      description
        "Injected CSMS pkt drop cnt across all links";
    }
    leaf counters_slice3_ifg1_ifgbi_oobi_frm_dropped_packets {
      type oc-yang:counter64;
      description
        "Injected FRM pkt drop cnt across all links";
    }
    leaf counters_slice3_ifg1_ifgbi_oobi_fte_fts_dropped_packets {
      type oc-yang:counter64;
      description
        "Injected FTE Fabric Time Sync pkt drop cnt across all links";
    }
    leaf counters_slice3_ifg1_ifgbi_oobi_fte_pd_req_dropped_packets {
      type oc-yang:counter64;
      description
        "Injected FTE Peer Delay Request pkt drop cnt across all links";
    }
    leaf counters_slice3_ifg1_ifgbi_oobi_fte_pd_res_dropped_packets {
      type oc-yang:counter64;
      description
        "Injected FTE Peer Delay Response pkt drop cnt across all links";
    }
    leaf counters_slice3_ifg1_ifgbi_recycle_recycle_drop_on_port0 {
      type oc-yang:counter64;
      description
        "IFG recycling drop counter. Increments based on the RcyDropCntrsCfg.";
    }
    leaf counters_slice3_ifg1_ifgbi_recycle_recycle_drop_on_port1 {
      type oc-yang:counter64;
      description
        "IFG recycling drop counter. Increments based on the RcyDropCntrsCfg.";
    }
    leaf counters_slice3_ifg1_ifgbi_recycle_recycle_drop_on_port10 {
      type oc-yang:counter64;
      description
        "IFG recycling drop counter. Increments based on the RcyDropCntrsCfg.";
    }
    leaf counters_slice3_ifg1_ifgbi_recycle_recycle_drop_on_port11 {
      type oc-yang:counter64;
      description
        "IFG recycling drop counter. Increments based on the RcyDropCntrsCfg.";
    }
    leaf counters_slice3_ifg1_ifgbi_recycle_recycle_drop_on_port12 {
      type oc-yang:counter64;
      description
        "IFG recycling drop counter. Increments based on the RcyDropCntrsCfg.";
    }
    leaf counters_slice3_ifg1_ifgbi_recycle_recycle_drop_on_port13 {
      type oc-yang:counter64;
      description
        "IFG recycling drop counter. Increments based on the RcyDropCntrsCfg.";
    }
    leaf counters_slice3_ifg1_ifgbi_recycle_recycle_drop_on_port14 {
      type oc-yang:counter64;
      description
        "IFG recycling drop counter. Increments based on the RcyDropCntrsCfg.";
    }
    leaf counters_slice3_ifg1_ifgbi_recycle_recycle_drop_on_port15 {
      type oc-yang:counter64;
      description
        "IFG recycling drop counter. Increments based on the RcyDropCntrsCfg.";
    }
    leaf counters_slice3_ifg1_ifgbi_recycle_recycle_drop_on_port16 {
      type oc-yang:counter64;
      description
        "IFG recycling drop counter. Increments based on the RcyDropCntrsCfg.";
    }
    leaf counters_slice3_ifg1_ifgbi_recycle_recycle_drop_on_port17 {
      type oc-yang:counter64;
      description
        "IFG recycling drop counter. Increments based on the RcyDropCntrsCfg.";
    }
    leaf counters_slice3_ifg1_ifgbi_recycle_recycle_drop_on_port18 {
      type oc-yang:counter64;
      description
        "IFG recycling drop counter. Increments based on the RcyDropCntrsCfg.";
    }
    leaf counters_slice3_ifg1_ifgbi_recycle_recycle_drop_on_port19 {
      type oc-yang:counter64;
      description
        "IFG recycling drop counter. Increments based on the RcyDropCntrsCfg.";
    }
    leaf counters_slice3_ifg1_ifgbi_recycle_recycle_drop_on_port2 {
      type oc-yang:counter64;
      description
        "IFG recycling drop counter. Increments based on the RcyDropCntrsCfg.";
    }
    leaf counters_slice3_ifg1_ifgbi_recycle_recycle_drop_on_port20 {
      type oc-yang:counter64;
      description
        "IFG recycling drop counter. Increments based on the RcyDropCntrsCfg.";
    }
    leaf counters_slice3_ifg1_ifgbi_recycle_recycle_drop_on_port21 {
      type oc-yang:counter64;
      description
        "IFG recycling drop counter. Increments based on the RcyDropCntrsCfg.";
    }
    leaf counters_slice3_ifg1_ifgbi_recycle_recycle_drop_on_port22 {
      type oc-yang:counter64;
      description
        "IFG recycling drop counter. Increments based on the RcyDropCntrsCfg.";
    }
    leaf counters_slice3_ifg1_ifgbi_recycle_recycle_drop_on_port23 {
      type oc-yang:counter64;
      description
        "IFG recycling drop counter. Increments based on the RcyDropCntrsCfg.";
    }
    leaf counters_slice3_ifg1_ifgbi_recycle_recycle_drop_on_port24 {
      type oc-yang:counter64;
      description
        "IFG recycling drop counter. Increments based on the RcyDropCntrsCfg.";
    }
    leaf counters_slice3_ifg1_ifgbi_recycle_recycle_drop_on_port25 {
      type oc-yang:counter64;
      description
        "IFG recycling drop counter. Increments based on the RcyDropCntrsCfg.";
    }
    leaf counters_slice3_ifg1_ifgbi_recycle_recycle_drop_on_port26 {
      type oc-yang:counter64;
      description
        "IFG recycling drop counter. Increments based on the RcyDropCntrsCfg.";
    }
    leaf counters_slice3_ifg1_ifgbi_recycle_recycle_drop_on_port27 {
      type oc-yang:counter64;
      description
        "IFG recycling drop counter. Increments based on the RcyDropCntrsCfg.";
    }
    leaf counters_slice3_ifg1_ifgbi_recycle_recycle_drop_on_port28 {
      type oc-yang:counter64;
      description
        "IFG recycling drop counter. Increments based on the RcyDropCntrsCfg.";
    }
    leaf counters_slice3_ifg1_ifgbi_recycle_recycle_drop_on_port29 {
      type oc-yang:counter64;
      description
        "IFG recycling drop counter. Increments based on the RcyDropCntrsCfg.";
    }
    leaf counters_slice3_ifg1_ifgbi_recycle_recycle_drop_on_port3 {
      type oc-yang:counter64;
      description
        "IFG recycling drop counter. Increments based on the RcyDropCntrsCfg.";
    }
    leaf counters_slice3_ifg1_ifgbi_recycle_recycle_drop_on_port30 {
      type oc-yang:counter64;
      description
        "IFG recycling drop counter. Increments based on the RcyDropCntrsCfg.";
    }
    leaf counters_slice3_ifg1_ifgbi_recycle_recycle_drop_on_port31 {
      type oc-yang:counter64;
      description
        "IFG recycling drop counter. Increments based on the RcyDropCntrsCfg.";
    }
    leaf counters_slice3_ifg1_ifgbi_recycle_recycle_drop_on_port4 {
      type oc-yang:counter64;
      description
        "IFG recycling drop counter. Increments based on the RcyDropCntrsCfg.";
    }
    leaf counters_slice3_ifg1_ifgbi_recycle_recycle_drop_on_port5 {
      type oc-yang:counter64;
      description
        "IFG recycling drop counter. Increments based on the RcyDropCntrsCfg.";
    }
    leaf counters_slice3_ifg1_ifgbi_recycle_recycle_drop_on_port6 {
      type oc-yang:counter64;
      description
        "IFG recycling drop counter. Increments based on the RcyDropCntrsCfg.";
    }
    leaf counters_slice3_ifg1_ifgbi_recycle_recycle_drop_on_port7 {
      type oc-yang:counter64;
      description
        "IFG recycling drop counter. Increments based on the RcyDropCntrsCfg.";
    }
    leaf counters_slice3_ifg1_ifgbi_recycle_recycle_drop_on_port8 {
      type oc-yang:counter64;
      description
        "IFG recycling drop counter. Increments based on the RcyDropCntrsCfg.";
    }
    leaf counters_slice3_ifg1_ifgbi_recycle_recycle_drop_on_port9 {
      type oc-yang:counter64;
      description
        "IFG recycling drop counter. Increments based on the RcyDropCntrsCfg.";
    }
    leaf counters_slice3_ifg1_ifgbi_rx_protection_abnormally_terminated_packets {
      type oc-yang:counter64;
      description
        "RXPP interface protection packets termiante abnormally counter";
    }
    leaf counters_slice3_ifg1_mac_pool80_port0_rx_oob_mac_type_errors {
      type oc-yang:counter64;
      description
        "Counts in interleaving mode OOB packets that are received with none OOB packet type.";
    }
    leaf counters_slice3_ifg1_mac_pool80_port1_rx_oob_mac_type_errors {
      type oc-yang:counter64;
      description
        "Counts in interleaving mode OOB packets that are received with none OOB packet type.";
    }
    leaf counters_slice3_ifg1_mac_pool80_port2_rx_oob_mac_type_errors {
      type oc-yang:counter64;
      description
        "Counts in interleaving mode OOB packets that are received with none OOB packet type.";
    }
    leaf counters_slice3_ifg1_mac_pool80_port3_rx_oob_mac_type_errors {
      type oc-yang:counter64;
      description
        "Counts in interleaving mode OOB packets that are received with none OOB packet type.";
    }
    leaf counters_slice3_ifg1_mac_pool81_port0_rx_oob_mac_type_errors {
      type oc-yang:counter64;
      description
        "Counts in interleaving mode OOB packets that are received with none OOB packet type.";
    }
    leaf counters_slice3_ifg1_mac_pool81_port1_rx_oob_mac_type_errors {
      type oc-yang:counter64;
      description
        "Counts in interleaving mode OOB packets that are received with none OOB packet type.";
    }
    leaf counters_slice3_ifg1_mac_pool81_port2_rx_oob_mac_type_errors {
      type oc-yang:counter64;
      description
        "Counts in interleaving mode OOB packets that are received with none OOB packet type.";
    }
    leaf counters_slice3_ifg1_mac_pool81_port3_rx_oob_mac_type_errors {
      type oc-yang:counter64;
      description
        "Counts in interleaving mode OOB packets that are received with none OOB packet type.";
    }
    leaf counters_slice3_ifg1_mac_pool82_port0_rx_oob_mac_type_errors {
      type oc-yang:counter64;
      description
        "Counts in interleaving mode OOB packets that are received with none OOB packet type.";
    }
    leaf counters_slice3_ifg1_mac_pool82_port1_rx_oob_mac_type_errors {
      type oc-yang:counter64;
      description
        "Counts in interleaving mode OOB packets that are received with none OOB packet type.";
    }
    leaf counters_slice3_ifg1_mac_pool82_port2_rx_oob_mac_type_errors {
      type oc-yang:counter64;
      description
        "Counts in interleaving mode OOB packets that are received with none OOB packet type.";
    }
    leaf counters_slice3_ifg1_mac_pool82_port3_rx_oob_mac_type_errors {
      type oc-yang:counter64;
      description
        "Counts in interleaving mode OOB packets that are received with none OOB packet type.";
    }
    leaf counters_slice3_ifg1_mac_pool83_port0_rx_oob_mac_type_errors {
      type oc-yang:counter64;
      description
        "Counts in interleaving mode OOB packets that are received with none OOB packet type.";
    }
    leaf counters_slice3_ifg1_mac_pool83_port1_rx_oob_mac_type_errors {
      type oc-yang:counter64;
      description
        "Counts in interleaving mode OOB packets that are received with none OOB packet type.";
    }
    leaf counters_slice3_ifg1_mac_pool83_port2_rx_oob_mac_type_errors {
      type oc-yang:counter64;
      description
        "Counts in interleaving mode OOB packets that are received with none OOB packet type.";
    }
    leaf counters_slice3_ifg1_mac_pool83_port3_rx_oob_mac_type_errors {
      type oc-yang:counter64;
      description
        "Counts in interleaving mode OOB packets that are received with none OOB packet type.";
    }
    leaf counters_slice3_ifg1_npu_txpp_ifc_cluster_dropped_bad_packets {
      type oc-yang:counter64;
      description
        "Counts bad packets arrived to txpp Number of packet drops at the output of TxPP on IFG <i>";
    }
    leaf counters_slice4_ifg0_ifgb_rx_protection_errors {
      type oc-yang:counter64;
      description
        "RXPP interface protection errors counter.";
    }
    leaf counters_slice4_ifg0_ifgb_tx_protection_dropped_packets {
      type oc-yang:counter64;
      description
        "TXPP interface protection packet drop counter. Number of invalid packets arrived to TX.";
    }
    leaf counters_slice4_ifg0_ifgb_tx_protection_dropped_words {
      type oc-yang:counter64;
      description
        "TXPP interface protection words drop counter. Number of invalid words arrived to TX.";
    }
    leaf counters_slice4_ifg0_ifgb_tx_protection_errors {
      type oc-yang:counter64;
      description
        "TXPP interface protection errors counter.";
    }
    leaf counters_slice4_ifg0_ifgbi_pif_sequence_number_error {
      type oc-yang:counter64;
      description
        "PIF Sequence Number Error Count";
    }
    leaf counters_slice4_ifg0_ifgbi_rx_context_allocation_errors {
      type oc-yang:counter64;
      description
        "The amount of RXPP backpressure assertion events.";
    }
    leaf counters_slice4_ifg0_ifgbi_dash0_hp_dropped_full_packet {
      type oc-yang:counter64;
      description
        "SOP Drop Pkt Count - Full High Priority packet drops based on WrSopThd";
    }
    leaf counters_slice4_ifg0_ifgbi_dash0_hp_dropped_packets {
      type oc-yang:counter64;
      description
        "FIFO Full Pkt Count - Partial High Priority packet drops due to no space in FIFO";
    }
    leaf counters_slice4_ifg0_ifgbi_dash0_hp_dropped_words {
      type oc-yang:counter64;
      description
        "Word Drop Count - Partial High Priority word drops due to no space in FIFO";
    }
    leaf counters_slice4_ifg0_ifgbi_dash0_lp_dropped_full_packet {
      type oc-yang:counter64;
      description
        "SOP Drop Pkt Count - Full Low Priority packet drops based on WrSopThd";
    }
    leaf counters_slice4_ifg0_ifgbi_dash0_lp_dropped_packets {
      type oc-yang:counter64;
      description
        "FIFO Full Pkt Count - Partial Low Priority packet drops due to no space in FIFO";
    }
    leaf counters_slice4_ifg0_ifgbi_dash0_lp_dropped_words {
      type oc-yang:counter64;
      description
        "Word Drop Count - Partial Low Priority word drops due to no space in FIFO";
    }
    leaf counters_slice4_ifg0_ifgbi_dash1_hp_dropped_full_packet {
      type oc-yang:counter64;
      description
        "SOP Drop Pkt Count - Full High Priority packet drops based on WrSopThd";
    }
    leaf counters_slice4_ifg0_ifgbi_dash1_hp_dropped_packets {
      type oc-yang:counter64;
      description
        "FIFO Full Pkt Count - Partial High Priority packet drops due to no space in FIFO";
    }
    leaf counters_slice4_ifg0_ifgbi_dash1_hp_dropped_words {
      type oc-yang:counter64;
      description
        "Word Drop Count - Partial High Priority word drops due to no space in FIFO";
    }
    leaf counters_slice4_ifg0_ifgbi_dash1_lp_dropped_full_packet {
      type oc-yang:counter64;
      description
        "SOP Drop Pkt Count - Full Low Priority packet drops based on WrSopThd";
    }
    leaf counters_slice4_ifg0_ifgbi_dash1_lp_dropped_packets {
      type oc-yang:counter64;
      description
        "FIFO Full Pkt Count - Partial Low Priority packet drops due to no space in FIFO";
    }
    leaf counters_slice4_ifg0_ifgbi_dash1_lp_dropped_words {
      type oc-yang:counter64;
      description
        "Word Drop Count - Partial Low Priority word drops due to no space in FIFO";
    }
    leaf counters_slice4_ifg0_ifgbi_inband_extract_nph_errored_packets {
      type oc-yang:counter64;
      description
        "Inband Extract Bad packet extracted";
    }
    leaf counters_slice4_ifg0_ifgbi_inband_extract_pdm_errored_packets {
      type oc-yang:counter64;
      description
        "Inband Extract Bad packet extracted";
    }
    leaf counters_slice4_ifg0_ifgbi_inband_inject_nph_errored_packets {
      type oc-yang:counter64;
      description
        "Inband Inject Bad packet injected";
    }
    leaf counters_slice4_ifg0_ifgbi_inband_inject_pdm_errored_packets {
      type oc-yang:counter64;
      description
        "Inband Inject Bad packet injected";
    }
    leaf counters_slice4_ifg0_ifgbi_oobi_csms_dropped_packets {
      type oc-yang:counter64;
      description
        "Injected CSMS pkt drop cnt across all links";
    }
    leaf counters_slice4_ifg0_ifgbi_oobi_frm_dropped_packets {
      type oc-yang:counter64;
      description
        "Injected FRM pkt drop cnt across all links";
    }
    leaf counters_slice4_ifg0_ifgbi_oobi_fte_fts_dropped_packets {
      type oc-yang:counter64;
      description
        "Injected FTE Fabric Time Sync pkt drop cnt across all links";
    }
    leaf counters_slice4_ifg0_ifgbi_oobi_fte_pd_req_dropped_packets {
      type oc-yang:counter64;
      description
        "Injected FTE Peer Delay Request pkt drop cnt across all links";
    }
    leaf counters_slice4_ifg0_ifgbi_oobi_fte_pd_res_dropped_packets {
      type oc-yang:counter64;
      description
        "Injected FTE Peer Delay Response pkt drop cnt across all links";
    }
    leaf counters_slice4_ifg0_ifgbi_recycle_recycle_drop_on_port0 {
      type oc-yang:counter64;
      description
        "IFG recycling drop counter. Increments based on the RcyDropCntrsCfg.";
    }
    leaf counters_slice4_ifg0_ifgbi_recycle_recycle_drop_on_port1 {
      type oc-yang:counter64;
      description
        "IFG recycling drop counter. Increments based on the RcyDropCntrsCfg.";
    }
    leaf counters_slice4_ifg0_ifgbi_recycle_recycle_drop_on_port10 {
      type oc-yang:counter64;
      description
        "IFG recycling drop counter. Increments based on the RcyDropCntrsCfg.";
    }
    leaf counters_slice4_ifg0_ifgbi_recycle_recycle_drop_on_port11 {
      type oc-yang:counter64;
      description
        "IFG recycling drop counter. Increments based on the RcyDropCntrsCfg.";
    }
    leaf counters_slice4_ifg0_ifgbi_recycle_recycle_drop_on_port12 {
      type oc-yang:counter64;
      description
        "IFG recycling drop counter. Increments based on the RcyDropCntrsCfg.";
    }
    leaf counters_slice4_ifg0_ifgbi_recycle_recycle_drop_on_port13 {
      type oc-yang:counter64;
      description
        "IFG recycling drop counter. Increments based on the RcyDropCntrsCfg.";
    }
    leaf counters_slice4_ifg0_ifgbi_recycle_recycle_drop_on_port14 {
      type oc-yang:counter64;
      description
        "IFG recycling drop counter. Increments based on the RcyDropCntrsCfg.";
    }
    leaf counters_slice4_ifg0_ifgbi_recycle_recycle_drop_on_port15 {
      type oc-yang:counter64;
      description
        "IFG recycling drop counter. Increments based on the RcyDropCntrsCfg.";
    }
    leaf counters_slice4_ifg0_ifgbi_recycle_recycle_drop_on_port16 {
      type oc-yang:counter64;
      description
        "IFG recycling drop counter. Increments based on the RcyDropCntrsCfg.";
    }
    leaf counters_slice4_ifg0_ifgbi_recycle_recycle_drop_on_port17 {
      type oc-yang:counter64;
      description
        "IFG recycling drop counter. Increments based on the RcyDropCntrsCfg.";
    }
    leaf counters_slice4_ifg0_ifgbi_recycle_recycle_drop_on_port18 {
      type oc-yang:counter64;
      description
        "IFG recycling drop counter. Increments based on the RcyDropCntrsCfg.";
    }
    leaf counters_slice4_ifg0_ifgbi_recycle_recycle_drop_on_port19 {
      type oc-yang:counter64;
      description
        "IFG recycling drop counter. Increments based on the RcyDropCntrsCfg.";
    }
    leaf counters_slice4_ifg0_ifgbi_recycle_recycle_drop_on_port2 {
      type oc-yang:counter64;
      description
        "IFG recycling drop counter. Increments based on the RcyDropCntrsCfg.";
    }
    leaf counters_slice4_ifg0_ifgbi_recycle_recycle_drop_on_port20 {
      type oc-yang:counter64;
      description
        "IFG recycling drop counter. Increments based on the RcyDropCntrsCfg.";
    }
    leaf counters_slice4_ifg0_ifgbi_recycle_recycle_drop_on_port21 {
      type oc-yang:counter64;
      description
        "IFG recycling drop counter. Increments based on the RcyDropCntrsCfg.";
    }
    leaf counters_slice4_ifg0_ifgbi_recycle_recycle_drop_on_port22 {
      type oc-yang:counter64;
      description
        "IFG recycling drop counter. Increments based on the RcyDropCntrsCfg.";
    }
    leaf counters_slice4_ifg0_ifgbi_recycle_recycle_drop_on_port23 {
      type oc-yang:counter64;
      description
        "IFG recycling drop counter. Increments based on the RcyDropCntrsCfg.";
    }
    leaf counters_slice4_ifg0_ifgbi_recycle_recycle_drop_on_port24 {
      type oc-yang:counter64;
      description
        "IFG recycling drop counter. Increments based on the RcyDropCntrsCfg.";
    }
    leaf counters_slice4_ifg0_ifgbi_recycle_recycle_drop_on_port25 {
      type oc-yang:counter64;
      description
        "IFG recycling drop counter. Increments based on the RcyDropCntrsCfg.";
    }
    leaf counters_slice4_ifg0_ifgbi_recycle_recycle_drop_on_port26 {
      type oc-yang:counter64;
      description
        "IFG recycling drop counter. Increments based on the RcyDropCntrsCfg.";
    }
    leaf counters_slice4_ifg0_ifgbi_recycle_recycle_drop_on_port27 {
      type oc-yang:counter64;
      description
        "IFG recycling drop counter. Increments based on the RcyDropCntrsCfg.";
    }
    leaf counters_slice4_ifg0_ifgbi_recycle_recycle_drop_on_port28 {
      type oc-yang:counter64;
      description
        "IFG recycling drop counter. Increments based on the RcyDropCntrsCfg.";
    }
    leaf counters_slice4_ifg0_ifgbi_recycle_recycle_drop_on_port29 {
      type oc-yang:counter64;
      description
        "IFG recycling drop counter. Increments based on the RcyDropCntrsCfg.";
    }
    leaf counters_slice4_ifg0_ifgbi_recycle_recycle_drop_on_port3 {
      type oc-yang:counter64;
      description
        "IFG recycling drop counter. Increments based on the RcyDropCntrsCfg.";
    }
    leaf counters_slice4_ifg0_ifgbi_recycle_recycle_drop_on_port30 {
      type oc-yang:counter64;
      description
        "IFG recycling drop counter. Increments based on the RcyDropCntrsCfg.";
    }
    leaf counters_slice4_ifg0_ifgbi_recycle_recycle_drop_on_port31 {
      type oc-yang:counter64;
      description
        "IFG recycling drop counter. Increments based on the RcyDropCntrsCfg.";
    }
    leaf counters_slice4_ifg0_ifgbi_recycle_recycle_drop_on_port4 {
      type oc-yang:counter64;
      description
        "IFG recycling drop counter. Increments based on the RcyDropCntrsCfg.";
    }
    leaf counters_slice4_ifg0_ifgbi_recycle_recycle_drop_on_port5 {
      type oc-yang:counter64;
      description
        "IFG recycling drop counter. Increments based on the RcyDropCntrsCfg.";
    }
    leaf counters_slice4_ifg0_ifgbi_recycle_recycle_drop_on_port6 {
      type oc-yang:counter64;
      description
        "IFG recycling drop counter. Increments based on the RcyDropCntrsCfg.";
    }
    leaf counters_slice4_ifg0_ifgbi_recycle_recycle_drop_on_port7 {
      type oc-yang:counter64;
      description
        "IFG recycling drop counter. Increments based on the RcyDropCntrsCfg.";
    }
    leaf counters_slice4_ifg0_ifgbi_recycle_recycle_drop_on_port8 {
      type oc-yang:counter64;
      description
        "IFG recycling drop counter. Increments based on the RcyDropCntrsCfg.";
    }
    leaf counters_slice4_ifg0_ifgbi_recycle_recycle_drop_on_port9 {
      type oc-yang:counter64;
      description
        "IFG recycling drop counter. Increments based on the RcyDropCntrsCfg.";
    }
    leaf counters_slice4_ifg0_ifgbi_rx_protection_abnormally_terminated_packets {
      type oc-yang:counter64;
      description
        "RXPP interface protection packets termiante abnormally counter";
    }
    leaf counters_slice4_ifg0_mac_pool80_port0_rx_oob_mac_type_errors {
      type oc-yang:counter64;
      description
        "Counts in interleaving mode OOB packets that are received with none OOB packet type.";
    }
    leaf counters_slice4_ifg0_mac_pool80_port1_rx_oob_mac_type_errors {
      type oc-yang:counter64;
      description
        "Counts in interleaving mode OOB packets that are received with none OOB packet type.";
    }
    leaf counters_slice4_ifg0_mac_pool80_port2_rx_oob_mac_type_errors {
      type oc-yang:counter64;
      description
        "Counts in interleaving mode OOB packets that are received with none OOB packet type.";
    }
    leaf counters_slice4_ifg0_mac_pool80_port3_rx_oob_mac_type_errors {
      type oc-yang:counter64;
      description
        "Counts in interleaving mode OOB packets that are received with none OOB packet type.";
    }
    leaf counters_slice4_ifg0_mac_pool81_port0_rx_oob_mac_type_errors {
      type oc-yang:counter64;
      description
        "Counts in interleaving mode OOB packets that are received with none OOB packet type.";
    }
    leaf counters_slice4_ifg0_mac_pool81_port1_rx_oob_mac_type_errors {
      type oc-yang:counter64;
      description
        "Counts in interleaving mode OOB packets that are received with none OOB packet type.";
    }
    leaf counters_slice4_ifg0_mac_pool81_port2_rx_oob_mac_type_errors {
      type oc-yang:counter64;
      description
        "Counts in interleaving mode OOB packets that are received with none OOB packet type.";
    }
    leaf counters_slice4_ifg0_mac_pool81_port3_rx_oob_mac_type_errors {
      type oc-yang:counter64;
      description
        "Counts in interleaving mode OOB packets that are received with none OOB packet type.";
    }
    leaf counters_slice4_ifg0_mac_pool82_port0_rx_oob_mac_type_errors {
      type oc-yang:counter64;
      description
        "Counts in interleaving mode OOB packets that are received with none OOB packet type.";
    }
    leaf counters_slice4_ifg0_mac_pool82_port1_rx_oob_mac_type_errors {
      type oc-yang:counter64;
      description
        "Counts in interleaving mode OOB packets that are received with none OOB packet type.";
    }
    leaf counters_slice4_ifg0_mac_pool82_port2_rx_oob_mac_type_errors {
      type oc-yang:counter64;
      description
        "Counts in interleaving mode OOB packets that are received with none OOB packet type.";
    }
    leaf counters_slice4_ifg0_mac_pool82_port3_rx_oob_mac_type_errors {
      type oc-yang:counter64;
      description
        "Counts in interleaving mode OOB packets that are received with none OOB packet type.";
    }
    leaf counters_slice4_ifg0_mac_pool83_port0_rx_oob_mac_type_errors {
      type oc-yang:counter64;
      description
        "Counts in interleaving mode OOB packets that are received with none OOB packet type.";
    }
    leaf counters_slice4_ifg0_mac_pool83_port1_rx_oob_mac_type_errors {
      type oc-yang:counter64;
      description
        "Counts in interleaving mode OOB packets that are received with none OOB packet type.";
    }
    leaf counters_slice4_ifg0_mac_pool83_port2_rx_oob_mac_type_errors {
      type oc-yang:counter64;
      description
        "Counts in interleaving mode OOB packets that are received with none OOB packet type.";
    }
    leaf counters_slice4_ifg0_mac_pool83_port3_rx_oob_mac_type_errors {
      type oc-yang:counter64;
      description
        "Counts in interleaving mode OOB packets that are received with none OOB packet type.";
    }
    leaf counters_slice4_ifg0_npu_txpp_ifc_cluster_dropped_bad_packets {
      type oc-yang:counter64;
      description
        "Counts bad packets arrived to txpp Number of packet drops at the output of TxPP on IFG <i>";
    }
    leaf counters_slice4_ifg1_ifgb_rx_protection_errors {
      type oc-yang:counter64;
      description
        "RXPP interface protection errors counter.";
    }
    leaf counters_slice4_ifg1_ifgb_tx_protection_dropped_packets {
      type oc-yang:counter64;
      description
        "TXPP interface protection packet drop counter. Number of invalid packets arrived to TX.";
    }
    leaf counters_slice4_ifg1_ifgb_tx_protection_dropped_words {
      type oc-yang:counter64;
      description
        "TXPP interface protection words drop counter. Number of invalid words arrived to TX.";
    }
    leaf counters_slice4_ifg1_ifgb_tx_protection_errors {
      type oc-yang:counter64;
      description
        "TXPP interface protection errors counter.";
    }
    leaf counters_slice4_ifg1_ifgbi_pif_sequence_number_error {
      type oc-yang:counter64;
      description
        "PIF Sequence Number Error Count";
    }
    leaf counters_slice4_ifg1_ifgbi_rx_context_allocation_errors {
      type oc-yang:counter64;
      description
        "The amount of RXPP backpressure assertion events.";
    }
    leaf counters_slice4_ifg1_ifgbi_dash0_hp_dropped_full_packet {
      type oc-yang:counter64;
      description
        "SOP Drop Pkt Count - Full High Priority packet drops based on WrSopThd";
    }
    leaf counters_slice4_ifg1_ifgbi_dash0_hp_dropped_packets {
      type oc-yang:counter64;
      description
        "FIFO Full Pkt Count - Partial High Priority packet drops due to no space in FIFO";
    }
    leaf counters_slice4_ifg1_ifgbi_dash0_hp_dropped_words {
      type oc-yang:counter64;
      description
        "Word Drop Count - Partial High Priority word drops due to no space in FIFO";
    }
    leaf counters_slice4_ifg1_ifgbi_dash0_lp_dropped_full_packet {
      type oc-yang:counter64;
      description
        "SOP Drop Pkt Count - Full Low Priority packet drops based on WrSopThd";
    }
    leaf counters_slice4_ifg1_ifgbi_dash0_lp_dropped_packets {
      type oc-yang:counter64;
      description
        "FIFO Full Pkt Count - Partial Low Priority packet drops due to no space in FIFO";
    }
    leaf counters_slice4_ifg1_ifgbi_dash0_lp_dropped_words {
      type oc-yang:counter64;
      description
        "Word Drop Count - Partial Low Priority word drops due to no space in FIFO";
    }
    leaf counters_slice4_ifg1_ifgbi_dash1_hp_dropped_full_packet {
      type oc-yang:counter64;
      description
        "SOP Drop Pkt Count - Full High Priority packet drops based on WrSopThd";
    }
    leaf counters_slice4_ifg1_ifgbi_dash1_hp_dropped_packets {
      type oc-yang:counter64;
      description
        "FIFO Full Pkt Count - Partial High Priority packet drops due to no space in FIFO";
    }
    leaf counters_slice4_ifg1_ifgbi_dash1_hp_dropped_words {
      type oc-yang:counter64;
      description
        "Word Drop Count - Partial High Priority word drops due to no space in FIFO";
    }
    leaf counters_slice4_ifg1_ifgbi_dash1_lp_dropped_full_packet {
      type oc-yang:counter64;
      description
        "SOP Drop Pkt Count - Full Low Priority packet drops based on WrSopThd";
    }
    leaf counters_slice4_ifg1_ifgbi_dash1_lp_dropped_packets {
      type oc-yang:counter64;
      description
        "FIFO Full Pkt Count - Partial Low Priority packet drops due to no space in FIFO";
    }
    leaf counters_slice4_ifg1_ifgbi_dash1_lp_dropped_words {
      type oc-yang:counter64;
      description
        "Word Drop Count - Partial Low Priority word drops due to no space in FIFO";
    }
    leaf counters_slice4_ifg1_ifgbi_inband_extract_nph_errored_packets {
      type oc-yang:counter64;
      description
        "Inband Extract Bad packet extracted";
    }
    leaf counters_slice4_ifg1_ifgbi_inband_extract_pdm_errored_packets {
      type oc-yang:counter64;
      description
        "Inband Extract Bad packet extracted";
    }
    leaf counters_slice4_ifg1_ifgbi_inband_inject_nph_errored_packets {
      type oc-yang:counter64;
      description
        "Inband Inject Bad packet injected";
    }
    leaf counters_slice4_ifg1_ifgbi_inband_inject_pdm_errored_packets {
      type oc-yang:counter64;
      description
        "Inband Inject Bad packet injected";
    }
    leaf counters_slice4_ifg1_ifgbi_oobi_csms_dropped_packets {
      type oc-yang:counter64;
      description
        "Injected CSMS pkt drop cnt across all links";
    }
    leaf counters_slice4_ifg1_ifgbi_oobi_frm_dropped_packets {
      type oc-yang:counter64;
      description
        "Injected FRM pkt drop cnt across all links";
    }
    leaf counters_slice4_ifg1_ifgbi_oobi_fte_fts_dropped_packets {
      type oc-yang:counter64;
      description
        "Injected FTE Fabric Time Sync pkt drop cnt across all links";
    }
    leaf counters_slice4_ifg1_ifgbi_oobi_fte_pd_req_dropped_packets {
      type oc-yang:counter64;
      description
        "Injected FTE Peer Delay Request pkt drop cnt across all links";
    }
    leaf counters_slice4_ifg1_ifgbi_oobi_fte_pd_res_dropped_packets {
      type oc-yang:counter64;
      description
        "Injected FTE Peer Delay Response pkt drop cnt across all links";
    }
    leaf counters_slice4_ifg1_ifgbi_recycle_recycle_drop_on_port0 {
      type oc-yang:counter64;
      description
        "IFG recycling drop counter. Increments based on the RcyDropCntrsCfg.";
    }
    leaf counters_slice4_ifg1_ifgbi_recycle_recycle_drop_on_port1 {
      type oc-yang:counter64;
      description
        "IFG recycling drop counter. Increments based on the RcyDropCntrsCfg.";
    }
    leaf counters_slice4_ifg1_ifgbi_recycle_recycle_drop_on_port10 {
      type oc-yang:counter64;
      description
        "IFG recycling drop counter. Increments based on the RcyDropCntrsCfg.";
    }
    leaf counters_slice4_ifg1_ifgbi_recycle_recycle_drop_on_port11 {
      type oc-yang:counter64;
      description
        "IFG recycling drop counter. Increments based on the RcyDropCntrsCfg.";
    }
    leaf counters_slice4_ifg1_ifgbi_recycle_recycle_drop_on_port12 {
      type oc-yang:counter64;
      description
        "IFG recycling drop counter. Increments based on the RcyDropCntrsCfg.";
    }
    leaf counters_slice4_ifg1_ifgbi_recycle_recycle_drop_on_port13 {
      type oc-yang:counter64;
      description
        "IFG recycling drop counter. Increments based on the RcyDropCntrsCfg.";
    }
    leaf counters_slice4_ifg1_ifgbi_recycle_recycle_drop_on_port14 {
      type oc-yang:counter64;
      description
        "IFG recycling drop counter. Increments based on the RcyDropCntrsCfg.";
    }
    leaf counters_slice4_ifg1_ifgbi_recycle_recycle_drop_on_port15 {
      type oc-yang:counter64;
      description
        "IFG recycling drop counter. Increments based on the RcyDropCntrsCfg.";
    }
    leaf counters_slice4_ifg1_ifgbi_recycle_recycle_drop_on_port16 {
      type oc-yang:counter64;
      description
        "IFG recycling drop counter. Increments based on the RcyDropCntrsCfg.";
    }
    leaf counters_slice4_ifg1_ifgbi_recycle_recycle_drop_on_port17 {
      type oc-yang:counter64;
      description
        "IFG recycling drop counter. Increments based on the RcyDropCntrsCfg.";
    }
    leaf counters_slice4_ifg1_ifgbi_recycle_recycle_drop_on_port18 {
      type oc-yang:counter64;
      description
        "IFG recycling drop counter. Increments based on the RcyDropCntrsCfg.";
    }
    leaf counters_slice4_ifg1_ifgbi_recycle_recycle_drop_on_port19 {
      type oc-yang:counter64;
      description
        "IFG recycling drop counter. Increments based on the RcyDropCntrsCfg.";
    }
    leaf counters_slice4_ifg1_ifgbi_recycle_recycle_drop_on_port2 {
      type oc-yang:counter64;
      description
        "IFG recycling drop counter. Increments based on the RcyDropCntrsCfg.";
    }
    leaf counters_slice4_ifg1_ifgbi_recycle_recycle_drop_on_port20 {
      type oc-yang:counter64;
      description
        "IFG recycling drop counter. Increments based on the RcyDropCntrsCfg.";
    }
    leaf counters_slice4_ifg1_ifgbi_recycle_recycle_drop_on_port21 {
      type oc-yang:counter64;
      description
        "IFG recycling drop counter. Increments based on the RcyDropCntrsCfg.";
    }
    leaf counters_slice4_ifg1_ifgbi_recycle_recycle_drop_on_port22 {
      type oc-yang:counter64;
      description
        "IFG recycling drop counter. Increments based on the RcyDropCntrsCfg.";
    }
    leaf counters_slice4_ifg1_ifgbi_recycle_recycle_drop_on_port23 {
      type oc-yang:counter64;
      description
        "IFG recycling drop counter. Increments based on the RcyDropCntrsCfg.";
    }
    leaf counters_slice4_ifg1_ifgbi_recycle_recycle_drop_on_port24 {
      type oc-yang:counter64;
      description
        "IFG recycling drop counter. Increments based on the RcyDropCntrsCfg.";
    }
    leaf counters_slice4_ifg1_ifgbi_recycle_recycle_drop_on_port25 {
      type oc-yang:counter64;
      description
        "IFG recycling drop counter. Increments based on the RcyDropCntrsCfg.";
    }
    leaf counters_slice4_ifg1_ifgbi_recycle_recycle_drop_on_port26 {
      type oc-yang:counter64;
      description
        "IFG recycling drop counter. Increments based on the RcyDropCntrsCfg.";
    }
    leaf counters_slice4_ifg1_ifgbi_recycle_recycle_drop_on_port27 {
      type oc-yang:counter64;
      description
        "IFG recycling drop counter. Increments based on the RcyDropCntrsCfg.";
    }
    leaf counters_slice4_ifg1_ifgbi_recycle_recycle_drop_on_port28 {
      type oc-yang:counter64;
      description
        "IFG recycling drop counter. Increments based on the RcyDropCntrsCfg.";
    }
    leaf counters_slice4_ifg1_ifgbi_recycle_recycle_drop_on_port29 {
      type oc-yang:counter64;
      description
        "IFG recycling drop counter. Increments based on the RcyDropCntrsCfg.";
    }
    leaf counters_slice4_ifg1_ifgbi_recycle_recycle_drop_on_port3 {
      type oc-yang:counter64;
      description
        "IFG recycling drop counter. Increments based on the RcyDropCntrsCfg.";
    }
    leaf counters_slice4_ifg1_ifgbi_recycle_recycle_drop_on_port30 {
      type oc-yang:counter64;
      description
        "IFG recycling drop counter. Increments based on the RcyDropCntrsCfg.";
    }
    leaf counters_slice4_ifg1_ifgbi_recycle_recycle_drop_on_port31 {
      type oc-yang:counter64;
      description
        "IFG recycling drop counter. Increments based on the RcyDropCntrsCfg.";
    }
    leaf counters_slice4_ifg1_ifgbi_recycle_recycle_drop_on_port4 {
      type oc-yang:counter64;
      description
        "IFG recycling drop counter. Increments based on the RcyDropCntrsCfg.";
    }
    leaf counters_slice4_ifg1_ifgbi_recycle_recycle_drop_on_port5 {
      type oc-yang:counter64;
      description
        "IFG recycling drop counter. Increments based on the RcyDropCntrsCfg.";
    }
    leaf counters_slice4_ifg1_ifgbi_recycle_recycle_drop_on_port6 {
      type oc-yang:counter64;
      description
        "IFG recycling drop counter. Increments based on the RcyDropCntrsCfg.";
    }
    leaf counters_slice4_ifg1_ifgbi_recycle_recycle_drop_on_port7 {
      type oc-yang:counter64;
      description
        "IFG recycling drop counter. Increments based on the RcyDropCntrsCfg.";
    }
    leaf counters_slice4_ifg1_ifgbi_recycle_recycle_drop_on_port8 {
      type oc-yang:counter64;
      description
        "IFG recycling drop counter. Increments based on the RcyDropCntrsCfg.";
    }
    leaf counters_slice4_ifg1_ifgbi_recycle_recycle_drop_on_port9 {
      type oc-yang:counter64;
      description
        "IFG recycling drop counter. Increments based on the RcyDropCntrsCfg.";
    }
    leaf counters_slice4_ifg1_ifgbi_rx_protection_abnormally_terminated_packets {
      type oc-yang:counter64;
      description
        "RXPP interface protection packets termiante abnormally counter";
    }
    leaf counters_slice4_ifg1_mac_pool80_port0_rx_oob_mac_type_errors {
      type oc-yang:counter64;
      description
        "Counts in interleaving mode OOB packets that are received with none OOB packet type.";
    }
    leaf counters_slice4_ifg1_mac_pool80_port1_rx_oob_mac_type_errors {
      type oc-yang:counter64;
      description
        "Counts in interleaving mode OOB packets that are received with none OOB packet type.";
    }
    leaf counters_slice4_ifg1_mac_pool80_port2_rx_oob_mac_type_errors {
      type oc-yang:counter64;
      description
        "Counts in interleaving mode OOB packets that are received with none OOB packet type.";
    }
    leaf counters_slice4_ifg1_mac_pool80_port3_rx_oob_mac_type_errors {
      type oc-yang:counter64;
      description
        "Counts in interleaving mode OOB packets that are received with none OOB packet type.";
    }
    leaf counters_slice4_ifg1_mac_pool81_port0_rx_oob_mac_type_errors {
      type oc-yang:counter64;
      description
        "Counts in interleaving mode OOB packets that are received with none OOB packet type.";
    }
    leaf counters_slice4_ifg1_mac_pool81_port1_rx_oob_mac_type_errors {
      type oc-yang:counter64;
      description
        "Counts in interleaving mode OOB packets that are received with none OOB packet type.";
    }
    leaf counters_slice4_ifg1_mac_pool81_port2_rx_oob_mac_type_errors {
      type oc-yang:counter64;
      description
        "Counts in interleaving mode OOB packets that are received with none OOB packet type.";
    }
    leaf counters_slice4_ifg1_mac_pool81_port3_rx_oob_mac_type_errors {
      type oc-yang:counter64;
      description
        "Counts in interleaving mode OOB packets that are received with none OOB packet type.";
    }
    leaf counters_slice4_ifg1_mac_pool82_port0_rx_oob_mac_type_errors {
      type oc-yang:counter64;
      description
        "Counts in interleaving mode OOB packets that are received with none OOB packet type.";
    }
    leaf counters_slice4_ifg1_mac_pool82_port1_rx_oob_mac_type_errors {
      type oc-yang:counter64;
      description
        "Counts in interleaving mode OOB packets that are received with none OOB packet type.";
    }
    leaf counters_slice4_ifg1_mac_pool82_port2_rx_oob_mac_type_errors {
      type oc-yang:counter64;
      description
        "Counts in interleaving mode OOB packets that are received with none OOB packet type.";
    }
    leaf counters_slice4_ifg1_mac_pool82_port3_rx_oob_mac_type_errors {
      type oc-yang:counter64;
      description
        "Counts in interleaving mode OOB packets that are received with none OOB packet type.";
    }
    leaf counters_slice4_ifg1_mac_pool83_port0_rx_oob_mac_type_errors {
      type oc-yang:counter64;
      description
        "Counts in interleaving mode OOB packets that are received with none OOB packet type.";
    }
    leaf counters_slice4_ifg1_mac_pool83_port1_rx_oob_mac_type_errors {
      type oc-yang:counter64;
      description
        "Counts in interleaving mode OOB packets that are received with none OOB packet type.";
    }
    leaf counters_slice4_ifg1_mac_pool83_port2_rx_oob_mac_type_errors {
      type oc-yang:counter64;
      description
        "Counts in interleaving mode OOB packets that are received with none OOB packet type.";
    }
    leaf counters_slice4_ifg1_mac_pool83_port3_rx_oob_mac_type_errors {
      type oc-yang:counter64;
      description
        "Counts in interleaving mode OOB packets that are received with none OOB packet type.";
    }
    leaf counters_slice4_ifg1_npu_txpp_ifc_cluster_dropped_bad_packets {
      type oc-yang:counter64;
      description
        "Counts bad packets arrived to txpp Number of packet drops at the output of TxPP on IFG <i>";
    }
    leaf counters_slice5_ifg0_ifgb_rx_protection_errors {
      type oc-yang:counter64;
      description
        "RXPP interface protection errors counter.";
    }
    leaf counters_slice5_ifg0_ifgb_tx_protection_dropped_packets {
      type oc-yang:counter64;
      description
        "TXPP interface protection packet drop counter. Number of invalid packets arrived to TX.";
    }
    leaf counters_slice5_ifg0_ifgb_tx_protection_dropped_words {
      type oc-yang:counter64;
      description
        "TXPP interface protection words drop counter. Number of invalid words arrived to TX.";
    }
    leaf counters_slice5_ifg0_ifgb_tx_protection_errors {
      type oc-yang:counter64;
      description
        "TXPP interface protection errors counter.";
    }
    leaf counters_slice5_ifg0_ifgbi_pif_sequence_number_error {
      type oc-yang:counter64;
      description
        "PIF Sequence Number Error Count";
    }
    leaf counters_slice5_ifg0_ifgbi_rx_context_allocation_errors {
      type oc-yang:counter64;
      description
        "The amount of RXPP backpressure assertion events.";
    }
    leaf counters_slice5_ifg0_ifgbi_dash0_hp_dropped_full_packet {
      type oc-yang:counter64;
      description
        "SOP Drop Pkt Count - Full High Priority packet drops based on WrSopThd";
    }
    leaf counters_slice5_ifg0_ifgbi_dash0_hp_dropped_packets {
      type oc-yang:counter64;
      description
        "FIFO Full Pkt Count - Partial High Priority packet drops due to no space in FIFO";
    }
    leaf counters_slice5_ifg0_ifgbi_dash0_hp_dropped_words {
      type oc-yang:counter64;
      description
        "Word Drop Count - Partial High Priority word drops due to no space in FIFO";
    }
    leaf counters_slice5_ifg0_ifgbi_dash0_lp_dropped_full_packet {
      type oc-yang:counter64;
      description
        "SOP Drop Pkt Count - Full Low Priority packet drops based on WrSopThd";
    }
    leaf counters_slice5_ifg0_ifgbi_dash0_lp_dropped_packets {
      type oc-yang:counter64;
      description
        "FIFO Full Pkt Count - Partial Low Priority packet drops due to no space in FIFO";
    }
    leaf counters_slice5_ifg0_ifgbi_dash0_lp_dropped_words {
      type oc-yang:counter64;
      description
        "Word Drop Count - Partial Low Priority word drops due to no space in FIFO";
    }
    leaf counters_slice5_ifg0_ifgbi_dash1_hp_dropped_full_packet {
      type oc-yang:counter64;
      description
        "SOP Drop Pkt Count - Full High Priority packet drops based on WrSopThd";
    }
    leaf counters_slice5_ifg0_ifgbi_dash1_hp_dropped_packets {
      type oc-yang:counter64;
      description
        "FIFO Full Pkt Count - Partial High Priority packet drops due to no space in FIFO";
    }
    leaf counters_slice5_ifg0_ifgbi_dash1_hp_dropped_words {
      type oc-yang:counter64;
      description
        "Word Drop Count - Partial High Priority word drops due to no space in FIFO";
    }
    leaf counters_slice5_ifg0_ifgbi_dash1_lp_dropped_full_packet {
      type oc-yang:counter64;
      description
        "SOP Drop Pkt Count - Full Low Priority packet drops based on WrSopThd";
    }
    leaf counters_slice5_ifg0_ifgbi_dash1_lp_dropped_packets {
      type oc-yang:counter64;
      description
        "FIFO Full Pkt Count - Partial Low Priority packet drops due to no space in FIFO";
    }
    leaf counters_slice5_ifg0_ifgbi_dash1_lp_dropped_words {
      type oc-yang:counter64;
      description
        "Word Drop Count - Partial Low Priority word drops due to no space in FIFO";
    }
    leaf counters_slice5_ifg0_ifgbi_inband_extract_nph_errored_packets {
      type oc-yang:counter64;
      description
        "Inband Extract Bad packet extracted";
    }
    leaf counters_slice5_ifg0_ifgbi_inband_extract_pdm_errored_packets {
      type oc-yang:counter64;
      description
        "Inband Extract Bad packet extracted";
    }
    leaf counters_slice5_ifg0_ifgbi_inband_inject_nph_errored_packets {
      type oc-yang:counter64;
      description
        "Inband Inject Bad packet injected";
    }
    leaf counters_slice5_ifg0_ifgbi_inband_inject_pdm_errored_packets {
      type oc-yang:counter64;
      description
        "Inband Inject Bad packet injected";
    }
    leaf counters_slice5_ifg0_ifgbi_oobi_csms_dropped_packets {
      type oc-yang:counter64;
      description
        "Injected CSMS pkt drop cnt across all links";
    }
    leaf counters_slice5_ifg0_ifgbi_oobi_frm_dropped_packets {
      type oc-yang:counter64;
      description
        "Injected FRM pkt drop cnt across all links";
    }
    leaf counters_slice5_ifg0_ifgbi_oobi_fte_fts_dropped_packets {
      type oc-yang:counter64;
      description
        "Injected FTE Fabric Time Sync pkt drop cnt across all links";
    }
    leaf counters_slice5_ifg0_ifgbi_oobi_fte_pd_req_dropped_packets {
      type oc-yang:counter64;
      description
        "Injected FTE Peer Delay Request pkt drop cnt across all links";
    }
    leaf counters_slice5_ifg0_ifgbi_oobi_fte_pd_res_dropped_packets {
      type oc-yang:counter64;
      description
        "Injected FTE Peer Delay Response pkt drop cnt across all links";
    }
    leaf counters_slice5_ifg0_ifgbi_recycle_recycle_drop_on_port0 {
      type oc-yang:counter64;
      description
        "IFG recycling drop counter. Increments based on the RcyDropCntrsCfg.";
    }
    leaf counters_slice5_ifg0_ifgbi_recycle_recycle_drop_on_port1 {
      type oc-yang:counter64;
      description
        "IFG recycling drop counter. Increments based on the RcyDropCntrsCfg.";
    }
    leaf counters_slice5_ifg0_ifgbi_recycle_recycle_drop_on_port10 {
      type oc-yang:counter64;
      description
        "IFG recycling drop counter. Increments based on the RcyDropCntrsCfg.";
    }
    leaf counters_slice5_ifg0_ifgbi_recycle_recycle_drop_on_port11 {
      type oc-yang:counter64;
      description
        "IFG recycling drop counter. Increments based on the RcyDropCntrsCfg.";
    }
    leaf counters_slice5_ifg0_ifgbi_recycle_recycle_drop_on_port12 {
      type oc-yang:counter64;
      description
        "IFG recycling drop counter. Increments based on the RcyDropCntrsCfg.";
    }
    leaf counters_slice5_ifg0_ifgbi_recycle_recycle_drop_on_port13 {
      type oc-yang:counter64;
      description
        "IFG recycling drop counter. Increments based on the RcyDropCntrsCfg.";
    }
    leaf counters_slice5_ifg0_ifgbi_recycle_recycle_drop_on_port14 {
      type oc-yang:counter64;
      description
        "IFG recycling drop counter. Increments based on the RcyDropCntrsCfg.";
    }
    leaf counters_slice5_ifg0_ifgbi_recycle_recycle_drop_on_port15 {
      type oc-yang:counter64;
      description
        "IFG recycling drop counter. Increments based on the RcyDropCntrsCfg.";
    }
    leaf counters_slice5_ifg0_ifgbi_recycle_recycle_drop_on_port16 {
      type oc-yang:counter64;
      description
        "IFG recycling drop counter. Increments based on the RcyDropCntrsCfg.";
    }
    leaf counters_slice5_ifg0_ifgbi_recycle_recycle_drop_on_port17 {
      type oc-yang:counter64;
      description
        "IFG recycling drop counter. Increments based on the RcyDropCntrsCfg.";
    }
    leaf counters_slice5_ifg0_ifgbi_recycle_recycle_drop_on_port18 {
      type oc-yang:counter64;
      description
        "IFG recycling drop counter. Increments based on the RcyDropCntrsCfg.";
    }
    leaf counters_slice5_ifg0_ifgbi_recycle_recycle_drop_on_port19 {
      type oc-yang:counter64;
      description
        "IFG recycling drop counter. Increments based on the RcyDropCntrsCfg.";
    }
    leaf counters_slice5_ifg0_ifgbi_recycle_recycle_drop_on_port2 {
      type oc-yang:counter64;
      description
        "IFG recycling drop counter. Increments based on the RcyDropCntrsCfg.";
    }
    leaf counters_slice5_ifg0_ifgbi_recycle_recycle_drop_on_port20 {
      type oc-yang:counter64;
      description
        "IFG recycling drop counter. Increments based on the RcyDropCntrsCfg.";
    }
    leaf counters_slice5_ifg0_ifgbi_recycle_recycle_drop_on_port21 {
      type oc-yang:counter64;
      description
        "IFG recycling drop counter. Increments based on the RcyDropCntrsCfg.";
    }
    leaf counters_slice5_ifg0_ifgbi_recycle_recycle_drop_on_port22 {
      type oc-yang:counter64;
      description
        "IFG recycling drop counter. Increments based on the RcyDropCntrsCfg.";
    }
    leaf counters_slice5_ifg0_ifgbi_recycle_recycle_drop_on_port23 {
      type oc-yang:counter64;
      description
        "IFG recycling drop counter. Increments based on the RcyDropCntrsCfg.";
    }
    leaf counters_slice5_ifg0_ifgbi_recycle_recycle_drop_on_port24 {
      type oc-yang:counter64;
      description
        "IFG recycling drop counter. Increments based on the RcyDropCntrsCfg.";
    }
    leaf counters_slice5_ifg0_ifgbi_recycle_recycle_drop_on_port25 {
      type oc-yang:counter64;
      description
        "IFG recycling drop counter. Increments based on the RcyDropCntrsCfg.";
    }
    leaf counters_slice5_ifg0_ifgbi_recycle_recycle_drop_on_port26 {
      type oc-yang:counter64;
      description
        "IFG recycling drop counter. Increments based on the RcyDropCntrsCfg.";
    }
    leaf counters_slice5_ifg0_ifgbi_recycle_recycle_drop_on_port27 {
      type oc-yang:counter64;
      description
        "IFG recycling drop counter. Increments based on the RcyDropCntrsCfg.";
    }
    leaf counters_slice5_ifg0_ifgbi_recycle_recycle_drop_on_port28 {
      type oc-yang:counter64;
      description
        "IFG recycling drop counter. Increments based on the RcyDropCntrsCfg.";
    }
    leaf counters_slice5_ifg0_ifgbi_recycle_recycle_drop_on_port29 {
      type oc-yang:counter64;
      description
        "IFG recycling drop counter. Increments based on the RcyDropCntrsCfg.";
    }
    leaf counters_slice5_ifg0_ifgbi_recycle_recycle_drop_on_port3 {
      type oc-yang:counter64;
      description
        "IFG recycling drop counter. Increments based on the RcyDropCntrsCfg.";
    }
    leaf counters_slice5_ifg0_ifgbi_recycle_recycle_drop_on_port30 {
      type oc-yang:counter64;
      description
        "IFG recycling drop counter. Increments based on the RcyDropCntrsCfg.";
    }
    leaf counters_slice5_ifg0_ifgbi_recycle_recycle_drop_on_port31 {
      type oc-yang:counter64;
      description
        "IFG recycling drop counter. Increments based on the RcyDropCntrsCfg.";
    }
    leaf counters_slice5_ifg0_ifgbi_recycle_recycle_drop_on_port4 {
      type oc-yang:counter64;
      description
        "IFG recycling drop counter. Increments based on the RcyDropCntrsCfg.";
    }
    leaf counters_slice5_ifg0_ifgbi_recycle_recycle_drop_on_port5 {
      type oc-yang:counter64;
      description
        "IFG recycling drop counter. Increments based on the RcyDropCntrsCfg.";
    }
    leaf counters_slice5_ifg0_ifgbi_recycle_recycle_drop_on_port6 {
      type oc-yang:counter64;
      description
        "IFG recycling drop counter. Increments based on the RcyDropCntrsCfg.";
    }
    leaf counters_slice5_ifg0_ifgbi_recycle_recycle_drop_on_port7 {
      type oc-yang:counter64;
      description
        "IFG recycling drop counter. Increments based on the RcyDropCntrsCfg.";
    }
    leaf counters_slice5_ifg0_ifgbi_recycle_recycle_drop_on_port8 {
      type oc-yang:counter64;
      description
        "IFG recycling drop counter. Increments based on the RcyDropCntrsCfg.";
    }
    leaf counters_slice5_ifg0_ifgbi_recycle_recycle_drop_on_port9 {
      type oc-yang:counter64;
      description
        "IFG recycling drop counter. Increments based on the RcyDropCntrsCfg.";
    }
    leaf counters_slice5_ifg0_ifgbi_rx_protection_abnormally_terminated_packets {
      type oc-yang:counter64;
      description
        "RXPP interface protection packets termiante abnormally counter";
    }
    leaf counters_slice5_ifg0_mac_pool80_port0_rx_oob_mac_type_errors {
      type oc-yang:counter64;
      description
        "Counts in interleaving mode OOB packets that are received with none OOB packet type.";
    }
    leaf counters_slice5_ifg0_mac_pool80_port1_rx_oob_mac_type_errors {
      type oc-yang:counter64;
      description
        "Counts in interleaving mode OOB packets that are received with none OOB packet type.";
    }
    leaf counters_slice5_ifg0_mac_pool80_port2_rx_oob_mac_type_errors {
      type oc-yang:counter64;
      description
        "Counts in interleaving mode OOB packets that are received with none OOB packet type.";
    }
    leaf counters_slice5_ifg0_mac_pool80_port3_rx_oob_mac_type_errors {
      type oc-yang:counter64;
      description
        "Counts in interleaving mode OOB packets that are received with none OOB packet type.";
    }
    leaf counters_slice5_ifg0_mac_pool81_port0_rx_oob_mac_type_errors {
      type oc-yang:counter64;
      description
        "Counts in interleaving mode OOB packets that are received with none OOB packet type.";
    }
    leaf counters_slice5_ifg0_mac_pool81_port1_rx_oob_mac_type_errors {
      type oc-yang:counter64;
      description
        "Counts in interleaving mode OOB packets that are received with none OOB packet type.";
    }
    leaf counters_slice5_ifg0_mac_pool81_port2_rx_oob_mac_type_errors {
      type oc-yang:counter64;
      description
        "Counts in interleaving mode OOB packets that are received with none OOB packet type.";
    }
    leaf counters_slice5_ifg0_mac_pool81_port3_rx_oob_mac_type_errors {
      type oc-yang:counter64;
      description
        "Counts in interleaving mode OOB packets that are received with none OOB packet type.";
    }
    leaf counters_slice5_ifg0_mac_pool82_port0_rx_oob_mac_type_errors {
      type oc-yang:counter64;
      description
        "Counts in interleaving mode OOB packets that are received with none OOB packet type.";
    }
    leaf counters_slice5_ifg0_mac_pool82_port1_rx_oob_mac_type_errors {
      type oc-yang:counter64;
      description
        "Counts in interleaving mode OOB packets that are received with none OOB packet type.";
    }
    leaf counters_slice5_ifg0_mac_pool82_port2_rx_oob_mac_type_errors {
      type oc-yang:counter64;
      description
        "Counts in interleaving mode OOB packets that are received with none OOB packet type.";
    }
    leaf counters_slice5_ifg0_mac_pool82_port3_rx_oob_mac_type_errors {
      type oc-yang:counter64;
      description
        "Counts in interleaving mode OOB packets that are received with none OOB packet type.";
    }
    leaf counters_slice5_ifg0_mac_pool83_port0_rx_oob_mac_type_errors {
      type oc-yang:counter64;
      description
        "Counts in interleaving mode OOB packets that are received with none OOB packet type.";
    }
    leaf counters_slice5_ifg0_mac_pool83_port1_rx_oob_mac_type_errors {
      type oc-yang:counter64;
      description
        "Counts in interleaving mode OOB packets that are received with none OOB packet type.";
    }
    leaf counters_slice5_ifg0_mac_pool83_port2_rx_oob_mac_type_errors {
      type oc-yang:counter64;
      description
        "Counts in interleaving mode OOB packets that are received with none OOB packet type.";
    }
    leaf counters_slice5_ifg0_mac_pool83_port3_rx_oob_mac_type_errors {
      type oc-yang:counter64;
      description
        "Counts in interleaving mode OOB packets that are received with none OOB packet type.";
    }
    leaf counters_slice5_ifg0_npu_txpp_ifc_cluster_dropped_bad_packets {
      type oc-yang:counter64;
      description
        "Counts bad packets arrived to txpp Number of packet drops at the output of TxPP on IFG <i>";
    }
    leaf counters_slice5_ifg1_ifgb_rx_protection_errors {
      type oc-yang:counter64;
      description
        "RXPP interface protection errors counter.";
    }
    leaf counters_slice5_ifg1_ifgb_tx_protection_dropped_packets {
      type oc-yang:counter64;
      description
        "TXPP interface protection packet drop counter. Number of invalid packets arrived to TX.";
    }
    leaf counters_slice5_ifg1_ifgb_tx_protection_dropped_words {
      type oc-yang:counter64;
      description
        "TXPP interface protection words drop counter. Number of invalid words arrived to TX.";
    }
    leaf counters_slice5_ifg1_ifgb_tx_protection_errors {
      type oc-yang:counter64;
      description
        "TXPP interface protection errors counter.";
    }
    leaf counters_slice5_ifg1_ifgbi_pif_sequence_number_error {
      type oc-yang:counter64;
      description
        "PIF Sequence Number Error Count";
    }
    leaf counters_slice5_ifg1_ifgbi_rx_context_allocation_errors {
      type oc-yang:counter64;
      description
        "The amount of RXPP backpressure assertion events.";
    }
    leaf counters_slice5_ifg1_ifgbi_dash0_hp_dropped_full_packet {
      type oc-yang:counter64;
      description
        "SOP Drop Pkt Count - Full High Priority packet drops based on WrSopThd";
    }
    leaf counters_slice5_ifg1_ifgbi_dash0_hp_dropped_packets {
      type oc-yang:counter64;
      description
        "FIFO Full Pkt Count - Partial High Priority packet drops due to no space in FIFO";
    }
    leaf counters_slice5_ifg1_ifgbi_dash0_hp_dropped_words {
      type oc-yang:counter64;
      description
        "Word Drop Count - Partial High Priority word drops due to no space in FIFO";
    }
    leaf counters_slice5_ifg1_ifgbi_dash0_lp_dropped_full_packet {
      type oc-yang:counter64;
      description
        "SOP Drop Pkt Count - Full Low Priority packet drops based on WrSopThd";
    }
    leaf counters_slice5_ifg1_ifgbi_dash0_lp_dropped_packets {
      type oc-yang:counter64;
      description
        "FIFO Full Pkt Count - Partial Low Priority packet drops due to no space in FIFO";
    }
    leaf counters_slice5_ifg1_ifgbi_dash0_lp_dropped_words {
      type oc-yang:counter64;
      description
        "Word Drop Count - Partial Low Priority word drops due to no space in FIFO";
    }
    leaf counters_slice5_ifg1_ifgbi_dash1_hp_dropped_full_packet {
      type oc-yang:counter64;
      description
        "SOP Drop Pkt Count - Full High Priority packet drops based on WrSopThd";
    }
    leaf counters_slice5_ifg1_ifgbi_dash1_hp_dropped_packets {
      type oc-yang:counter64;
      description
        "FIFO Full Pkt Count - Partial High Priority packet drops due to no space in FIFO";
    }
    leaf counters_slice5_ifg1_ifgbi_dash1_hp_dropped_words {
      type oc-yang:counter64;
      description
        "Word Drop Count - Partial High Priority word drops due to no space in FIFO";
    }
    leaf counters_slice5_ifg1_ifgbi_dash1_lp_dropped_full_packet {
      type oc-yang:counter64;
      description
        "SOP Drop Pkt Count - Full Low Priority packet drops based on WrSopThd";
    }
    leaf counters_slice5_ifg1_ifgbi_dash1_lp_dropped_packets {
      type oc-yang:counter64;
      description
        "FIFO Full Pkt Count - Partial Low Priority packet drops due to no space in FIFO";
    }
    leaf counters_slice5_ifg1_ifgbi_dash1_lp_dropped_words {
      type oc-yang:counter64;
      description
        "Word Drop Count - Partial Low Priority word drops due to no space in FIFO";
    }
    leaf counters_slice5_ifg1_ifgbi_inband_extract_nph_errored_packets {
      type oc-yang:counter64;
      description
        "Inband Extract Bad packet extracted";
    }
    leaf counters_slice5_ifg1_ifgbi_inband_extract_pdm_errored_packets {
      type oc-yang:counter64;
      description
        "Inband Extract Bad packet extracted";
    }
    leaf counters_slice5_ifg1_ifgbi_inband_inject_nph_errored_packets {
      type oc-yang:counter64;
      description
        "Inband Inject Bad packet injected";
    }
    leaf counters_slice5_ifg1_ifgbi_inband_inject_pdm_errored_packets {
      type oc-yang:counter64;
      description
        "Inband Inject Bad packet injected";
    }
    leaf counters_slice5_ifg1_ifgbi_oobi_csms_dropped_packets {
      type oc-yang:counter64;
      description
        "Injected CSMS pkt drop cnt across all links";
    }
    leaf counters_slice5_ifg1_ifgbi_oobi_frm_dropped_packets {
      type oc-yang:counter64;
      description
        "Injected FRM pkt drop cnt across all links";
    }
    leaf counters_slice5_ifg1_ifgbi_oobi_fte_fts_dropped_packets {
      type oc-yang:counter64;
      description
        "Injected FTE Fabric Time Sync pkt drop cnt across all links";
    }
    leaf counters_slice5_ifg1_ifgbi_oobi_fte_pd_req_dropped_packets {
      type oc-yang:counter64;
      description
        "Injected FTE Peer Delay Request pkt drop cnt across all links";
    }
    leaf counters_slice5_ifg1_ifgbi_oobi_fte_pd_res_dropped_packets {
      type oc-yang:counter64;
      description
        "Injected FTE Peer Delay Response pkt drop cnt across all links";
    }
    leaf counters_slice5_ifg1_ifgbi_recycle_recycle_drop_on_port0 {
      type oc-yang:counter64;
      description
        "IFG recycling drop counter. Increments based on the RcyDropCntrsCfg.";
    }
    leaf counters_slice5_ifg1_ifgbi_recycle_recycle_drop_on_port1 {
      type oc-yang:counter64;
      description
        "IFG recycling drop counter. Increments based on the RcyDropCntrsCfg.";
    }
    leaf counters_slice5_ifg1_ifgbi_recycle_recycle_drop_on_port10 {
      type oc-yang:counter64;
      description
        "IFG recycling drop counter. Increments based on the RcyDropCntrsCfg.";
    }
    leaf counters_slice5_ifg1_ifgbi_recycle_recycle_drop_on_port11 {
      type oc-yang:counter64;
      description
        "IFG recycling drop counter. Increments based on the RcyDropCntrsCfg.";
    }
    leaf counters_slice5_ifg1_ifgbi_recycle_recycle_drop_on_port12 {
      type oc-yang:counter64;
      description
        "IFG recycling drop counter. Increments based on the RcyDropCntrsCfg.";
    }
    leaf counters_slice5_ifg1_ifgbi_recycle_recycle_drop_on_port13 {
      type oc-yang:counter64;
      description
        "IFG recycling drop counter. Increments based on the RcyDropCntrsCfg.";
    }
    leaf counters_slice5_ifg1_ifgbi_recycle_recycle_drop_on_port14 {
      type oc-yang:counter64;
      description
        "IFG recycling drop counter. Increments based on the RcyDropCntrsCfg.";
    }
    leaf counters_slice5_ifg1_ifgbi_recycle_recycle_drop_on_port15 {
      type oc-yang:counter64;
      description
        "IFG recycling drop counter. Increments based on the RcyDropCntrsCfg.";
    }
    leaf counters_slice5_ifg1_ifgbi_recycle_recycle_drop_on_port16 {
      type oc-yang:counter64;
      description
        "IFG recycling drop counter. Increments based on the RcyDropCntrsCfg.";
    }
    leaf counters_slice5_ifg1_ifgbi_recycle_recycle_drop_on_port17 {
      type oc-yang:counter64;
      description
        "IFG recycling drop counter. Increments based on the RcyDropCntrsCfg.";
    }
    leaf counters_slice5_ifg1_ifgbi_recycle_recycle_drop_on_port18 {
      type oc-yang:counter64;
      description
        "IFG recycling drop counter. Increments based on the RcyDropCntrsCfg.";
    }
    leaf counters_slice5_ifg1_ifgbi_recycle_recycle_drop_on_port19 {
      type oc-yang:counter64;
      description
        "IFG recycling drop counter. Increments based on the RcyDropCntrsCfg.";
    }
    leaf counters_slice5_ifg1_ifgbi_recycle_recycle_drop_on_port2 {
      type oc-yang:counter64;
      description
        "IFG recycling drop counter. Increments based on the RcyDropCntrsCfg.";
    }
    leaf counters_slice5_ifg1_ifgbi_recycle_recycle_drop_on_port20 {
      type oc-yang:counter64;
      description
        "IFG recycling drop counter. Increments based on the RcyDropCntrsCfg.";
    }
    leaf counters_slice5_ifg1_ifgbi_recycle_recycle_drop_on_port21 {
      type oc-yang:counter64;
      description
        "IFG recycling drop counter. Increments based on the RcyDropCntrsCfg.";
    }
    leaf counters_slice5_ifg1_ifgbi_recycle_recycle_drop_on_port22 {
      type oc-yang:counter64;
      description
        "IFG recycling drop counter. Increments based on the RcyDropCntrsCfg.";
    }
    leaf counters_slice5_ifg1_ifgbi_recycle_recycle_drop_on_port23 {
      type oc-yang:counter64;
      description
        "IFG recycling drop counter. Increments based on the RcyDropCntrsCfg.";
    }
    leaf counters_slice5_ifg1_ifgbi_recycle_recycle_drop_on_port24 {
      type oc-yang:counter64;
      description
        "IFG recycling drop counter. Increments based on the RcyDropCntrsCfg.";
    }
    leaf counters_slice5_ifg1_ifgbi_recycle_recycle_drop_on_port25 {
      type oc-yang:counter64;
      description
        "IFG recycling drop counter. Increments based on the RcyDropCntrsCfg.";
    }
    leaf counters_slice5_ifg1_ifgbi_recycle_recycle_drop_on_port26 {
      type oc-yang:counter64;
      description
        "IFG recycling drop counter. Increments based on the RcyDropCntrsCfg.";
    }
    leaf counters_slice5_ifg1_ifgbi_recycle_recycle_drop_on_port27 {
      type oc-yang:counter64;
      description
        "IFG recycling drop counter. Increments based on the RcyDropCntrsCfg.";
    }
    leaf counters_slice5_ifg1_ifgbi_recycle_recycle_drop_on_port28 {
      type oc-yang:counter64;
      description
        "IFG recycling drop counter. Increments based on the RcyDropCntrsCfg.";
    }
    leaf counters_slice5_ifg1_ifgbi_recycle_recycle_drop_on_port29 {
      type oc-yang:counter64;
      description
        "IFG recycling drop counter. Increments based on the RcyDropCntrsCfg.";
    }
    leaf counters_slice5_ifg1_ifgbi_recycle_recycle_drop_on_port3 {
      type oc-yang:counter64;
      description
        "IFG recycling drop counter. Increments based on the RcyDropCntrsCfg.";
    }
    leaf counters_slice5_ifg1_ifgbi_recycle_recycle_drop_on_port30 {
      type oc-yang:counter64;
      description
        "IFG recycling drop counter. Increments based on the RcyDropCntrsCfg.";
    }
    leaf counters_slice5_ifg1_ifgbi_recycle_recycle_drop_on_port31 {
      type oc-yang:counter64;
      description
        "IFG recycling drop counter. Increments based on the RcyDropCntrsCfg.";
    }
    leaf counters_slice5_ifg1_ifgbi_recycle_recycle_drop_on_port4 {
      type oc-yang:counter64;
      description
        "IFG recycling drop counter. Increments based on the RcyDropCntrsCfg.";
    }
    leaf counters_slice5_ifg1_ifgbi_recycle_recycle_drop_on_port5 {
      type oc-yang:counter64;
      description
        "IFG recycling drop counter. Increments based on the RcyDropCntrsCfg.";
    }
    leaf counters_slice5_ifg1_ifgbi_recycle_recycle_drop_on_port6 {
      type oc-yang:counter64;
      description
        "IFG recycling drop counter. Increments based on the RcyDropCntrsCfg.";
    }
    leaf counters_slice5_ifg1_ifgbi_recycle_recycle_drop_on_port7 {
      type oc-yang:counter64;
      description
        "IFG recycling drop counter. Increments based on the RcyDropCntrsCfg.";
    }
    leaf counters_slice5_ifg1_ifgbi_recycle_recycle_drop_on_port8 {
      type oc-yang:counter64;
      description
        "IFG recycling drop counter. Increments based on the RcyDropCntrsCfg.";
    }
    leaf counters_slice5_ifg1_ifgbi_recycle_recycle_drop_on_port9 {
      type oc-yang:counter64;
      description
        "IFG recycling drop counter. Increments based on the RcyDropCntrsCfg.";
    }
    leaf counters_slice5_ifg1_ifgbi_rx_protection_abnormally_terminated_packets {
      type oc-yang:counter64;
      description
        "RXPP interface protection packets termiante abnormally counter";
    }
    leaf counters_slice5_ifg1_mac_pool80_port0_rx_oob_mac_type_errors {
      type oc-yang:counter64;
      description
        "Counts in interleaving mode OOB packets that are received with none OOB packet type.";
    }
    leaf counters_slice5_ifg1_mac_pool80_port1_rx_oob_mac_type_errors {
      type oc-yang:counter64;
      description
        "Counts in interleaving mode OOB packets that are received with none OOB packet type.";
    }
    leaf counters_slice5_ifg1_mac_pool80_port2_rx_oob_mac_type_errors {
      type oc-yang:counter64;
      description
        "Counts in interleaving mode OOB packets that are received with none OOB packet type.";
    }
    leaf counters_slice5_ifg1_mac_pool80_port3_rx_oob_mac_type_errors {
      type oc-yang:counter64;
      description
        "Counts in interleaving mode OOB packets that are received with none OOB packet type.";
    }
    leaf counters_slice5_ifg1_mac_pool81_port0_rx_oob_mac_type_errors {
      type oc-yang:counter64;
      description
        "Counts in interleaving mode OOB packets that are received with none OOB packet type.";
    }
    leaf counters_slice5_ifg1_mac_pool81_port1_rx_oob_mac_type_errors {
      type oc-yang:counter64;
      description
        "Counts in interleaving mode OOB packets that are received with none OOB packet type.";
    }
    leaf counters_slice5_ifg1_mac_pool81_port2_rx_oob_mac_type_errors {
      type oc-yang:counter64;
      description
        "Counts in interleaving mode OOB packets that are received with none OOB packet type.";
    }
    leaf counters_slice5_ifg1_mac_pool81_port3_rx_oob_mac_type_errors {
      type oc-yang:counter64;
      description
        "Counts in interleaving mode OOB packets that are received with none OOB packet type.";
    }
    leaf counters_slice5_ifg1_mac_pool82_port0_rx_oob_mac_type_errors {
      type oc-yang:counter64;
      description
        "Counts in interleaving mode OOB packets that are received with none OOB packet type.";
    }
    leaf counters_slice5_ifg1_mac_pool82_port1_rx_oob_mac_type_errors {
      type oc-yang:counter64;
      description
        "Counts in interleaving mode OOB packets that are received with none OOB packet type.";
    }
    leaf counters_slice5_ifg1_mac_pool82_port2_rx_oob_mac_type_errors {
      type oc-yang:counter64;
      description
        "Counts in interleaving mode OOB packets that are received with none OOB packet type.";
    }
    leaf counters_slice5_ifg1_mac_pool82_port3_rx_oob_mac_type_errors {
      type oc-yang:counter64;
      description
        "Counts in interleaving mode OOB packets that are received with none OOB packet type.";
    }
    leaf counters_slice5_ifg1_mac_pool83_port0_rx_oob_mac_type_errors {
      type oc-yang:counter64;
      description
        "Counts in interleaving mode OOB packets that are received with none OOB packet type.";
    }
    leaf counters_slice5_ifg1_mac_pool83_port1_rx_oob_mac_type_errors {
      type oc-yang:counter64;
      description
        "Counts in interleaving mode OOB packets that are received with none OOB packet type.";
    }
    leaf counters_slice5_ifg1_mac_pool83_port2_rx_oob_mac_type_errors {
      type oc-yang:counter64;
      description
        "Counts in interleaving mode OOB packets that are received with none OOB packet type.";
    }
    leaf counters_slice5_ifg1_mac_pool83_port3_rx_oob_mac_type_errors {
      type oc-yang:counter64;
      description
        "Counts in interleaving mode OOB packets that are received with none OOB packet type.";
    }
    leaf counters_slice5_ifg1_npu_txpp_ifc_cluster_dropped_bad_packets {
      type oc-yang:counter64;
      description
        "Counts bad packets arrived to txpp Number of packet drops at the output of TxPP on IFG <i>";
    }
  }

  grouping cisco-p100-congestion-drop-counters {
    description
      "Congestion Drop leafs grouping for the p100 asic";
    leaf exact_meter_packet_got_dropped_due_to_exact_meter {
      type oc-yang:counter64;
      description
        " Packet got dropped due to exact meter";
    }
    leaf statistical_meter_packet_got_dropped_due_to_statistical_meter {
      type oc-yang:counter64;
      description
        "Packet got dropped due to statistical metering";
    }
    leaf counters_npu_host_evq_dropped_events {
      type oc-yang:counter64;
      description
        "number of events npu host dropped due to event queue fullness";
    }
    leaf counters_pdoq_shared_mem_dram_slice_dropped_packets {
      type oc-yang:counter64;
      description
        "Dropped packets in DRAM slice";
    }
    leaf counters_pdvoq_shared_mma_voq_counters0_dropped_bytes {
      type oc-yang:counter64;
      description
        "programmable counter set that are controlled by VOQ ranges";
    }
    leaf counters_pdvoq_shared_mma_voq_counters0_dropped_packets {
      type oc-yang:counter64;
      description
        "programmable counter set that are controlled by VOQ ranges";
    }
    leaf counters_pdvoq_shared_mma_voq_counters10_dropped_bytes {
      type oc-yang:counter64;
      description
        "programmable counter set that are controlled by VOQ ranges";
    }
    leaf counters_pdvoq_shared_mma_voq_counters10_dropped_packets {
      type oc-yang:counter64;
      description
        "programmable counter set that are controlled by VOQ ranges";
    }
    leaf counters_pdvoq_shared_mma_voq_counters11_dropped_bytes {
      type oc-yang:counter64;
      description
        "programmable counter set that are controlled by VOQ ranges";
    }
    leaf counters_pdvoq_shared_mma_voq_counters11_dropped_packets {
      type oc-yang:counter64;
      description
        "programmable counter set that are controlled by VOQ ranges";
    }
    leaf counters_pdvoq_shared_mma_voq_counters12_dropped_bytes {
      type oc-yang:counter64;
      description
        "programmable counter set that are controlled by VOQ ranges";
    }
    leaf counters_pdvoq_shared_mma_voq_counters12_dropped_packets {
      type oc-yang:counter64;
      description
        "programmable counter set that are controlled by VOQ ranges";
    }
    leaf counters_pdvoq_shared_mma_voq_counters13_dropped_bytes {
      type oc-yang:counter64;
      description
        "programmable counter set that are controlled by VOQ ranges";
    }
    leaf counters_pdvoq_shared_mma_voq_counters13_dropped_packets {
      type oc-yang:counter64;
      description
        "programmable counter set that are controlled by VOQ ranges";
    }
    leaf counters_pdvoq_shared_mma_voq_counters14_dropped_bytes {
      type oc-yang:counter64;
      description
        "programmable counter set that are controlled by VOQ ranges";
    }
    leaf counters_pdvoq_shared_mma_voq_counters14_dropped_packets {
      type oc-yang:counter64;
      description
        "programmable counter set that are controlled by VOQ ranges";
    }
    leaf counters_pdvoq_shared_mma_voq_counters15_dropped_bytes {
      type oc-yang:counter64;
      description
        "programmable counter set that are controlled by VOQ ranges";
    }
    leaf counters_pdvoq_shared_mma_voq_counters15_dropped_packets {
      type oc-yang:counter64;
      description
        "programmable counter set that are controlled by VOQ ranges";
    }
    leaf counters_pdvoq_shared_mma_voq_counters16_dropped_bytes {
      type oc-yang:counter64;
      description
        "programmable counter set that are controlled by VOQ ranges";
    }
    leaf counters_pdvoq_shared_mma_voq_counters16_dropped_packets {
      type oc-yang:counter64;
      description
        "programmable counter set that are controlled by VOQ ranges";
    }
    leaf counters_pdvoq_shared_mma_voq_counters17_dropped_bytes {
      type oc-yang:counter64;
      description
        "programmable counter set that are controlled by VOQ ranges";
    }
    leaf counters_pdvoq_shared_mma_voq_counters17_dropped_packets {
      type oc-yang:counter64;
      description
        "programmable counter set that are controlled by VOQ ranges";
    }
    leaf counters_pdvoq_shared_mma_voq_counters18_dropped_bytes {
      type oc-yang:counter64;
      description
        "programmable counter set that are controlled by VOQ ranges";
    }
    leaf counters_pdvoq_shared_mma_voq_counters18_dropped_packets {
      type oc-yang:counter64;
      description
        "programmable counter set that are controlled by VOQ ranges";
    }
    leaf counters_pdvoq_shared_mma_voq_counters19_dropped_bytes {
      type oc-yang:counter64;
      description
        "programmable counter set that are controlled by VOQ ranges";
    }
    leaf counters_pdvoq_shared_mma_voq_counters19_dropped_packets {
      type oc-yang:counter64;
      description
        "programmable counter set that are controlled by VOQ ranges";
    }
    leaf counters_pdvoq_shared_mma_voq_counters1_dropped_bytes {
      type oc-yang:counter64;
      description
        "programmable counter set that are controlled by VOQ ranges";
    }
    leaf counters_pdvoq_shared_mma_voq_counters1_dropped_packets {
      type oc-yang:counter64;
      description
        "programmable counter set that are controlled by VOQ ranges";
    }
    leaf counters_pdvoq_shared_mma_voq_counters20_dropped_bytes {
      type oc-yang:counter64;
      description
        "programmable counter set that are controlled by VOQ ranges";
    }
    leaf counters_pdvoq_shared_mma_voq_counters20_dropped_packets {
      type oc-yang:counter64;
      description
        "programmable counter set that are controlled by VOQ ranges";
    }
    leaf counters_pdvoq_shared_mma_voq_counters21_dropped_bytes {
      type oc-yang:counter64;
      description
        "programmable counter set that are controlled by VOQ ranges";
    }
    leaf counters_pdvoq_shared_mma_voq_counters21_dropped_packets {
      type oc-yang:counter64;
      description
        "programmable counter set that are controlled by VOQ ranges";
    }
    leaf counters_pdvoq_shared_mma_voq_counters22_dropped_bytes {
      type oc-yang:counter64;
      description
        "programmable counter set that are controlled by VOQ ranges";
    }
    leaf counters_pdvoq_shared_mma_voq_counters22_dropped_packets {
      type oc-yang:counter64;
      description
        "programmable counter set that are controlled by VOQ ranges";
    }
    leaf counters_pdvoq_shared_mma_voq_counters23_dropped_bytes {
      type oc-yang:counter64;
      description
        "programmable counter set that are controlled by VOQ ranges";
    }
    leaf counters_pdvoq_shared_mma_voq_counters23_dropped_packets {
      type oc-yang:counter64;
      description
        "programmable counter set that are controlled by VOQ ranges";
    }
    leaf counters_pdvoq_shared_mma_voq_counters2_dropped_bytes {
      type oc-yang:counter64;
      description
        "programmable counter set that are controlled by VOQ ranges";
    }
    leaf counters_pdvoq_shared_mma_voq_counters2_dropped_packets {
      type oc-yang:counter64;
      description
        "programmable counter set that are controlled by VOQ ranges";
    }
    leaf counters_pdvoq_shared_mma_voq_counters3_dropped_bytes {
      type oc-yang:counter64;
      description
        "programmable counter set that are controlled by VOQ ranges";
    }
    leaf counters_pdvoq_shared_mma_voq_counters3_dropped_packets {
      type oc-yang:counter64;
      description
        "programmable counter set that are controlled by VOQ ranges";
    }
    leaf counters_pdvoq_shared_mma_voq_counters4_dropped_bytes {
      type oc-yang:counter64;
      description
        "programmable counter set that are controlled by VOQ ranges";
    }
    leaf counters_pdvoq_shared_mma_voq_counters4_dropped_packets {
      type oc-yang:counter64;
      description
        "programmable counter set that are controlled by VOQ ranges";
    }
    leaf counters_pdvoq_shared_mma_voq_counters5_dropped_bytes {
      type oc-yang:counter64;
      description
        "programmable counter set that are controlled by VOQ ranges";
    }
    leaf counters_pdvoq_shared_mma_voq_counters5_dropped_packets {
      type oc-yang:counter64;
      description
        "programmable counter set that are controlled by VOQ ranges";
    }
    leaf counters_pdvoq_shared_mma_voq_counters6_dropped_bytes {
      type oc-yang:counter64;
      description
        "programmable counter set that are controlled by VOQ ranges";
    }
    leaf counters_pdvoq_shared_mma_voq_counters6_dropped_packets {
      type oc-yang:counter64;
      description
        "programmable counter set that are controlled by VOQ ranges";
    }
    leaf counters_pdvoq_shared_mma_voq_counters7_dropped_bytes {
      type oc-yang:counter64;
      description
        "programmable counter set that are controlled by VOQ ranges";
    }
    leaf counters_pdvoq_shared_mma_voq_counters7_dropped_packets {
      type oc-yang:counter64;
      description
        "programmable counter set that are controlled by VOQ ranges";
    }
    leaf counters_pdvoq_shared_mma_voq_counters8_dropped_bytes {
      type oc-yang:counter64;
      description
        "programmable counter set that are controlled by VOQ ranges";
    }
    leaf counters_pdvoq_shared_mma_voq_counters8_dropped_packets {
      type oc-yang:counter64;
      description
        "programmable counter set that are controlled by VOQ ranges";
    }
    leaf counters_pdvoq_shared_mma_voq_counters9_dropped_bytes {
      type oc-yang:counter64;
      description
        "programmable counter set that are controlled by VOQ ranges";
    }
    leaf counters_pdvoq_shared_mma_voq_counters9_dropped_packets {
      type oc-yang:counter64;
      description
        "programmable counter set that are controlled by VOQ ranges";
    }
    leaf counters_pdvoq_shared_mma_voq_drop_counters_evict_not_ok_drop {
      type oc-yang:counter64;
      description
        "nan";
    }
    leaf counters_pdvoq_shared_mma_voq_drop_counters_guarantee_drop {
      type oc-yang:counter64;
      description
        "nan";
    }
    leaf counters_pdvoq_shared_mma_voq_drop_counters_pd_pool_ovf_drop {
      type oc-yang:counter64;
      description
        "nan";
    }
    leaf counters_pdvoq_shared_mma_voq_drop_counters_green_dram_lut_packets {
      type oc-yang:counter64;
      description
        "nan";
    }
    leaf counters_pdvoq_shared_mma_voq_drop_counters_green_dram_wred_packets {
      type oc-yang:counter64;
      description
        "nan";
    }
    leaf counters_pdvoq_shared_mma_voq_drop_counters_green_evicted_buffers {
      type oc-yang:counter64;
      description
        "nan";
    }
    leaf counters_pdvoq_shared_mma_voq_drop_counters_green_sms_buffers {
      type oc-yang:counter64;
      description
        "nan";
    }
    leaf counters_pdvoq_shared_mma_voq_drop_counters_green_sms_packets {
      type oc-yang:counter64;
      description
        "nan";
    }
    leaf counters_pdvoq_shared_mma_voq_drop_counters_yellow_dram_lut_packets {
      type oc-yang:counter64;
      description
        "nan";
    }
    leaf counters_pdvoq_shared_mma_voq_drop_counters_yellow_dram_wred_packets {
      type oc-yang:counter64;
      description
        "nan";
    }
    leaf counters_pdvoq_shared_mma_voq_drop_counters_yellow_evicted_buffers {
      type oc-yang:counter64;
      description
        "nan";
    }
    leaf counters_pdvoq_shared_mma_voq_drop_counters_yellow_sms_buffers {
      type oc-yang:counter64;
      description
        "nan";
    }
    leaf counters_pdvoq_shared_mma_voq_drop_counters_yellow_sms_packets {
      type oc-yang:counter64;
      description
        "nan";
    }
    leaf counters_rx_cgm_sq0_dropped_packets {
      type oc-yang:counter64;
      description
        "Counts the number of packets that were dropped and were mapped by the profile map table to the counter.";
    }
    leaf counters_rx_cgm_sq10_dropped_packets {
      type oc-yang:counter64;
      description
        "Counts the number of packets that were dropped and were mapped by the profile map table to the counter.";
    }
    leaf counters_rx_cgm_sq11_dropped_packets {
      type oc-yang:counter64;
      description
        "Counts the number of packets that were dropped and were mapped by the profile map table to the counter.";
    }
    leaf counters_rx_cgm_sq12_dropped_packets {
      type oc-yang:counter64;
      description
        "Counts the number of packets that were dropped and were mapped by the profile map table to the counter.";
    }
    leaf counters_rx_cgm_sq13_dropped_packets {
      type oc-yang:counter64;
      description
        "Counts the number of packets that were dropped and were mapped by the profile map table to the counter.";
    }
    leaf counters_rx_cgm_sq14_dropped_packets {
      type oc-yang:counter64;
      description
        "Counts the number of packets that were dropped and were mapped by the profile map table to the counter.";
    }
    leaf counters_rx_cgm_sq15_dropped_packets {
      type oc-yang:counter64;
      description
        "Counts the number of packets that were dropped and were mapped by the profile map table to the counter.";
    }
    leaf counters_rx_cgm_sq16_dropped_packets {
      type oc-yang:counter64;
      description
        "Counts the number of packets that were dropped and were mapped by the profile map table to the counter.";
    }
    leaf counters_rx_cgm_sq17_dropped_packets {
      type oc-yang:counter64;
      description
        "Counts the number of packets that were dropped and were mapped by the profile map table to the counter.";
    }
    leaf counters_rx_cgm_sq18_dropped_packets {
      type oc-yang:counter64;
      description
        "Counts the number of packets that were dropped and were mapped by the profile map table to the counter.";
    }
    leaf counters_rx_cgm_sq19_dropped_packets {
      type oc-yang:counter64;
      description
        "Counts the number of packets that were dropped and were mapped by the profile map table to the counter.";
    }
    leaf counters_rx_cgm_sq1_dropped_packets {
      type oc-yang:counter64;
      description
        "Counts the number of packets that were dropped and were mapped by the profile map table to the counter.";
    }
    leaf counters_rx_cgm_sq20_dropped_packets {
      type oc-yang:counter64;
      description
        "Counts the number of packets that were dropped and were mapped by the profile map table to the counter.";
    }
    leaf counters_rx_cgm_sq21_dropped_packets {
      type oc-yang:counter64;
      description
        "Counts the number of packets that were dropped and were mapped by the profile map table to the counter.";
    }
    leaf counters_rx_cgm_sq22_dropped_packets {
      type oc-yang:counter64;
      description
        "Counts the number of packets that were dropped and were mapped by the profile map table to the counter.";
    }
    leaf counters_rx_cgm_sq23_dropped_packets {
      type oc-yang:counter64;
      description
        "Counts the number of packets that were dropped and were mapped by the profile map table to the counter.";
    }
    leaf counters_rx_cgm_sq24_dropped_packets {
      type oc-yang:counter64;
      description
        "Counts the number of packets that were dropped and were mapped by the profile map table to the counter.";
    }
    leaf counters_rx_cgm_sq25_dropped_packets {
      type oc-yang:counter64;
      description
        "Counts the number of packets that were dropped and were mapped by the profile map table to the counter.";
    }
    leaf counters_rx_cgm_sq26_dropped_packets {
      type oc-yang:counter64;
      description
        "Counts the number of packets that were dropped and were mapped by the profile map table to the counter.";
    }
    leaf counters_rx_cgm_sq27_dropped_packets {
      type oc-yang:counter64;
      description
        "Counts the number of packets that were dropped and were mapped by the profile map table to the counter.";
    }
    leaf counters_rx_cgm_sq28_dropped_packets {
      type oc-yang:counter64;
      description
        "Counts the number of packets that were dropped and were mapped by the profile map table to the counter.";
    }
    leaf counters_rx_cgm_sq29_dropped_packets {
      type oc-yang:counter64;
      description
        "Counts the number of packets that were dropped and were mapped by the profile map table to the counter.";
    }
    leaf counters_rx_cgm_sq2_dropped_packets {
      type oc-yang:counter64;
      description
        "Counts the number of packets that were dropped and were mapped by the profile map table to the counter.";
    }
    leaf counters_rx_cgm_sq30_dropped_packets {
      type oc-yang:counter64;
      description
        "Counts the number of packets that were dropped and were mapped by the profile map table to the counter.";
    }
    leaf counters_rx_cgm_sq31_dropped_packets {
      type oc-yang:counter64;
      description
        "Counts the number of packets that were dropped and were mapped by the profile map table to the counter.";
    }
    leaf counters_rx_cgm_sq32_dropped_packets {
      type oc-yang:counter64;
      description
        "Counts the number of packets that were dropped and were mapped by the profile map table to the counter.";
    }
    leaf counters_rx_cgm_sq33_dropped_packets {
      type oc-yang:counter64;
      description
        "Counts the number of packets that were dropped and were mapped by the profile map table to the counter.";
    }
    leaf counters_rx_cgm_sq34_dropped_packets {
      type oc-yang:counter64;
      description
        "Counts the number of packets that were dropped and were mapped by the profile map table to the counter.";
    }
    leaf counters_rx_cgm_sq35_dropped_packets {
      type oc-yang:counter64;
      description
        "Counts the number of packets that were dropped and were mapped by the profile map table to the counter.";
    }
    leaf counters_rx_cgm_sq36_dropped_packets {
      type oc-yang:counter64;
      description
        "Counts the number of packets that were dropped and were mapped by the profile map table to the counter.";
    }
    leaf counters_rx_cgm_sq37_dropped_packets {
      type oc-yang:counter64;
      description
        "Counts the number of packets that were dropped and were mapped by the profile map table to the counter.";
    }
    leaf counters_rx_cgm_sq38_dropped_packets {
      type oc-yang:counter64;
      description
        "Counts the number of packets that were dropped and were mapped by the profile map table to the counter.";
    }
    leaf counters_rx_cgm_sq39_dropped_packets {
      type oc-yang:counter64;
      description
        "Counts the number of packets that were dropped and were mapped by the profile map table to the counter.";
    }
    leaf counters_rx_cgm_sq3_dropped_packets {
      type oc-yang:counter64;
      description
        "Counts the number of packets that were dropped and were mapped by the profile map table to the counter.";
    }
    leaf counters_rx_cgm_sq40_dropped_packets {
      type oc-yang:counter64;
      description
        "Counts the number of packets that were dropped and were mapped by the profile map table to the counter.";
    }
    leaf counters_rx_cgm_sq41_dropped_packets {
      type oc-yang:counter64;
      description
        "Counts the number of packets that were dropped and were mapped by the profile map table to the counter.";
    }
    leaf counters_rx_cgm_sq42_dropped_packets {
      type oc-yang:counter64;
      description
        "Counts the number of packets that were dropped and were mapped by the profile map table to the counter.";
    }
    leaf counters_rx_cgm_sq43_dropped_packets {
      type oc-yang:counter64;
      description
        "Counts the number of packets that were dropped and were mapped by the profile map table to the counter.";
    }
    leaf counters_rx_cgm_sq44_dropped_packets {
      type oc-yang:counter64;
      description
        "Counts the number of packets that were dropped and were mapped by the profile map table to the counter.";
    }
    leaf counters_rx_cgm_sq45_dropped_packets {
      type oc-yang:counter64;
      description
        "Counts the number of packets that were dropped and were mapped by the profile map table to the counter.";
    }
    leaf counters_rx_cgm_sq46_dropped_packets {
      type oc-yang:counter64;
      description
        "Counts the number of packets that were dropped and were mapped by the profile map table to the counter.";
    }
    leaf counters_rx_cgm_sq47_dropped_packets {
      type oc-yang:counter64;
      description
        "Counts the number of packets that were dropped and were mapped by the profile map table to the counter.";
    }
    leaf counters_rx_cgm_sq4_dropped_packets {
      type oc-yang:counter64;
      description
        "Counts the number of packets that were dropped and were mapped by the profile map table to the counter.";
    }
    leaf counters_rx_cgm_sq5_dropped_packets {
      type oc-yang:counter64;
      description
        "Counts the number of packets that were dropped and were mapped by the profile map table to the counter.";
    }
    leaf counters_rx_cgm_sq6_dropped_packets {
      type oc-yang:counter64;
      description
        "Counts the number of packets that were dropped and were mapped by the profile map table to the counter.";
    }
    leaf counters_rx_cgm_sq7_dropped_packets {
      type oc-yang:counter64;
      description
        "Counts the number of packets that were dropped and were mapped by the profile map table to the counter.";
    }
    leaf counters_rx_cgm_sq8_dropped_packets {
      type oc-yang:counter64;
      description
        "Counts the number of packets that were dropped and were mapped by the profile map table to the counter.";
    }
    leaf counters_rx_cgm_sq9_dropped_packets {
      type oc-yang:counter64;
      description
        "Counts the number of packets that were dropped and were mapped by the profile map table to the counter.";
    }
    leaf counters_rx_cgm_tc0_dropped_packets {
      type oc-yang:counter64;
      description
        "Counts the number of packets that were dropped and belong to the CGM TC.";
    }
    leaf counters_rx_cgm_tc1_dropped_packets {
      type oc-yang:counter64;
      description
        "Counts the number of packets that were dropped and belong to the CGM TC.";
    }
    leaf counters_rx_cgm_tc2_dropped_packets {
      type oc-yang:counter64;
      description
        "Counts the number of packets that were dropped and belong to the CGM TC.";
    }
    leaf counters_rx_cgm_tc3_dropped_packets {
      type oc-yang:counter64;
      description
        "Counts the number of packets that were dropped and belong to the CGM TC.";
    }
    leaf counters_rx_cgm_tc4_dropped_packets {
      type oc-yang:counter64;
      description
        "Counts the number of packets that were dropped and belong to the CGM TC.";
    }
    leaf counters_rx_cgm_tc5_dropped_packets {
      type oc-yang:counter64;
      description
        "Counts the number of packets that were dropped and belong to the CGM TC.";
    }
    leaf counters_rx_cgm_tc6_dropped_packets {
      type oc-yang:counter64;
      description
        "Counts the number of packets that were dropped and belong to the CGM TC.";
    }
    leaf counters_rx_cgm_tc7_dropped_packets {
      type oc-yang:counter64;
      description
        "Counts the number of packets that were dropped and belong to the CGM TC.";
    }
    leaf counters_rx_meter_top_debug_counter0_dropped_packets {
      type oc-yang:counter64;
      description
        "Counts the number of packets that were dropped by the rx meter block.";
    }
    leaf counters_rx_meter_top_debug_counter1_dropped_packets {
      type oc-yang:counter64;
      description
        "Counts the number of packets that were dropped by the rx meter block.";
    }
    leaf counters_rx_meter_top_debug_counter2_dropped_packets {
      type oc-yang:counter64;
      description
        "Counts the number of packets that were dropped by the rx meter block.";
    }
    leaf counters_rx_meter_top_debug_counter3_dropped_packets {
      type oc-yang:counter64;
      description
        "Counts the number of packets that were dropped by the rx meter block.";
    }
    leaf counters_rx_meter_top_debug_counter4_dropped_packets {
      type oc-yang:counter64;
      description
        "Counts the number of packets that were dropped by the rx meter block.";
    }
    leaf counters_rx_meter_top_debug_counter5_dropped_packets {
      type oc-yang:counter64;
      description
        "Counts the number of packets that were dropped by the rx meter block.";
    }
    leaf counters_slice0_ifg0_ifgb_rx_port_0_cgm_tc0_dropped_packets {
      type oc-yang:counter64;
      description
        "RX port cgm ostc0 drops counter. Counts packets that were totally dropped and will not be seen on RX side.";
    }
    leaf counters_slice0_ifg0_ifgb_rx_port_0_cgm_tc0_partially_dropped_packets {
      type oc-yang:counter64;
      description
        "RX port cgm ostc0 partial drops counter. Counts packets that were partially dropped and will be seen on RX side.";
    }
    leaf counters_slice0_ifg0_ifgb_rx_port_0_cgm_tc1_dropped_packets {
      type oc-yang:counter64;
      description
        "RX port cgm ostc1 drops counter. Counts packets that were totally dropped and will not be seen on RX side.";
    }
    leaf counters_slice0_ifg0_ifgb_rx_port_0_cgm_tc1_partially_dropped_packets {
      type oc-yang:counter64;
      description
        "RX port cgm ostc1 partial drops counter. Counts packets that were partially dropped and will be seen on RX side.";
    }
    leaf counters_slice0_ifg0_ifgb_rx_port_0_cgm_tc2_dropped_packets {
      type oc-yang:counter64;
      description
        "RX port cgm ostc2 drops counter. Counts packets that were totally dropped and will not be seen on RX side.";
    }
    leaf counters_slice0_ifg0_ifgb_rx_port_0_cgm_tc2_partially_dropped_packets {
      type oc-yang:counter64;
      description
        "RX port cgm ostc2 partial drops counter. Counts packets that were partially dropped and will be seen on RX side.";
    }
    leaf counters_slice0_ifg0_ifgb_rx_port_0_cgm_tc3_dropped_packets {
      type oc-yang:counter64;
      description
        "RX port cgm ostc3 drops counter. Counts packets that were totally dropped and will not be seen on RX side.";
    }
    leaf counters_slice0_ifg0_ifgb_rx_port_0_cgm_tc3_partially_dropped_packets {
      type oc-yang:counter64;
      description
        "RX port cgm ostc3 partial drops counter. Counts packets that were partially dropped and will be seen on RX side.";
    }
    leaf counters_slice0_ifg0_ifgb_rx_port_1_cgm_tc0_dropped_packets {
      type oc-yang:counter64;
      description
        "RX port cgm ostc0 drops counter. Counts packets that were totally dropped and will not be seen on RX side.";
    }
    leaf counters_slice0_ifg0_ifgb_rx_port_1_cgm_tc0_partially_dropped_packets {
      type oc-yang:counter64;
      description
        "RX port cgm ostc0 partial drops counter. Counts packets that were partially dropped and will be seen on RX side.";
    }
    leaf counters_slice0_ifg0_ifgb_rx_port_1_cgm_tc1_dropped_packets {
      type oc-yang:counter64;
      description
        "RX port cgm ostc1 drops counter. Counts packets that were totally dropped and will not be seen on RX side.";
    }
    leaf counters_slice0_ifg0_ifgb_rx_port_1_cgm_tc1_partially_dropped_packets {
      type oc-yang:counter64;
      description
        "RX port cgm ostc1 partial drops counter. Counts packets that were partially dropped and will be seen on RX side.";
    }
    leaf counters_slice0_ifg0_ifgb_rx_port_1_cgm_tc2_dropped_packets {
      type oc-yang:counter64;
      description
        "RX port cgm ostc2 drops counter. Counts packets that were totally dropped and will not be seen on RX side.";
    }
    leaf counters_slice0_ifg0_ifgb_rx_port_1_cgm_tc2_partially_dropped_packets {
      type oc-yang:counter64;
      description
        "RX port cgm ostc2 partial drops counter. Counts packets that were partially dropped and will be seen on RX side.";
    }
    leaf counters_slice0_ifg0_ifgb_rx_port_1_cgm_tc3_dropped_packets {
      type oc-yang:counter64;
      description
        "RX port cgm ostc3 drops counter. Counts packets that were totally dropped and will not be seen on RX side.";
    }
    leaf counters_slice0_ifg0_ifgb_rx_port_1_cgm_tc3_partially_dropped_packets {
      type oc-yang:counter64;
      description
        "RX port cgm ostc3 partial drops counter. Counts packets that were partially dropped and will be seen on RX side.";
    }
    leaf counters_slice0_ifg0_ifgb_rx_port_10_cgm_tc0_dropped_packets {
      type oc-yang:counter64;
      description
        "RX port cgm ostc0 drops counter. Counts packets that were totally dropped and will not be seen on RX side.";
    }
    leaf counters_slice0_ifg0_ifgb_rx_port_10_cgm_tc0_partially_dropped_packets {
      type oc-yang:counter64;
      description
        "RX port cgm ostc0 partial drops counter. Counts packets that were partially dropped and will be seen on RX side.";
    }
    leaf counters_slice0_ifg0_ifgb_rx_port_10_cgm_tc1_dropped_packets {
      type oc-yang:counter64;
      description
        "RX port cgm ostc1 drops counter. Counts packets that were totally dropped and will not be seen on RX side.";
    }
    leaf counters_slice0_ifg0_ifgb_rx_port_10_cgm_tc1_partially_dropped_packets {
      type oc-yang:counter64;
      description
        "RX port cgm ostc1 partial drops counter. Counts packets that were partially dropped and will be seen on RX side.";
    }
    leaf counters_slice0_ifg0_ifgb_rx_port_10_cgm_tc2_dropped_packets {
      type oc-yang:counter64;
      description
        "RX port cgm ostc2 drops counter. Counts packets that were totally dropped and will not be seen on RX side.";
    }
    leaf counters_slice0_ifg0_ifgb_rx_port_10_cgm_tc2_partially_dropped_packets {
      type oc-yang:counter64;
      description
        "RX port cgm ostc2 partial drops counter. Counts packets that were partially dropped and will be seen on RX side.";
    }
    leaf counters_slice0_ifg0_ifgb_rx_port_10_cgm_tc3_dropped_packets {
      type oc-yang:counter64;
      description
        "RX port cgm ostc3 drops counter. Counts packets that were totally dropped and will not be seen on RX side.";
    }
    leaf counters_slice0_ifg0_ifgb_rx_port_10_cgm_tc3_partially_dropped_packets {
      type oc-yang:counter64;
      description
        "RX port cgm ostc3 partial drops counter. Counts packets that were partially dropped and will be seen on RX side.";
    }
    leaf counters_slice0_ifg0_ifgb_rx_port_11_cgm_tc0_dropped_packets {
      type oc-yang:counter64;
      description
        "RX port cgm ostc0 drops counter. Counts packets that were totally dropped and will not be seen on RX side.";
    }
    leaf counters_slice0_ifg0_ifgb_rx_port_11_cgm_tc0_partially_dropped_packets {
      type oc-yang:counter64;
      description
        "RX port cgm ostc0 partial drops counter. Counts packets that were partially dropped and will be seen on RX side.";
    }
    leaf counters_slice0_ifg0_ifgb_rx_port_11_cgm_tc1_dropped_packets {
      type oc-yang:counter64;
      description
        "RX port cgm ostc1 drops counter. Counts packets that were totally dropped and will not be seen on RX side.";
    }
    leaf counters_slice0_ifg0_ifgb_rx_port_11_cgm_tc1_partially_dropped_packets {
      type oc-yang:counter64;
      description
        "RX port cgm ostc1 partial drops counter. Counts packets that were partially dropped and will be seen on RX side.";
    }
    leaf counters_slice0_ifg0_ifgb_rx_port_11_cgm_tc2_dropped_packets {
      type oc-yang:counter64;
      description
        "RX port cgm ostc2 drops counter. Counts packets that were totally dropped and will not be seen on RX side.";
    }
    leaf counters_slice0_ifg0_ifgb_rx_port_11_cgm_tc2_partially_dropped_packets {
      type oc-yang:counter64;
      description
        "RX port cgm ostc2 partial drops counter. Counts packets that were partially dropped and will be seen on RX side.";
    }
    leaf counters_slice0_ifg0_ifgb_rx_port_11_cgm_tc3_dropped_packets {
      type oc-yang:counter64;
      description
        "RX port cgm ostc3 drops counter. Counts packets that were totally dropped and will not be seen on RX side.";
    }
    leaf counters_slice0_ifg0_ifgb_rx_port_11_cgm_tc3_partially_dropped_packets {
      type oc-yang:counter64;
      description
        "RX port cgm ostc3 partial drops counter. Counts packets that were partially dropped and will be seen on RX side.";
    }
    leaf counters_slice0_ifg0_ifgb_rx_port_12_cgm_tc0_dropped_packets {
      type oc-yang:counter64;
      description
        "RX port cgm ostc0 drops counter. Counts packets that were totally dropped and will not be seen on RX side.";
    }
    leaf counters_slice0_ifg0_ifgb_rx_port_12_cgm_tc0_partially_dropped_packets {
      type oc-yang:counter64;
      description
        "RX port cgm ostc0 partial drops counter. Counts packets that were partially dropped and will be seen on RX side.";
    }
    leaf counters_slice0_ifg0_ifgb_rx_port_12_cgm_tc1_dropped_packets {
      type oc-yang:counter64;
      description
        "RX port cgm ostc1 drops counter. Counts packets that were totally dropped and will not be seen on RX side.";
    }
    leaf counters_slice0_ifg0_ifgb_rx_port_12_cgm_tc1_partially_dropped_packets {
      type oc-yang:counter64;
      description
        "RX port cgm ostc1 partial drops counter. Counts packets that were partially dropped and will be seen on RX side.";
    }
    leaf counters_slice0_ifg0_ifgb_rx_port_12_cgm_tc2_dropped_packets {
      type oc-yang:counter64;
      description
        "RX port cgm ostc2 drops counter. Counts packets that were totally dropped and will not be seen on RX side.";
    }
    leaf counters_slice0_ifg0_ifgb_rx_port_12_cgm_tc2_partially_dropped_packets {
      type oc-yang:counter64;
      description
        "RX port cgm ostc2 partial drops counter. Counts packets that were partially dropped and will be seen on RX side.";
    }
    leaf counters_slice0_ifg0_ifgb_rx_port_12_cgm_tc3_dropped_packets {
      type oc-yang:counter64;
      description
        "RX port cgm ostc3 drops counter. Counts packets that were totally dropped and will not be seen on RX side.";
    }
    leaf counters_slice0_ifg0_ifgb_rx_port_12_cgm_tc3_partially_dropped_packets {
      type oc-yang:counter64;
      description
        "RX port cgm ostc3 partial drops counter. Counts packets that were partially dropped and will be seen on RX side.";
    }
    leaf counters_slice0_ifg0_ifgb_rx_port_13_cgm_tc0_dropped_packets {
      type oc-yang:counter64;
      description
        "RX port cgm ostc0 drops counter. Counts packets that were totally dropped and will not be seen on RX side.";
    }
    leaf counters_slice0_ifg0_ifgb_rx_port_13_cgm_tc0_partially_dropped_packets {
      type oc-yang:counter64;
      description
        "RX port cgm ostc0 partial drops counter. Counts packets that were partially dropped and will be seen on RX side.";
    }
    leaf counters_slice0_ifg0_ifgb_rx_port_13_cgm_tc1_dropped_packets {
      type oc-yang:counter64;
      description
        "RX port cgm ostc1 drops counter. Counts packets that were totally dropped and will not be seen on RX side.";
    }
    leaf counters_slice0_ifg0_ifgb_rx_port_13_cgm_tc1_partially_dropped_packets {
      type oc-yang:counter64;
      description
        "RX port cgm ostc1 partial drops counter. Counts packets that were partially dropped and will be seen on RX side.";
    }
    leaf counters_slice0_ifg0_ifgb_rx_port_13_cgm_tc2_dropped_packets {
      type oc-yang:counter64;
      description
        "RX port cgm ostc2 drops counter. Counts packets that were totally dropped and will not be seen on RX side.";
    }
    leaf counters_slice0_ifg0_ifgb_rx_port_13_cgm_tc2_partially_dropped_packets {
      type oc-yang:counter64;
      description
        "RX port cgm ostc2 partial drops counter. Counts packets that were partially dropped and will be seen on RX side.";
    }
    leaf counters_slice0_ifg0_ifgb_rx_port_13_cgm_tc3_dropped_packets {
      type oc-yang:counter64;
      description
        "RX port cgm ostc3 drops counter. Counts packets that were totally dropped and will not be seen on RX side.";
    }
    leaf counters_slice0_ifg0_ifgb_rx_port_13_cgm_tc3_partially_dropped_packets {
      type oc-yang:counter64;
      description
        "RX port cgm ostc3 partial drops counter. Counts packets that were partially dropped and will be seen on RX side.";
    }
    leaf counters_slice0_ifg0_ifgb_rx_port_14_cgm_tc0_dropped_packets {
      type oc-yang:counter64;
      description
        "RX port cgm ostc0 drops counter. Counts packets that were totally dropped and will not be seen on RX side.";
    }
    leaf counters_slice0_ifg0_ifgb_rx_port_14_cgm_tc0_partially_dropped_packets {
      type oc-yang:counter64;
      description
        "RX port cgm ostc0 partial drops counter. Counts packets that were partially dropped and will be seen on RX side.";
    }
    leaf counters_slice0_ifg0_ifgb_rx_port_14_cgm_tc1_dropped_packets {
      type oc-yang:counter64;
      description
        "RX port cgm ostc1 drops counter. Counts packets that were totally dropped and will not be seen on RX side.";
    }
    leaf counters_slice0_ifg0_ifgb_rx_port_14_cgm_tc1_partially_dropped_packets {
      type oc-yang:counter64;
      description
        "RX port cgm ostc1 partial drops counter. Counts packets that were partially dropped and will be seen on RX side.";
    }
    leaf counters_slice0_ifg0_ifgb_rx_port_14_cgm_tc2_dropped_packets {
      type oc-yang:counter64;
      description
        "RX port cgm ostc2 drops counter. Counts packets that were totally dropped and will not be seen on RX side.";
    }
    leaf counters_slice0_ifg0_ifgb_rx_port_14_cgm_tc2_partially_dropped_packets {
      type oc-yang:counter64;
      description
        "RX port cgm ostc2 partial drops counter. Counts packets that were partially dropped and will be seen on RX side.";
    }
    leaf counters_slice0_ifg0_ifgb_rx_port_14_cgm_tc3_dropped_packets {
      type oc-yang:counter64;
      description
        "RX port cgm ostc3 drops counter. Counts packets that were totally dropped and will not be seen on RX side.";
    }
    leaf counters_slice0_ifg0_ifgb_rx_port_14_cgm_tc3_partially_dropped_packets {
      type oc-yang:counter64;
      description
        "RX port cgm ostc3 partial drops counter. Counts packets that were partially dropped and will be seen on RX side.";
    }
    leaf counters_slice0_ifg0_ifgb_rx_port_15_cgm_tc0_dropped_packets {
      type oc-yang:counter64;
      description
        "RX port cgm ostc0 drops counter. Counts packets that were totally dropped and will not be seen on RX side.";
    }
    leaf counters_slice0_ifg0_ifgb_rx_port_15_cgm_tc0_partially_dropped_packets {
      type oc-yang:counter64;
      description
        "RX port cgm ostc0 partial drops counter. Counts packets that were partially dropped and will be seen on RX side.";
    }
    leaf counters_slice0_ifg0_ifgb_rx_port_15_cgm_tc1_dropped_packets {
      type oc-yang:counter64;
      description
        "RX port cgm ostc1 drops counter. Counts packets that were totally dropped and will not be seen on RX side.";
    }
    leaf counters_slice0_ifg0_ifgb_rx_port_15_cgm_tc1_partially_dropped_packets {
      type oc-yang:counter64;
      description
        "RX port cgm ostc1 partial drops counter. Counts packets that were partially dropped and will be seen on RX side.";
    }
    leaf counters_slice0_ifg0_ifgb_rx_port_15_cgm_tc2_dropped_packets {
      type oc-yang:counter64;
      description
        "RX port cgm ostc2 drops counter. Counts packets that were totally dropped and will not be seen on RX side.";
    }
    leaf counters_slice0_ifg0_ifgb_rx_port_15_cgm_tc2_partially_dropped_packets {
      type oc-yang:counter64;
      description
        "RX port cgm ostc2 partial drops counter. Counts packets that were partially dropped and will be seen on RX side.";
    }
    leaf counters_slice0_ifg0_ifgb_rx_port_15_cgm_tc3_dropped_packets {
      type oc-yang:counter64;
      description
        "RX port cgm ostc3 drops counter. Counts packets that were totally dropped and will not be seen on RX side.";
    }
    leaf counters_slice0_ifg0_ifgb_rx_port_15_cgm_tc3_partially_dropped_packets {
      type oc-yang:counter64;
      description
        "RX port cgm ostc3 partial drops counter. Counts packets that were partially dropped and will be seen on RX side.";
    }
    leaf counters_slice0_ifg0_ifgb_rx_port_16_cgm_tc0_dropped_packets {
      type oc-yang:counter64;
      description
        "RX port cgm ostc0 drops counter. Counts packets that were totally dropped and will not be seen on RX side.";
    }
    leaf counters_slice0_ifg0_ifgb_rx_port_16_cgm_tc0_partially_dropped_packets {
      type oc-yang:counter64;
      description
        "RX port cgm ostc0 partial drops counter. Counts packets that were partially dropped and will be seen on RX side.";
    }
    leaf counters_slice0_ifg0_ifgb_rx_port_16_cgm_tc1_dropped_packets {
      type oc-yang:counter64;
      description
        "RX port cgm ostc1 drops counter. Counts packets that were totally dropped and will not be seen on RX side.";
    }
    leaf counters_slice0_ifg0_ifgb_rx_port_16_cgm_tc1_partially_dropped_packets {
      type oc-yang:counter64;
      description
        "RX port cgm ostc1 partial drops counter. Counts packets that were partially dropped and will be seen on RX side.";
    }
    leaf counters_slice0_ifg0_ifgb_rx_port_16_cgm_tc2_dropped_packets {
      type oc-yang:counter64;
      description
        "RX port cgm ostc2 drops counter. Counts packets that were totally dropped and will not be seen on RX side.";
    }
    leaf counters_slice0_ifg0_ifgb_rx_port_16_cgm_tc2_partially_dropped_packets {
      type oc-yang:counter64;
      description
        "RX port cgm ostc2 partial drops counter. Counts packets that were partially dropped and will be seen on RX side.";
    }
    leaf counters_slice0_ifg0_ifgb_rx_port_16_cgm_tc3_dropped_packets {
      type oc-yang:counter64;
      description
        "RX port cgm ostc3 drops counter. Counts packets that were totally dropped and will not be seen on RX side.";
    }
    leaf counters_slice0_ifg0_ifgb_rx_port_16_cgm_tc3_partially_dropped_packets {
      type oc-yang:counter64;
      description
        "RX port cgm ostc3 partial drops counter. Counts packets that were partially dropped and will be seen on RX side.";
    }
    leaf counters_slice0_ifg0_ifgb_rx_port_17_cgm_tc0_dropped_packets {
      type oc-yang:counter64;
      description
        "RX port cgm ostc0 drops counter. Counts packets that were totally dropped and will not be seen on RX side.";
    }
    leaf counters_slice0_ifg0_ifgb_rx_port_17_cgm_tc0_partially_dropped_packets {
      type oc-yang:counter64;
      description
        "RX port cgm ostc0 partial drops counter. Counts packets that were partially dropped and will be seen on RX side.";
    }
    leaf counters_slice0_ifg0_ifgb_rx_port_17_cgm_tc1_dropped_packets {
      type oc-yang:counter64;
      description
        "RX port cgm ostc1 drops counter. Counts packets that were totally dropped and will not be seen on RX side.";
    }
    leaf counters_slice0_ifg0_ifgb_rx_port_17_cgm_tc1_partially_dropped_packets {
      type oc-yang:counter64;
      description
        "RX port cgm ostc1 partial drops counter. Counts packets that were partially dropped and will be seen on RX side.";
    }
    leaf counters_slice0_ifg0_ifgb_rx_port_17_cgm_tc2_dropped_packets {
      type oc-yang:counter64;
      description
        "RX port cgm ostc2 drops counter. Counts packets that were totally dropped and will not be seen on RX side.";
    }
    leaf counters_slice0_ifg0_ifgb_rx_port_17_cgm_tc2_partially_dropped_packets {
      type oc-yang:counter64;
      description
        "RX port cgm ostc2 partial drops counter. Counts packets that were partially dropped and will be seen on RX side.";
    }
    leaf counters_slice0_ifg0_ifgb_rx_port_17_cgm_tc3_dropped_packets {
      type oc-yang:counter64;
      description
        "RX port cgm ostc3 drops counter. Counts packets that were totally dropped and will not be seen on RX side.";
    }
    leaf counters_slice0_ifg0_ifgb_rx_port_17_cgm_tc3_partially_dropped_packets {
      type oc-yang:counter64;
      description
        "RX port cgm ostc3 partial drops counter. Counts packets that were partially dropped and will be seen on RX side.";
    }
    leaf counters_slice0_ifg0_ifgb_rx_port_18_cgm_tc0_dropped_packets {
      type oc-yang:counter64;
      description
        "RX port cgm ostc0 drops counter. Counts packets that were totally dropped and will not be seen on RX side.";
    }
    leaf counters_slice0_ifg0_ifgb_rx_port_18_cgm_tc0_partially_dropped_packets {
      type oc-yang:counter64;
      description
        "RX port cgm ostc0 partial drops counter. Counts packets that were partially dropped and will be seen on RX side.";
    }
    leaf counters_slice0_ifg0_ifgb_rx_port_18_cgm_tc1_dropped_packets {
      type oc-yang:counter64;
      description
        "RX port cgm ostc1 drops counter. Counts packets that were totally dropped and will not be seen on RX side.";
    }
    leaf counters_slice0_ifg0_ifgb_rx_port_18_cgm_tc1_partially_dropped_packets {
      type oc-yang:counter64;
      description
        "RX port cgm ostc1 partial drops counter. Counts packets that were partially dropped and will be seen on RX side.";
    }
    leaf counters_slice0_ifg0_ifgb_rx_port_18_cgm_tc2_dropped_packets {
      type oc-yang:counter64;
      description
        "RX port cgm ostc2 drops counter. Counts packets that were totally dropped and will not be seen on RX side.";
    }
    leaf counters_slice0_ifg0_ifgb_rx_port_18_cgm_tc2_partially_dropped_packets {
      type oc-yang:counter64;
      description
        "RX port cgm ostc2 partial drops counter. Counts packets that were partially dropped and will be seen on RX side.";
    }
    leaf counters_slice0_ifg0_ifgb_rx_port_18_cgm_tc3_dropped_packets {
      type oc-yang:counter64;
      description
        "RX port cgm ostc3 drops counter. Counts packets that were totally dropped and will not be seen on RX side.";
    }
    leaf counters_slice0_ifg0_ifgb_rx_port_18_cgm_tc3_partially_dropped_packets {
      type oc-yang:counter64;
      description
        "RX port cgm ostc3 partial drops counter. Counts packets that were partially dropped and will be seen on RX side.";
    }
    leaf counters_slice0_ifg0_ifgb_rx_port_19_cgm_tc0_dropped_packets {
      type oc-yang:counter64;
      description
        "RX port cgm ostc0 drops counter. Counts packets that were totally dropped and will not be seen on RX side.";
    }
    leaf counters_slice0_ifg0_ifgb_rx_port_19_cgm_tc0_partially_dropped_packets {
      type oc-yang:counter64;
      description
        "RX port cgm ostc0 partial drops counter. Counts packets that were partially dropped and will be seen on RX side.";
    }
    leaf counters_slice0_ifg0_ifgb_rx_port_19_cgm_tc1_dropped_packets {
      type oc-yang:counter64;
      description
        "RX port cgm ostc1 drops counter. Counts packets that were totally dropped and will not be seen on RX side.";
    }
    leaf counters_slice0_ifg0_ifgb_rx_port_19_cgm_tc1_partially_dropped_packets {
      type oc-yang:counter64;
      description
        "RX port cgm ostc1 partial drops counter. Counts packets that were partially dropped and will be seen on RX side.";
    }
    leaf counters_slice0_ifg0_ifgb_rx_port_19_cgm_tc2_dropped_packets {
      type oc-yang:counter64;
      description
        "RX port cgm ostc2 drops counter. Counts packets that were totally dropped and will not be seen on RX side.";
    }
    leaf counters_slice0_ifg0_ifgb_rx_port_19_cgm_tc2_partially_dropped_packets {
      type oc-yang:counter64;
      description
        "RX port cgm ostc2 partial drops counter. Counts packets that were partially dropped and will be seen on RX side.";
    }
    leaf counters_slice0_ifg0_ifgb_rx_port_19_cgm_tc3_dropped_packets {
      type oc-yang:counter64;
      description
        "RX port cgm ostc3 drops counter. Counts packets that were totally dropped and will not be seen on RX side.";
    }
    leaf counters_slice0_ifg0_ifgb_rx_port_19_cgm_tc3_partially_dropped_packets {
      type oc-yang:counter64;
      description
        "RX port cgm ostc3 partial drops counter. Counts packets that were partially dropped and will be seen on RX side.";
    }
    leaf counters_slice0_ifg0_ifgb_rx_port_2_cgm_tc0_dropped_packets {
      type oc-yang:counter64;
      description
        "RX port cgm ostc0 drops counter. Counts packets that were totally dropped and will not be seen on RX side.";
    }
    leaf counters_slice0_ifg0_ifgb_rx_port_2_cgm_tc0_partially_dropped_packets {
      type oc-yang:counter64;
      description
        "RX port cgm ostc0 partial drops counter. Counts packets that were partially dropped and will be seen on RX side.";
    }
    leaf counters_slice0_ifg0_ifgb_rx_port_2_cgm_tc1_dropped_packets {
      type oc-yang:counter64;
      description
        "RX port cgm ostc1 drops counter. Counts packets that were totally dropped and will not be seen on RX side.";
    }
    leaf counters_slice0_ifg0_ifgb_rx_port_2_cgm_tc1_partially_dropped_packets {
      type oc-yang:counter64;
      description
        "RX port cgm ostc1 partial drops counter. Counts packets that were partially dropped and will be seen on RX side.";
    }
    leaf counters_slice0_ifg0_ifgb_rx_port_2_cgm_tc2_dropped_packets {
      type oc-yang:counter64;
      description
        "RX port cgm ostc2 drops counter. Counts packets that were totally dropped and will not be seen on RX side.";
    }
    leaf counters_slice0_ifg0_ifgb_rx_port_2_cgm_tc2_partially_dropped_packets {
      type oc-yang:counter64;
      description
        "RX port cgm ostc2 partial drops counter. Counts packets that were partially dropped and will be seen on RX side.";
    }
    leaf counters_slice0_ifg0_ifgb_rx_port_2_cgm_tc3_dropped_packets {
      type oc-yang:counter64;
      description
        "RX port cgm ostc3 drops counter. Counts packets that were totally dropped and will not be seen on RX side.";
    }
    leaf counters_slice0_ifg0_ifgb_rx_port_2_cgm_tc3_partially_dropped_packets {
      type oc-yang:counter64;
      description
        "RX port cgm ostc3 partial drops counter. Counts packets that were partially dropped and will be seen on RX side.";
    }
    leaf counters_slice0_ifg0_ifgb_rx_port_20_cgm_tc0_dropped_packets {
      type oc-yang:counter64;
      description
        "RX port cgm ostc0 drops counter. Counts packets that were totally dropped and will not be seen on RX side.";
    }
    leaf counters_slice0_ifg0_ifgb_rx_port_20_cgm_tc0_partially_dropped_packets {
      type oc-yang:counter64;
      description
        "RX port cgm ostc0 partial drops counter. Counts packets that were partially dropped and will be seen on RX side.";
    }
    leaf counters_slice0_ifg0_ifgb_rx_port_20_cgm_tc1_dropped_packets {
      type oc-yang:counter64;
      description
        "RX port cgm ostc1 drops counter. Counts packets that were totally dropped and will not be seen on RX side.";
    }
    leaf counters_slice0_ifg0_ifgb_rx_port_20_cgm_tc1_partially_dropped_packets {
      type oc-yang:counter64;
      description
        "RX port cgm ostc1 partial drops counter. Counts packets that were partially dropped and will be seen on RX side.";
    }
    leaf counters_slice0_ifg0_ifgb_rx_port_20_cgm_tc2_dropped_packets {
      type oc-yang:counter64;
      description
        "RX port cgm ostc2 drops counter. Counts packets that were totally dropped and will not be seen on RX side.";
    }
    leaf counters_slice0_ifg0_ifgb_rx_port_20_cgm_tc2_partially_dropped_packets {
      type oc-yang:counter64;
      description
        "RX port cgm ostc2 partial drops counter. Counts packets that were partially dropped and will be seen on RX side.";
    }
    leaf counters_slice0_ifg0_ifgb_rx_port_20_cgm_tc3_dropped_packets {
      type oc-yang:counter64;
      description
        "RX port cgm ostc3 drops counter. Counts packets that were totally dropped and will not be seen on RX side.";
    }
    leaf counters_slice0_ifg0_ifgb_rx_port_20_cgm_tc3_partially_dropped_packets {
      type oc-yang:counter64;
      description
        "RX port cgm ostc3 partial drops counter. Counts packets that were partially dropped and will be seen on RX side.";
    }
    leaf counters_slice0_ifg0_ifgb_rx_port_21_cgm_tc0_dropped_packets {
      type oc-yang:counter64;
      description
        "RX port cgm ostc0 drops counter. Counts packets that were totally dropped and will not be seen on RX side.";
    }
    leaf counters_slice0_ifg0_ifgb_rx_port_21_cgm_tc0_partially_dropped_packets {
      type oc-yang:counter64;
      description
        "RX port cgm ostc0 partial drops counter. Counts packets that were partially dropped and will be seen on RX side.";
    }
    leaf counters_slice0_ifg0_ifgb_rx_port_21_cgm_tc1_dropped_packets {
      type oc-yang:counter64;
      description
        "RX port cgm ostc1 drops counter. Counts packets that were totally dropped and will not be seen on RX side.";
    }
    leaf counters_slice0_ifg0_ifgb_rx_port_21_cgm_tc1_partially_dropped_packets {
      type oc-yang:counter64;
      description
        "RX port cgm ostc1 partial drops counter. Counts packets that were partially dropped and will be seen on RX side.";
    }
    leaf counters_slice0_ifg0_ifgb_rx_port_21_cgm_tc2_dropped_packets {
      type oc-yang:counter64;
      description
        "RX port cgm ostc2 drops counter. Counts packets that were totally dropped and will not be seen on RX side.";
    }
    leaf counters_slice0_ifg0_ifgb_rx_port_21_cgm_tc2_partially_dropped_packets {
      type oc-yang:counter64;
      description
        "RX port cgm ostc2 partial drops counter. Counts packets that were partially dropped and will be seen on RX side.";
    }
    leaf counters_slice0_ifg0_ifgb_rx_port_21_cgm_tc3_dropped_packets {
      type oc-yang:counter64;
      description
        "RX port cgm ostc3 drops counter. Counts packets that were totally dropped and will not be seen on RX side.";
    }
    leaf counters_slice0_ifg0_ifgb_rx_port_21_cgm_tc3_partially_dropped_packets {
      type oc-yang:counter64;
      description
        "RX port cgm ostc3 partial drops counter. Counts packets that were partially dropped and will be seen on RX side.";
    }
    leaf counters_slice0_ifg0_ifgb_rx_port_22_cgm_tc0_dropped_packets {
      type oc-yang:counter64;
      description
        "RX port cgm ostc0 drops counter. Counts packets that were totally dropped and will not be seen on RX side.";
    }
    leaf counters_slice0_ifg0_ifgb_rx_port_22_cgm_tc0_partially_dropped_packets {
      type oc-yang:counter64;
      description
        "RX port cgm ostc0 partial drops counter. Counts packets that were partially dropped and will be seen on RX side.";
    }
    leaf counters_slice0_ifg0_ifgb_rx_port_22_cgm_tc1_dropped_packets {
      type oc-yang:counter64;
      description
        "RX port cgm ostc1 drops counter. Counts packets that were totally dropped and will not be seen on RX side.";
    }
    leaf counters_slice0_ifg0_ifgb_rx_port_22_cgm_tc1_partially_dropped_packets {
      type oc-yang:counter64;
      description
        "RX port cgm ostc1 partial drops counter. Counts packets that were partially dropped and will be seen on RX side.";
    }
    leaf counters_slice0_ifg0_ifgb_rx_port_22_cgm_tc2_dropped_packets {
      type oc-yang:counter64;
      description
        "RX port cgm ostc2 drops counter. Counts packets that were totally dropped and will not be seen on RX side.";
    }
    leaf counters_slice0_ifg0_ifgb_rx_port_22_cgm_tc2_partially_dropped_packets {
      type oc-yang:counter64;
      description
        "RX port cgm ostc2 partial drops counter. Counts packets that were partially dropped and will be seen on RX side.";
    }
    leaf counters_slice0_ifg0_ifgb_rx_port_22_cgm_tc3_dropped_packets {
      type oc-yang:counter64;
      description
        "RX port cgm ostc3 drops counter. Counts packets that were totally dropped and will not be seen on RX side.";
    }
    leaf counters_slice0_ifg0_ifgb_rx_port_22_cgm_tc3_partially_dropped_packets {
      type oc-yang:counter64;
      description
        "RX port cgm ostc3 partial drops counter. Counts packets that were partially dropped and will be seen on RX side.";
    }
    leaf counters_slice0_ifg0_ifgb_rx_port_23_cgm_tc0_dropped_packets {
      type oc-yang:counter64;
      description
        "RX port cgm ostc0 drops counter. Counts packets that were totally dropped and will not be seen on RX side.";
    }
    leaf counters_slice0_ifg0_ifgb_rx_port_23_cgm_tc0_partially_dropped_packets {
      type oc-yang:counter64;
      description
        "RX port cgm ostc0 partial drops counter. Counts packets that were partially dropped and will be seen on RX side.";
    }
    leaf counters_slice0_ifg0_ifgb_rx_port_23_cgm_tc1_dropped_packets {
      type oc-yang:counter64;
      description
        "RX port cgm ostc1 drops counter. Counts packets that were totally dropped and will not be seen on RX side.";
    }
    leaf counters_slice0_ifg0_ifgb_rx_port_23_cgm_tc1_partially_dropped_packets {
      type oc-yang:counter64;
      description
        "RX port cgm ostc1 partial drops counter. Counts packets that were partially dropped and will be seen on RX side.";
    }
    leaf counters_slice0_ifg0_ifgb_rx_port_23_cgm_tc2_dropped_packets {
      type oc-yang:counter64;
      description
        "RX port cgm ostc2 drops counter. Counts packets that were totally dropped and will not be seen on RX side.";
    }
    leaf counters_slice0_ifg0_ifgb_rx_port_23_cgm_tc2_partially_dropped_packets {
      type oc-yang:counter64;
      description
        "RX port cgm ostc2 partial drops counter. Counts packets that were partially dropped and will be seen on RX side.";
    }
    leaf counters_slice0_ifg0_ifgb_rx_port_23_cgm_tc3_dropped_packets {
      type oc-yang:counter64;
      description
        "RX port cgm ostc3 drops counter. Counts packets that were totally dropped and will not be seen on RX side.";
    }
    leaf counters_slice0_ifg0_ifgb_rx_port_23_cgm_tc3_partially_dropped_packets {
      type oc-yang:counter64;
      description
        "RX port cgm ostc3 partial drops counter. Counts packets that were partially dropped and will be seen on RX side.";
    }
    leaf counters_slice0_ifg0_ifgb_rx_port_24_cgm_tc0_dropped_packets {
      type oc-yang:counter64;
      description
        "RX port cgm ostc0 drops counter. Counts packets that were totally dropped and will not be seen on RX side.";
    }
    leaf counters_slice0_ifg0_ifgb_rx_port_24_cgm_tc0_partially_dropped_packets {
      type oc-yang:counter64;
      description
        "RX port cgm ostc0 partial drops counter. Counts packets that were partially dropped and will be seen on RX side.";
    }
    leaf counters_slice0_ifg0_ifgb_rx_port_24_cgm_tc1_dropped_packets {
      type oc-yang:counter64;
      description
        "RX port cgm ostc1 drops counter. Counts packets that were totally dropped and will not be seen on RX side.";
    }
    leaf counters_slice0_ifg0_ifgb_rx_port_24_cgm_tc1_partially_dropped_packets {
      type oc-yang:counter64;
      description
        "RX port cgm ostc1 partial drops counter. Counts packets that were partially dropped and will be seen on RX side.";
    }
    leaf counters_slice0_ifg0_ifgb_rx_port_24_cgm_tc2_dropped_packets {
      type oc-yang:counter64;
      description
        "RX port cgm ostc2 drops counter. Counts packets that were totally dropped and will not be seen on RX side.";
    }
    leaf counters_slice0_ifg0_ifgb_rx_port_24_cgm_tc2_partially_dropped_packets {
      type oc-yang:counter64;
      description
        "RX port cgm ostc2 partial drops counter. Counts packets that were partially dropped and will be seen on RX side.";
    }
    leaf counters_slice0_ifg0_ifgb_rx_port_24_cgm_tc3_dropped_packets {
      type oc-yang:counter64;
      description
        "RX port cgm ostc3 drops counter. Counts packets that were totally dropped and will not be seen on RX side.";
    }
    leaf counters_slice0_ifg0_ifgb_rx_port_24_cgm_tc3_partially_dropped_packets {
      type oc-yang:counter64;
      description
        "RX port cgm ostc3 partial drops counter. Counts packets that were partially dropped and will be seen on RX side.";
    }
    leaf counters_slice0_ifg0_ifgb_rx_port_25_cgm_tc0_dropped_packets {
      type oc-yang:counter64;
      description
        "RX port cgm ostc0 drops counter. Counts packets that were totally dropped and will not be seen on RX side.";
    }
    leaf counters_slice0_ifg0_ifgb_rx_port_25_cgm_tc0_partially_dropped_packets {
      type oc-yang:counter64;
      description
        "RX port cgm ostc0 partial drops counter. Counts packets that were partially dropped and will be seen on RX side.";
    }
    leaf counters_slice0_ifg0_ifgb_rx_port_25_cgm_tc1_dropped_packets {
      type oc-yang:counter64;
      description
        "RX port cgm ostc1 drops counter. Counts packets that were totally dropped and will not be seen on RX side.";
    }
    leaf counters_slice0_ifg0_ifgb_rx_port_25_cgm_tc1_partially_dropped_packets {
      type oc-yang:counter64;
      description
        "RX port cgm ostc1 partial drops counter. Counts packets that were partially dropped and will be seen on RX side.";
    }
    leaf counters_slice0_ifg0_ifgb_rx_port_25_cgm_tc2_dropped_packets {
      type oc-yang:counter64;
      description
        "RX port cgm ostc2 drops counter. Counts packets that were totally dropped and will not be seen on RX side.";
    }
    leaf counters_slice0_ifg0_ifgb_rx_port_25_cgm_tc2_partially_dropped_packets {
      type oc-yang:counter64;
      description
        "RX port cgm ostc2 partial drops counter. Counts packets that were partially dropped and will be seen on RX side.";
    }
    leaf counters_slice0_ifg0_ifgb_rx_port_25_cgm_tc3_dropped_packets {
      type oc-yang:counter64;
      description
        "RX port cgm ostc3 drops counter. Counts packets that were totally dropped and will not be seen on RX side.";
    }
    leaf counters_slice0_ifg0_ifgb_rx_port_25_cgm_tc3_partially_dropped_packets {
      type oc-yang:counter64;
      description
        "RX port cgm ostc3 partial drops counter. Counts packets that were partially dropped and will be seen on RX side.";
    }
    leaf counters_slice0_ifg0_ifgb_rx_port_26_cgm_tc0_dropped_packets {
      type oc-yang:counter64;
      description
        "RX port cgm ostc0 drops counter. Counts packets that were totally dropped and will not be seen on RX side.";
    }
    leaf counters_slice0_ifg0_ifgb_rx_port_26_cgm_tc0_partially_dropped_packets {
      type oc-yang:counter64;
      description
        "RX port cgm ostc0 partial drops counter. Counts packets that were partially dropped and will be seen on RX side.";
    }
    leaf counters_slice0_ifg0_ifgb_rx_port_26_cgm_tc1_dropped_packets {
      type oc-yang:counter64;
      description
        "RX port cgm ostc1 drops counter. Counts packets that were totally dropped and will not be seen on RX side.";
    }
    leaf counters_slice0_ifg0_ifgb_rx_port_26_cgm_tc1_partially_dropped_packets {
      type oc-yang:counter64;
      description
        "RX port cgm ostc1 partial drops counter. Counts packets that were partially dropped and will be seen on RX side.";
    }
    leaf counters_slice0_ifg0_ifgb_rx_port_26_cgm_tc2_dropped_packets {
      type oc-yang:counter64;
      description
        "RX port cgm ostc2 drops counter. Counts packets that were totally dropped and will not be seen on RX side.";
    }
    leaf counters_slice0_ifg0_ifgb_rx_port_26_cgm_tc2_partially_dropped_packets {
      type oc-yang:counter64;
      description
        "RX port cgm ostc2 partial drops counter. Counts packets that were partially dropped and will be seen on RX side.";
    }
    leaf counters_slice0_ifg0_ifgb_rx_port_26_cgm_tc3_dropped_packets {
      type oc-yang:counter64;
      description
        "RX port cgm ostc3 drops counter. Counts packets that were totally dropped and will not be seen on RX side.";
    }
    leaf counters_slice0_ifg0_ifgb_rx_port_26_cgm_tc3_partially_dropped_packets {
      type oc-yang:counter64;
      description
        "RX port cgm ostc3 partial drops counter. Counts packets that were partially dropped and will be seen on RX side.";
    }
    leaf counters_slice0_ifg0_ifgb_rx_port_27_cgm_tc0_dropped_packets {
      type oc-yang:counter64;
      description
        "RX port cgm ostc0 drops counter. Counts packets that were totally dropped and will not be seen on RX side.";
    }
    leaf counters_slice0_ifg0_ifgb_rx_port_27_cgm_tc0_partially_dropped_packets {
      type oc-yang:counter64;
      description
        "RX port cgm ostc0 partial drops counter. Counts packets that were partially dropped and will be seen on RX side.";
    }
    leaf counters_slice0_ifg0_ifgb_rx_port_27_cgm_tc1_dropped_packets {
      type oc-yang:counter64;
      description
        "RX port cgm ostc1 drops counter. Counts packets that were totally dropped and will not be seen on RX side.";
    }
    leaf counters_slice0_ifg0_ifgb_rx_port_27_cgm_tc1_partially_dropped_packets {
      type oc-yang:counter64;
      description
        "RX port cgm ostc1 partial drops counter. Counts packets that were partially dropped and will be seen on RX side.";
    }
    leaf counters_slice0_ifg0_ifgb_rx_port_27_cgm_tc2_dropped_packets {
      type oc-yang:counter64;
      description
        "RX port cgm ostc2 drops counter. Counts packets that were totally dropped and will not be seen on RX side.";
    }
    leaf counters_slice0_ifg0_ifgb_rx_port_27_cgm_tc2_partially_dropped_packets {
      type oc-yang:counter64;
      description
        "RX port cgm ostc2 partial drops counter. Counts packets that were partially dropped and will be seen on RX side.";
    }
    leaf counters_slice0_ifg0_ifgb_rx_port_27_cgm_tc3_dropped_packets {
      type oc-yang:counter64;
      description
        "RX port cgm ostc3 drops counter. Counts packets that were totally dropped and will not be seen on RX side.";
    }
    leaf counters_slice0_ifg0_ifgb_rx_port_27_cgm_tc3_partially_dropped_packets {
      type oc-yang:counter64;
      description
        "RX port cgm ostc3 partial drops counter. Counts packets that were partially dropped and will be seen on RX side.";
    }
    leaf counters_slice0_ifg0_ifgb_rx_port_28_cgm_tc0_dropped_packets {
      type oc-yang:counter64;
      description
        "RX port cgm ostc0 drops counter. Counts packets that were totally dropped and will not be seen on RX side.";
    }
    leaf counters_slice0_ifg0_ifgb_rx_port_28_cgm_tc0_partially_dropped_packets {
      type oc-yang:counter64;
      description
        "RX port cgm ostc0 partial drops counter. Counts packets that were partially dropped and will be seen on RX side.";
    }
    leaf counters_slice0_ifg0_ifgb_rx_port_28_cgm_tc1_dropped_packets {
      type oc-yang:counter64;
      description
        "RX port cgm ostc1 drops counter. Counts packets that were totally dropped and will not be seen on RX side.";
    }
    leaf counters_slice0_ifg0_ifgb_rx_port_28_cgm_tc1_partially_dropped_packets {
      type oc-yang:counter64;
      description
        "RX port cgm ostc1 partial drops counter. Counts packets that were partially dropped and will be seen on RX side.";
    }
    leaf counters_slice0_ifg0_ifgb_rx_port_28_cgm_tc2_dropped_packets {
      type oc-yang:counter64;
      description
        "RX port cgm ostc2 drops counter. Counts packets that were totally dropped and will not be seen on RX side.";
    }
    leaf counters_slice0_ifg0_ifgb_rx_port_28_cgm_tc2_partially_dropped_packets {
      type oc-yang:counter64;
      description
        "RX port cgm ostc2 partial drops counter. Counts packets that were partially dropped and will be seen on RX side.";
    }
    leaf counters_slice0_ifg0_ifgb_rx_port_28_cgm_tc3_dropped_packets {
      type oc-yang:counter64;
      description
        "RX port cgm ostc3 drops counter. Counts packets that were totally dropped and will not be seen on RX side.";
    }
    leaf counters_slice0_ifg0_ifgb_rx_port_28_cgm_tc3_partially_dropped_packets {
      type oc-yang:counter64;
      description
        "RX port cgm ostc3 partial drops counter. Counts packets that were partially dropped and will be seen on RX side.";
    }
    leaf counters_slice0_ifg0_ifgb_rx_port_29_cgm_tc0_dropped_packets {
      type oc-yang:counter64;
      description
        "RX port cgm ostc0 drops counter. Counts packets that were totally dropped and will not be seen on RX side.";
    }
    leaf counters_slice0_ifg0_ifgb_rx_port_29_cgm_tc0_partially_dropped_packets {
      type oc-yang:counter64;
      description
        "RX port cgm ostc0 partial drops counter. Counts packets that were partially dropped and will be seen on RX side.";
    }
    leaf counters_slice0_ifg0_ifgb_rx_port_29_cgm_tc1_dropped_packets {
      type oc-yang:counter64;
      description
        "RX port cgm ostc1 drops counter. Counts packets that were totally dropped and will not be seen on RX side.";
    }
    leaf counters_slice0_ifg0_ifgb_rx_port_29_cgm_tc1_partially_dropped_packets {
      type oc-yang:counter64;
      description
        "RX port cgm ostc1 partial drops counter. Counts packets that were partially dropped and will be seen on RX side.";
    }
    leaf counters_slice0_ifg0_ifgb_rx_port_29_cgm_tc2_dropped_packets {
      type oc-yang:counter64;
      description
        "RX port cgm ostc2 drops counter. Counts packets that were totally dropped and will not be seen on RX side.";
    }
    leaf counters_slice0_ifg0_ifgb_rx_port_29_cgm_tc2_partially_dropped_packets {
      type oc-yang:counter64;
      description
        "RX port cgm ostc2 partial drops counter. Counts packets that were partially dropped and will be seen on RX side.";
    }
    leaf counters_slice0_ifg0_ifgb_rx_port_29_cgm_tc3_dropped_packets {
      type oc-yang:counter64;
      description
        "RX port cgm ostc3 drops counter. Counts packets that were totally dropped and will not be seen on RX side.";
    }
    leaf counters_slice0_ifg0_ifgb_rx_port_29_cgm_tc3_partially_dropped_packets {
      type oc-yang:counter64;
      description
        "RX port cgm ostc3 partial drops counter. Counts packets that were partially dropped and will be seen on RX side.";
    }
    leaf counters_slice0_ifg0_ifgb_rx_port_3_cgm_tc0_dropped_packets {
      type oc-yang:counter64;
      description
        "RX port cgm ostc0 drops counter. Counts packets that were totally dropped and will not be seen on RX side.";
    }
    leaf counters_slice0_ifg0_ifgb_rx_port_3_cgm_tc0_partially_dropped_packets {
      type oc-yang:counter64;
      description
        "RX port cgm ostc0 partial drops counter. Counts packets that were partially dropped and will be seen on RX side.";
    }
    leaf counters_slice0_ifg0_ifgb_rx_port_3_cgm_tc1_dropped_packets {
      type oc-yang:counter64;
      description
        "RX port cgm ostc1 drops counter. Counts packets that were totally dropped and will not be seen on RX side.";
    }
    leaf counters_slice0_ifg0_ifgb_rx_port_3_cgm_tc1_partially_dropped_packets {
      type oc-yang:counter64;
      description
        "RX port cgm ostc1 partial drops counter. Counts packets that were partially dropped and will be seen on RX side.";
    }
    leaf counters_slice0_ifg0_ifgb_rx_port_3_cgm_tc2_dropped_packets {
      type oc-yang:counter64;
      description
        "RX port cgm ostc2 drops counter. Counts packets that were totally dropped and will not be seen on RX side.";
    }
    leaf counters_slice0_ifg0_ifgb_rx_port_3_cgm_tc2_partially_dropped_packets {
      type oc-yang:counter64;
      description
        "RX port cgm ostc2 partial drops counter. Counts packets that were partially dropped and will be seen on RX side.";
    }
    leaf counters_slice0_ifg0_ifgb_rx_port_3_cgm_tc3_dropped_packets {
      type oc-yang:counter64;
      description
        "RX port cgm ostc3 drops counter. Counts packets that were totally dropped and will not be seen on RX side.";
    }
    leaf counters_slice0_ifg0_ifgb_rx_port_3_cgm_tc3_partially_dropped_packets {
      type oc-yang:counter64;
      description
        "RX port cgm ostc3 partial drops counter. Counts packets that were partially dropped and will be seen on RX side.";
    }
    leaf counters_slice0_ifg0_ifgb_rx_port_30_cgm_tc0_dropped_packets {
      type oc-yang:counter64;
      description
        "RX port cgm ostc0 drops counter. Counts packets that were totally dropped and will not be seen on RX side.";
    }
    leaf counters_slice0_ifg0_ifgb_rx_port_30_cgm_tc0_partially_dropped_packets {
      type oc-yang:counter64;
      description
        "RX port cgm ostc0 partial drops counter. Counts packets that were partially dropped and will be seen on RX side.";
    }
    leaf counters_slice0_ifg0_ifgb_rx_port_30_cgm_tc1_dropped_packets {
      type oc-yang:counter64;
      description
        "RX port cgm ostc1 drops counter. Counts packets that were totally dropped and will not be seen on RX side.";
    }
    leaf counters_slice0_ifg0_ifgb_rx_port_30_cgm_tc1_partially_dropped_packets {
      type oc-yang:counter64;
      description
        "RX port cgm ostc1 partial drops counter. Counts packets that were partially dropped and will be seen on RX side.";
    }
    leaf counters_slice0_ifg0_ifgb_rx_port_30_cgm_tc2_dropped_packets {
      type oc-yang:counter64;
      description
        "RX port cgm ostc2 drops counter. Counts packets that were totally dropped and will not be seen on RX side.";
    }
    leaf counters_slice0_ifg0_ifgb_rx_port_30_cgm_tc2_partially_dropped_packets {
      type oc-yang:counter64;
      description
        "RX port cgm ostc2 partial drops counter. Counts packets that were partially dropped and will be seen on RX side.";
    }
    leaf counters_slice0_ifg0_ifgb_rx_port_30_cgm_tc3_dropped_packets {
      type oc-yang:counter64;
      description
        "RX port cgm ostc3 drops counter. Counts packets that were totally dropped and will not be seen on RX side.";
    }
    leaf counters_slice0_ifg0_ifgb_rx_port_30_cgm_tc3_partially_dropped_packets {
      type oc-yang:counter64;
      description
        "RX port cgm ostc3 partial drops counter. Counts packets that were partially dropped and will be seen on RX side.";
    }
    leaf counters_slice0_ifg0_ifgb_rx_port_31_cgm_tc0_dropped_packets {
      type oc-yang:counter64;
      description
        "RX port cgm ostc0 drops counter. Counts packets that were totally dropped and will not be seen on RX side.";
    }
    leaf counters_slice0_ifg0_ifgb_rx_port_31_cgm_tc0_partially_dropped_packets {
      type oc-yang:counter64;
      description
        "RX port cgm ostc0 partial drops counter. Counts packets that were partially dropped and will be seen on RX side.";
    }
    leaf counters_slice0_ifg0_ifgb_rx_port_31_cgm_tc1_dropped_packets {
      type oc-yang:counter64;
      description
        "RX port cgm ostc1 drops counter. Counts packets that were totally dropped and will not be seen on RX side.";
    }
    leaf counters_slice0_ifg0_ifgb_rx_port_31_cgm_tc1_partially_dropped_packets {
      type oc-yang:counter64;
      description
        "RX port cgm ostc1 partial drops counter. Counts packets that were partially dropped and will be seen on RX side.";
    }
    leaf counters_slice0_ifg0_ifgb_rx_port_31_cgm_tc2_dropped_packets {
      type oc-yang:counter64;
      description
        "RX port cgm ostc2 drops counter. Counts packets that were totally dropped and will not be seen on RX side.";
    }
    leaf counters_slice0_ifg0_ifgb_rx_port_31_cgm_tc2_partially_dropped_packets {
      type oc-yang:counter64;
      description
        "RX port cgm ostc2 partial drops counter. Counts packets that were partially dropped and will be seen on RX side.";
    }
    leaf counters_slice0_ifg0_ifgb_rx_port_31_cgm_tc3_dropped_packets {
      type oc-yang:counter64;
      description
        "RX port cgm ostc3 drops counter. Counts packets that were totally dropped and will not be seen on RX side.";
    }
    leaf counters_slice0_ifg0_ifgb_rx_port_31_cgm_tc3_partially_dropped_packets {
      type oc-yang:counter64;
      description
        "RX port cgm ostc3 partial drops counter. Counts packets that were partially dropped and will be seen on RX side.";
    }
    leaf counters_slice0_ifg0_ifgb_rx_port_4_cgm_tc0_dropped_packets {
      type oc-yang:counter64;
      description
        "RX port cgm ostc0 drops counter. Counts packets that were totally dropped and will not be seen on RX side.";
    }
    leaf counters_slice0_ifg0_ifgb_rx_port_4_cgm_tc0_partially_dropped_packets {
      type oc-yang:counter64;
      description
        "RX port cgm ostc0 partial drops counter. Counts packets that were partially dropped and will be seen on RX side.";
    }
    leaf counters_slice0_ifg0_ifgb_rx_port_4_cgm_tc1_dropped_packets {
      type oc-yang:counter64;
      description
        "RX port cgm ostc1 drops counter. Counts packets that were totally dropped and will not be seen on RX side.";
    }
    leaf counters_slice0_ifg0_ifgb_rx_port_4_cgm_tc1_partially_dropped_packets {
      type oc-yang:counter64;
      description
        "RX port cgm ostc1 partial drops counter. Counts packets that were partially dropped and will be seen on RX side.";
    }
    leaf counters_slice0_ifg0_ifgb_rx_port_4_cgm_tc2_dropped_packets {
      type oc-yang:counter64;
      description
        "RX port cgm ostc2 drops counter. Counts packets that were totally dropped and will not be seen on RX side.";
    }
    leaf counters_slice0_ifg0_ifgb_rx_port_4_cgm_tc2_partially_dropped_packets {
      type oc-yang:counter64;
      description
        "RX port cgm ostc2 partial drops counter. Counts packets that were partially dropped and will be seen on RX side.";
    }
    leaf counters_slice0_ifg0_ifgb_rx_port_4_cgm_tc3_dropped_packets {
      type oc-yang:counter64;
      description
        "RX port cgm ostc3 drops counter. Counts packets that were totally dropped and will not be seen on RX side.";
    }
    leaf counters_slice0_ifg0_ifgb_rx_port_4_cgm_tc3_partially_dropped_packets {
      type oc-yang:counter64;
      description
        "RX port cgm ostc3 partial drops counter. Counts packets that were partially dropped and will be seen on RX side.";
    }
    leaf counters_slice0_ifg0_ifgb_rx_port_5_cgm_tc0_dropped_packets {
      type oc-yang:counter64;
      description
        "RX port cgm ostc0 drops counter. Counts packets that were totally dropped and will not be seen on RX side.";
    }
    leaf counters_slice0_ifg0_ifgb_rx_port_5_cgm_tc0_partially_dropped_packets {
      type oc-yang:counter64;
      description
        "RX port cgm ostc0 partial drops counter. Counts packets that were partially dropped and will be seen on RX side.";
    }
    leaf counters_slice0_ifg0_ifgb_rx_port_5_cgm_tc1_dropped_packets {
      type oc-yang:counter64;
      description
        "RX port cgm ostc1 drops counter. Counts packets that were totally dropped and will not be seen on RX side.";
    }
    leaf counters_slice0_ifg0_ifgb_rx_port_5_cgm_tc1_partially_dropped_packets {
      type oc-yang:counter64;
      description
        "RX port cgm ostc1 partial drops counter. Counts packets that were partially dropped and will be seen on RX side.";
    }
    leaf counters_slice0_ifg0_ifgb_rx_port_5_cgm_tc2_dropped_packets {
      type oc-yang:counter64;
      description
        "RX port cgm ostc2 drops counter. Counts packets that were totally dropped and will not be seen on RX side.";
    }
    leaf counters_slice0_ifg0_ifgb_rx_port_5_cgm_tc2_partially_dropped_packets {
      type oc-yang:counter64;
      description
        "RX port cgm ostc2 partial drops counter. Counts packets that were partially dropped and will be seen on RX side.";
    }
    leaf counters_slice0_ifg0_ifgb_rx_port_5_cgm_tc3_dropped_packets {
      type oc-yang:counter64;
      description
        "RX port cgm ostc3 drops counter. Counts packets that were totally dropped and will not be seen on RX side.";
    }
    leaf counters_slice0_ifg0_ifgb_rx_port_5_cgm_tc3_partially_dropped_packets {
      type oc-yang:counter64;
      description
        "RX port cgm ostc3 partial drops counter. Counts packets that were partially dropped and will be seen on RX side.";
    }
    leaf counters_slice0_ifg0_ifgb_rx_port_6_cgm_tc0_dropped_packets {
      type oc-yang:counter64;
      description
        "RX port cgm ostc0 drops counter. Counts packets that were totally dropped and will not be seen on RX side.";
    }
    leaf counters_slice0_ifg0_ifgb_rx_port_6_cgm_tc0_partially_dropped_packets {
      type oc-yang:counter64;
      description
        "RX port cgm ostc0 partial drops counter. Counts packets that were partially dropped and will be seen on RX side.";
    }
    leaf counters_slice0_ifg0_ifgb_rx_port_6_cgm_tc1_dropped_packets {
      type oc-yang:counter64;
      description
        "RX port cgm ostc1 drops counter. Counts packets that were totally dropped and will not be seen on RX side.";
    }
    leaf counters_slice0_ifg0_ifgb_rx_port_6_cgm_tc1_partially_dropped_packets {
      type oc-yang:counter64;
      description
        "RX port cgm ostc1 partial drops counter. Counts packets that were partially dropped and will be seen on RX side.";
    }
    leaf counters_slice0_ifg0_ifgb_rx_port_6_cgm_tc2_dropped_packets {
      type oc-yang:counter64;
      description
        "RX port cgm ostc2 drops counter. Counts packets that were totally dropped and will not be seen on RX side.";
    }
    leaf counters_slice0_ifg0_ifgb_rx_port_6_cgm_tc2_partially_dropped_packets {
      type oc-yang:counter64;
      description
        "RX port cgm ostc2 partial drops counter. Counts packets that were partially dropped and will be seen on RX side.";
    }
    leaf counters_slice0_ifg0_ifgb_rx_port_6_cgm_tc3_dropped_packets {
      type oc-yang:counter64;
      description
        "RX port cgm ostc3 drops counter. Counts packets that were totally dropped and will not be seen on RX side.";
    }
    leaf counters_slice0_ifg0_ifgb_rx_port_6_cgm_tc3_partially_dropped_packets {
      type oc-yang:counter64;
      description
        "RX port cgm ostc3 partial drops counter. Counts packets that were partially dropped and will be seen on RX side.";
    }
    leaf counters_slice0_ifg0_ifgb_rx_port_7_cgm_tc0_dropped_packets {
      type oc-yang:counter64;
      description
        "RX port cgm ostc0 drops counter. Counts packets that were totally dropped and will not be seen on RX side.";
    }
    leaf counters_slice0_ifg0_ifgb_rx_port_7_cgm_tc0_partially_dropped_packets {
      type oc-yang:counter64;
      description
        "RX port cgm ostc0 partial drops counter. Counts packets that were partially dropped and will be seen on RX side.";
    }
    leaf counters_slice0_ifg0_ifgb_rx_port_7_cgm_tc1_dropped_packets {
      type oc-yang:counter64;
      description
        "RX port cgm ostc1 drops counter. Counts packets that were totally dropped and will not be seen on RX side.";
    }
    leaf counters_slice0_ifg0_ifgb_rx_port_7_cgm_tc1_partially_dropped_packets {
      type oc-yang:counter64;
      description
        "RX port cgm ostc1 partial drops counter. Counts packets that were partially dropped and will be seen on RX side.";
    }
    leaf counters_slice0_ifg0_ifgb_rx_port_7_cgm_tc2_dropped_packets {
      type oc-yang:counter64;
      description
        "RX port cgm ostc2 drops counter. Counts packets that were totally dropped and will not be seen on RX side.";
    }
    leaf counters_slice0_ifg0_ifgb_rx_port_7_cgm_tc2_partially_dropped_packets {
      type oc-yang:counter64;
      description
        "RX port cgm ostc2 partial drops counter. Counts packets that were partially dropped and will be seen on RX side.";
    }
    leaf counters_slice0_ifg0_ifgb_rx_port_7_cgm_tc3_dropped_packets {
      type oc-yang:counter64;
      description
        "RX port cgm ostc3 drops counter. Counts packets that were totally dropped and will not be seen on RX side.";
    }
    leaf counters_slice0_ifg0_ifgb_rx_port_7_cgm_tc3_partially_dropped_packets {
      type oc-yang:counter64;
      description
        "RX port cgm ostc3 partial drops counter. Counts packets that were partially dropped and will be seen on RX side.";
    }
    leaf counters_slice0_ifg0_ifgb_rx_port_8_cgm_tc0_dropped_packets {
      type oc-yang:counter64;
      description
        "RX port cgm ostc0 drops counter. Counts packets that were totally dropped and will not be seen on RX side.";
    }
    leaf counters_slice0_ifg0_ifgb_rx_port_8_cgm_tc0_partially_dropped_packets {
      type oc-yang:counter64;
      description
        "RX port cgm ostc0 partial drops counter. Counts packets that were partially dropped and will be seen on RX side.";
    }
    leaf counters_slice0_ifg0_ifgb_rx_port_8_cgm_tc1_dropped_packets {
      type oc-yang:counter64;
      description
        "RX port cgm ostc1 drops counter. Counts packets that were totally dropped and will not be seen on RX side.";
    }
    leaf counters_slice0_ifg0_ifgb_rx_port_8_cgm_tc1_partially_dropped_packets {
      type oc-yang:counter64;
      description
        "RX port cgm ostc1 partial drops counter. Counts packets that were partially dropped and will be seen on RX side.";
    }
    leaf counters_slice0_ifg0_ifgb_rx_port_8_cgm_tc2_dropped_packets {
      type oc-yang:counter64;
      description
        "RX port cgm ostc2 drops counter. Counts packets that were totally dropped and will not be seen on RX side.";
    }
    leaf counters_slice0_ifg0_ifgb_rx_port_8_cgm_tc2_partially_dropped_packets {
      type oc-yang:counter64;
      description
        "RX port cgm ostc2 partial drops counter. Counts packets that were partially dropped and will be seen on RX side.";
    }
    leaf counters_slice0_ifg0_ifgb_rx_port_8_cgm_tc3_dropped_packets {
      type oc-yang:counter64;
      description
        "RX port cgm ostc3 drops counter. Counts packets that were totally dropped and will not be seen on RX side.";
    }
    leaf counters_slice0_ifg0_ifgb_rx_port_8_cgm_tc3_partially_dropped_packets {
      type oc-yang:counter64;
      description
        "RX port cgm ostc3 partial drops counter. Counts packets that were partially dropped and will be seen on RX side.";
    }
    leaf counters_slice0_ifg0_ifgb_rx_port_9_cgm_tc0_dropped_packets {
      type oc-yang:counter64;
      description
        "RX port cgm ostc0 drops counter. Counts packets that were totally dropped and will not be seen on RX side.";
    }
    leaf counters_slice0_ifg0_ifgb_rx_port_9_cgm_tc0_partially_dropped_packets {
      type oc-yang:counter64;
      description
        "RX port cgm ostc0 partial drops counter. Counts packets that were partially dropped and will be seen on RX side.";
    }
    leaf counters_slice0_ifg0_ifgb_rx_port_9_cgm_tc1_dropped_packets {
      type oc-yang:counter64;
      description
        "RX port cgm ostc1 drops counter. Counts packets that were totally dropped and will not be seen on RX side.";
    }
    leaf counters_slice0_ifg0_ifgb_rx_port_9_cgm_tc1_partially_dropped_packets {
      type oc-yang:counter64;
      description
        "RX port cgm ostc1 partial drops counter. Counts packets that were partially dropped and will be seen on RX side.";
    }
    leaf counters_slice0_ifg0_ifgb_rx_port_9_cgm_tc2_dropped_packets {
      type oc-yang:counter64;
      description
        "RX port cgm ostc2 drops counter. Counts packets that were totally dropped and will not be seen on RX side.";
    }
    leaf counters_slice0_ifg0_ifgb_rx_port_9_cgm_tc2_partially_dropped_packets {
      type oc-yang:counter64;
      description
        "RX port cgm ostc2 partial drops counter. Counts packets that were partially dropped and will be seen on RX side.";
    }
    leaf counters_slice0_ifg0_ifgb_rx_port_9_cgm_tc3_dropped_packets {
      type oc-yang:counter64;
      description
        "RX port cgm ostc3 drops counter. Counts packets that were totally dropped and will not be seen on RX side.";
    }
    leaf counters_slice0_ifg0_ifgb_rx_port_9_cgm_tc3_partially_dropped_packets {
      type oc-yang:counter64;
      description
        "RX port cgm ostc3 partial drops counter. Counts packets that were partially dropped and will be seen on RX side.";
    }
    leaf counters_slice0_ifg1_ifgb_rx_port_0_cgm_tc0_dropped_packets {
      type oc-yang:counter64;
      description
        "RX port cgm ostc0 drops counter. Counts packets that were totally dropped and will not be seen on RX side.";
    }
    leaf counters_slice0_ifg1_ifgb_rx_port_0_cgm_tc0_partially_dropped_packets {
      type oc-yang:counter64;
      description
        "RX port cgm ostc0 partial drops counter. Counts packets that were partially dropped and will be seen on RX side.";
    }
    leaf counters_slice0_ifg1_ifgb_rx_port_0_cgm_tc1_dropped_packets {
      type oc-yang:counter64;
      description
        "RX port cgm ostc1 drops counter. Counts packets that were totally dropped and will not be seen on RX side.";
    }
    leaf counters_slice0_ifg1_ifgb_rx_port_0_cgm_tc1_partially_dropped_packets {
      type oc-yang:counter64;
      description
        "RX port cgm ostc1 partial drops counter. Counts packets that were partially dropped and will be seen on RX side.";
    }
    leaf counters_slice0_ifg1_ifgb_rx_port_0_cgm_tc2_dropped_packets {
      type oc-yang:counter64;
      description
        "RX port cgm ostc2 drops counter. Counts packets that were totally dropped and will not be seen on RX side.";
    }
    leaf counters_slice0_ifg1_ifgb_rx_port_0_cgm_tc2_partially_dropped_packets {
      type oc-yang:counter64;
      description
        "RX port cgm ostc2 partial drops counter. Counts packets that were partially dropped and will be seen on RX side.";
    }
    leaf counters_slice0_ifg1_ifgb_rx_port_0_cgm_tc3_dropped_packets {
      type oc-yang:counter64;
      description
        "RX port cgm ostc3 drops counter. Counts packets that were totally dropped and will not be seen on RX side.";
    }
    leaf counters_slice0_ifg1_ifgb_rx_port_0_cgm_tc3_partially_dropped_packets {
      type oc-yang:counter64;
      description
        "RX port cgm ostc3 partial drops counter. Counts packets that were partially dropped and will be seen on RX side.";
    }
    leaf counters_slice0_ifg1_ifgb_rx_port_1_cgm_tc0_dropped_packets {
      type oc-yang:counter64;
      description
        "RX port cgm ostc0 drops counter. Counts packets that were totally dropped and will not be seen on RX side.";
    }
    leaf counters_slice0_ifg1_ifgb_rx_port_1_cgm_tc0_partially_dropped_packets {
      type oc-yang:counter64;
      description
        "RX port cgm ostc0 partial drops counter. Counts packets that were partially dropped and will be seen on RX side.";
    }
    leaf counters_slice0_ifg1_ifgb_rx_port_1_cgm_tc1_dropped_packets {
      type oc-yang:counter64;
      description
        "RX port cgm ostc1 drops counter. Counts packets that were totally dropped and will not be seen on RX side.";
    }
    leaf counters_slice0_ifg1_ifgb_rx_port_1_cgm_tc1_partially_dropped_packets {
      type oc-yang:counter64;
      description
        "RX port cgm ostc1 partial drops counter. Counts packets that were partially dropped and will be seen on RX side.";
    }
    leaf counters_slice0_ifg1_ifgb_rx_port_1_cgm_tc2_dropped_packets {
      type oc-yang:counter64;
      description
        "RX port cgm ostc2 drops counter. Counts packets that were totally dropped and will not be seen on RX side.";
    }
    leaf counters_slice0_ifg1_ifgb_rx_port_1_cgm_tc2_partially_dropped_packets {
      type oc-yang:counter64;
      description
        "RX port cgm ostc2 partial drops counter. Counts packets that were partially dropped and will be seen on RX side.";
    }
    leaf counters_slice0_ifg1_ifgb_rx_port_1_cgm_tc3_dropped_packets {
      type oc-yang:counter64;
      description
        "RX port cgm ostc3 drops counter. Counts packets that were totally dropped and will not be seen on RX side.";
    }
    leaf counters_slice0_ifg1_ifgb_rx_port_1_cgm_tc3_partially_dropped_packets {
      type oc-yang:counter64;
      description
        "RX port cgm ostc3 partial drops counter. Counts packets that were partially dropped and will be seen on RX side.";
    }
    leaf counters_slice0_ifg1_ifgb_rx_port_10_cgm_tc0_dropped_packets {
      type oc-yang:counter64;
      description
        "RX port cgm ostc0 drops counter. Counts packets that were totally dropped and will not be seen on RX side.";
    }
    leaf counters_slice0_ifg1_ifgb_rx_port_10_cgm_tc0_partially_dropped_packets {
      type oc-yang:counter64;
      description
        "RX port cgm ostc0 partial drops counter. Counts packets that were partially dropped and will be seen on RX side.";
    }
    leaf counters_slice0_ifg1_ifgb_rx_port_10_cgm_tc1_dropped_packets {
      type oc-yang:counter64;
      description
        "RX port cgm ostc1 drops counter. Counts packets that were totally dropped and will not be seen on RX side.";
    }
    leaf counters_slice0_ifg1_ifgb_rx_port_10_cgm_tc1_partially_dropped_packets {
      type oc-yang:counter64;
      description
        "RX port cgm ostc1 partial drops counter. Counts packets that were partially dropped and will be seen on RX side.";
    }
    leaf counters_slice0_ifg1_ifgb_rx_port_10_cgm_tc2_dropped_packets {
      type oc-yang:counter64;
      description
        "RX port cgm ostc2 drops counter. Counts packets that were totally dropped and will not be seen on RX side.";
    }
    leaf counters_slice0_ifg1_ifgb_rx_port_10_cgm_tc2_partially_dropped_packets {
      type oc-yang:counter64;
      description
        "RX port cgm ostc2 partial drops counter. Counts packets that were partially dropped and will be seen on RX side.";
    }
    leaf counters_slice0_ifg1_ifgb_rx_port_10_cgm_tc3_dropped_packets {
      type oc-yang:counter64;
      description
        "RX port cgm ostc3 drops counter. Counts packets that were totally dropped and will not be seen on RX side.";
    }
    leaf counters_slice0_ifg1_ifgb_rx_port_10_cgm_tc3_partially_dropped_packets {
      type oc-yang:counter64;
      description
        "RX port cgm ostc3 partial drops counter. Counts packets that were partially dropped and will be seen on RX side.";
    }
    leaf counters_slice0_ifg1_ifgb_rx_port_11_cgm_tc0_dropped_packets {
      type oc-yang:counter64;
      description
        "RX port cgm ostc0 drops counter. Counts packets that were totally dropped and will not be seen on RX side.";
    }
    leaf counters_slice0_ifg1_ifgb_rx_port_11_cgm_tc0_partially_dropped_packets {
      type oc-yang:counter64;
      description
        "RX port cgm ostc0 partial drops counter. Counts packets that were partially dropped and will be seen on RX side.";
    }
    leaf counters_slice0_ifg1_ifgb_rx_port_11_cgm_tc1_dropped_packets {
      type oc-yang:counter64;
      description
        "RX port cgm ostc1 drops counter. Counts packets that were totally dropped and will not be seen on RX side.";
    }
    leaf counters_slice0_ifg1_ifgb_rx_port_11_cgm_tc1_partially_dropped_packets {
      type oc-yang:counter64;
      description
        "RX port cgm ostc1 partial drops counter. Counts packets that were partially dropped and will be seen on RX side.";
    }
    leaf counters_slice0_ifg1_ifgb_rx_port_11_cgm_tc2_dropped_packets {
      type oc-yang:counter64;
      description
        "RX port cgm ostc2 drops counter. Counts packets that were totally dropped and will not be seen on RX side.";
    }
    leaf counters_slice0_ifg1_ifgb_rx_port_11_cgm_tc2_partially_dropped_packets {
      type oc-yang:counter64;
      description
        "RX port cgm ostc2 partial drops counter. Counts packets that were partially dropped and will be seen on RX side.";
    }
    leaf counters_slice0_ifg1_ifgb_rx_port_11_cgm_tc3_dropped_packets {
      type oc-yang:counter64;
      description
        "RX port cgm ostc3 drops counter. Counts packets that were totally dropped and will not be seen on RX side.";
    }
    leaf counters_slice0_ifg1_ifgb_rx_port_11_cgm_tc3_partially_dropped_packets {
      type oc-yang:counter64;
      description
        "RX port cgm ostc3 partial drops counter. Counts packets that were partially dropped and will be seen on RX side.";
    }
    leaf counters_slice0_ifg1_ifgb_rx_port_12_cgm_tc0_dropped_packets {
      type oc-yang:counter64;
      description
        "RX port cgm ostc0 drops counter. Counts packets that were totally dropped and will not be seen on RX side.";
    }
    leaf counters_slice0_ifg1_ifgb_rx_port_12_cgm_tc0_partially_dropped_packets {
      type oc-yang:counter64;
      description
        "RX port cgm ostc0 partial drops counter. Counts packets that were partially dropped and will be seen on RX side.";
    }
    leaf counters_slice0_ifg1_ifgb_rx_port_12_cgm_tc1_dropped_packets {
      type oc-yang:counter64;
      description
        "RX port cgm ostc1 drops counter. Counts packets that were totally dropped and will not be seen on RX side.";
    }
    leaf counters_slice0_ifg1_ifgb_rx_port_12_cgm_tc1_partially_dropped_packets {
      type oc-yang:counter64;
      description
        "RX port cgm ostc1 partial drops counter. Counts packets that were partially dropped and will be seen on RX side.";
    }
    leaf counters_slice0_ifg1_ifgb_rx_port_12_cgm_tc2_dropped_packets {
      type oc-yang:counter64;
      description
        "RX port cgm ostc2 drops counter. Counts packets that were totally dropped and will not be seen on RX side.";
    }
    leaf counters_slice0_ifg1_ifgb_rx_port_12_cgm_tc2_partially_dropped_packets {
      type oc-yang:counter64;
      description
        "RX port cgm ostc2 partial drops counter. Counts packets that were partially dropped and will be seen on RX side.";
    }
    leaf counters_slice0_ifg1_ifgb_rx_port_12_cgm_tc3_dropped_packets {
      type oc-yang:counter64;
      description
        "RX port cgm ostc3 drops counter. Counts packets that were totally dropped and will not be seen on RX side.";
    }
    leaf counters_slice0_ifg1_ifgb_rx_port_12_cgm_tc3_partially_dropped_packets {
      type oc-yang:counter64;
      description
        "RX port cgm ostc3 partial drops counter. Counts packets that were partially dropped and will be seen on RX side.";
    }
    leaf counters_slice0_ifg1_ifgb_rx_port_13_cgm_tc0_dropped_packets {
      type oc-yang:counter64;
      description
        "RX port cgm ostc0 drops counter. Counts packets that were totally dropped and will not be seen on RX side.";
    }
    leaf counters_slice0_ifg1_ifgb_rx_port_13_cgm_tc0_partially_dropped_packets {
      type oc-yang:counter64;
      description
        "RX port cgm ostc0 partial drops counter. Counts packets that were partially dropped and will be seen on RX side.";
    }
    leaf counters_slice0_ifg1_ifgb_rx_port_13_cgm_tc1_dropped_packets {
      type oc-yang:counter64;
      description
        "RX port cgm ostc1 drops counter. Counts packets that were totally dropped and will not be seen on RX side.";
    }
    leaf counters_slice0_ifg1_ifgb_rx_port_13_cgm_tc1_partially_dropped_packets {
      type oc-yang:counter64;
      description
        "RX port cgm ostc1 partial drops counter. Counts packets that were partially dropped and will be seen on RX side.";
    }
    leaf counters_slice0_ifg1_ifgb_rx_port_13_cgm_tc2_dropped_packets {
      type oc-yang:counter64;
      description
        "RX port cgm ostc2 drops counter. Counts packets that were totally dropped and will not be seen on RX side.";
    }
    leaf counters_slice0_ifg1_ifgb_rx_port_13_cgm_tc2_partially_dropped_packets {
      type oc-yang:counter64;
      description
        "RX port cgm ostc2 partial drops counter. Counts packets that were partially dropped and will be seen on RX side.";
    }
    leaf counters_slice0_ifg1_ifgb_rx_port_13_cgm_tc3_dropped_packets {
      type oc-yang:counter64;
      description
        "RX port cgm ostc3 drops counter. Counts packets that were totally dropped and will not be seen on RX side.";
    }
    leaf counters_slice0_ifg1_ifgb_rx_port_13_cgm_tc3_partially_dropped_packets {
      type oc-yang:counter64;
      description
        "RX port cgm ostc3 partial drops counter. Counts packets that were partially dropped and will be seen on RX side.";
    }
    leaf counters_slice0_ifg1_ifgb_rx_port_14_cgm_tc0_dropped_packets {
      type oc-yang:counter64;
      description
        "RX port cgm ostc0 drops counter. Counts packets that were totally dropped and will not be seen on RX side.";
    }
    leaf counters_slice0_ifg1_ifgb_rx_port_14_cgm_tc0_partially_dropped_packets {
      type oc-yang:counter64;
      description
        "RX port cgm ostc0 partial drops counter. Counts packets that were partially dropped and will be seen on RX side.";
    }
    leaf counters_slice0_ifg1_ifgb_rx_port_14_cgm_tc1_dropped_packets {
      type oc-yang:counter64;
      description
        "RX port cgm ostc1 drops counter. Counts packets that were totally dropped and will not be seen on RX side.";
    }
    leaf counters_slice0_ifg1_ifgb_rx_port_14_cgm_tc1_partially_dropped_packets {
      type oc-yang:counter64;
      description
        "RX port cgm ostc1 partial drops counter. Counts packets that were partially dropped and will be seen on RX side.";
    }
    leaf counters_slice0_ifg1_ifgb_rx_port_14_cgm_tc2_dropped_packets {
      type oc-yang:counter64;
      description
        "RX port cgm ostc2 drops counter. Counts packets that were totally dropped and will not be seen on RX side.";
    }
    leaf counters_slice0_ifg1_ifgb_rx_port_14_cgm_tc2_partially_dropped_packets {
      type oc-yang:counter64;
      description
        "RX port cgm ostc2 partial drops counter. Counts packets that were partially dropped and will be seen on RX side.";
    }
    leaf counters_slice0_ifg1_ifgb_rx_port_14_cgm_tc3_dropped_packets {
      type oc-yang:counter64;
      description
        "RX port cgm ostc3 drops counter. Counts packets that were totally dropped and will not be seen on RX side.";
    }
    leaf counters_slice0_ifg1_ifgb_rx_port_14_cgm_tc3_partially_dropped_packets {
      type oc-yang:counter64;
      description
        "RX port cgm ostc3 partial drops counter. Counts packets that were partially dropped and will be seen on RX side.";
    }
    leaf counters_slice0_ifg1_ifgb_rx_port_15_cgm_tc0_dropped_packets {
      type oc-yang:counter64;
      description
        "RX port cgm ostc0 drops counter. Counts packets that were totally dropped and will not be seen on RX side.";
    }
    leaf counters_slice0_ifg1_ifgb_rx_port_15_cgm_tc0_partially_dropped_packets {
      type oc-yang:counter64;
      description
        "RX port cgm ostc0 partial drops counter. Counts packets that were partially dropped and will be seen on RX side.";
    }
    leaf counters_slice0_ifg1_ifgb_rx_port_15_cgm_tc1_dropped_packets {
      type oc-yang:counter64;
      description
        "RX port cgm ostc1 drops counter. Counts packets that were totally dropped and will not be seen on RX side.";
    }
    leaf counters_slice0_ifg1_ifgb_rx_port_15_cgm_tc1_partially_dropped_packets {
      type oc-yang:counter64;
      description
        "RX port cgm ostc1 partial drops counter. Counts packets that were partially dropped and will be seen on RX side.";
    }
    leaf counters_slice0_ifg1_ifgb_rx_port_15_cgm_tc2_dropped_packets {
      type oc-yang:counter64;
      description
        "RX port cgm ostc2 drops counter. Counts packets that were totally dropped and will not be seen on RX side.";
    }
    leaf counters_slice0_ifg1_ifgb_rx_port_15_cgm_tc2_partially_dropped_packets {
      type oc-yang:counter64;
      description
        "RX port cgm ostc2 partial drops counter. Counts packets that were partially dropped and will be seen on RX side.";
    }
    leaf counters_slice0_ifg1_ifgb_rx_port_15_cgm_tc3_dropped_packets {
      type oc-yang:counter64;
      description
        "RX port cgm ostc3 drops counter. Counts packets that were totally dropped and will not be seen on RX side.";
    }
    leaf counters_slice0_ifg1_ifgb_rx_port_15_cgm_tc3_partially_dropped_packets {
      type oc-yang:counter64;
      description
        "RX port cgm ostc3 partial drops counter. Counts packets that were partially dropped and will be seen on RX side.";
    }
    leaf counters_slice0_ifg1_ifgb_rx_port_16_cgm_tc0_dropped_packets {
      type oc-yang:counter64;
      description
        "RX port cgm ostc0 drops counter. Counts packets that were totally dropped and will not be seen on RX side.";
    }
    leaf counters_slice0_ifg1_ifgb_rx_port_16_cgm_tc0_partially_dropped_packets {
      type oc-yang:counter64;
      description
        "RX port cgm ostc0 partial drops counter. Counts packets that were partially dropped and will be seen on RX side.";
    }
    leaf counters_slice0_ifg1_ifgb_rx_port_16_cgm_tc1_dropped_packets {
      type oc-yang:counter64;
      description
        "RX port cgm ostc1 drops counter. Counts packets that were totally dropped and will not be seen on RX side.";
    }
    leaf counters_slice0_ifg1_ifgb_rx_port_16_cgm_tc1_partially_dropped_packets {
      type oc-yang:counter64;
      description
        "RX port cgm ostc1 partial drops counter. Counts packets that were partially dropped and will be seen on RX side.";
    }
    leaf counters_slice0_ifg1_ifgb_rx_port_16_cgm_tc2_dropped_packets {
      type oc-yang:counter64;
      description
        "RX port cgm ostc2 drops counter. Counts packets that were totally dropped and will not be seen on RX side.";
    }
    leaf counters_slice0_ifg1_ifgb_rx_port_16_cgm_tc2_partially_dropped_packets {
      type oc-yang:counter64;
      description
        "RX port cgm ostc2 partial drops counter. Counts packets that were partially dropped and will be seen on RX side.";
    }
    leaf counters_slice0_ifg1_ifgb_rx_port_16_cgm_tc3_dropped_packets {
      type oc-yang:counter64;
      description
        "RX port cgm ostc3 drops counter. Counts packets that were totally dropped and will not be seen on RX side.";
    }
    leaf counters_slice0_ifg1_ifgb_rx_port_16_cgm_tc3_partially_dropped_packets {
      type oc-yang:counter64;
      description
        "RX port cgm ostc3 partial drops counter. Counts packets that were partially dropped and will be seen on RX side.";
    }
    leaf counters_slice0_ifg1_ifgb_rx_port_17_cgm_tc0_dropped_packets {
      type oc-yang:counter64;
      description
        "RX port cgm ostc0 drops counter. Counts packets that were totally dropped and will not be seen on RX side.";
    }
    leaf counters_slice0_ifg1_ifgb_rx_port_17_cgm_tc0_partially_dropped_packets {
      type oc-yang:counter64;
      description
        "RX port cgm ostc0 partial drops counter. Counts packets that were partially dropped and will be seen on RX side.";
    }
    leaf counters_slice0_ifg1_ifgb_rx_port_17_cgm_tc1_dropped_packets {
      type oc-yang:counter64;
      description
        "RX port cgm ostc1 drops counter. Counts packets that were totally dropped and will not be seen on RX side.";
    }
    leaf counters_slice0_ifg1_ifgb_rx_port_17_cgm_tc1_partially_dropped_packets {
      type oc-yang:counter64;
      description
        "RX port cgm ostc1 partial drops counter. Counts packets that were partially dropped and will be seen on RX side.";
    }
    leaf counters_slice0_ifg1_ifgb_rx_port_17_cgm_tc2_dropped_packets {
      type oc-yang:counter64;
      description
        "RX port cgm ostc2 drops counter. Counts packets that were totally dropped and will not be seen on RX side.";
    }
    leaf counters_slice0_ifg1_ifgb_rx_port_17_cgm_tc2_partially_dropped_packets {
      type oc-yang:counter64;
      description
        "RX port cgm ostc2 partial drops counter. Counts packets that were partially dropped and will be seen on RX side.";
    }
    leaf counters_slice0_ifg1_ifgb_rx_port_17_cgm_tc3_dropped_packets {
      type oc-yang:counter64;
      description
        "RX port cgm ostc3 drops counter. Counts packets that were totally dropped and will not be seen on RX side.";
    }
    leaf counters_slice0_ifg1_ifgb_rx_port_17_cgm_tc3_partially_dropped_packets {
      type oc-yang:counter64;
      description
        "RX port cgm ostc3 partial drops counter. Counts packets that were partially dropped and will be seen on RX side.";
    }
    leaf counters_slice0_ifg1_ifgb_rx_port_18_cgm_tc0_dropped_packets {
      type oc-yang:counter64;
      description
        "RX port cgm ostc0 drops counter. Counts packets that were totally dropped and will not be seen on RX side.";
    }
    leaf counters_slice0_ifg1_ifgb_rx_port_18_cgm_tc0_partially_dropped_packets {
      type oc-yang:counter64;
      description
        "RX port cgm ostc0 partial drops counter. Counts packets that were partially dropped and will be seen on RX side.";
    }
    leaf counters_slice0_ifg1_ifgb_rx_port_18_cgm_tc1_dropped_packets {
      type oc-yang:counter64;
      description
        "RX port cgm ostc1 drops counter. Counts packets that were totally dropped and will not be seen on RX side.";
    }
    leaf counters_slice0_ifg1_ifgb_rx_port_18_cgm_tc1_partially_dropped_packets {
      type oc-yang:counter64;
      description
        "RX port cgm ostc1 partial drops counter. Counts packets that were partially dropped and will be seen on RX side.";
    }
    leaf counters_slice0_ifg1_ifgb_rx_port_18_cgm_tc2_dropped_packets {
      type oc-yang:counter64;
      description
        "RX port cgm ostc2 drops counter. Counts packets that were totally dropped and will not be seen on RX side.";
    }
    leaf counters_slice0_ifg1_ifgb_rx_port_18_cgm_tc2_partially_dropped_packets {
      type oc-yang:counter64;
      description
        "RX port cgm ostc2 partial drops counter. Counts packets that were partially dropped and will be seen on RX side.";
    }
    leaf counters_slice0_ifg1_ifgb_rx_port_18_cgm_tc3_dropped_packets {
      type oc-yang:counter64;
      description
        "RX port cgm ostc3 drops counter. Counts packets that were totally dropped and will not be seen on RX side.";
    }
    leaf counters_slice0_ifg1_ifgb_rx_port_18_cgm_tc3_partially_dropped_packets {
      type oc-yang:counter64;
      description
        "RX port cgm ostc3 partial drops counter. Counts packets that were partially dropped and will be seen on RX side.";
    }
    leaf counters_slice0_ifg1_ifgb_rx_port_19_cgm_tc0_dropped_packets {
      type oc-yang:counter64;
      description
        "RX port cgm ostc0 drops counter. Counts packets that were totally dropped and will not be seen on RX side.";
    }
    leaf counters_slice0_ifg1_ifgb_rx_port_19_cgm_tc0_partially_dropped_packets {
      type oc-yang:counter64;
      description
        "RX port cgm ostc0 partial drops counter. Counts packets that were partially dropped and will be seen on RX side.";
    }
    leaf counters_slice0_ifg1_ifgb_rx_port_19_cgm_tc1_dropped_packets {
      type oc-yang:counter64;
      description
        "RX port cgm ostc1 drops counter. Counts packets that were totally dropped and will not be seen on RX side.";
    }
    leaf counters_slice0_ifg1_ifgb_rx_port_19_cgm_tc1_partially_dropped_packets {
      type oc-yang:counter64;
      description
        "RX port cgm ostc1 partial drops counter. Counts packets that were partially dropped and will be seen on RX side.";
    }
    leaf counters_slice0_ifg1_ifgb_rx_port_19_cgm_tc2_dropped_packets {
      type oc-yang:counter64;
      description
        "RX port cgm ostc2 drops counter. Counts packets that were totally dropped and will not be seen on RX side.";
    }
    leaf counters_slice0_ifg1_ifgb_rx_port_19_cgm_tc2_partially_dropped_packets {
      type oc-yang:counter64;
      description
        "RX port cgm ostc2 partial drops counter. Counts packets that were partially dropped and will be seen on RX side.";
    }
    leaf counters_slice0_ifg1_ifgb_rx_port_19_cgm_tc3_dropped_packets {
      type oc-yang:counter64;
      description
        "RX port cgm ostc3 drops counter. Counts packets that were totally dropped and will not be seen on RX side.";
    }
    leaf counters_slice0_ifg1_ifgb_rx_port_19_cgm_tc3_partially_dropped_packets {
      type oc-yang:counter64;
      description
        "RX port cgm ostc3 partial drops counter. Counts packets that were partially dropped and will be seen on RX side.";
    }
    leaf counters_slice0_ifg1_ifgb_rx_port_2_cgm_tc0_dropped_packets {
      type oc-yang:counter64;
      description
        "RX port cgm ostc0 drops counter. Counts packets that were totally dropped and will not be seen on RX side.";
    }
    leaf counters_slice0_ifg1_ifgb_rx_port_2_cgm_tc0_partially_dropped_packets {
      type oc-yang:counter64;
      description
        "RX port cgm ostc0 partial drops counter. Counts packets that were partially dropped and will be seen on RX side.";
    }
    leaf counters_slice0_ifg1_ifgb_rx_port_2_cgm_tc1_dropped_packets {
      type oc-yang:counter64;
      description
        "RX port cgm ostc1 drops counter. Counts packets that were totally dropped and will not be seen on RX side.";
    }
    leaf counters_slice0_ifg1_ifgb_rx_port_2_cgm_tc1_partially_dropped_packets {
      type oc-yang:counter64;
      description
        "RX port cgm ostc1 partial drops counter. Counts packets that were partially dropped and will be seen on RX side.";
    }
    leaf counters_slice0_ifg1_ifgb_rx_port_2_cgm_tc2_dropped_packets {
      type oc-yang:counter64;
      description
        "RX port cgm ostc2 drops counter. Counts packets that were totally dropped and will not be seen on RX side.";
    }
    leaf counters_slice0_ifg1_ifgb_rx_port_2_cgm_tc2_partially_dropped_packets {
      type oc-yang:counter64;
      description
        "RX port cgm ostc2 partial drops counter. Counts packets that were partially dropped and will be seen on RX side.";
    }
    leaf counters_slice0_ifg1_ifgb_rx_port_2_cgm_tc3_dropped_packets {
      type oc-yang:counter64;
      description
        "RX port cgm ostc3 drops counter. Counts packets that were totally dropped and will not be seen on RX side.";
    }
    leaf counters_slice0_ifg1_ifgb_rx_port_2_cgm_tc3_partially_dropped_packets {
      type oc-yang:counter64;
      description
        "RX port cgm ostc3 partial drops counter. Counts packets that were partially dropped and will be seen on RX side.";
    }
    leaf counters_slice0_ifg1_ifgb_rx_port_20_cgm_tc0_dropped_packets {
      type oc-yang:counter64;
      description
        "RX port cgm ostc0 drops counter. Counts packets that were totally dropped and will not be seen on RX side.";
    }
    leaf counters_slice0_ifg1_ifgb_rx_port_20_cgm_tc0_partially_dropped_packets {
      type oc-yang:counter64;
      description
        "RX port cgm ostc0 partial drops counter. Counts packets that were partially dropped and will be seen on RX side.";
    }
    leaf counters_slice0_ifg1_ifgb_rx_port_20_cgm_tc1_dropped_packets {
      type oc-yang:counter64;
      description
        "RX port cgm ostc1 drops counter. Counts packets that were totally dropped and will not be seen on RX side.";
    }
    leaf counters_slice0_ifg1_ifgb_rx_port_20_cgm_tc1_partially_dropped_packets {
      type oc-yang:counter64;
      description
        "RX port cgm ostc1 partial drops counter. Counts packets that were partially dropped and will be seen on RX side.";
    }
    leaf counters_slice0_ifg1_ifgb_rx_port_20_cgm_tc2_dropped_packets {
      type oc-yang:counter64;
      description
        "RX port cgm ostc2 drops counter. Counts packets that were totally dropped and will not be seen on RX side.";
    }
    leaf counters_slice0_ifg1_ifgb_rx_port_20_cgm_tc2_partially_dropped_packets {
      type oc-yang:counter64;
      description
        "RX port cgm ostc2 partial drops counter. Counts packets that were partially dropped and will be seen on RX side.";
    }
    leaf counters_slice0_ifg1_ifgb_rx_port_20_cgm_tc3_dropped_packets {
      type oc-yang:counter64;
      description
        "RX port cgm ostc3 drops counter. Counts packets that were totally dropped and will not be seen on RX side.";
    }
    leaf counters_slice0_ifg1_ifgb_rx_port_20_cgm_tc3_partially_dropped_packets {
      type oc-yang:counter64;
      description
        "RX port cgm ostc3 partial drops counter. Counts packets that were partially dropped and will be seen on RX side.";
    }
    leaf counters_slice0_ifg1_ifgb_rx_port_21_cgm_tc0_dropped_packets {
      type oc-yang:counter64;
      description
        "RX port cgm ostc0 drops counter. Counts packets that were totally dropped and will not be seen on RX side.";
    }
    leaf counters_slice0_ifg1_ifgb_rx_port_21_cgm_tc0_partially_dropped_packets {
      type oc-yang:counter64;
      description
        "RX port cgm ostc0 partial drops counter. Counts packets that were partially dropped and will be seen on RX side.";
    }
    leaf counters_slice0_ifg1_ifgb_rx_port_21_cgm_tc1_dropped_packets {
      type oc-yang:counter64;
      description
        "RX port cgm ostc1 drops counter. Counts packets that were totally dropped and will not be seen on RX side.";
    }
    leaf counters_slice0_ifg1_ifgb_rx_port_21_cgm_tc1_partially_dropped_packets {
      type oc-yang:counter64;
      description
        "RX port cgm ostc1 partial drops counter. Counts packets that were partially dropped and will be seen on RX side.";
    }
    leaf counters_slice0_ifg1_ifgb_rx_port_21_cgm_tc2_dropped_packets {
      type oc-yang:counter64;
      description
        "RX port cgm ostc2 drops counter. Counts packets that were totally dropped and will not be seen on RX side.";
    }
    leaf counters_slice0_ifg1_ifgb_rx_port_21_cgm_tc2_partially_dropped_packets {
      type oc-yang:counter64;
      description
        "RX port cgm ostc2 partial drops counter. Counts packets that were partially dropped and will be seen on RX side.";
    }
    leaf counters_slice0_ifg1_ifgb_rx_port_21_cgm_tc3_dropped_packets {
      type oc-yang:counter64;
      description
        "RX port cgm ostc3 drops counter. Counts packets that were totally dropped and will not be seen on RX side.";
    }
    leaf counters_slice0_ifg1_ifgb_rx_port_21_cgm_tc3_partially_dropped_packets {
      type oc-yang:counter64;
      description
        "RX port cgm ostc3 partial drops counter. Counts packets that were partially dropped and will be seen on RX side.";
    }
    leaf counters_slice0_ifg1_ifgb_rx_port_22_cgm_tc0_dropped_packets {
      type oc-yang:counter64;
      description
        "RX port cgm ostc0 drops counter. Counts packets that were totally dropped and will not be seen on RX side.";
    }
    leaf counters_slice0_ifg1_ifgb_rx_port_22_cgm_tc0_partially_dropped_packets {
      type oc-yang:counter64;
      description
        "RX port cgm ostc0 partial drops counter. Counts packets that were partially dropped and will be seen on RX side.";
    }
    leaf counters_slice0_ifg1_ifgb_rx_port_22_cgm_tc1_dropped_packets {
      type oc-yang:counter64;
      description
        "RX port cgm ostc1 drops counter. Counts packets that were totally dropped and will not be seen on RX side.";
    }
    leaf counters_slice0_ifg1_ifgb_rx_port_22_cgm_tc1_partially_dropped_packets {
      type oc-yang:counter64;
      description
        "RX port cgm ostc1 partial drops counter. Counts packets that were partially dropped and will be seen on RX side.";
    }
    leaf counters_slice0_ifg1_ifgb_rx_port_22_cgm_tc2_dropped_packets {
      type oc-yang:counter64;
      description
        "RX port cgm ostc2 drops counter. Counts packets that were totally dropped and will not be seen on RX side.";
    }
    leaf counters_slice0_ifg1_ifgb_rx_port_22_cgm_tc2_partially_dropped_packets {
      type oc-yang:counter64;
      description
        "RX port cgm ostc2 partial drops counter. Counts packets that were partially dropped and will be seen on RX side.";
    }
    leaf counters_slice0_ifg1_ifgb_rx_port_22_cgm_tc3_dropped_packets {
      type oc-yang:counter64;
      description
        "RX port cgm ostc3 drops counter. Counts packets that were totally dropped and will not be seen on RX side.";
    }
    leaf counters_slice0_ifg1_ifgb_rx_port_22_cgm_tc3_partially_dropped_packets {
      type oc-yang:counter64;
      description
        "RX port cgm ostc3 partial drops counter. Counts packets that were partially dropped and will be seen on RX side.";
    }
    leaf counters_slice0_ifg1_ifgb_rx_port_23_cgm_tc0_dropped_packets {
      type oc-yang:counter64;
      description
        "RX port cgm ostc0 drops counter. Counts packets that were totally dropped and will not be seen on RX side.";
    }
    leaf counters_slice0_ifg1_ifgb_rx_port_23_cgm_tc0_partially_dropped_packets {
      type oc-yang:counter64;
      description
        "RX port cgm ostc0 partial drops counter. Counts packets that were partially dropped and will be seen on RX side.";
    }
    leaf counters_slice0_ifg1_ifgb_rx_port_23_cgm_tc1_dropped_packets {
      type oc-yang:counter64;
      description
        "RX port cgm ostc1 drops counter. Counts packets that were totally dropped and will not be seen on RX side.";
    }
    leaf counters_slice0_ifg1_ifgb_rx_port_23_cgm_tc1_partially_dropped_packets {
      type oc-yang:counter64;
      description
        "RX port cgm ostc1 partial drops counter. Counts packets that were partially dropped and will be seen on RX side.";
    }
    leaf counters_slice0_ifg1_ifgb_rx_port_23_cgm_tc2_dropped_packets {
      type oc-yang:counter64;
      description
        "RX port cgm ostc2 drops counter. Counts packets that were totally dropped and will not be seen on RX side.";
    }
    leaf counters_slice0_ifg1_ifgb_rx_port_23_cgm_tc2_partially_dropped_packets {
      type oc-yang:counter64;
      description
        "RX port cgm ostc2 partial drops counter. Counts packets that were partially dropped and will be seen on RX side.";
    }
    leaf counters_slice0_ifg1_ifgb_rx_port_23_cgm_tc3_dropped_packets {
      type oc-yang:counter64;
      description
        "RX port cgm ostc3 drops counter. Counts packets that were totally dropped and will not be seen on RX side.";
    }
    leaf counters_slice0_ifg1_ifgb_rx_port_23_cgm_tc3_partially_dropped_packets {
      type oc-yang:counter64;
      description
        "RX port cgm ostc3 partial drops counter. Counts packets that were partially dropped and will be seen on RX side.";
    }
    leaf counters_slice0_ifg1_ifgb_rx_port_24_cgm_tc0_dropped_packets {
      type oc-yang:counter64;
      description
        "RX port cgm ostc0 drops counter. Counts packets that were totally dropped and will not be seen on RX side.";
    }
    leaf counters_slice0_ifg1_ifgb_rx_port_24_cgm_tc0_partially_dropped_packets {
      type oc-yang:counter64;
      description
        "RX port cgm ostc0 partial drops counter. Counts packets that were partially dropped and will be seen on RX side.";
    }
    leaf counters_slice0_ifg1_ifgb_rx_port_24_cgm_tc1_dropped_packets {
      type oc-yang:counter64;
      description
        "RX port cgm ostc1 drops counter. Counts packets that were totally dropped and will not be seen on RX side.";
    }
    leaf counters_slice0_ifg1_ifgb_rx_port_24_cgm_tc1_partially_dropped_packets {
      type oc-yang:counter64;
      description
        "RX port cgm ostc1 partial drops counter. Counts packets that were partially dropped and will be seen on RX side.";
    }
    leaf counters_slice0_ifg1_ifgb_rx_port_24_cgm_tc2_dropped_packets {
      type oc-yang:counter64;
      description
        "RX port cgm ostc2 drops counter. Counts packets that were totally dropped and will not be seen on RX side.";
    }
    leaf counters_slice0_ifg1_ifgb_rx_port_24_cgm_tc2_partially_dropped_packets {
      type oc-yang:counter64;
      description
        "RX port cgm ostc2 partial drops counter. Counts packets that were partially dropped and will be seen on RX side.";
    }
    leaf counters_slice0_ifg1_ifgb_rx_port_24_cgm_tc3_dropped_packets {
      type oc-yang:counter64;
      description
        "RX port cgm ostc3 drops counter. Counts packets that were totally dropped and will not be seen on RX side.";
    }
    leaf counters_slice0_ifg1_ifgb_rx_port_24_cgm_tc3_partially_dropped_packets {
      type oc-yang:counter64;
      description
        "RX port cgm ostc3 partial drops counter. Counts packets that were partially dropped and will be seen on RX side.";
    }
    leaf counters_slice0_ifg1_ifgb_rx_port_25_cgm_tc0_dropped_packets {
      type oc-yang:counter64;
      description
        "RX port cgm ostc0 drops counter. Counts packets that were totally dropped and will not be seen on RX side.";
    }
    leaf counters_slice0_ifg1_ifgb_rx_port_25_cgm_tc0_partially_dropped_packets {
      type oc-yang:counter64;
      description
        "RX port cgm ostc0 partial drops counter. Counts packets that were partially dropped and will be seen on RX side.";
    }
    leaf counters_slice0_ifg1_ifgb_rx_port_25_cgm_tc1_dropped_packets {
      type oc-yang:counter64;
      description
        "RX port cgm ostc1 drops counter. Counts packets that were totally dropped and will not be seen on RX side.";
    }
    leaf counters_slice0_ifg1_ifgb_rx_port_25_cgm_tc1_partially_dropped_packets {
      type oc-yang:counter64;
      description
        "RX port cgm ostc1 partial drops counter. Counts packets that were partially dropped and will be seen on RX side.";
    }
    leaf counters_slice0_ifg1_ifgb_rx_port_25_cgm_tc2_dropped_packets {
      type oc-yang:counter64;
      description
        "RX port cgm ostc2 drops counter. Counts packets that were totally dropped and will not be seen on RX side.";
    }
    leaf counters_slice0_ifg1_ifgb_rx_port_25_cgm_tc2_partially_dropped_packets {
      type oc-yang:counter64;
      description
        "RX port cgm ostc2 partial drops counter. Counts packets that were partially dropped and will be seen on RX side.";
    }
    leaf counters_slice0_ifg1_ifgb_rx_port_25_cgm_tc3_dropped_packets {
      type oc-yang:counter64;
      description
        "RX port cgm ostc3 drops counter. Counts packets that were totally dropped and will not be seen on RX side.";
    }
    leaf counters_slice0_ifg1_ifgb_rx_port_25_cgm_tc3_partially_dropped_packets {
      type oc-yang:counter64;
      description
        "RX port cgm ostc3 partial drops counter. Counts packets that were partially dropped and will be seen on RX side.";
    }
    leaf counters_slice0_ifg1_ifgb_rx_port_26_cgm_tc0_dropped_packets {
      type oc-yang:counter64;
      description
        "RX port cgm ostc0 drops counter. Counts packets that were totally dropped and will not be seen on RX side.";
    }
    leaf counters_slice0_ifg1_ifgb_rx_port_26_cgm_tc0_partially_dropped_packets {
      type oc-yang:counter64;
      description
        "RX port cgm ostc0 partial drops counter. Counts packets that were partially dropped and will be seen on RX side.";
    }
    leaf counters_slice0_ifg1_ifgb_rx_port_26_cgm_tc1_dropped_packets {
      type oc-yang:counter64;
      description
        "RX port cgm ostc1 drops counter. Counts packets that were totally dropped and will not be seen on RX side.";
    }
    leaf counters_slice0_ifg1_ifgb_rx_port_26_cgm_tc1_partially_dropped_packets {
      type oc-yang:counter64;
      description
        "RX port cgm ostc1 partial drops counter. Counts packets that were partially dropped and will be seen on RX side.";
    }
    leaf counters_slice0_ifg1_ifgb_rx_port_26_cgm_tc2_dropped_packets {
      type oc-yang:counter64;
      description
        "RX port cgm ostc2 drops counter. Counts packets that were totally dropped and will not be seen on RX side.";
    }
    leaf counters_slice0_ifg1_ifgb_rx_port_26_cgm_tc2_partially_dropped_packets {
      type oc-yang:counter64;
      description
        "RX port cgm ostc2 partial drops counter. Counts packets that were partially dropped and will be seen on RX side.";
    }
    leaf counters_slice0_ifg1_ifgb_rx_port_26_cgm_tc3_dropped_packets {
      type oc-yang:counter64;
      description
        "RX port cgm ostc3 drops counter. Counts packets that were totally dropped and will not be seen on RX side.";
    }
    leaf counters_slice0_ifg1_ifgb_rx_port_26_cgm_tc3_partially_dropped_packets {
      type oc-yang:counter64;
      description
        "RX port cgm ostc3 partial drops counter. Counts packets that were partially dropped and will be seen on RX side.";
    }
    leaf counters_slice0_ifg1_ifgb_rx_port_27_cgm_tc0_dropped_packets {
      type oc-yang:counter64;
      description
        "RX port cgm ostc0 drops counter. Counts packets that were totally dropped and will not be seen on RX side.";
    }
    leaf counters_slice0_ifg1_ifgb_rx_port_27_cgm_tc0_partially_dropped_packets {
      type oc-yang:counter64;
      description
        "RX port cgm ostc0 partial drops counter. Counts packets that were partially dropped and will be seen on RX side.";
    }
    leaf counters_slice0_ifg1_ifgb_rx_port_27_cgm_tc1_dropped_packets {
      type oc-yang:counter64;
      description
        "RX port cgm ostc1 drops counter. Counts packets that were totally dropped and will not be seen on RX side.";
    }
    leaf counters_slice0_ifg1_ifgb_rx_port_27_cgm_tc1_partially_dropped_packets {
      type oc-yang:counter64;
      description
        "RX port cgm ostc1 partial drops counter. Counts packets that were partially dropped and will be seen on RX side.";
    }
    leaf counters_slice0_ifg1_ifgb_rx_port_27_cgm_tc2_dropped_packets {
      type oc-yang:counter64;
      description
        "RX port cgm ostc2 drops counter. Counts packets that were totally dropped and will not be seen on RX side.";
    }
    leaf counters_slice0_ifg1_ifgb_rx_port_27_cgm_tc2_partially_dropped_packets {
      type oc-yang:counter64;
      description
        "RX port cgm ostc2 partial drops counter. Counts packets that were partially dropped and will be seen on RX side.";
    }
    leaf counters_slice0_ifg1_ifgb_rx_port_27_cgm_tc3_dropped_packets {
      type oc-yang:counter64;
      description
        "RX port cgm ostc3 drops counter. Counts packets that were totally dropped and will not be seen on RX side.";
    }
    leaf counters_slice0_ifg1_ifgb_rx_port_27_cgm_tc3_partially_dropped_packets {
      type oc-yang:counter64;
      description
        "RX port cgm ostc3 partial drops counter. Counts packets that were partially dropped and will be seen on RX side.";
    }
    leaf counters_slice0_ifg1_ifgb_rx_port_28_cgm_tc0_dropped_packets {
      type oc-yang:counter64;
      description
        "RX port cgm ostc0 drops counter. Counts packets that were totally dropped and will not be seen on RX side.";
    }
    leaf counters_slice0_ifg1_ifgb_rx_port_28_cgm_tc0_partially_dropped_packets {
      type oc-yang:counter64;
      description
        "RX port cgm ostc0 partial drops counter. Counts packets that were partially dropped and will be seen on RX side.";
    }
    leaf counters_slice0_ifg1_ifgb_rx_port_28_cgm_tc1_dropped_packets {
      type oc-yang:counter64;
      description
        "RX port cgm ostc1 drops counter. Counts packets that were totally dropped and will not be seen on RX side.";
    }
    leaf counters_slice0_ifg1_ifgb_rx_port_28_cgm_tc1_partially_dropped_packets {
      type oc-yang:counter64;
      description
        "RX port cgm ostc1 partial drops counter. Counts packets that were partially dropped and will be seen on RX side.";
    }
    leaf counters_slice0_ifg1_ifgb_rx_port_28_cgm_tc2_dropped_packets {
      type oc-yang:counter64;
      description
        "RX port cgm ostc2 drops counter. Counts packets that were totally dropped and will not be seen on RX side.";
    }
    leaf counters_slice0_ifg1_ifgb_rx_port_28_cgm_tc2_partially_dropped_packets {
      type oc-yang:counter64;
      description
        "RX port cgm ostc2 partial drops counter. Counts packets that were partially dropped and will be seen on RX side.";
    }
    leaf counters_slice0_ifg1_ifgb_rx_port_28_cgm_tc3_dropped_packets {
      type oc-yang:counter64;
      description
        "RX port cgm ostc3 drops counter. Counts packets that were totally dropped and will not be seen on RX side.";
    }
    leaf counters_slice0_ifg1_ifgb_rx_port_28_cgm_tc3_partially_dropped_packets {
      type oc-yang:counter64;
      description
        "RX port cgm ostc3 partial drops counter. Counts packets that were partially dropped and will be seen on RX side.";
    }
    leaf counters_slice0_ifg1_ifgb_rx_port_29_cgm_tc0_dropped_packets {
      type oc-yang:counter64;
      description
        "RX port cgm ostc0 drops counter. Counts packets that were totally dropped and will not be seen on RX side.";
    }
    leaf counters_slice0_ifg1_ifgb_rx_port_29_cgm_tc0_partially_dropped_packets {
      type oc-yang:counter64;
      description
        "RX port cgm ostc0 partial drops counter. Counts packets that were partially dropped and will be seen on RX side.";
    }
    leaf counters_slice0_ifg1_ifgb_rx_port_29_cgm_tc1_dropped_packets {
      type oc-yang:counter64;
      description
        "RX port cgm ostc1 drops counter. Counts packets that were totally dropped and will not be seen on RX side.";
    }
    leaf counters_slice0_ifg1_ifgb_rx_port_29_cgm_tc1_partially_dropped_packets {
      type oc-yang:counter64;
      description
        "RX port cgm ostc1 partial drops counter. Counts packets that were partially dropped and will be seen on RX side.";
    }
    leaf counters_slice0_ifg1_ifgb_rx_port_29_cgm_tc2_dropped_packets {
      type oc-yang:counter64;
      description
        "RX port cgm ostc2 drops counter. Counts packets that were totally dropped and will not be seen on RX side.";
    }
    leaf counters_slice0_ifg1_ifgb_rx_port_29_cgm_tc2_partially_dropped_packets {
      type oc-yang:counter64;
      description
        "RX port cgm ostc2 partial drops counter. Counts packets that were partially dropped and will be seen on RX side.";
    }
    leaf counters_slice0_ifg1_ifgb_rx_port_29_cgm_tc3_dropped_packets {
      type oc-yang:counter64;
      description
        "RX port cgm ostc3 drops counter. Counts packets that were totally dropped and will not be seen on RX side.";
    }
    leaf counters_slice0_ifg1_ifgb_rx_port_29_cgm_tc3_partially_dropped_packets {
      type oc-yang:counter64;
      description
        "RX port cgm ostc3 partial drops counter. Counts packets that were partially dropped and will be seen on RX side.";
    }
    leaf counters_slice0_ifg1_ifgb_rx_port_3_cgm_tc0_dropped_packets {
      type oc-yang:counter64;
      description
        "RX port cgm ostc0 drops counter. Counts packets that were totally dropped and will not be seen on RX side.";
    }
    leaf counters_slice0_ifg1_ifgb_rx_port_3_cgm_tc0_partially_dropped_packets {
      type oc-yang:counter64;
      description
        "RX port cgm ostc0 partial drops counter. Counts packets that were partially dropped and will be seen on RX side.";
    }
    leaf counters_slice0_ifg1_ifgb_rx_port_3_cgm_tc1_dropped_packets {
      type oc-yang:counter64;
      description
        "RX port cgm ostc1 drops counter. Counts packets that were totally dropped and will not be seen on RX side.";
    }
    leaf counters_slice0_ifg1_ifgb_rx_port_3_cgm_tc1_partially_dropped_packets {
      type oc-yang:counter64;
      description
        "RX port cgm ostc1 partial drops counter. Counts packets that were partially dropped and will be seen on RX side.";
    }
    leaf counters_slice0_ifg1_ifgb_rx_port_3_cgm_tc2_dropped_packets {
      type oc-yang:counter64;
      description
        "RX port cgm ostc2 drops counter. Counts packets that were totally dropped and will not be seen on RX side.";
    }
    leaf counters_slice0_ifg1_ifgb_rx_port_3_cgm_tc2_partially_dropped_packets {
      type oc-yang:counter64;
      description
        "RX port cgm ostc2 partial drops counter. Counts packets that were partially dropped and will be seen on RX side.";
    }
    leaf counters_slice0_ifg1_ifgb_rx_port_3_cgm_tc3_dropped_packets {
      type oc-yang:counter64;
      description
        "RX port cgm ostc3 drops counter. Counts packets that were totally dropped and will not be seen on RX side.";
    }
    leaf counters_slice0_ifg1_ifgb_rx_port_3_cgm_tc3_partially_dropped_packets {
      type oc-yang:counter64;
      description
        "RX port cgm ostc3 partial drops counter. Counts packets that were partially dropped and will be seen on RX side.";
    }
    leaf counters_slice0_ifg1_ifgb_rx_port_30_cgm_tc0_dropped_packets {
      type oc-yang:counter64;
      description
        "RX port cgm ostc0 drops counter. Counts packets that were totally dropped and will not be seen on RX side.";
    }
    leaf counters_slice0_ifg1_ifgb_rx_port_30_cgm_tc0_partially_dropped_packets {
      type oc-yang:counter64;
      description
        "RX port cgm ostc0 partial drops counter. Counts packets that were partially dropped and will be seen on RX side.";
    }
    leaf counters_slice0_ifg1_ifgb_rx_port_30_cgm_tc1_dropped_packets {
      type oc-yang:counter64;
      description
        "RX port cgm ostc1 drops counter. Counts packets that were totally dropped and will not be seen on RX side.";
    }
    leaf counters_slice0_ifg1_ifgb_rx_port_30_cgm_tc1_partially_dropped_packets {
      type oc-yang:counter64;
      description
        "RX port cgm ostc1 partial drops counter. Counts packets that were partially dropped and will be seen on RX side.";
    }
    leaf counters_slice0_ifg1_ifgb_rx_port_30_cgm_tc2_dropped_packets {
      type oc-yang:counter64;
      description
        "RX port cgm ostc2 drops counter. Counts packets that were totally dropped and will not be seen on RX side.";
    }
    leaf counters_slice0_ifg1_ifgb_rx_port_30_cgm_tc2_partially_dropped_packets {
      type oc-yang:counter64;
      description
        "RX port cgm ostc2 partial drops counter. Counts packets that were partially dropped and will be seen on RX side.";
    }
    leaf counters_slice0_ifg1_ifgb_rx_port_30_cgm_tc3_dropped_packets {
      type oc-yang:counter64;
      description
        "RX port cgm ostc3 drops counter. Counts packets that were totally dropped and will not be seen on RX side.";
    }
    leaf counters_slice0_ifg1_ifgb_rx_port_30_cgm_tc3_partially_dropped_packets {
      type oc-yang:counter64;
      description
        "RX port cgm ostc3 partial drops counter. Counts packets that were partially dropped and will be seen on RX side.";
    }
    leaf counters_slice0_ifg1_ifgb_rx_port_31_cgm_tc0_dropped_packets {
      type oc-yang:counter64;
      description
        "RX port cgm ostc0 drops counter. Counts packets that were totally dropped and will not be seen on RX side.";
    }
    leaf counters_slice0_ifg1_ifgb_rx_port_31_cgm_tc0_partially_dropped_packets {
      type oc-yang:counter64;
      description
        "RX port cgm ostc0 partial drops counter. Counts packets that were partially dropped and will be seen on RX side.";
    }
    leaf counters_slice0_ifg1_ifgb_rx_port_31_cgm_tc1_dropped_packets {
      type oc-yang:counter64;
      description
        "RX port cgm ostc1 drops counter. Counts packets that were totally dropped and will not be seen on RX side.";
    }
    leaf counters_slice0_ifg1_ifgb_rx_port_31_cgm_tc1_partially_dropped_packets {
      type oc-yang:counter64;
      description
        "RX port cgm ostc1 partial drops counter. Counts packets that were partially dropped and will be seen on RX side.";
    }
    leaf counters_slice0_ifg1_ifgb_rx_port_31_cgm_tc2_dropped_packets {
      type oc-yang:counter64;
      description
        "RX port cgm ostc2 drops counter. Counts packets that were totally dropped and will not be seen on RX side.";
    }
    leaf counters_slice0_ifg1_ifgb_rx_port_31_cgm_tc2_partially_dropped_packets {
      type oc-yang:counter64;
      description
        "RX port cgm ostc2 partial drops counter. Counts packets that were partially dropped and will be seen on RX side.";
    }
    leaf counters_slice0_ifg1_ifgb_rx_port_31_cgm_tc3_dropped_packets {
      type oc-yang:counter64;
      description
        "RX port cgm ostc3 drops counter. Counts packets that were totally dropped and will not be seen on RX side.";
    }
    leaf counters_slice0_ifg1_ifgb_rx_port_31_cgm_tc3_partially_dropped_packets {
      type oc-yang:counter64;
      description
        "RX port cgm ostc3 partial drops counter. Counts packets that were partially dropped and will be seen on RX side.";
    }
    leaf counters_slice0_ifg1_ifgb_rx_port_4_cgm_tc0_dropped_packets {
      type oc-yang:counter64;
      description
        "RX port cgm ostc0 drops counter. Counts packets that were totally dropped and will not be seen on RX side.";
    }
    leaf counters_slice0_ifg1_ifgb_rx_port_4_cgm_tc0_partially_dropped_packets {
      type oc-yang:counter64;
      description
        "RX port cgm ostc0 partial drops counter. Counts packets that were partially dropped and will be seen on RX side.";
    }
    leaf counters_slice0_ifg1_ifgb_rx_port_4_cgm_tc1_dropped_packets {
      type oc-yang:counter64;
      description
        "RX port cgm ostc1 drops counter. Counts packets that were totally dropped and will not be seen on RX side.";
    }
    leaf counters_slice0_ifg1_ifgb_rx_port_4_cgm_tc1_partially_dropped_packets {
      type oc-yang:counter64;
      description
        "RX port cgm ostc1 partial drops counter. Counts packets that were partially dropped and will be seen on RX side.";
    }
    leaf counters_slice0_ifg1_ifgb_rx_port_4_cgm_tc2_dropped_packets {
      type oc-yang:counter64;
      description
        "RX port cgm ostc2 drops counter. Counts packets that were totally dropped and will not be seen on RX side.";
    }
    leaf counters_slice0_ifg1_ifgb_rx_port_4_cgm_tc2_partially_dropped_packets {
      type oc-yang:counter64;
      description
        "RX port cgm ostc2 partial drops counter. Counts packets that were partially dropped and will be seen on RX side.";
    }
    leaf counters_slice0_ifg1_ifgb_rx_port_4_cgm_tc3_dropped_packets {
      type oc-yang:counter64;
      description
        "RX port cgm ostc3 drops counter. Counts packets that were totally dropped and will not be seen on RX side.";
    }
    leaf counters_slice0_ifg1_ifgb_rx_port_4_cgm_tc3_partially_dropped_packets {
      type oc-yang:counter64;
      description
        "RX port cgm ostc3 partial drops counter. Counts packets that were partially dropped and will be seen on RX side.";
    }
    leaf counters_slice0_ifg1_ifgb_rx_port_5_cgm_tc0_dropped_packets {
      type oc-yang:counter64;
      description
        "RX port cgm ostc0 drops counter. Counts packets that were totally dropped and will not be seen on RX side.";
    }
    leaf counters_slice0_ifg1_ifgb_rx_port_5_cgm_tc0_partially_dropped_packets {
      type oc-yang:counter64;
      description
        "RX port cgm ostc0 partial drops counter. Counts packets that were partially dropped and will be seen on RX side.";
    }
    leaf counters_slice0_ifg1_ifgb_rx_port_5_cgm_tc1_dropped_packets {
      type oc-yang:counter64;
      description
        "RX port cgm ostc1 drops counter. Counts packets that were totally dropped and will not be seen on RX side.";
    }
    leaf counters_slice0_ifg1_ifgb_rx_port_5_cgm_tc1_partially_dropped_packets {
      type oc-yang:counter64;
      description
        "RX port cgm ostc1 partial drops counter. Counts packets that were partially dropped and will be seen on RX side.";
    }
    leaf counters_slice0_ifg1_ifgb_rx_port_5_cgm_tc2_dropped_packets {
      type oc-yang:counter64;
      description
        "RX port cgm ostc2 drops counter. Counts packets that were totally dropped and will not be seen on RX side.";
    }
    leaf counters_slice0_ifg1_ifgb_rx_port_5_cgm_tc2_partially_dropped_packets {
      type oc-yang:counter64;
      description
        "RX port cgm ostc2 partial drops counter. Counts packets that were partially dropped and will be seen on RX side.";
    }
    leaf counters_slice0_ifg1_ifgb_rx_port_5_cgm_tc3_dropped_packets {
      type oc-yang:counter64;
      description
        "RX port cgm ostc3 drops counter. Counts packets that were totally dropped and will not be seen on RX side.";
    }
    leaf counters_slice0_ifg1_ifgb_rx_port_5_cgm_tc3_partially_dropped_packets {
      type oc-yang:counter64;
      description
        "RX port cgm ostc3 partial drops counter. Counts packets that were partially dropped and will be seen on RX side.";
    }
    leaf counters_slice0_ifg1_ifgb_rx_port_6_cgm_tc0_dropped_packets {
      type oc-yang:counter64;
      description
        "RX port cgm ostc0 drops counter. Counts packets that were totally dropped and will not be seen on RX side.";
    }
    leaf counters_slice0_ifg1_ifgb_rx_port_6_cgm_tc0_partially_dropped_packets {
      type oc-yang:counter64;
      description
        "RX port cgm ostc0 partial drops counter. Counts packets that were partially dropped and will be seen on RX side.";
    }
    leaf counters_slice0_ifg1_ifgb_rx_port_6_cgm_tc1_dropped_packets {
      type oc-yang:counter64;
      description
        "RX port cgm ostc1 drops counter. Counts packets that were totally dropped and will not be seen on RX side.";
    }
    leaf counters_slice0_ifg1_ifgb_rx_port_6_cgm_tc1_partially_dropped_packets {
      type oc-yang:counter64;
      description
        "RX port cgm ostc1 partial drops counter. Counts packets that were partially dropped and will be seen on RX side.";
    }
    leaf counters_slice0_ifg1_ifgb_rx_port_6_cgm_tc2_dropped_packets {
      type oc-yang:counter64;
      description
        "RX port cgm ostc2 drops counter. Counts packets that were totally dropped and will not be seen on RX side.";
    }
    leaf counters_slice0_ifg1_ifgb_rx_port_6_cgm_tc2_partially_dropped_packets {
      type oc-yang:counter64;
      description
        "RX port cgm ostc2 partial drops counter. Counts packets that were partially dropped and will be seen on RX side.";
    }
    leaf counters_slice0_ifg1_ifgb_rx_port_6_cgm_tc3_dropped_packets {
      type oc-yang:counter64;
      description
        "RX port cgm ostc3 drops counter. Counts packets that were totally dropped and will not be seen on RX side.";
    }
    leaf counters_slice0_ifg1_ifgb_rx_port_6_cgm_tc3_partially_dropped_packets {
      type oc-yang:counter64;
      description
        "RX port cgm ostc3 partial drops counter. Counts packets that were partially dropped and will be seen on RX side.";
    }
    leaf counters_slice0_ifg1_ifgb_rx_port_7_cgm_tc0_dropped_packets {
      type oc-yang:counter64;
      description
        "RX port cgm ostc0 drops counter. Counts packets that were totally dropped and will not be seen on RX side.";
    }
    leaf counters_slice0_ifg1_ifgb_rx_port_7_cgm_tc0_partially_dropped_packets {
      type oc-yang:counter64;
      description
        "RX port cgm ostc0 partial drops counter. Counts packets that were partially dropped and will be seen on RX side.";
    }
    leaf counters_slice0_ifg1_ifgb_rx_port_7_cgm_tc1_dropped_packets {
      type oc-yang:counter64;
      description
        "RX port cgm ostc1 drops counter. Counts packets that were totally dropped and will not be seen on RX side.";
    }
    leaf counters_slice0_ifg1_ifgb_rx_port_7_cgm_tc1_partially_dropped_packets {
      type oc-yang:counter64;
      description
        "RX port cgm ostc1 partial drops counter. Counts packets that were partially dropped and will be seen on RX side.";
    }
    leaf counters_slice0_ifg1_ifgb_rx_port_7_cgm_tc2_dropped_packets {
      type oc-yang:counter64;
      description
        "RX port cgm ostc2 drops counter. Counts packets that were totally dropped and will not be seen on RX side.";
    }
    leaf counters_slice0_ifg1_ifgb_rx_port_7_cgm_tc2_partially_dropped_packets {
      type oc-yang:counter64;
      description
        "RX port cgm ostc2 partial drops counter. Counts packets that were partially dropped and will be seen on RX side.";
    }
    leaf counters_slice0_ifg1_ifgb_rx_port_7_cgm_tc3_dropped_packets {
      type oc-yang:counter64;
      description
        "RX port cgm ostc3 drops counter. Counts packets that were totally dropped and will not be seen on RX side.";
    }
    leaf counters_slice0_ifg1_ifgb_rx_port_7_cgm_tc3_partially_dropped_packets {
      type oc-yang:counter64;
      description
        "RX port cgm ostc3 partial drops counter. Counts packets that were partially dropped and will be seen on RX side.";
    }
    leaf counters_slice0_ifg1_ifgb_rx_port_8_cgm_tc0_dropped_packets {
      type oc-yang:counter64;
      description
        "RX port cgm ostc0 drops counter. Counts packets that were totally dropped and will not be seen on RX side.";
    }
    leaf counters_slice0_ifg1_ifgb_rx_port_8_cgm_tc0_partially_dropped_packets {
      type oc-yang:counter64;
      description
        "RX port cgm ostc0 partial drops counter. Counts packets that were partially dropped and will be seen on RX side.";
    }
    leaf counters_slice0_ifg1_ifgb_rx_port_8_cgm_tc1_dropped_packets {
      type oc-yang:counter64;
      description
        "RX port cgm ostc1 drops counter. Counts packets that were totally dropped and will not be seen on RX side.";
    }
    leaf counters_slice0_ifg1_ifgb_rx_port_8_cgm_tc1_partially_dropped_packets {
      type oc-yang:counter64;
      description
        "RX port cgm ostc1 partial drops counter. Counts packets that were partially dropped and will be seen on RX side.";
    }
    leaf counters_slice0_ifg1_ifgb_rx_port_8_cgm_tc2_dropped_packets {
      type oc-yang:counter64;
      description
        "RX port cgm ostc2 drops counter. Counts packets that were totally dropped and will not be seen on RX side.";
    }
    leaf counters_slice0_ifg1_ifgb_rx_port_8_cgm_tc2_partially_dropped_packets {
      type oc-yang:counter64;
      description
        "RX port cgm ostc2 partial drops counter. Counts packets that were partially dropped and will be seen on RX side.";
    }
    leaf counters_slice0_ifg1_ifgb_rx_port_8_cgm_tc3_dropped_packets {
      type oc-yang:counter64;
      description
        "RX port cgm ostc3 drops counter. Counts packets that were totally dropped and will not be seen on RX side.";
    }
    leaf counters_slice0_ifg1_ifgb_rx_port_8_cgm_tc3_partially_dropped_packets {
      type oc-yang:counter64;
      description
        "RX port cgm ostc3 partial drops counter. Counts packets that were partially dropped and will be seen on RX side.";
    }
    leaf counters_slice0_ifg1_ifgb_rx_port_9_cgm_tc0_dropped_packets {
      type oc-yang:counter64;
      description
        "RX port cgm ostc0 drops counter. Counts packets that were totally dropped and will not be seen on RX side.";
    }
    leaf counters_slice0_ifg1_ifgb_rx_port_9_cgm_tc0_partially_dropped_packets {
      type oc-yang:counter64;
      description
        "RX port cgm ostc0 partial drops counter. Counts packets that were partially dropped and will be seen on RX side.";
    }
    leaf counters_slice0_ifg1_ifgb_rx_port_9_cgm_tc1_dropped_packets {
      type oc-yang:counter64;
      description
        "RX port cgm ostc1 drops counter. Counts packets that were totally dropped and will not be seen on RX side.";
    }
    leaf counters_slice0_ifg1_ifgb_rx_port_9_cgm_tc1_partially_dropped_packets {
      type oc-yang:counter64;
      description
        "RX port cgm ostc1 partial drops counter. Counts packets that were partially dropped and will be seen on RX side.";
    }
    leaf counters_slice0_ifg1_ifgb_rx_port_9_cgm_tc2_dropped_packets {
      type oc-yang:counter64;
      description
        "RX port cgm ostc2 drops counter. Counts packets that were totally dropped and will not be seen on RX side.";
    }
    leaf counters_slice0_ifg1_ifgb_rx_port_9_cgm_tc2_partially_dropped_packets {
      type oc-yang:counter64;
      description
        "RX port cgm ostc2 partial drops counter. Counts packets that were partially dropped and will be seen on RX side.";
    }
    leaf counters_slice0_ifg1_ifgb_rx_port_9_cgm_tc3_dropped_packets {
      type oc-yang:counter64;
      description
        "RX port cgm ostc3 drops counter. Counts packets that were totally dropped and will not be seen on RX side.";
    }
    leaf counters_slice0_ifg1_ifgb_rx_port_9_cgm_tc3_partially_dropped_packets {
      type oc-yang:counter64;
      description
        "RX port cgm ostc3 partial drops counter. Counts packets that were partially dropped and will be seen on RX side.";
    }
    leaf counters_slice0_tx_cgm_dropped_packets_due_to_max_allowed_qsize {
      type oc-yang:counter64;
      description
        "Counts number of dropped packets by max allowed threshold";
    }
    leaf counters_slice0_tx_cgm_local_sch_uc_buffer_c_dropped_packets {
      type oc-yang:counter64;
      description
        "Counts number of dropped packets by counter C";
    }
    leaf counters_slice0_tx_cgm_mc_silently_dropped_packets {
      type oc-yang:counter64;
      description
        "Counter of dropped MC packets that were silently dropped";
    }
    leaf counters_slice0_tx_cgm_sch_uc_buffers_cd_dropped_packets {
      type oc-yang:counter64;
      description
        "Counts number of dropped packets by counter C+D";
    }
    leaf counters_slice0_tx_cgm_sch_uc_counter_z_dropped_packets {
      type oc-yang:counter64;
      description
        "Counts number of dropped packets by counter Z";
    }
    leaf counters_slice0_tx_cgm_total_dropped_packets {
      type oc-yang:counter64;
      description
        "Counts number of dropped in TxCGM only packets";
    }
    leaf counters_slice0_tx_cgm_uc_oq_test_dropped_packets {
      type oc-yang:counter64;
      description
        "Counts number of dropped by UC OQ test";
    }
    leaf counters_slice0_tx_cgm_uc_oqg_dropped_packets {
      type oc-yang:counter64;
      description
        "Counts number of dropped by UC OQG test";
    }
    leaf counters_slice0_tx_cgm_unsch_counter_w_dropped_packets {
      type oc-yang:counter64;
      description
        "Counts number of dropped packets by counter W";
    }
    leaf counters_slice0_tx_cgm_green_mc_oq_bytes_test_dropped_packets {
      type oc-yang:counter64;
      description
        "Counts number of dropped packets by OQ MC green bytes test";
    }
    leaf counters_slice0_tx_cgm_green_mc_oq_pds_test_dropped_packets {
      type oc-yang:counter64;
      description
        "Counts number of dropped packets by OQ MC green PDs test";
    }
    leaf counters_slice0_tx_cgm_mc_color_test0_dropped_packets {
      type oc-yang:counter64;
      description
        "Counts number of dropped packet by MC color test for:0 - Green1 - Yellow2 - Red3 - Other";
    }
    leaf counters_slice0_tx_cgm_mc_color_test1_dropped_packets {
      type oc-yang:counter64;
      description
        "Counts number of dropped packet by MC color test for:0 - Green1 - Yellow2 - Red3 - Other";
    }
    leaf counters_slice0_tx_cgm_mc_color_test2_dropped_packets {
      type oc-yang:counter64;
      description
        "Counts number of dropped packet by MC color test for:0 - Green1 - Yellow2 - Red3 - Other";
    }
    leaf counters_slice0_tx_cgm_mc_color_test3_dropped_packets {
      type oc-yang:counter64;
      description
        "Counts number of dropped packet by MC color test for:0 - Green1 - Yellow2 - Red3 - Other";
    }
    leaf counters_slice0_tx_cgm_mc_set0_dropped_bytes {
      type oc-yang:counter64;
      description
        "Counts MC dropped bytes";
    }
    leaf counters_slice0_tx_cgm_mc_set0_dropped_packets {
      type oc-yang:counter64;
      description
        "Counts MC dropped packets";
    }
    leaf counters_slice0_tx_cgm_mc_set1_dropped_bytes {
      type oc-yang:counter64;
      description
        "Counts MC dropped bytes";
    }
    leaf counters_slice0_tx_cgm_mc_set1_dropped_packets {
      type oc-yang:counter64;
      description
        "Counts MC dropped packets";
    }
    leaf counters_slice0_tx_cgm_mc_set2_dropped_bytes {
      type oc-yang:counter64;
      description
        "Counts MC dropped bytes";
    }
    leaf counters_slice0_tx_cgm_mc_set2_dropped_packets {
      type oc-yang:counter64;
      description
        "Counts MC dropped packets";
    }
    leaf counters_slice0_tx_cgm_mc_set3_dropped_bytes {
      type oc-yang:counter64;
      description
        "Counts MC dropped bytes";
    }
    leaf counters_slice0_tx_cgm_mc_set3_dropped_packets {
      type oc-yang:counter64;
      description
        "Counts MC dropped packets";
    }
    leaf counters_slice0_tx_cgm_uc_color_test0_dropped_packets {
      type oc-yang:counter64;
      description
        "Counts number of dropped packet by UC color test for:0 - Green1 - Yellow2 - Red3 - Other";
    }
    leaf counters_slice0_tx_cgm_uc_color_test1_dropped_packets {
      type oc-yang:counter64;
      description
        "Counts number of dropped packet by UC color test for:0 - Green1 - Yellow2 - Red3 - Other";
    }
    leaf counters_slice0_tx_cgm_uc_color_test2_dropped_packets {
      type oc-yang:counter64;
      description
        "Counts number of dropped packet by UC color test for:0 - Green1 - Yellow2 - Red3 - Other";
    }
    leaf counters_slice0_tx_cgm_uc_color_test3_dropped_packets {
      type oc-yang:counter64;
      description
        "Counts number of dropped packet by UC color test for:0 - Green1 - Yellow2 - Red3 - Other";
    }
    leaf counters_slice0_tx_cgm_uc_set0_dropped_bytes {
      type oc-yang:counter64;
      description
        "Counts UC dropped bytes";
    }
    leaf counters_slice0_tx_cgm_uc_set0_dropped_packets {
      type oc-yang:counter64;
      description
        "Counts UC dropped packets";
    }
    leaf counters_slice0_tx_cgm_uc_set1_dropped_bytes {
      type oc-yang:counter64;
      description
        "Counts UC dropped bytes";
    }
    leaf counters_slice0_tx_cgm_uc_set1_dropped_packets {
      type oc-yang:counter64;
      description
        "Counts UC dropped packets";
    }
    leaf counters_slice0_tx_cgm_uc_set2_dropped_bytes {
      type oc-yang:counter64;
      description
        "Counts UC dropped bytes";
    }
    leaf counters_slice0_tx_cgm_uc_set2_dropped_packets {
      type oc-yang:counter64;
      description
        "Counts UC dropped packets";
    }
    leaf counters_slice0_tx_cgm_uc_set3_dropped_bytes {
      type oc-yang:counter64;
      description
        "Counts UC dropped bytes";
    }
    leaf counters_slice0_tx_cgm_uc_set3_dropped_packets {
      type oc-yang:counter64;
      description
        "Counts UC dropped packets";
    }
    leaf counters_slice0_tx_cgm_yellow_mc_oq_bytes_test_dropped_packets {
      type oc-yang:counter64;
      description
        "Counts number of dropped packets by OQ MC yellow bytes test";
    }
    leaf counters_slice0_tx_cgm_yellow_mc_oq_pds_test_dropped_packets {
      type oc-yang:counter64;
      description
        "Counts number of dropped packets by OQ MC yellow PDs test";
    }
    leaf counters_slice0_tx_pdr_txrq_full_egress_rep_dropped_packets {
      type oc-yang:counter64;
      description
        "Number of dropped packets";
    }
    leaf counters_slice0_tx_pdr_txrq_overload_egress_rep_dropped_packets {
      type oc-yang:counter64;
      description
        "Number of dropped packets";
    }
    leaf counters_slice0_tx_pdr_txrq0_full_egress_rep_dropped_packets {
      type oc-yang:counter64;
      description
        "Number of dropped packets";
    }
    leaf counters_slice0_tx_pdr_txrq0_threshold0_deq_dropped_packets {
      type oc-yang:counter64;
      description
        "Number of dropped packets in TXRQ deq";
    }
    leaf counters_slice0_tx_pdr_txrq0_threshold0_enq_dropped_packets {
      type oc-yang:counter64;
      description
        "Number of dropped packets in TXRQ enq";
    }
    leaf counters_slice0_tx_pdr_txrq0_threshold0_unscheduled_cgm_drops {
      type oc-yang:counter64;
      description
        "nan";
    }
    leaf counters_slice0_tx_pdr_txrq0_threshold1_deq_dropped_packets {
      type oc-yang:counter64;
      description
        "Number of dropped packets in TXRQ deq";
    }
    leaf counters_slice0_tx_pdr_txrq0_threshold1_enq_dropped_packets {
      type oc-yang:counter64;
      description
        "Number of dropped packets in TXRQ enq";
    }
    leaf counters_slice0_tx_pdr_txrq0_threshold1_unscheduled_cgm_drops {
      type oc-yang:counter64;
      description
        "nan";
    }
    leaf counters_slice0_tx_pdr_txrq1_full_egress_rep_dropped_packets {
      type oc-yang:counter64;
      description
        "Number of dropped packets";
    }
    leaf counters_slice0_tx_pdr_txrq1_threshold0_deq_dropped_packets {
      type oc-yang:counter64;
      description
        "Number of dropped packets in TXRQ deq";
    }
    leaf counters_slice0_tx_pdr_txrq1_threshold0_enq_dropped_packets {
      type oc-yang:counter64;
      description
        "Number of dropped packets in TXRQ enq";
    }
    leaf counters_slice0_tx_pdr_txrq1_threshold0_unscheduled_cgm_drops {
      type oc-yang:counter64;
      description
        "nan";
    }
    leaf counters_slice0_tx_pdr_txrq1_threshold1_deq_dropped_packets {
      type oc-yang:counter64;
      description
        "Number of dropped packets in TXRQ deq";
    }
    leaf counters_slice0_tx_pdr_txrq1_threshold1_enq_dropped_packets {
      type oc-yang:counter64;
      description
        "Number of dropped packets in TXRQ enq";
    }
    leaf counters_slice0_tx_pdr_txrq1_threshold1_unscheduled_cgm_drops {
      type oc-yang:counter64;
      description
        "nan";
    }
    leaf counters_slice0_tx_pdr_txrq2_full_egress_rep_dropped_packets {
      type oc-yang:counter64;
      description
        "Number of dropped packets";
    }
    leaf counters_slice0_tx_pdr_txrq2_threshold0_deq_dropped_packets {
      type oc-yang:counter64;
      description
        "Number of dropped packets in TXRQ deq";
    }
    leaf counters_slice0_tx_pdr_txrq2_threshold0_enq_dropped_packets {
      type oc-yang:counter64;
      description
        "Number of dropped packets in TXRQ enq";
    }
    leaf counters_slice0_tx_pdr_txrq2_threshold1_deq_dropped_packets {
      type oc-yang:counter64;
      description
        "Number of dropped packets in TXRQ deq";
    }
    leaf counters_slice0_tx_pdr_txrq2_threshold1_enq_dropped_packets {
      type oc-yang:counter64;
      description
        "Number of dropped packets in TXRQ enq";
    }
    leaf counters_slice0_tx_pdr_txrq3_full_egress_rep_dropped_packets {
      type oc-yang:counter64;
      description
        "Number of dropped packets";
    }
    leaf counters_slice0_tx_pdr_txrq3_threshold0_deq_dropped_packets {
      type oc-yang:counter64;
      description
        "Number of dropped packets in TXRQ deq";
    }
    leaf counters_slice0_tx_pdr_txrq3_threshold0_enq_dropped_packets {
      type oc-yang:counter64;
      description
        "Number of dropped packets in TXRQ enq";
    }
    leaf counters_slice0_tx_pdr_txrq3_threshold1_deq_dropped_packets {
      type oc-yang:counter64;
      description
        "Number of dropped packets in TXRQ deq";
    }
    leaf counters_slice0_tx_pdr_txrq3_threshold1_enq_dropped_packets {
      type oc-yang:counter64;
      description
        "Number of dropped packets in TXRQ enq";
    }
    leaf counters_slice1_ifg0_ifgb_rx_port_0_cgm_tc0_dropped_packets {
      type oc-yang:counter64;
      description
        "RX port cgm ostc0 drops counter. Counts packets that were totally dropped and will not be seen on RX side.";
    }
    leaf counters_slice1_ifg0_ifgb_rx_port_0_cgm_tc0_partially_dropped_packets {
      type oc-yang:counter64;
      description
        "RX port cgm ostc0 partial drops counter. Counts packets that were partially dropped and will be seen on RX side.";
    }
    leaf counters_slice1_ifg0_ifgb_rx_port_0_cgm_tc1_dropped_packets {
      type oc-yang:counter64;
      description
        "RX port cgm ostc1 drops counter. Counts packets that were totally dropped and will not be seen on RX side.";
    }
    leaf counters_slice1_ifg0_ifgb_rx_port_0_cgm_tc1_partially_dropped_packets {
      type oc-yang:counter64;
      description
        "RX port cgm ostc1 partial drops counter. Counts packets that were partially dropped and will be seen on RX side.";
    }
    leaf counters_slice1_ifg0_ifgb_rx_port_0_cgm_tc2_dropped_packets {
      type oc-yang:counter64;
      description
        "RX port cgm ostc2 drops counter. Counts packets that were totally dropped and will not be seen on RX side.";
    }
    leaf counters_slice1_ifg0_ifgb_rx_port_0_cgm_tc2_partially_dropped_packets {
      type oc-yang:counter64;
      description
        "RX port cgm ostc2 partial drops counter. Counts packets that were partially dropped and will be seen on RX side.";
    }
    leaf counters_slice1_ifg0_ifgb_rx_port_0_cgm_tc3_dropped_packets {
      type oc-yang:counter64;
      description
        "RX port cgm ostc3 drops counter. Counts packets that were totally dropped and will not be seen on RX side.";
    }
    leaf counters_slice1_ifg0_ifgb_rx_port_0_cgm_tc3_partially_dropped_packets {
      type oc-yang:counter64;
      description
        "RX port cgm ostc3 partial drops counter. Counts packets that were partially dropped and will be seen on RX side.";
    }
    leaf counters_slice1_ifg0_ifgb_rx_port_1_cgm_tc0_dropped_packets {
      type oc-yang:counter64;
      description
        "RX port cgm ostc0 drops counter. Counts packets that were totally dropped and will not be seen on RX side.";
    }
    leaf counters_slice1_ifg0_ifgb_rx_port_1_cgm_tc0_partially_dropped_packets {
      type oc-yang:counter64;
      description
        "RX port cgm ostc0 partial drops counter. Counts packets that were partially dropped and will be seen on RX side.";
    }
    leaf counters_slice1_ifg0_ifgb_rx_port_1_cgm_tc1_dropped_packets {
      type oc-yang:counter64;
      description
        "RX port cgm ostc1 drops counter. Counts packets that were totally dropped and will not be seen on RX side.";
    }
    leaf counters_slice1_ifg0_ifgb_rx_port_1_cgm_tc1_partially_dropped_packets {
      type oc-yang:counter64;
      description
        "RX port cgm ostc1 partial drops counter. Counts packets that were partially dropped and will be seen on RX side.";
    }
    leaf counters_slice1_ifg0_ifgb_rx_port_1_cgm_tc2_dropped_packets {
      type oc-yang:counter64;
      description
        "RX port cgm ostc2 drops counter. Counts packets that were totally dropped and will not be seen on RX side.";
    }
    leaf counters_slice1_ifg0_ifgb_rx_port_1_cgm_tc2_partially_dropped_packets {
      type oc-yang:counter64;
      description
        "RX port cgm ostc2 partial drops counter. Counts packets that were partially dropped and will be seen on RX side.";
    }
    leaf counters_slice1_ifg0_ifgb_rx_port_1_cgm_tc3_dropped_packets {
      type oc-yang:counter64;
      description
        "RX port cgm ostc3 drops counter. Counts packets that were totally dropped and will not be seen on RX side.";
    }
    leaf counters_slice1_ifg0_ifgb_rx_port_1_cgm_tc3_partially_dropped_packets {
      type oc-yang:counter64;
      description
        "RX port cgm ostc3 partial drops counter. Counts packets that were partially dropped and will be seen on RX side.";
    }
    leaf counters_slice1_ifg0_ifgb_rx_port_10_cgm_tc0_dropped_packets {
      type oc-yang:counter64;
      description
        "RX port cgm ostc0 drops counter. Counts packets that were totally dropped and will not be seen on RX side.";
    }
    leaf counters_slice1_ifg0_ifgb_rx_port_10_cgm_tc0_partially_dropped_packets {
      type oc-yang:counter64;
      description
        "RX port cgm ostc0 partial drops counter. Counts packets that were partially dropped and will be seen on RX side.";
    }
    leaf counters_slice1_ifg0_ifgb_rx_port_10_cgm_tc1_dropped_packets {
      type oc-yang:counter64;
      description
        "RX port cgm ostc1 drops counter. Counts packets that were totally dropped and will not be seen on RX side.";
    }
    leaf counters_slice1_ifg0_ifgb_rx_port_10_cgm_tc1_partially_dropped_packets {
      type oc-yang:counter64;
      description
        "RX port cgm ostc1 partial drops counter. Counts packets that were partially dropped and will be seen on RX side.";
    }
    leaf counters_slice1_ifg0_ifgb_rx_port_10_cgm_tc2_dropped_packets {
      type oc-yang:counter64;
      description
        "RX port cgm ostc2 drops counter. Counts packets that were totally dropped and will not be seen on RX side.";
    }
    leaf counters_slice1_ifg0_ifgb_rx_port_10_cgm_tc2_partially_dropped_packets {
      type oc-yang:counter64;
      description
        "RX port cgm ostc2 partial drops counter. Counts packets that were partially dropped and will be seen on RX side.";
    }
    leaf counters_slice1_ifg0_ifgb_rx_port_10_cgm_tc3_dropped_packets {
      type oc-yang:counter64;
      description
        "RX port cgm ostc3 drops counter. Counts packets that were totally dropped and will not be seen on RX side.";
    }
    leaf counters_slice1_ifg0_ifgb_rx_port_10_cgm_tc3_partially_dropped_packets {
      type oc-yang:counter64;
      description
        "RX port cgm ostc3 partial drops counter. Counts packets that were partially dropped and will be seen on RX side.";
    }
    leaf counters_slice1_ifg0_ifgb_rx_port_11_cgm_tc0_dropped_packets {
      type oc-yang:counter64;
      description
        "RX port cgm ostc0 drops counter. Counts packets that were totally dropped and will not be seen on RX side.";
    }
    leaf counters_slice1_ifg0_ifgb_rx_port_11_cgm_tc0_partially_dropped_packets {
      type oc-yang:counter64;
      description
        "RX port cgm ostc0 partial drops counter. Counts packets that were partially dropped and will be seen on RX side.";
    }
    leaf counters_slice1_ifg0_ifgb_rx_port_11_cgm_tc1_dropped_packets {
      type oc-yang:counter64;
      description
        "RX port cgm ostc1 drops counter. Counts packets that were totally dropped and will not be seen on RX side.";
    }
    leaf counters_slice1_ifg0_ifgb_rx_port_11_cgm_tc1_partially_dropped_packets {
      type oc-yang:counter64;
      description
        "RX port cgm ostc1 partial drops counter. Counts packets that were partially dropped and will be seen on RX side.";
    }
    leaf counters_slice1_ifg0_ifgb_rx_port_11_cgm_tc2_dropped_packets {
      type oc-yang:counter64;
      description
        "RX port cgm ostc2 drops counter. Counts packets that were totally dropped and will not be seen on RX side.";
    }
    leaf counters_slice1_ifg0_ifgb_rx_port_11_cgm_tc2_partially_dropped_packets {
      type oc-yang:counter64;
      description
        "RX port cgm ostc2 partial drops counter. Counts packets that were partially dropped and will be seen on RX side.";
    }
    leaf counters_slice1_ifg0_ifgb_rx_port_11_cgm_tc3_dropped_packets {
      type oc-yang:counter64;
      description
        "RX port cgm ostc3 drops counter. Counts packets that were totally dropped and will not be seen on RX side.";
    }
    leaf counters_slice1_ifg0_ifgb_rx_port_11_cgm_tc3_partially_dropped_packets {
      type oc-yang:counter64;
      description
        "RX port cgm ostc3 partial drops counter. Counts packets that were partially dropped and will be seen on RX side.";
    }
    leaf counters_slice1_ifg0_ifgb_rx_port_12_cgm_tc0_dropped_packets {
      type oc-yang:counter64;
      description
        "RX port cgm ostc0 drops counter. Counts packets that were totally dropped and will not be seen on RX side.";
    }
    leaf counters_slice1_ifg0_ifgb_rx_port_12_cgm_tc0_partially_dropped_packets {
      type oc-yang:counter64;
      description
        "RX port cgm ostc0 partial drops counter. Counts packets that were partially dropped and will be seen on RX side.";
    }
    leaf counters_slice1_ifg0_ifgb_rx_port_12_cgm_tc1_dropped_packets {
      type oc-yang:counter64;
      description
        "RX port cgm ostc1 drops counter. Counts packets that were totally dropped and will not be seen on RX side.";
    }
    leaf counters_slice1_ifg0_ifgb_rx_port_12_cgm_tc1_partially_dropped_packets {
      type oc-yang:counter64;
      description
        "RX port cgm ostc1 partial drops counter. Counts packets that were partially dropped and will be seen on RX side.";
    }
    leaf counters_slice1_ifg0_ifgb_rx_port_12_cgm_tc2_dropped_packets {
      type oc-yang:counter64;
      description
        "RX port cgm ostc2 drops counter. Counts packets that were totally dropped and will not be seen on RX side.";
    }
    leaf counters_slice1_ifg0_ifgb_rx_port_12_cgm_tc2_partially_dropped_packets {
      type oc-yang:counter64;
      description
        "RX port cgm ostc2 partial drops counter. Counts packets that were partially dropped and will be seen on RX side.";
    }
    leaf counters_slice1_ifg0_ifgb_rx_port_12_cgm_tc3_dropped_packets {
      type oc-yang:counter64;
      description
        "RX port cgm ostc3 drops counter. Counts packets that were totally dropped and will not be seen on RX side.";
    }
    leaf counters_slice1_ifg0_ifgb_rx_port_12_cgm_tc3_partially_dropped_packets {
      type oc-yang:counter64;
      description
        "RX port cgm ostc3 partial drops counter. Counts packets that were partially dropped and will be seen on RX side.";
    }
    leaf counters_slice1_ifg0_ifgb_rx_port_13_cgm_tc0_dropped_packets {
      type oc-yang:counter64;
      description
        "RX port cgm ostc0 drops counter. Counts packets that were totally dropped and will not be seen on RX side.";
    }
    leaf counters_slice1_ifg0_ifgb_rx_port_13_cgm_tc0_partially_dropped_packets {
      type oc-yang:counter64;
      description
        "RX port cgm ostc0 partial drops counter. Counts packets that were partially dropped and will be seen on RX side.";
    }
    leaf counters_slice1_ifg0_ifgb_rx_port_13_cgm_tc1_dropped_packets {
      type oc-yang:counter64;
      description
        "RX port cgm ostc1 drops counter. Counts packets that were totally dropped and will not be seen on RX side.";
    }
    leaf counters_slice1_ifg0_ifgb_rx_port_13_cgm_tc1_partially_dropped_packets {
      type oc-yang:counter64;
      description
        "RX port cgm ostc1 partial drops counter. Counts packets that were partially dropped and will be seen on RX side.";
    }
    leaf counters_slice1_ifg0_ifgb_rx_port_13_cgm_tc2_dropped_packets {
      type oc-yang:counter64;
      description
        "RX port cgm ostc2 drops counter. Counts packets that were totally dropped and will not be seen on RX side.";
    }
    leaf counters_slice1_ifg0_ifgb_rx_port_13_cgm_tc2_partially_dropped_packets {
      type oc-yang:counter64;
      description
        "RX port cgm ostc2 partial drops counter. Counts packets that were partially dropped and will be seen on RX side.";
    }
    leaf counters_slice1_ifg0_ifgb_rx_port_13_cgm_tc3_dropped_packets {
      type oc-yang:counter64;
      description
        "RX port cgm ostc3 drops counter. Counts packets that were totally dropped and will not be seen on RX side.";
    }
    leaf counters_slice1_ifg0_ifgb_rx_port_13_cgm_tc3_partially_dropped_packets {
      type oc-yang:counter64;
      description
        "RX port cgm ostc3 partial drops counter. Counts packets that were partially dropped and will be seen on RX side.";
    }
    leaf counters_slice1_ifg0_ifgb_rx_port_14_cgm_tc0_dropped_packets {
      type oc-yang:counter64;
      description
        "RX port cgm ostc0 drops counter. Counts packets that were totally dropped and will not be seen on RX side.";
    }
    leaf counters_slice1_ifg0_ifgb_rx_port_14_cgm_tc0_partially_dropped_packets {
      type oc-yang:counter64;
      description
        "RX port cgm ostc0 partial drops counter. Counts packets that were partially dropped and will be seen on RX side.";
    }
    leaf counters_slice1_ifg0_ifgb_rx_port_14_cgm_tc1_dropped_packets {
      type oc-yang:counter64;
      description
        "RX port cgm ostc1 drops counter. Counts packets that were totally dropped and will not be seen on RX side.";
    }
    leaf counters_slice1_ifg0_ifgb_rx_port_14_cgm_tc1_partially_dropped_packets {
      type oc-yang:counter64;
      description
        "RX port cgm ostc1 partial drops counter. Counts packets that were partially dropped and will be seen on RX side.";
    }
    leaf counters_slice1_ifg0_ifgb_rx_port_14_cgm_tc2_dropped_packets {
      type oc-yang:counter64;
      description
        "RX port cgm ostc2 drops counter. Counts packets that were totally dropped and will not be seen on RX side.";
    }
    leaf counters_slice1_ifg0_ifgb_rx_port_14_cgm_tc2_partially_dropped_packets {
      type oc-yang:counter64;
      description
        "RX port cgm ostc2 partial drops counter. Counts packets that were partially dropped and will be seen on RX side.";
    }
    leaf counters_slice1_ifg0_ifgb_rx_port_14_cgm_tc3_dropped_packets {
      type oc-yang:counter64;
      description
        "RX port cgm ostc3 drops counter. Counts packets that were totally dropped and will not be seen on RX side.";
    }
    leaf counters_slice1_ifg0_ifgb_rx_port_14_cgm_tc3_partially_dropped_packets {
      type oc-yang:counter64;
      description
        "RX port cgm ostc3 partial drops counter. Counts packets that were partially dropped and will be seen on RX side.";
    }
    leaf counters_slice1_ifg0_ifgb_rx_port_15_cgm_tc0_dropped_packets {
      type oc-yang:counter64;
      description
        "RX port cgm ostc0 drops counter. Counts packets that were totally dropped and will not be seen on RX side.";
    }
    leaf counters_slice1_ifg0_ifgb_rx_port_15_cgm_tc0_partially_dropped_packets {
      type oc-yang:counter64;
      description
        "RX port cgm ostc0 partial drops counter. Counts packets that were partially dropped and will be seen on RX side.";
    }
    leaf counters_slice1_ifg0_ifgb_rx_port_15_cgm_tc1_dropped_packets {
      type oc-yang:counter64;
      description
        "RX port cgm ostc1 drops counter. Counts packets that were totally dropped and will not be seen on RX side.";
    }
    leaf counters_slice1_ifg0_ifgb_rx_port_15_cgm_tc1_partially_dropped_packets {
      type oc-yang:counter64;
      description
        "RX port cgm ostc1 partial drops counter. Counts packets that were partially dropped and will be seen on RX side.";
    }
    leaf counters_slice1_ifg0_ifgb_rx_port_15_cgm_tc2_dropped_packets {
      type oc-yang:counter64;
      description
        "RX port cgm ostc2 drops counter. Counts packets that were totally dropped and will not be seen on RX side.";
    }
    leaf counters_slice1_ifg0_ifgb_rx_port_15_cgm_tc2_partially_dropped_packets {
      type oc-yang:counter64;
      description
        "RX port cgm ostc2 partial drops counter. Counts packets that were partially dropped and will be seen on RX side.";
    }
    leaf counters_slice1_ifg0_ifgb_rx_port_15_cgm_tc3_dropped_packets {
      type oc-yang:counter64;
      description
        "RX port cgm ostc3 drops counter. Counts packets that were totally dropped and will not be seen on RX side.";
    }
    leaf counters_slice1_ifg0_ifgb_rx_port_15_cgm_tc3_partially_dropped_packets {
      type oc-yang:counter64;
      description
        "RX port cgm ostc3 partial drops counter. Counts packets that were partially dropped and will be seen on RX side.";
    }
    leaf counters_slice1_ifg0_ifgb_rx_port_16_cgm_tc0_dropped_packets {
      type oc-yang:counter64;
      description
        "RX port cgm ostc0 drops counter. Counts packets that were totally dropped and will not be seen on RX side.";
    }
    leaf counters_slice1_ifg0_ifgb_rx_port_16_cgm_tc0_partially_dropped_packets {
      type oc-yang:counter64;
      description
        "RX port cgm ostc0 partial drops counter. Counts packets that were partially dropped and will be seen on RX side.";
    }
    leaf counters_slice1_ifg0_ifgb_rx_port_16_cgm_tc1_dropped_packets {
      type oc-yang:counter64;
      description
        "RX port cgm ostc1 drops counter. Counts packets that were totally dropped and will not be seen on RX side.";
    }
    leaf counters_slice1_ifg0_ifgb_rx_port_16_cgm_tc1_partially_dropped_packets {
      type oc-yang:counter64;
      description
        "RX port cgm ostc1 partial drops counter. Counts packets that were partially dropped and will be seen on RX side.";
    }
    leaf counters_slice1_ifg0_ifgb_rx_port_16_cgm_tc2_dropped_packets {
      type oc-yang:counter64;
      description
        "RX port cgm ostc2 drops counter. Counts packets that were totally dropped and will not be seen on RX side.";
    }
    leaf counters_slice1_ifg0_ifgb_rx_port_16_cgm_tc2_partially_dropped_packets {
      type oc-yang:counter64;
      description
        "RX port cgm ostc2 partial drops counter. Counts packets that were partially dropped and will be seen on RX side.";
    }
    leaf counters_slice1_ifg0_ifgb_rx_port_16_cgm_tc3_dropped_packets {
      type oc-yang:counter64;
      description
        "RX port cgm ostc3 drops counter. Counts packets that were totally dropped and will not be seen on RX side.";
    }
    leaf counters_slice1_ifg0_ifgb_rx_port_16_cgm_tc3_partially_dropped_packets {
      type oc-yang:counter64;
      description
        "RX port cgm ostc3 partial drops counter. Counts packets that were partially dropped and will be seen on RX side.";
    }
    leaf counters_slice1_ifg0_ifgb_rx_port_17_cgm_tc0_dropped_packets {
      type oc-yang:counter64;
      description
        "RX port cgm ostc0 drops counter. Counts packets that were totally dropped and will not be seen on RX side.";
    }
    leaf counters_slice1_ifg0_ifgb_rx_port_17_cgm_tc0_partially_dropped_packets {
      type oc-yang:counter64;
      description
        "RX port cgm ostc0 partial drops counter. Counts packets that were partially dropped and will be seen on RX side.";
    }
    leaf counters_slice1_ifg0_ifgb_rx_port_17_cgm_tc1_dropped_packets {
      type oc-yang:counter64;
      description
        "RX port cgm ostc1 drops counter. Counts packets that were totally dropped and will not be seen on RX side.";
    }
    leaf counters_slice1_ifg0_ifgb_rx_port_17_cgm_tc1_partially_dropped_packets {
      type oc-yang:counter64;
      description
        "RX port cgm ostc1 partial drops counter. Counts packets that were partially dropped and will be seen on RX side.";
    }
    leaf counters_slice1_ifg0_ifgb_rx_port_17_cgm_tc2_dropped_packets {
      type oc-yang:counter64;
      description
        "RX port cgm ostc2 drops counter. Counts packets that were totally dropped and will not be seen on RX side.";
    }
    leaf counters_slice1_ifg0_ifgb_rx_port_17_cgm_tc2_partially_dropped_packets {
      type oc-yang:counter64;
      description
        "RX port cgm ostc2 partial drops counter. Counts packets that were partially dropped and will be seen on RX side.";
    }
    leaf counters_slice1_ifg0_ifgb_rx_port_17_cgm_tc3_dropped_packets {
      type oc-yang:counter64;
      description
        "RX port cgm ostc3 drops counter. Counts packets that were totally dropped and will not be seen on RX side.";
    }
    leaf counters_slice1_ifg0_ifgb_rx_port_17_cgm_tc3_partially_dropped_packets {
      type oc-yang:counter64;
      description
        "RX port cgm ostc3 partial drops counter. Counts packets that were partially dropped and will be seen on RX side.";
    }
    leaf counters_slice1_ifg0_ifgb_rx_port_18_cgm_tc0_dropped_packets {
      type oc-yang:counter64;
      description
        "RX port cgm ostc0 drops counter. Counts packets that were totally dropped and will not be seen on RX side.";
    }
    leaf counters_slice1_ifg0_ifgb_rx_port_18_cgm_tc0_partially_dropped_packets {
      type oc-yang:counter64;
      description
        "RX port cgm ostc0 partial drops counter. Counts packets that were partially dropped and will be seen on RX side.";
    }
    leaf counters_slice1_ifg0_ifgb_rx_port_18_cgm_tc1_dropped_packets {
      type oc-yang:counter64;
      description
        "RX port cgm ostc1 drops counter. Counts packets that were totally dropped and will not be seen on RX side.";
    }
    leaf counters_slice1_ifg0_ifgb_rx_port_18_cgm_tc1_partially_dropped_packets {
      type oc-yang:counter64;
      description
        "RX port cgm ostc1 partial drops counter. Counts packets that were partially dropped and will be seen on RX side.";
    }
    leaf counters_slice1_ifg0_ifgb_rx_port_18_cgm_tc2_dropped_packets {
      type oc-yang:counter64;
      description
        "RX port cgm ostc2 drops counter. Counts packets that were totally dropped and will not be seen on RX side.";
    }
    leaf counters_slice1_ifg0_ifgb_rx_port_18_cgm_tc2_partially_dropped_packets {
      type oc-yang:counter64;
      description
        "RX port cgm ostc2 partial drops counter. Counts packets that were partially dropped and will be seen on RX side.";
    }
    leaf counters_slice1_ifg0_ifgb_rx_port_18_cgm_tc3_dropped_packets {
      type oc-yang:counter64;
      description
        "RX port cgm ostc3 drops counter. Counts packets that were totally dropped and will not be seen on RX side.";
    }
    leaf counters_slice1_ifg0_ifgb_rx_port_18_cgm_tc3_partially_dropped_packets {
      type oc-yang:counter64;
      description
        "RX port cgm ostc3 partial drops counter. Counts packets that were partially dropped and will be seen on RX side.";
    }
    leaf counters_slice1_ifg0_ifgb_rx_port_19_cgm_tc0_dropped_packets {
      type oc-yang:counter64;
      description
        "RX port cgm ostc0 drops counter. Counts packets that were totally dropped and will not be seen on RX side.";
    }
    leaf counters_slice1_ifg0_ifgb_rx_port_19_cgm_tc0_partially_dropped_packets {
      type oc-yang:counter64;
      description
        "RX port cgm ostc0 partial drops counter. Counts packets that were partially dropped and will be seen on RX side.";
    }
    leaf counters_slice1_ifg0_ifgb_rx_port_19_cgm_tc1_dropped_packets {
      type oc-yang:counter64;
      description
        "RX port cgm ostc1 drops counter. Counts packets that were totally dropped and will not be seen on RX side.";
    }
    leaf counters_slice1_ifg0_ifgb_rx_port_19_cgm_tc1_partially_dropped_packets {
      type oc-yang:counter64;
      description
        "RX port cgm ostc1 partial drops counter. Counts packets that were partially dropped and will be seen on RX side.";
    }
    leaf counters_slice1_ifg0_ifgb_rx_port_19_cgm_tc2_dropped_packets {
      type oc-yang:counter64;
      description
        "RX port cgm ostc2 drops counter. Counts packets that were totally dropped and will not be seen on RX side.";
    }
    leaf counters_slice1_ifg0_ifgb_rx_port_19_cgm_tc2_partially_dropped_packets {
      type oc-yang:counter64;
      description
        "RX port cgm ostc2 partial drops counter. Counts packets that were partially dropped and will be seen on RX side.";
    }
    leaf counters_slice1_ifg0_ifgb_rx_port_19_cgm_tc3_dropped_packets {
      type oc-yang:counter64;
      description
        "RX port cgm ostc3 drops counter. Counts packets that were totally dropped and will not be seen on RX side.";
    }
    leaf counters_slice1_ifg0_ifgb_rx_port_19_cgm_tc3_partially_dropped_packets {
      type oc-yang:counter64;
      description
        "RX port cgm ostc3 partial drops counter. Counts packets that were partially dropped and will be seen on RX side.";
    }
    leaf counters_slice1_ifg0_ifgb_rx_port_2_cgm_tc0_dropped_packets {
      type oc-yang:counter64;
      description
        "RX port cgm ostc0 drops counter. Counts packets that were totally dropped and will not be seen on RX side.";
    }
    leaf counters_slice1_ifg0_ifgb_rx_port_2_cgm_tc0_partially_dropped_packets {
      type oc-yang:counter64;
      description
        "RX port cgm ostc0 partial drops counter. Counts packets that were partially dropped and will be seen on RX side.";
    }
    leaf counters_slice1_ifg0_ifgb_rx_port_2_cgm_tc1_dropped_packets {
      type oc-yang:counter64;
      description
        "RX port cgm ostc1 drops counter. Counts packets that were totally dropped and will not be seen on RX side.";
    }
    leaf counters_slice1_ifg0_ifgb_rx_port_2_cgm_tc1_partially_dropped_packets {
      type oc-yang:counter64;
      description
        "RX port cgm ostc1 partial drops counter. Counts packets that were partially dropped and will be seen on RX side.";
    }
    leaf counters_slice1_ifg0_ifgb_rx_port_2_cgm_tc2_dropped_packets {
      type oc-yang:counter64;
      description
        "RX port cgm ostc2 drops counter. Counts packets that were totally dropped and will not be seen on RX side.";
    }
    leaf counters_slice1_ifg0_ifgb_rx_port_2_cgm_tc2_partially_dropped_packets {
      type oc-yang:counter64;
      description
        "RX port cgm ostc2 partial drops counter. Counts packets that were partially dropped and will be seen on RX side.";
    }
    leaf counters_slice1_ifg0_ifgb_rx_port_2_cgm_tc3_dropped_packets {
      type oc-yang:counter64;
      description
        "RX port cgm ostc3 drops counter. Counts packets that were totally dropped and will not be seen on RX side.";
    }
    leaf counters_slice1_ifg0_ifgb_rx_port_2_cgm_tc3_partially_dropped_packets {
      type oc-yang:counter64;
      description
        "RX port cgm ostc3 partial drops counter. Counts packets that were partially dropped and will be seen on RX side.";
    }
    leaf counters_slice1_ifg0_ifgb_rx_port_20_cgm_tc0_dropped_packets {
      type oc-yang:counter64;
      description
        "RX port cgm ostc0 drops counter. Counts packets that were totally dropped and will not be seen on RX side.";
    }
    leaf counters_slice1_ifg0_ifgb_rx_port_20_cgm_tc0_partially_dropped_packets {
      type oc-yang:counter64;
      description
        "RX port cgm ostc0 partial drops counter. Counts packets that were partially dropped and will be seen on RX side.";
    }
    leaf counters_slice1_ifg0_ifgb_rx_port_20_cgm_tc1_dropped_packets {
      type oc-yang:counter64;
      description
        "RX port cgm ostc1 drops counter. Counts packets that were totally dropped and will not be seen on RX side.";
    }
    leaf counters_slice1_ifg0_ifgb_rx_port_20_cgm_tc1_partially_dropped_packets {
      type oc-yang:counter64;
      description
        "RX port cgm ostc1 partial drops counter. Counts packets that were partially dropped and will be seen on RX side.";
    }
    leaf counters_slice1_ifg0_ifgb_rx_port_20_cgm_tc2_dropped_packets {
      type oc-yang:counter64;
      description
        "RX port cgm ostc2 drops counter. Counts packets that were totally dropped and will not be seen on RX side.";
    }
    leaf counters_slice1_ifg0_ifgb_rx_port_20_cgm_tc2_partially_dropped_packets {
      type oc-yang:counter64;
      description
        "RX port cgm ostc2 partial drops counter. Counts packets that were partially dropped and will be seen on RX side.";
    }
    leaf counters_slice1_ifg0_ifgb_rx_port_20_cgm_tc3_dropped_packets {
      type oc-yang:counter64;
      description
        "RX port cgm ostc3 drops counter. Counts packets that were totally dropped and will not be seen on RX side.";
    }
    leaf counters_slice1_ifg0_ifgb_rx_port_20_cgm_tc3_partially_dropped_packets {
      type oc-yang:counter64;
      description
        "RX port cgm ostc3 partial drops counter. Counts packets that were partially dropped and will be seen on RX side.";
    }
    leaf counters_slice1_ifg0_ifgb_rx_port_21_cgm_tc0_dropped_packets {
      type oc-yang:counter64;
      description
        "RX port cgm ostc0 drops counter. Counts packets that were totally dropped and will not be seen on RX side.";
    }
    leaf counters_slice1_ifg0_ifgb_rx_port_21_cgm_tc0_partially_dropped_packets {
      type oc-yang:counter64;
      description
        "RX port cgm ostc0 partial drops counter. Counts packets that were partially dropped and will be seen on RX side.";
    }
    leaf counters_slice1_ifg0_ifgb_rx_port_21_cgm_tc1_dropped_packets {
      type oc-yang:counter64;
      description
        "RX port cgm ostc1 drops counter. Counts packets that were totally dropped and will not be seen on RX side.";
    }
    leaf counters_slice1_ifg0_ifgb_rx_port_21_cgm_tc1_partially_dropped_packets {
      type oc-yang:counter64;
      description
        "RX port cgm ostc1 partial drops counter. Counts packets that were partially dropped and will be seen on RX side.";
    }
    leaf counters_slice1_ifg0_ifgb_rx_port_21_cgm_tc2_dropped_packets {
      type oc-yang:counter64;
      description
        "RX port cgm ostc2 drops counter. Counts packets that were totally dropped and will not be seen on RX side.";
    }
    leaf counters_slice1_ifg0_ifgb_rx_port_21_cgm_tc2_partially_dropped_packets {
      type oc-yang:counter64;
      description
        "RX port cgm ostc2 partial drops counter. Counts packets that were partially dropped and will be seen on RX side.";
    }
    leaf counters_slice1_ifg0_ifgb_rx_port_21_cgm_tc3_dropped_packets {
      type oc-yang:counter64;
      description
        "RX port cgm ostc3 drops counter. Counts packets that were totally dropped and will not be seen on RX side.";
    }
    leaf counters_slice1_ifg0_ifgb_rx_port_21_cgm_tc3_partially_dropped_packets {
      type oc-yang:counter64;
      description
        "RX port cgm ostc3 partial drops counter. Counts packets that were partially dropped and will be seen on RX side.";
    }
    leaf counters_slice1_ifg0_ifgb_rx_port_22_cgm_tc0_dropped_packets {
      type oc-yang:counter64;
      description
        "RX port cgm ostc0 drops counter. Counts packets that were totally dropped and will not be seen on RX side.";
    }
    leaf counters_slice1_ifg0_ifgb_rx_port_22_cgm_tc0_partially_dropped_packets {
      type oc-yang:counter64;
      description
        "RX port cgm ostc0 partial drops counter. Counts packets that were partially dropped and will be seen on RX side.";
    }
    leaf counters_slice1_ifg0_ifgb_rx_port_22_cgm_tc1_dropped_packets {
      type oc-yang:counter64;
      description
        "RX port cgm ostc1 drops counter. Counts packets that were totally dropped and will not be seen on RX side.";
    }
    leaf counters_slice1_ifg0_ifgb_rx_port_22_cgm_tc1_partially_dropped_packets {
      type oc-yang:counter64;
      description
        "RX port cgm ostc1 partial drops counter. Counts packets that were partially dropped and will be seen on RX side.";
    }
    leaf counters_slice1_ifg0_ifgb_rx_port_22_cgm_tc2_dropped_packets {
      type oc-yang:counter64;
      description
        "RX port cgm ostc2 drops counter. Counts packets that were totally dropped and will not be seen on RX side.";
    }
    leaf counters_slice1_ifg0_ifgb_rx_port_22_cgm_tc2_partially_dropped_packets {
      type oc-yang:counter64;
      description
        "RX port cgm ostc2 partial drops counter. Counts packets that were partially dropped and will be seen on RX side.";
    }
    leaf counters_slice1_ifg0_ifgb_rx_port_22_cgm_tc3_dropped_packets {
      type oc-yang:counter64;
      description
        "RX port cgm ostc3 drops counter. Counts packets that were totally dropped and will not be seen on RX side.";
    }
    leaf counters_slice1_ifg0_ifgb_rx_port_22_cgm_tc3_partially_dropped_packets {
      type oc-yang:counter64;
      description
        "RX port cgm ostc3 partial drops counter. Counts packets that were partially dropped and will be seen on RX side.";
    }
    leaf counters_slice1_ifg0_ifgb_rx_port_23_cgm_tc0_dropped_packets {
      type oc-yang:counter64;
      description
        "RX port cgm ostc0 drops counter. Counts packets that were totally dropped and will not be seen on RX side.";
    }
    leaf counters_slice1_ifg0_ifgb_rx_port_23_cgm_tc0_partially_dropped_packets {
      type oc-yang:counter64;
      description
        "RX port cgm ostc0 partial drops counter. Counts packets that were partially dropped and will be seen on RX side.";
    }
    leaf counters_slice1_ifg0_ifgb_rx_port_23_cgm_tc1_dropped_packets {
      type oc-yang:counter64;
      description
        "RX port cgm ostc1 drops counter. Counts packets that were totally dropped and will not be seen on RX side.";
    }
    leaf counters_slice1_ifg0_ifgb_rx_port_23_cgm_tc1_partially_dropped_packets {
      type oc-yang:counter64;
      description
        "RX port cgm ostc1 partial drops counter. Counts packets that were partially dropped and will be seen on RX side.";
    }
    leaf counters_slice1_ifg0_ifgb_rx_port_23_cgm_tc2_dropped_packets {
      type oc-yang:counter64;
      description
        "RX port cgm ostc2 drops counter. Counts packets that were totally dropped and will not be seen on RX side.";
    }
    leaf counters_slice1_ifg0_ifgb_rx_port_23_cgm_tc2_partially_dropped_packets {
      type oc-yang:counter64;
      description
        "RX port cgm ostc2 partial drops counter. Counts packets that were partially dropped and will be seen on RX side.";
    }
    leaf counters_slice1_ifg0_ifgb_rx_port_23_cgm_tc3_dropped_packets {
      type oc-yang:counter64;
      description
        "RX port cgm ostc3 drops counter. Counts packets that were totally dropped and will not be seen on RX side.";
    }
    leaf counters_slice1_ifg0_ifgb_rx_port_23_cgm_tc3_partially_dropped_packets {
      type oc-yang:counter64;
      description
        "RX port cgm ostc3 partial drops counter. Counts packets that were partially dropped and will be seen on RX side.";
    }
    leaf counters_slice1_ifg0_ifgb_rx_port_24_cgm_tc0_dropped_packets {
      type oc-yang:counter64;
      description
        "RX port cgm ostc0 drops counter. Counts packets that were totally dropped and will not be seen on RX side.";
    }
    leaf counters_slice1_ifg0_ifgb_rx_port_24_cgm_tc0_partially_dropped_packets {
      type oc-yang:counter64;
      description
        "RX port cgm ostc0 partial drops counter. Counts packets that were partially dropped and will be seen on RX side.";
    }
    leaf counters_slice1_ifg0_ifgb_rx_port_24_cgm_tc1_dropped_packets {
      type oc-yang:counter64;
      description
        "RX port cgm ostc1 drops counter. Counts packets that were totally dropped and will not be seen on RX side.";
    }
    leaf counters_slice1_ifg0_ifgb_rx_port_24_cgm_tc1_partially_dropped_packets {
      type oc-yang:counter64;
      description
        "RX port cgm ostc1 partial drops counter. Counts packets that were partially dropped and will be seen on RX side.";
    }
    leaf counters_slice1_ifg0_ifgb_rx_port_24_cgm_tc2_dropped_packets {
      type oc-yang:counter64;
      description
        "RX port cgm ostc2 drops counter. Counts packets that were totally dropped and will not be seen on RX side.";
    }
    leaf counters_slice1_ifg0_ifgb_rx_port_24_cgm_tc2_partially_dropped_packets {
      type oc-yang:counter64;
      description
        "RX port cgm ostc2 partial drops counter. Counts packets that were partially dropped and will be seen on RX side.";
    }
    leaf counters_slice1_ifg0_ifgb_rx_port_24_cgm_tc3_dropped_packets {
      type oc-yang:counter64;
      description
        "RX port cgm ostc3 drops counter. Counts packets that were totally dropped and will not be seen on RX side.";
    }
    leaf counters_slice1_ifg0_ifgb_rx_port_24_cgm_tc3_partially_dropped_packets {
      type oc-yang:counter64;
      description
        "RX port cgm ostc3 partial drops counter. Counts packets that were partially dropped and will be seen on RX side.";
    }
    leaf counters_slice1_ifg0_ifgb_rx_port_25_cgm_tc0_dropped_packets {
      type oc-yang:counter64;
      description
        "RX port cgm ostc0 drops counter. Counts packets that were totally dropped and will not be seen on RX side.";
    }
    leaf counters_slice1_ifg0_ifgb_rx_port_25_cgm_tc0_partially_dropped_packets {
      type oc-yang:counter64;
      description
        "RX port cgm ostc0 partial drops counter. Counts packets that were partially dropped and will be seen on RX side.";
    }
    leaf counters_slice1_ifg0_ifgb_rx_port_25_cgm_tc1_dropped_packets {
      type oc-yang:counter64;
      description
        "RX port cgm ostc1 drops counter. Counts packets that were totally dropped and will not be seen on RX side.";
    }
    leaf counters_slice1_ifg0_ifgb_rx_port_25_cgm_tc1_partially_dropped_packets {
      type oc-yang:counter64;
      description
        "RX port cgm ostc1 partial drops counter. Counts packets that were partially dropped and will be seen on RX side.";
    }
    leaf counters_slice1_ifg0_ifgb_rx_port_25_cgm_tc2_dropped_packets {
      type oc-yang:counter64;
      description
        "RX port cgm ostc2 drops counter. Counts packets that were totally dropped and will not be seen on RX side.";
    }
    leaf counters_slice1_ifg0_ifgb_rx_port_25_cgm_tc2_partially_dropped_packets {
      type oc-yang:counter64;
      description
        "RX port cgm ostc2 partial drops counter. Counts packets that were partially dropped and will be seen on RX side.";
    }
    leaf counters_slice1_ifg0_ifgb_rx_port_25_cgm_tc3_dropped_packets {
      type oc-yang:counter64;
      description
        "RX port cgm ostc3 drops counter. Counts packets that were totally dropped and will not be seen on RX side.";
    }
    leaf counters_slice1_ifg0_ifgb_rx_port_25_cgm_tc3_partially_dropped_packets {
      type oc-yang:counter64;
      description
        "RX port cgm ostc3 partial drops counter. Counts packets that were partially dropped and will be seen on RX side.";
    }
    leaf counters_slice1_ifg0_ifgb_rx_port_26_cgm_tc0_dropped_packets {
      type oc-yang:counter64;
      description
        "RX port cgm ostc0 drops counter. Counts packets that were totally dropped and will not be seen on RX side.";
    }
    leaf counters_slice1_ifg0_ifgb_rx_port_26_cgm_tc0_partially_dropped_packets {
      type oc-yang:counter64;
      description
        "RX port cgm ostc0 partial drops counter. Counts packets that were partially dropped and will be seen on RX side.";
    }
    leaf counters_slice1_ifg0_ifgb_rx_port_26_cgm_tc1_dropped_packets {
      type oc-yang:counter64;
      description
        "RX port cgm ostc1 drops counter. Counts packets that were totally dropped and will not be seen on RX side.";
    }
    leaf counters_slice1_ifg0_ifgb_rx_port_26_cgm_tc1_partially_dropped_packets {
      type oc-yang:counter64;
      description
        "RX port cgm ostc1 partial drops counter. Counts packets that were partially dropped and will be seen on RX side.";
    }
    leaf counters_slice1_ifg0_ifgb_rx_port_26_cgm_tc2_dropped_packets {
      type oc-yang:counter64;
      description
        "RX port cgm ostc2 drops counter. Counts packets that were totally dropped and will not be seen on RX side.";
    }
    leaf counters_slice1_ifg0_ifgb_rx_port_26_cgm_tc2_partially_dropped_packets {
      type oc-yang:counter64;
      description
        "RX port cgm ostc2 partial drops counter. Counts packets that were partially dropped and will be seen on RX side.";
    }
    leaf counters_slice1_ifg0_ifgb_rx_port_26_cgm_tc3_dropped_packets {
      type oc-yang:counter64;
      description
        "RX port cgm ostc3 drops counter. Counts packets that were totally dropped and will not be seen on RX side.";
    }
    leaf counters_slice1_ifg0_ifgb_rx_port_26_cgm_tc3_partially_dropped_packets {
      type oc-yang:counter64;
      description
        "RX port cgm ostc3 partial drops counter. Counts packets that were partially dropped and will be seen on RX side.";
    }
    leaf counters_slice1_ifg0_ifgb_rx_port_27_cgm_tc0_dropped_packets {
      type oc-yang:counter64;
      description
        "RX port cgm ostc0 drops counter. Counts packets that were totally dropped and will not be seen on RX side.";
    }
    leaf counters_slice1_ifg0_ifgb_rx_port_27_cgm_tc0_partially_dropped_packets {
      type oc-yang:counter64;
      description
        "RX port cgm ostc0 partial drops counter. Counts packets that were partially dropped and will be seen on RX side.";
    }
    leaf counters_slice1_ifg0_ifgb_rx_port_27_cgm_tc1_dropped_packets {
      type oc-yang:counter64;
      description
        "RX port cgm ostc1 drops counter. Counts packets that were totally dropped and will not be seen on RX side.";
    }
    leaf counters_slice1_ifg0_ifgb_rx_port_27_cgm_tc1_partially_dropped_packets {
      type oc-yang:counter64;
      description
        "RX port cgm ostc1 partial drops counter. Counts packets that were partially dropped and will be seen on RX side.";
    }
    leaf counters_slice1_ifg0_ifgb_rx_port_27_cgm_tc2_dropped_packets {
      type oc-yang:counter64;
      description
        "RX port cgm ostc2 drops counter. Counts packets that were totally dropped and will not be seen on RX side.";
    }
    leaf counters_slice1_ifg0_ifgb_rx_port_27_cgm_tc2_partially_dropped_packets {
      type oc-yang:counter64;
      description
        "RX port cgm ostc2 partial drops counter. Counts packets that were partially dropped and will be seen on RX side.";
    }
    leaf counters_slice1_ifg0_ifgb_rx_port_27_cgm_tc3_dropped_packets {
      type oc-yang:counter64;
      description
        "RX port cgm ostc3 drops counter. Counts packets that were totally dropped and will not be seen on RX side.";
    }
    leaf counters_slice1_ifg0_ifgb_rx_port_27_cgm_tc3_partially_dropped_packets {
      type oc-yang:counter64;
      description
        "RX port cgm ostc3 partial drops counter. Counts packets that were partially dropped and will be seen on RX side.";
    }
    leaf counters_slice1_ifg0_ifgb_rx_port_28_cgm_tc0_dropped_packets {
      type oc-yang:counter64;
      description
        "RX port cgm ostc0 drops counter. Counts packets that were totally dropped and will not be seen on RX side.";
    }
    leaf counters_slice1_ifg0_ifgb_rx_port_28_cgm_tc0_partially_dropped_packets {
      type oc-yang:counter64;
      description
        "RX port cgm ostc0 partial drops counter. Counts packets that were partially dropped and will be seen on RX side.";
    }
    leaf counters_slice1_ifg0_ifgb_rx_port_28_cgm_tc1_dropped_packets {
      type oc-yang:counter64;
      description
        "RX port cgm ostc1 drops counter. Counts packets that were totally dropped and will not be seen on RX side.";
    }
    leaf counters_slice1_ifg0_ifgb_rx_port_28_cgm_tc1_partially_dropped_packets {
      type oc-yang:counter64;
      description
        "RX port cgm ostc1 partial drops counter. Counts packets that were partially dropped and will be seen on RX side.";
    }
    leaf counters_slice1_ifg0_ifgb_rx_port_28_cgm_tc2_dropped_packets {
      type oc-yang:counter64;
      description
        "RX port cgm ostc2 drops counter. Counts packets that were totally dropped and will not be seen on RX side.";
    }
    leaf counters_slice1_ifg0_ifgb_rx_port_28_cgm_tc2_partially_dropped_packets {
      type oc-yang:counter64;
      description
        "RX port cgm ostc2 partial drops counter. Counts packets that were partially dropped and will be seen on RX side.";
    }
    leaf counters_slice1_ifg0_ifgb_rx_port_28_cgm_tc3_dropped_packets {
      type oc-yang:counter64;
      description
        "RX port cgm ostc3 drops counter. Counts packets that were totally dropped and will not be seen on RX side.";
    }
    leaf counters_slice1_ifg0_ifgb_rx_port_28_cgm_tc3_partially_dropped_packets {
      type oc-yang:counter64;
      description
        "RX port cgm ostc3 partial drops counter. Counts packets that were partially dropped and will be seen on RX side.";
    }
    leaf counters_slice1_ifg0_ifgb_rx_port_29_cgm_tc0_dropped_packets {
      type oc-yang:counter64;
      description
        "RX port cgm ostc0 drops counter. Counts packets that were totally dropped and will not be seen on RX side.";
    }
    leaf counters_slice1_ifg0_ifgb_rx_port_29_cgm_tc0_partially_dropped_packets {
      type oc-yang:counter64;
      description
        "RX port cgm ostc0 partial drops counter. Counts packets that were partially dropped and will be seen on RX side.";
    }
    leaf counters_slice1_ifg0_ifgb_rx_port_29_cgm_tc1_dropped_packets {
      type oc-yang:counter64;
      description
        "RX port cgm ostc1 drops counter. Counts packets that were totally dropped and will not be seen on RX side.";
    }
    leaf counters_slice1_ifg0_ifgb_rx_port_29_cgm_tc1_partially_dropped_packets {
      type oc-yang:counter64;
      description
        "RX port cgm ostc1 partial drops counter. Counts packets that were partially dropped and will be seen on RX side.";
    }
    leaf counters_slice1_ifg0_ifgb_rx_port_29_cgm_tc2_dropped_packets {
      type oc-yang:counter64;
      description
        "RX port cgm ostc2 drops counter. Counts packets that were totally dropped and will not be seen on RX side.";
    }
    leaf counters_slice1_ifg0_ifgb_rx_port_29_cgm_tc2_partially_dropped_packets {
      type oc-yang:counter64;
      description
        "RX port cgm ostc2 partial drops counter. Counts packets that were partially dropped and will be seen on RX side.";
    }
    leaf counters_slice1_ifg0_ifgb_rx_port_29_cgm_tc3_dropped_packets {
      type oc-yang:counter64;
      description
        "RX port cgm ostc3 drops counter. Counts packets that were totally dropped and will not be seen on RX side.";
    }
    leaf counters_slice1_ifg0_ifgb_rx_port_29_cgm_tc3_partially_dropped_packets {
      type oc-yang:counter64;
      description
        "RX port cgm ostc3 partial drops counter. Counts packets that were partially dropped and will be seen on RX side.";
    }
    leaf counters_slice1_ifg0_ifgb_rx_port_3_cgm_tc0_dropped_packets {
      type oc-yang:counter64;
      description
        "RX port cgm ostc0 drops counter. Counts packets that were totally dropped and will not be seen on RX side.";
    }
    leaf counters_slice1_ifg0_ifgb_rx_port_3_cgm_tc0_partially_dropped_packets {
      type oc-yang:counter64;
      description
        "RX port cgm ostc0 partial drops counter. Counts packets that were partially dropped and will be seen on RX side.";
    }
    leaf counters_slice1_ifg0_ifgb_rx_port_3_cgm_tc1_dropped_packets {
      type oc-yang:counter64;
      description
        "RX port cgm ostc1 drops counter. Counts packets that were totally dropped and will not be seen on RX side.";
    }
    leaf counters_slice1_ifg0_ifgb_rx_port_3_cgm_tc1_partially_dropped_packets {
      type oc-yang:counter64;
      description
        "RX port cgm ostc1 partial drops counter. Counts packets that were partially dropped and will be seen on RX side.";
    }
    leaf counters_slice1_ifg0_ifgb_rx_port_3_cgm_tc2_dropped_packets {
      type oc-yang:counter64;
      description
        "RX port cgm ostc2 drops counter. Counts packets that were totally dropped and will not be seen on RX side.";
    }
    leaf counters_slice1_ifg0_ifgb_rx_port_3_cgm_tc2_partially_dropped_packets {
      type oc-yang:counter64;
      description
        "RX port cgm ostc2 partial drops counter. Counts packets that were partially dropped and will be seen on RX side.";
    }
    leaf counters_slice1_ifg0_ifgb_rx_port_3_cgm_tc3_dropped_packets {
      type oc-yang:counter64;
      description
        "RX port cgm ostc3 drops counter. Counts packets that were totally dropped and will not be seen on RX side.";
    }
    leaf counters_slice1_ifg0_ifgb_rx_port_3_cgm_tc3_partially_dropped_packets {
      type oc-yang:counter64;
      description
        "RX port cgm ostc3 partial drops counter. Counts packets that were partially dropped and will be seen on RX side.";
    }
    leaf counters_slice1_ifg0_ifgb_rx_port_30_cgm_tc0_dropped_packets {
      type oc-yang:counter64;
      description
        "RX port cgm ostc0 drops counter. Counts packets that were totally dropped and will not be seen on RX side.";
    }
    leaf counters_slice1_ifg0_ifgb_rx_port_30_cgm_tc0_partially_dropped_packets {
      type oc-yang:counter64;
      description
        "RX port cgm ostc0 partial drops counter. Counts packets that were partially dropped and will be seen on RX side.";
    }
    leaf counters_slice1_ifg0_ifgb_rx_port_30_cgm_tc1_dropped_packets {
      type oc-yang:counter64;
      description
        "RX port cgm ostc1 drops counter. Counts packets that were totally dropped and will not be seen on RX side.";
    }
    leaf counters_slice1_ifg0_ifgb_rx_port_30_cgm_tc1_partially_dropped_packets {
      type oc-yang:counter64;
      description
        "RX port cgm ostc1 partial drops counter. Counts packets that were partially dropped and will be seen on RX side.";
    }
    leaf counters_slice1_ifg0_ifgb_rx_port_30_cgm_tc2_dropped_packets {
      type oc-yang:counter64;
      description
        "RX port cgm ostc2 drops counter. Counts packets that were totally dropped and will not be seen on RX side.";
    }
    leaf counters_slice1_ifg0_ifgb_rx_port_30_cgm_tc2_partially_dropped_packets {
      type oc-yang:counter64;
      description
        "RX port cgm ostc2 partial drops counter. Counts packets that were partially dropped and will be seen on RX side.";
    }
    leaf counters_slice1_ifg0_ifgb_rx_port_30_cgm_tc3_dropped_packets {
      type oc-yang:counter64;
      description
        "RX port cgm ostc3 drops counter. Counts packets that were totally dropped and will not be seen on RX side.";
    }
    leaf counters_slice1_ifg0_ifgb_rx_port_30_cgm_tc3_partially_dropped_packets {
      type oc-yang:counter64;
      description
        "RX port cgm ostc3 partial drops counter. Counts packets that were partially dropped and will be seen on RX side.";
    }
    leaf counters_slice1_ifg0_ifgb_rx_port_31_cgm_tc0_dropped_packets {
      type oc-yang:counter64;
      description
        "RX port cgm ostc0 drops counter. Counts packets that were totally dropped and will not be seen on RX side.";
    }
    leaf counters_slice1_ifg0_ifgb_rx_port_31_cgm_tc0_partially_dropped_packets {
      type oc-yang:counter64;
      description
        "RX port cgm ostc0 partial drops counter. Counts packets that were partially dropped and will be seen on RX side.";
    }
    leaf counters_slice1_ifg0_ifgb_rx_port_31_cgm_tc1_dropped_packets {
      type oc-yang:counter64;
      description
        "RX port cgm ostc1 drops counter. Counts packets that were totally dropped and will not be seen on RX side.";
    }
    leaf counters_slice1_ifg0_ifgb_rx_port_31_cgm_tc1_partially_dropped_packets {
      type oc-yang:counter64;
      description
        "RX port cgm ostc1 partial drops counter. Counts packets that were partially dropped and will be seen on RX side.";
    }
    leaf counters_slice1_ifg0_ifgb_rx_port_31_cgm_tc2_dropped_packets {
      type oc-yang:counter64;
      description
        "RX port cgm ostc2 drops counter. Counts packets that were totally dropped and will not be seen on RX side.";
    }
    leaf counters_slice1_ifg0_ifgb_rx_port_31_cgm_tc2_partially_dropped_packets {
      type oc-yang:counter64;
      description
        "RX port cgm ostc2 partial drops counter. Counts packets that were partially dropped and will be seen on RX side.";
    }
    leaf counters_slice1_ifg0_ifgb_rx_port_31_cgm_tc3_dropped_packets {
      type oc-yang:counter64;
      description
        "RX port cgm ostc3 drops counter. Counts packets that were totally dropped and will not be seen on RX side.";
    }
    leaf counters_slice1_ifg0_ifgb_rx_port_31_cgm_tc3_partially_dropped_packets {
      type oc-yang:counter64;
      description
        "RX port cgm ostc3 partial drops counter. Counts packets that were partially dropped and will be seen on RX side.";
    }
    leaf counters_slice1_ifg0_ifgb_rx_port_4_cgm_tc0_dropped_packets {
      type oc-yang:counter64;
      description
        "RX port cgm ostc0 drops counter. Counts packets that were totally dropped and will not be seen on RX side.";
    }
    leaf counters_slice1_ifg0_ifgb_rx_port_4_cgm_tc0_partially_dropped_packets {
      type oc-yang:counter64;
      description
        "RX port cgm ostc0 partial drops counter. Counts packets that were partially dropped and will be seen on RX side.";
    }
    leaf counters_slice1_ifg0_ifgb_rx_port_4_cgm_tc1_dropped_packets {
      type oc-yang:counter64;
      description
        "RX port cgm ostc1 drops counter. Counts packets that were totally dropped and will not be seen on RX side.";
    }
    leaf counters_slice1_ifg0_ifgb_rx_port_4_cgm_tc1_partially_dropped_packets {
      type oc-yang:counter64;
      description
        "RX port cgm ostc1 partial drops counter. Counts packets that were partially dropped and will be seen on RX side.";
    }
    leaf counters_slice1_ifg0_ifgb_rx_port_4_cgm_tc2_dropped_packets {
      type oc-yang:counter64;
      description
        "RX port cgm ostc2 drops counter. Counts packets that were totally dropped and will not be seen on RX side.";
    }
    leaf counters_slice1_ifg0_ifgb_rx_port_4_cgm_tc2_partially_dropped_packets {
      type oc-yang:counter64;
      description
        "RX port cgm ostc2 partial drops counter. Counts packets that were partially dropped and will be seen on RX side.";
    }
    leaf counters_slice1_ifg0_ifgb_rx_port_4_cgm_tc3_dropped_packets {
      type oc-yang:counter64;
      description
        "RX port cgm ostc3 drops counter. Counts packets that were totally dropped and will not be seen on RX side.";
    }
    leaf counters_slice1_ifg0_ifgb_rx_port_4_cgm_tc3_partially_dropped_packets {
      type oc-yang:counter64;
      description
        "RX port cgm ostc3 partial drops counter. Counts packets that were partially dropped and will be seen on RX side.";
    }
    leaf counters_slice1_ifg0_ifgb_rx_port_5_cgm_tc0_dropped_packets {
      type oc-yang:counter64;
      description
        "RX port cgm ostc0 drops counter. Counts packets that were totally dropped and will not be seen on RX side.";
    }
    leaf counters_slice1_ifg0_ifgb_rx_port_5_cgm_tc0_partially_dropped_packets {
      type oc-yang:counter64;
      description
        "RX port cgm ostc0 partial drops counter. Counts packets that were partially dropped and will be seen on RX side.";
    }
    leaf counters_slice1_ifg0_ifgb_rx_port_5_cgm_tc1_dropped_packets {
      type oc-yang:counter64;
      description
        "RX port cgm ostc1 drops counter. Counts packets that were totally dropped and will not be seen on RX side.";
    }
    leaf counters_slice1_ifg0_ifgb_rx_port_5_cgm_tc1_partially_dropped_packets {
      type oc-yang:counter64;
      description
        "RX port cgm ostc1 partial drops counter. Counts packets that were partially dropped and will be seen on RX side.";
    }
    leaf counters_slice1_ifg0_ifgb_rx_port_5_cgm_tc2_dropped_packets {
      type oc-yang:counter64;
      description
        "RX port cgm ostc2 drops counter. Counts packets that were totally dropped and will not be seen on RX side.";
    }
    leaf counters_slice1_ifg0_ifgb_rx_port_5_cgm_tc2_partially_dropped_packets {
      type oc-yang:counter64;
      description
        "RX port cgm ostc2 partial drops counter. Counts packets that were partially dropped and will be seen on RX side.";
    }
    leaf counters_slice1_ifg0_ifgb_rx_port_5_cgm_tc3_dropped_packets {
      type oc-yang:counter64;
      description
        "RX port cgm ostc3 drops counter. Counts packets that were totally dropped and will not be seen on RX side.";
    }
    leaf counters_slice1_ifg0_ifgb_rx_port_5_cgm_tc3_partially_dropped_packets {
      type oc-yang:counter64;
      description
        "RX port cgm ostc3 partial drops counter. Counts packets that were partially dropped and will be seen on RX side.";
    }
    leaf counters_slice1_ifg0_ifgb_rx_port_6_cgm_tc0_dropped_packets {
      type oc-yang:counter64;
      description
        "RX port cgm ostc0 drops counter. Counts packets that were totally dropped and will not be seen on RX side.";
    }
    leaf counters_slice1_ifg0_ifgb_rx_port_6_cgm_tc0_partially_dropped_packets {
      type oc-yang:counter64;
      description
        "RX port cgm ostc0 partial drops counter. Counts packets that were partially dropped and will be seen on RX side.";
    }
    leaf counters_slice1_ifg0_ifgb_rx_port_6_cgm_tc1_dropped_packets {
      type oc-yang:counter64;
      description
        "RX port cgm ostc1 drops counter. Counts packets that were totally dropped and will not be seen on RX side.";
    }
    leaf counters_slice1_ifg0_ifgb_rx_port_6_cgm_tc1_partially_dropped_packets {
      type oc-yang:counter64;
      description
        "RX port cgm ostc1 partial drops counter. Counts packets that were partially dropped and will be seen on RX side.";
    }
    leaf counters_slice1_ifg0_ifgb_rx_port_6_cgm_tc2_dropped_packets {
      type oc-yang:counter64;
      description
        "RX port cgm ostc2 drops counter. Counts packets that were totally dropped and will not be seen on RX side.";
    }
    leaf counters_slice1_ifg0_ifgb_rx_port_6_cgm_tc2_partially_dropped_packets {
      type oc-yang:counter64;
      description
        "RX port cgm ostc2 partial drops counter. Counts packets that were partially dropped and will be seen on RX side.";
    }
    leaf counters_slice1_ifg0_ifgb_rx_port_6_cgm_tc3_dropped_packets {
      type oc-yang:counter64;
      description
        "RX port cgm ostc3 drops counter. Counts packets that were totally dropped and will not be seen on RX side.";
    }
    leaf counters_slice1_ifg0_ifgb_rx_port_6_cgm_tc3_partially_dropped_packets {
      type oc-yang:counter64;
      description
        "RX port cgm ostc3 partial drops counter. Counts packets that were partially dropped and will be seen on RX side.";
    }
    leaf counters_slice1_ifg0_ifgb_rx_port_7_cgm_tc0_dropped_packets {
      type oc-yang:counter64;
      description
        "RX port cgm ostc0 drops counter. Counts packets that were totally dropped and will not be seen on RX side.";
    }
    leaf counters_slice1_ifg0_ifgb_rx_port_7_cgm_tc0_partially_dropped_packets {
      type oc-yang:counter64;
      description
        "RX port cgm ostc0 partial drops counter. Counts packets that were partially dropped and will be seen on RX side.";
    }
    leaf counters_slice1_ifg0_ifgb_rx_port_7_cgm_tc1_dropped_packets {
      type oc-yang:counter64;
      description
        "RX port cgm ostc1 drops counter. Counts packets that were totally dropped and will not be seen on RX side.";
    }
    leaf counters_slice1_ifg0_ifgb_rx_port_7_cgm_tc1_partially_dropped_packets {
      type oc-yang:counter64;
      description
        "RX port cgm ostc1 partial drops counter. Counts packets that were partially dropped and will be seen on RX side.";
    }
    leaf counters_slice1_ifg0_ifgb_rx_port_7_cgm_tc2_dropped_packets {
      type oc-yang:counter64;
      description
        "RX port cgm ostc2 drops counter. Counts packets that were totally dropped and will not be seen on RX side.";
    }
    leaf counters_slice1_ifg0_ifgb_rx_port_7_cgm_tc2_partially_dropped_packets {
      type oc-yang:counter64;
      description
        "RX port cgm ostc2 partial drops counter. Counts packets that were partially dropped and will be seen on RX side.";
    }
    leaf counters_slice1_ifg0_ifgb_rx_port_7_cgm_tc3_dropped_packets {
      type oc-yang:counter64;
      description
        "RX port cgm ostc3 drops counter. Counts packets that were totally dropped and will not be seen on RX side.";
    }
    leaf counters_slice1_ifg0_ifgb_rx_port_7_cgm_tc3_partially_dropped_packets {
      type oc-yang:counter64;
      description
        "RX port cgm ostc3 partial drops counter. Counts packets that were partially dropped and will be seen on RX side.";
    }
    leaf counters_slice1_ifg0_ifgb_rx_port_8_cgm_tc0_dropped_packets {
      type oc-yang:counter64;
      description
        "RX port cgm ostc0 drops counter. Counts packets that were totally dropped and will not be seen on RX side.";
    }
    leaf counters_slice1_ifg0_ifgb_rx_port_8_cgm_tc0_partially_dropped_packets {
      type oc-yang:counter64;
      description
        "RX port cgm ostc0 partial drops counter. Counts packets that were partially dropped and will be seen on RX side.";
    }
    leaf counters_slice1_ifg0_ifgb_rx_port_8_cgm_tc1_dropped_packets {
      type oc-yang:counter64;
      description
        "RX port cgm ostc1 drops counter. Counts packets that were totally dropped and will not be seen on RX side.";
    }
    leaf counters_slice1_ifg0_ifgb_rx_port_8_cgm_tc1_partially_dropped_packets {
      type oc-yang:counter64;
      description
        "RX port cgm ostc1 partial drops counter. Counts packets that were partially dropped and will be seen on RX side.";
    }
    leaf counters_slice1_ifg0_ifgb_rx_port_8_cgm_tc2_dropped_packets {
      type oc-yang:counter64;
      description
        "RX port cgm ostc2 drops counter. Counts packets that were totally dropped and will not be seen on RX side.";
    }
    leaf counters_slice1_ifg0_ifgb_rx_port_8_cgm_tc2_partially_dropped_packets {
      type oc-yang:counter64;
      description
        "RX port cgm ostc2 partial drops counter. Counts packets that were partially dropped and will be seen on RX side.";
    }
    leaf counters_slice1_ifg0_ifgb_rx_port_8_cgm_tc3_dropped_packets {
      type oc-yang:counter64;
      description
        "RX port cgm ostc3 drops counter. Counts packets that were totally dropped and will not be seen on RX side.";
    }
    leaf counters_slice1_ifg0_ifgb_rx_port_8_cgm_tc3_partially_dropped_packets {
      type oc-yang:counter64;
      description
        "RX port cgm ostc3 partial drops counter. Counts packets that were partially dropped and will be seen on RX side.";
    }
    leaf counters_slice1_ifg0_ifgb_rx_port_9_cgm_tc0_dropped_packets {
      type oc-yang:counter64;
      description
        "RX port cgm ostc0 drops counter. Counts packets that were totally dropped and will not be seen on RX side.";
    }
    leaf counters_slice1_ifg0_ifgb_rx_port_9_cgm_tc0_partially_dropped_packets {
      type oc-yang:counter64;
      description
        "RX port cgm ostc0 partial drops counter. Counts packets that were partially dropped and will be seen on RX side.";
    }
    leaf counters_slice1_ifg0_ifgb_rx_port_9_cgm_tc1_dropped_packets {
      type oc-yang:counter64;
      description
        "RX port cgm ostc1 drops counter. Counts packets that were totally dropped and will not be seen on RX side.";
    }
    leaf counters_slice1_ifg0_ifgb_rx_port_9_cgm_tc1_partially_dropped_packets {
      type oc-yang:counter64;
      description
        "RX port cgm ostc1 partial drops counter. Counts packets that were partially dropped and will be seen on RX side.";
    }
    leaf counters_slice1_ifg0_ifgb_rx_port_9_cgm_tc2_dropped_packets {
      type oc-yang:counter64;
      description
        "RX port cgm ostc2 drops counter. Counts packets that were totally dropped and will not be seen on RX side.";
    }
    leaf counters_slice1_ifg0_ifgb_rx_port_9_cgm_tc2_partially_dropped_packets {
      type oc-yang:counter64;
      description
        "RX port cgm ostc2 partial drops counter. Counts packets that were partially dropped and will be seen on RX side.";
    }
    leaf counters_slice1_ifg0_ifgb_rx_port_9_cgm_tc3_dropped_packets {
      type oc-yang:counter64;
      description
        "RX port cgm ostc3 drops counter. Counts packets that were totally dropped and will not be seen on RX side.";
    }
    leaf counters_slice1_ifg0_ifgb_rx_port_9_cgm_tc3_partially_dropped_packets {
      type oc-yang:counter64;
      description
        "RX port cgm ostc3 partial drops counter. Counts packets that were partially dropped and will be seen on RX side.";
    }
    leaf counters_slice1_ifg1_ifgb_rx_port_0_cgm_tc0_dropped_packets {
      type oc-yang:counter64;
      description
        "RX port cgm ostc0 drops counter. Counts packets that were totally dropped and will not be seen on RX side.";
    }
    leaf counters_slice1_ifg1_ifgb_rx_port_0_cgm_tc0_partially_dropped_packets {
      type oc-yang:counter64;
      description
        "RX port cgm ostc0 partial drops counter. Counts packets that were partially dropped and will be seen on RX side.";
    }
    leaf counters_slice1_ifg1_ifgb_rx_port_0_cgm_tc1_dropped_packets {
      type oc-yang:counter64;
      description
        "RX port cgm ostc1 drops counter. Counts packets that were totally dropped and will not be seen on RX side.";
    }
    leaf counters_slice1_ifg1_ifgb_rx_port_0_cgm_tc1_partially_dropped_packets {
      type oc-yang:counter64;
      description
        "RX port cgm ostc1 partial drops counter. Counts packets that were partially dropped and will be seen on RX side.";
    }
    leaf counters_slice1_ifg1_ifgb_rx_port_0_cgm_tc2_dropped_packets {
      type oc-yang:counter64;
      description
        "RX port cgm ostc2 drops counter. Counts packets that were totally dropped and will not be seen on RX side.";
    }
    leaf counters_slice1_ifg1_ifgb_rx_port_0_cgm_tc2_partially_dropped_packets {
      type oc-yang:counter64;
      description
        "RX port cgm ostc2 partial drops counter. Counts packets that were partially dropped and will be seen on RX side.";
    }
    leaf counters_slice1_ifg1_ifgb_rx_port_0_cgm_tc3_dropped_packets {
      type oc-yang:counter64;
      description
        "RX port cgm ostc3 drops counter. Counts packets that were totally dropped and will not be seen on RX side.";
    }
    leaf counters_slice1_ifg1_ifgb_rx_port_0_cgm_tc3_partially_dropped_packets {
      type oc-yang:counter64;
      description
        "RX port cgm ostc3 partial drops counter. Counts packets that were partially dropped and will be seen on RX side.";
    }
    leaf counters_slice1_ifg1_ifgb_rx_port_1_cgm_tc0_dropped_packets {
      type oc-yang:counter64;
      description
        "RX port cgm ostc0 drops counter. Counts packets that were totally dropped and will not be seen on RX side.";
    }
    leaf counters_slice1_ifg1_ifgb_rx_port_1_cgm_tc0_partially_dropped_packets {
      type oc-yang:counter64;
      description
        "RX port cgm ostc0 partial drops counter. Counts packets that were partially dropped and will be seen on RX side.";
    }
    leaf counters_slice1_ifg1_ifgb_rx_port_1_cgm_tc1_dropped_packets {
      type oc-yang:counter64;
      description
        "RX port cgm ostc1 drops counter. Counts packets that were totally dropped and will not be seen on RX side.";
    }
    leaf counters_slice1_ifg1_ifgb_rx_port_1_cgm_tc1_partially_dropped_packets {
      type oc-yang:counter64;
      description
        "RX port cgm ostc1 partial drops counter. Counts packets that were partially dropped and will be seen on RX side.";
    }
    leaf counters_slice1_ifg1_ifgb_rx_port_1_cgm_tc2_dropped_packets {
      type oc-yang:counter64;
      description
        "RX port cgm ostc2 drops counter. Counts packets that were totally dropped and will not be seen on RX side.";
    }
    leaf counters_slice1_ifg1_ifgb_rx_port_1_cgm_tc2_partially_dropped_packets {
      type oc-yang:counter64;
      description
        "RX port cgm ostc2 partial drops counter. Counts packets that were partially dropped and will be seen on RX side.";
    }
    leaf counters_slice1_ifg1_ifgb_rx_port_1_cgm_tc3_dropped_packets {
      type oc-yang:counter64;
      description
        "RX port cgm ostc3 drops counter. Counts packets that were totally dropped and will not be seen on RX side.";
    }
    leaf counters_slice1_ifg1_ifgb_rx_port_1_cgm_tc3_partially_dropped_packets {
      type oc-yang:counter64;
      description
        "RX port cgm ostc3 partial drops counter. Counts packets that were partially dropped and will be seen on RX side.";
    }
    leaf counters_slice1_ifg1_ifgb_rx_port_10_cgm_tc0_dropped_packets {
      type oc-yang:counter64;
      description
        "RX port cgm ostc0 drops counter. Counts packets that were totally dropped and will not be seen on RX side.";
    }
    leaf counters_slice1_ifg1_ifgb_rx_port_10_cgm_tc0_partially_dropped_packets {
      type oc-yang:counter64;
      description
        "RX port cgm ostc0 partial drops counter. Counts packets that were partially dropped and will be seen on RX side.";
    }
    leaf counters_slice1_ifg1_ifgb_rx_port_10_cgm_tc1_dropped_packets {
      type oc-yang:counter64;
      description
        "RX port cgm ostc1 drops counter. Counts packets that were totally dropped and will not be seen on RX side.";
    }
    leaf counters_slice1_ifg1_ifgb_rx_port_10_cgm_tc1_partially_dropped_packets {
      type oc-yang:counter64;
      description
        "RX port cgm ostc1 partial drops counter. Counts packets that were partially dropped and will be seen on RX side.";
    }
    leaf counters_slice1_ifg1_ifgb_rx_port_10_cgm_tc2_dropped_packets {
      type oc-yang:counter64;
      description
        "RX port cgm ostc2 drops counter. Counts packets that were totally dropped and will not be seen on RX side.";
    }
    leaf counters_slice1_ifg1_ifgb_rx_port_10_cgm_tc2_partially_dropped_packets {
      type oc-yang:counter64;
      description
        "RX port cgm ostc2 partial drops counter. Counts packets that were partially dropped and will be seen on RX side.";
    }
    leaf counters_slice1_ifg1_ifgb_rx_port_10_cgm_tc3_dropped_packets {
      type oc-yang:counter64;
      description
        "RX port cgm ostc3 drops counter. Counts packets that were totally dropped and will not be seen on RX side.";
    }
    leaf counters_slice1_ifg1_ifgb_rx_port_10_cgm_tc3_partially_dropped_packets {
      type oc-yang:counter64;
      description
        "RX port cgm ostc3 partial drops counter. Counts packets that were partially dropped and will be seen on RX side.";
    }
    leaf counters_slice1_ifg1_ifgb_rx_port_11_cgm_tc0_dropped_packets {
      type oc-yang:counter64;
      description
        "RX port cgm ostc0 drops counter. Counts packets that were totally dropped and will not be seen on RX side.";
    }
    leaf counters_slice1_ifg1_ifgb_rx_port_11_cgm_tc0_partially_dropped_packets {
      type oc-yang:counter64;
      description
        "RX port cgm ostc0 partial drops counter. Counts packets that were partially dropped and will be seen on RX side.";
    }
    leaf counters_slice1_ifg1_ifgb_rx_port_11_cgm_tc1_dropped_packets {
      type oc-yang:counter64;
      description
        "RX port cgm ostc1 drops counter. Counts packets that were totally dropped and will not be seen on RX side.";
    }
    leaf counters_slice1_ifg1_ifgb_rx_port_11_cgm_tc1_partially_dropped_packets {
      type oc-yang:counter64;
      description
        "RX port cgm ostc1 partial drops counter. Counts packets that were partially dropped and will be seen on RX side.";
    }
    leaf counters_slice1_ifg1_ifgb_rx_port_11_cgm_tc2_dropped_packets {
      type oc-yang:counter64;
      description
        "RX port cgm ostc2 drops counter. Counts packets that were totally dropped and will not be seen on RX side.";
    }
    leaf counters_slice1_ifg1_ifgb_rx_port_11_cgm_tc2_partially_dropped_packets {
      type oc-yang:counter64;
      description
        "RX port cgm ostc2 partial drops counter. Counts packets that were partially dropped and will be seen on RX side.";
    }
    leaf counters_slice1_ifg1_ifgb_rx_port_11_cgm_tc3_dropped_packets {
      type oc-yang:counter64;
      description
        "RX port cgm ostc3 drops counter. Counts packets that were totally dropped and will not be seen on RX side.";
    }
    leaf counters_slice1_ifg1_ifgb_rx_port_11_cgm_tc3_partially_dropped_packets {
      type oc-yang:counter64;
      description
        "RX port cgm ostc3 partial drops counter. Counts packets that were partially dropped and will be seen on RX side.";
    }
    leaf counters_slice1_ifg1_ifgb_rx_port_12_cgm_tc0_dropped_packets {
      type oc-yang:counter64;
      description
        "RX port cgm ostc0 drops counter. Counts packets that were totally dropped and will not be seen on RX side.";
    }
    leaf counters_slice1_ifg1_ifgb_rx_port_12_cgm_tc0_partially_dropped_packets {
      type oc-yang:counter64;
      description
        "RX port cgm ostc0 partial drops counter. Counts packets that were partially dropped and will be seen on RX side.";
    }
    leaf counters_slice1_ifg1_ifgb_rx_port_12_cgm_tc1_dropped_packets {
      type oc-yang:counter64;
      description
        "RX port cgm ostc1 drops counter. Counts packets that were totally dropped and will not be seen on RX side.";
    }
    leaf counters_slice1_ifg1_ifgb_rx_port_12_cgm_tc1_partially_dropped_packets {
      type oc-yang:counter64;
      description
        "RX port cgm ostc1 partial drops counter. Counts packets that were partially dropped and will be seen on RX side.";
    }
    leaf counters_slice1_ifg1_ifgb_rx_port_12_cgm_tc2_dropped_packets {
      type oc-yang:counter64;
      description
        "RX port cgm ostc2 drops counter. Counts packets that were totally dropped and will not be seen on RX side.";
    }
    leaf counters_slice1_ifg1_ifgb_rx_port_12_cgm_tc2_partially_dropped_packets {
      type oc-yang:counter64;
      description
        "RX port cgm ostc2 partial drops counter. Counts packets that were partially dropped and will be seen on RX side.";
    }
    leaf counters_slice1_ifg1_ifgb_rx_port_12_cgm_tc3_dropped_packets {
      type oc-yang:counter64;
      description
        "RX port cgm ostc3 drops counter. Counts packets that were totally dropped and will not be seen on RX side.";
    }
    leaf counters_slice1_ifg1_ifgb_rx_port_12_cgm_tc3_partially_dropped_packets {
      type oc-yang:counter64;
      description
        "RX port cgm ostc3 partial drops counter. Counts packets that were partially dropped and will be seen on RX side.";
    }
    leaf counters_slice1_ifg1_ifgb_rx_port_13_cgm_tc0_dropped_packets {
      type oc-yang:counter64;
      description
        "RX port cgm ostc0 drops counter. Counts packets that were totally dropped and will not be seen on RX side.";
    }
    leaf counters_slice1_ifg1_ifgb_rx_port_13_cgm_tc0_partially_dropped_packets {
      type oc-yang:counter64;
      description
        "RX port cgm ostc0 partial drops counter. Counts packets that were partially dropped and will be seen on RX side.";
    }
    leaf counters_slice1_ifg1_ifgb_rx_port_13_cgm_tc1_dropped_packets {
      type oc-yang:counter64;
      description
        "RX port cgm ostc1 drops counter. Counts packets that were totally dropped and will not be seen on RX side.";
    }
    leaf counters_slice1_ifg1_ifgb_rx_port_13_cgm_tc1_partially_dropped_packets {
      type oc-yang:counter64;
      description
        "RX port cgm ostc1 partial drops counter. Counts packets that were partially dropped and will be seen on RX side.";
    }
    leaf counters_slice1_ifg1_ifgb_rx_port_13_cgm_tc2_dropped_packets {
      type oc-yang:counter64;
      description
        "RX port cgm ostc2 drops counter. Counts packets that were totally dropped and will not be seen on RX side.";
    }
    leaf counters_slice1_ifg1_ifgb_rx_port_13_cgm_tc2_partially_dropped_packets {
      type oc-yang:counter64;
      description
        "RX port cgm ostc2 partial drops counter. Counts packets that were partially dropped and will be seen on RX side.";
    }
    leaf counters_slice1_ifg1_ifgb_rx_port_13_cgm_tc3_dropped_packets {
      type oc-yang:counter64;
      description
        "RX port cgm ostc3 drops counter. Counts packets that were totally dropped and will not be seen on RX side.";
    }
    leaf counters_slice1_ifg1_ifgb_rx_port_13_cgm_tc3_partially_dropped_packets {
      type oc-yang:counter64;
      description
        "RX port cgm ostc3 partial drops counter. Counts packets that were partially dropped and will be seen on RX side.";
    }
    leaf counters_slice1_ifg1_ifgb_rx_port_14_cgm_tc0_dropped_packets {
      type oc-yang:counter64;
      description
        "RX port cgm ostc0 drops counter. Counts packets that were totally dropped and will not be seen on RX side.";
    }
    leaf counters_slice1_ifg1_ifgb_rx_port_14_cgm_tc0_partially_dropped_packets {
      type oc-yang:counter64;
      description
        "RX port cgm ostc0 partial drops counter. Counts packets that were partially dropped and will be seen on RX side.";
    }
    leaf counters_slice1_ifg1_ifgb_rx_port_14_cgm_tc1_dropped_packets {
      type oc-yang:counter64;
      description
        "RX port cgm ostc1 drops counter. Counts packets that were totally dropped and will not be seen on RX side.";
    }
    leaf counters_slice1_ifg1_ifgb_rx_port_14_cgm_tc1_partially_dropped_packets {
      type oc-yang:counter64;
      description
        "RX port cgm ostc1 partial drops counter. Counts packets that were partially dropped and will be seen on RX side.";
    }
    leaf counters_slice1_ifg1_ifgb_rx_port_14_cgm_tc2_dropped_packets {
      type oc-yang:counter64;
      description
        "RX port cgm ostc2 drops counter. Counts packets that were totally dropped and will not be seen on RX side.";
    }
    leaf counters_slice1_ifg1_ifgb_rx_port_14_cgm_tc2_partially_dropped_packets {
      type oc-yang:counter64;
      description
        "RX port cgm ostc2 partial drops counter. Counts packets that were partially dropped and will be seen on RX side.";
    }
    leaf counters_slice1_ifg1_ifgb_rx_port_14_cgm_tc3_dropped_packets {
      type oc-yang:counter64;
      description
        "RX port cgm ostc3 drops counter. Counts packets that were totally dropped and will not be seen on RX side.";
    }
    leaf counters_slice1_ifg1_ifgb_rx_port_14_cgm_tc3_partially_dropped_packets {
      type oc-yang:counter64;
      description
        "RX port cgm ostc3 partial drops counter. Counts packets that were partially dropped and will be seen on RX side.";
    }
    leaf counters_slice1_ifg1_ifgb_rx_port_15_cgm_tc0_dropped_packets {
      type oc-yang:counter64;
      description
        "RX port cgm ostc0 drops counter. Counts packets that were totally dropped and will not be seen on RX side.";
    }
    leaf counters_slice1_ifg1_ifgb_rx_port_15_cgm_tc0_partially_dropped_packets {
      type oc-yang:counter64;
      description
        "RX port cgm ostc0 partial drops counter. Counts packets that were partially dropped and will be seen on RX side.";
    }
    leaf counters_slice1_ifg1_ifgb_rx_port_15_cgm_tc1_dropped_packets {
      type oc-yang:counter64;
      description
        "RX port cgm ostc1 drops counter. Counts packets that were totally dropped and will not be seen on RX side.";
    }
    leaf counters_slice1_ifg1_ifgb_rx_port_15_cgm_tc1_partially_dropped_packets {
      type oc-yang:counter64;
      description
        "RX port cgm ostc1 partial drops counter. Counts packets that were partially dropped and will be seen on RX side.";
    }
    leaf counters_slice1_ifg1_ifgb_rx_port_15_cgm_tc2_dropped_packets {
      type oc-yang:counter64;
      description
        "RX port cgm ostc2 drops counter. Counts packets that were totally dropped and will not be seen on RX side.";
    }
    leaf counters_slice1_ifg1_ifgb_rx_port_15_cgm_tc2_partially_dropped_packets {
      type oc-yang:counter64;
      description
        "RX port cgm ostc2 partial drops counter. Counts packets that were partially dropped and will be seen on RX side.";
    }
    leaf counters_slice1_ifg1_ifgb_rx_port_15_cgm_tc3_dropped_packets {
      type oc-yang:counter64;
      description
        "RX port cgm ostc3 drops counter. Counts packets that were totally dropped and will not be seen on RX side.";
    }
    leaf counters_slice1_ifg1_ifgb_rx_port_15_cgm_tc3_partially_dropped_packets {
      type oc-yang:counter64;
      description
        "RX port cgm ostc3 partial drops counter. Counts packets that were partially dropped and will be seen on RX side.";
    }
    leaf counters_slice1_ifg1_ifgb_rx_port_16_cgm_tc0_dropped_packets {
      type oc-yang:counter64;
      description
        "RX port cgm ostc0 drops counter. Counts packets that were totally dropped and will not be seen on RX side.";
    }
    leaf counters_slice1_ifg1_ifgb_rx_port_16_cgm_tc0_partially_dropped_packets {
      type oc-yang:counter64;
      description
        "RX port cgm ostc0 partial drops counter. Counts packets that were partially dropped and will be seen on RX side.";
    }
    leaf counters_slice1_ifg1_ifgb_rx_port_16_cgm_tc1_dropped_packets {
      type oc-yang:counter64;
      description
        "RX port cgm ostc1 drops counter. Counts packets that were totally dropped and will not be seen on RX side.";
    }
    leaf counters_slice1_ifg1_ifgb_rx_port_16_cgm_tc1_partially_dropped_packets {
      type oc-yang:counter64;
      description
        "RX port cgm ostc1 partial drops counter. Counts packets that were partially dropped and will be seen on RX side.";
    }
    leaf counters_slice1_ifg1_ifgb_rx_port_16_cgm_tc2_dropped_packets {
      type oc-yang:counter64;
      description
        "RX port cgm ostc2 drops counter. Counts packets that were totally dropped and will not be seen on RX side.";
    }
    leaf counters_slice1_ifg1_ifgb_rx_port_16_cgm_tc2_partially_dropped_packets {
      type oc-yang:counter64;
      description
        "RX port cgm ostc2 partial drops counter. Counts packets that were partially dropped and will be seen on RX side.";
    }
    leaf counters_slice1_ifg1_ifgb_rx_port_16_cgm_tc3_dropped_packets {
      type oc-yang:counter64;
      description
        "RX port cgm ostc3 drops counter. Counts packets that were totally dropped and will not be seen on RX side.";
    }
    leaf counters_slice1_ifg1_ifgb_rx_port_16_cgm_tc3_partially_dropped_packets {
      type oc-yang:counter64;
      description
        "RX port cgm ostc3 partial drops counter. Counts packets that were partially dropped and will be seen on RX side.";
    }
    leaf counters_slice1_ifg1_ifgb_rx_port_17_cgm_tc0_dropped_packets {
      type oc-yang:counter64;
      description
        "RX port cgm ostc0 drops counter. Counts packets that were totally dropped and will not be seen on RX side.";
    }
    leaf counters_slice1_ifg1_ifgb_rx_port_17_cgm_tc0_partially_dropped_packets {
      type oc-yang:counter64;
      description
        "RX port cgm ostc0 partial drops counter. Counts packets that were partially dropped and will be seen on RX side.";
    }
    leaf counters_slice1_ifg1_ifgb_rx_port_17_cgm_tc1_dropped_packets {
      type oc-yang:counter64;
      description
        "RX port cgm ostc1 drops counter. Counts packets that were totally dropped and will not be seen on RX side.";
    }
    leaf counters_slice1_ifg1_ifgb_rx_port_17_cgm_tc1_partially_dropped_packets {
      type oc-yang:counter64;
      description
        "RX port cgm ostc1 partial drops counter. Counts packets that were partially dropped and will be seen on RX side.";
    }
    leaf counters_slice1_ifg1_ifgb_rx_port_17_cgm_tc2_dropped_packets {
      type oc-yang:counter64;
      description
        "RX port cgm ostc2 drops counter. Counts packets that were totally dropped and will not be seen on RX side.";
    }
    leaf counters_slice1_ifg1_ifgb_rx_port_17_cgm_tc2_partially_dropped_packets {
      type oc-yang:counter64;
      description
        "RX port cgm ostc2 partial drops counter. Counts packets that were partially dropped and will be seen on RX side.";
    }
    leaf counters_slice1_ifg1_ifgb_rx_port_17_cgm_tc3_dropped_packets {
      type oc-yang:counter64;
      description
        "RX port cgm ostc3 drops counter. Counts packets that were totally dropped and will not be seen on RX side.";
    }
    leaf counters_slice1_ifg1_ifgb_rx_port_17_cgm_tc3_partially_dropped_packets {
      type oc-yang:counter64;
      description
        "RX port cgm ostc3 partial drops counter. Counts packets that were partially dropped and will be seen on RX side.";
    }
    leaf counters_slice1_ifg1_ifgb_rx_port_18_cgm_tc0_dropped_packets {
      type oc-yang:counter64;
      description
        "RX port cgm ostc0 drops counter. Counts packets that were totally dropped and will not be seen on RX side.";
    }
    leaf counters_slice1_ifg1_ifgb_rx_port_18_cgm_tc0_partially_dropped_packets {
      type oc-yang:counter64;
      description
        "RX port cgm ostc0 partial drops counter. Counts packets that were partially dropped and will be seen on RX side.";
    }
    leaf counters_slice1_ifg1_ifgb_rx_port_18_cgm_tc1_dropped_packets {
      type oc-yang:counter64;
      description
        "RX port cgm ostc1 drops counter. Counts packets that were totally dropped and will not be seen on RX side.";
    }
    leaf counters_slice1_ifg1_ifgb_rx_port_18_cgm_tc1_partially_dropped_packets {
      type oc-yang:counter64;
      description
        "RX port cgm ostc1 partial drops counter. Counts packets that were partially dropped and will be seen on RX side.";
    }
    leaf counters_slice1_ifg1_ifgb_rx_port_18_cgm_tc2_dropped_packets {
      type oc-yang:counter64;
      description
        "RX port cgm ostc2 drops counter. Counts packets that were totally dropped and will not be seen on RX side.";
    }
    leaf counters_slice1_ifg1_ifgb_rx_port_18_cgm_tc2_partially_dropped_packets {
      type oc-yang:counter64;
      description
        "RX port cgm ostc2 partial drops counter. Counts packets that were partially dropped and will be seen on RX side.";
    }
    leaf counters_slice1_ifg1_ifgb_rx_port_18_cgm_tc3_dropped_packets {
      type oc-yang:counter64;
      description
        "RX port cgm ostc3 drops counter. Counts packets that were totally dropped and will not be seen on RX side.";
    }
    leaf counters_slice1_ifg1_ifgb_rx_port_18_cgm_tc3_partially_dropped_packets {
      type oc-yang:counter64;
      description
        "RX port cgm ostc3 partial drops counter. Counts packets that were partially dropped and will be seen on RX side.";
    }
    leaf counters_slice1_ifg1_ifgb_rx_port_19_cgm_tc0_dropped_packets {
      type oc-yang:counter64;
      description
        "RX port cgm ostc0 drops counter. Counts packets that were totally dropped and will not be seen on RX side.";
    }
    leaf counters_slice1_ifg1_ifgb_rx_port_19_cgm_tc0_partially_dropped_packets {
      type oc-yang:counter64;
      description
        "RX port cgm ostc0 partial drops counter. Counts packets that were partially dropped and will be seen on RX side.";
    }
    leaf counters_slice1_ifg1_ifgb_rx_port_19_cgm_tc1_dropped_packets {
      type oc-yang:counter64;
      description
        "RX port cgm ostc1 drops counter. Counts packets that were totally dropped and will not be seen on RX side.";
    }
    leaf counters_slice1_ifg1_ifgb_rx_port_19_cgm_tc1_partially_dropped_packets {
      type oc-yang:counter64;
      description
        "RX port cgm ostc1 partial drops counter. Counts packets that were partially dropped and will be seen on RX side.";
    }
    leaf counters_slice1_ifg1_ifgb_rx_port_19_cgm_tc2_dropped_packets {
      type oc-yang:counter64;
      description
        "RX port cgm ostc2 drops counter. Counts packets that were totally dropped and will not be seen on RX side.";
    }
    leaf counters_slice1_ifg1_ifgb_rx_port_19_cgm_tc2_partially_dropped_packets {
      type oc-yang:counter64;
      description
        "RX port cgm ostc2 partial drops counter. Counts packets that were partially dropped and will be seen on RX side.";
    }
    leaf counters_slice1_ifg1_ifgb_rx_port_19_cgm_tc3_dropped_packets {
      type oc-yang:counter64;
      description
        "RX port cgm ostc3 drops counter. Counts packets that were totally dropped and will not be seen on RX side.";
    }
    leaf counters_slice1_ifg1_ifgb_rx_port_19_cgm_tc3_partially_dropped_packets {
      type oc-yang:counter64;
      description
        "RX port cgm ostc3 partial drops counter. Counts packets that were partially dropped and will be seen on RX side.";
    }
    leaf counters_slice1_ifg1_ifgb_rx_port_2_cgm_tc0_dropped_packets {
      type oc-yang:counter64;
      description
        "RX port cgm ostc0 drops counter. Counts packets that were totally dropped and will not be seen on RX side.";
    }
    leaf counters_slice1_ifg1_ifgb_rx_port_2_cgm_tc0_partially_dropped_packets {
      type oc-yang:counter64;
      description
        "RX port cgm ostc0 partial drops counter. Counts packets that were partially dropped and will be seen on RX side.";
    }
    leaf counters_slice1_ifg1_ifgb_rx_port_2_cgm_tc1_dropped_packets {
      type oc-yang:counter64;
      description
        "RX port cgm ostc1 drops counter. Counts packets that were totally dropped and will not be seen on RX side.";
    }
    leaf counters_slice1_ifg1_ifgb_rx_port_2_cgm_tc1_partially_dropped_packets {
      type oc-yang:counter64;
      description
        "RX port cgm ostc1 partial drops counter. Counts packets that were partially dropped and will be seen on RX side.";
    }
    leaf counters_slice1_ifg1_ifgb_rx_port_2_cgm_tc2_dropped_packets {
      type oc-yang:counter64;
      description
        "RX port cgm ostc2 drops counter. Counts packets that were totally dropped and will not be seen on RX side.";
    }
    leaf counters_slice1_ifg1_ifgb_rx_port_2_cgm_tc2_partially_dropped_packets {
      type oc-yang:counter64;
      description
        "RX port cgm ostc2 partial drops counter. Counts packets that were partially dropped and will be seen on RX side.";
    }
    leaf counters_slice1_ifg1_ifgb_rx_port_2_cgm_tc3_dropped_packets {
      type oc-yang:counter64;
      description
        "RX port cgm ostc3 drops counter. Counts packets that were totally dropped and will not be seen on RX side.";
    }
    leaf counters_slice1_ifg1_ifgb_rx_port_2_cgm_tc3_partially_dropped_packets {
      type oc-yang:counter64;
      description
        "RX port cgm ostc3 partial drops counter. Counts packets that were partially dropped and will be seen on RX side.";
    }
    leaf counters_slice1_ifg1_ifgb_rx_port_20_cgm_tc0_dropped_packets {
      type oc-yang:counter64;
      description
        "RX port cgm ostc0 drops counter. Counts packets that were totally dropped and will not be seen on RX side.";
    }
    leaf counters_slice1_ifg1_ifgb_rx_port_20_cgm_tc0_partially_dropped_packets {
      type oc-yang:counter64;
      description
        "RX port cgm ostc0 partial drops counter. Counts packets that were partially dropped and will be seen on RX side.";
    }
    leaf counters_slice1_ifg1_ifgb_rx_port_20_cgm_tc1_dropped_packets {
      type oc-yang:counter64;
      description
        "RX port cgm ostc1 drops counter. Counts packets that were totally dropped and will not be seen on RX side.";
    }
    leaf counters_slice1_ifg1_ifgb_rx_port_20_cgm_tc1_partially_dropped_packets {
      type oc-yang:counter64;
      description
        "RX port cgm ostc1 partial drops counter. Counts packets that were partially dropped and will be seen on RX side.";
    }
    leaf counters_slice1_ifg1_ifgb_rx_port_20_cgm_tc2_dropped_packets {
      type oc-yang:counter64;
      description
        "RX port cgm ostc2 drops counter. Counts packets that were totally dropped and will not be seen on RX side.";
    }
    leaf counters_slice1_ifg1_ifgb_rx_port_20_cgm_tc2_partially_dropped_packets {
      type oc-yang:counter64;
      description
        "RX port cgm ostc2 partial drops counter. Counts packets that were partially dropped and will be seen on RX side.";
    }
    leaf counters_slice1_ifg1_ifgb_rx_port_20_cgm_tc3_dropped_packets {
      type oc-yang:counter64;
      description
        "RX port cgm ostc3 drops counter. Counts packets that were totally dropped and will not be seen on RX side.";
    }
    leaf counters_slice1_ifg1_ifgb_rx_port_20_cgm_tc3_partially_dropped_packets {
      type oc-yang:counter64;
      description
        "RX port cgm ostc3 partial drops counter. Counts packets that were partially dropped and will be seen on RX side.";
    }
    leaf counters_slice1_ifg1_ifgb_rx_port_21_cgm_tc0_dropped_packets {
      type oc-yang:counter64;
      description
        "RX port cgm ostc0 drops counter. Counts packets that were totally dropped and will not be seen on RX side.";
    }
    leaf counters_slice1_ifg1_ifgb_rx_port_21_cgm_tc0_partially_dropped_packets {
      type oc-yang:counter64;
      description
        "RX port cgm ostc0 partial drops counter. Counts packets that were partially dropped and will be seen on RX side.";
    }
    leaf counters_slice1_ifg1_ifgb_rx_port_21_cgm_tc1_dropped_packets {
      type oc-yang:counter64;
      description
        "RX port cgm ostc1 drops counter. Counts packets that were totally dropped and will not be seen on RX side.";
    }
    leaf counters_slice1_ifg1_ifgb_rx_port_21_cgm_tc1_partially_dropped_packets {
      type oc-yang:counter64;
      description
        "RX port cgm ostc1 partial drops counter. Counts packets that were partially dropped and will be seen on RX side.";
    }
    leaf counters_slice1_ifg1_ifgb_rx_port_21_cgm_tc2_dropped_packets {
      type oc-yang:counter64;
      description
        "RX port cgm ostc2 drops counter. Counts packets that were totally dropped and will not be seen on RX side.";
    }
    leaf counters_slice1_ifg1_ifgb_rx_port_21_cgm_tc2_partially_dropped_packets {
      type oc-yang:counter64;
      description
        "RX port cgm ostc2 partial drops counter. Counts packets that were partially dropped and will be seen on RX side.";
    }
    leaf counters_slice1_ifg1_ifgb_rx_port_21_cgm_tc3_dropped_packets {
      type oc-yang:counter64;
      description
        "RX port cgm ostc3 drops counter. Counts packets that were totally dropped and will not be seen on RX side.";
    }
    leaf counters_slice1_ifg1_ifgb_rx_port_21_cgm_tc3_partially_dropped_packets {
      type oc-yang:counter64;
      description
        "RX port cgm ostc3 partial drops counter. Counts packets that were partially dropped and will be seen on RX side.";
    }
    leaf counters_slice1_ifg1_ifgb_rx_port_22_cgm_tc0_dropped_packets {
      type oc-yang:counter64;
      description
        "RX port cgm ostc0 drops counter. Counts packets that were totally dropped and will not be seen on RX side.";
    }
    leaf counters_slice1_ifg1_ifgb_rx_port_22_cgm_tc0_partially_dropped_packets {
      type oc-yang:counter64;
      description
        "RX port cgm ostc0 partial drops counter. Counts packets that were partially dropped and will be seen on RX side.";
    }
    leaf counters_slice1_ifg1_ifgb_rx_port_22_cgm_tc1_dropped_packets {
      type oc-yang:counter64;
      description
        "RX port cgm ostc1 drops counter. Counts packets that were totally dropped and will not be seen on RX side.";
    }
    leaf counters_slice1_ifg1_ifgb_rx_port_22_cgm_tc1_partially_dropped_packets {
      type oc-yang:counter64;
      description
        "RX port cgm ostc1 partial drops counter. Counts packets that were partially dropped and will be seen on RX side.";
    }
    leaf counters_slice1_ifg1_ifgb_rx_port_22_cgm_tc2_dropped_packets {
      type oc-yang:counter64;
      description
        "RX port cgm ostc2 drops counter. Counts packets that were totally dropped and will not be seen on RX side.";
    }
    leaf counters_slice1_ifg1_ifgb_rx_port_22_cgm_tc2_partially_dropped_packets {
      type oc-yang:counter64;
      description
        "RX port cgm ostc2 partial drops counter. Counts packets that were partially dropped and will be seen on RX side.";
    }
    leaf counters_slice1_ifg1_ifgb_rx_port_22_cgm_tc3_dropped_packets {
      type oc-yang:counter64;
      description
        "RX port cgm ostc3 drops counter. Counts packets that were totally dropped and will not be seen on RX side.";
    }
    leaf counters_slice1_ifg1_ifgb_rx_port_22_cgm_tc3_partially_dropped_packets {
      type oc-yang:counter64;
      description
        "RX port cgm ostc3 partial drops counter. Counts packets that were partially dropped and will be seen on RX side.";
    }
    leaf counters_slice1_ifg1_ifgb_rx_port_23_cgm_tc0_dropped_packets {
      type oc-yang:counter64;
      description
        "RX port cgm ostc0 drops counter. Counts packets that were totally dropped and will not be seen on RX side.";
    }
    leaf counters_slice1_ifg1_ifgb_rx_port_23_cgm_tc0_partially_dropped_packets {
      type oc-yang:counter64;
      description
        "RX port cgm ostc0 partial drops counter. Counts packets that were partially dropped and will be seen on RX side.";
    }
    leaf counters_slice1_ifg1_ifgb_rx_port_23_cgm_tc1_dropped_packets {
      type oc-yang:counter64;
      description
        "RX port cgm ostc1 drops counter. Counts packets that were totally dropped and will not be seen on RX side.";
    }
    leaf counters_slice1_ifg1_ifgb_rx_port_23_cgm_tc1_partially_dropped_packets {
      type oc-yang:counter64;
      description
        "RX port cgm ostc1 partial drops counter. Counts packets that were partially dropped and will be seen on RX side.";
    }
    leaf counters_slice1_ifg1_ifgb_rx_port_23_cgm_tc2_dropped_packets {
      type oc-yang:counter64;
      description
        "RX port cgm ostc2 drops counter. Counts packets that were totally dropped and will not be seen on RX side.";
    }
    leaf counters_slice1_ifg1_ifgb_rx_port_23_cgm_tc2_partially_dropped_packets {
      type oc-yang:counter64;
      description
        "RX port cgm ostc2 partial drops counter. Counts packets that were partially dropped and will be seen on RX side.";
    }
    leaf counters_slice1_ifg1_ifgb_rx_port_23_cgm_tc3_dropped_packets {
      type oc-yang:counter64;
      description
        "RX port cgm ostc3 drops counter. Counts packets that were totally dropped and will not be seen on RX side.";
    }
    leaf counters_slice1_ifg1_ifgb_rx_port_23_cgm_tc3_partially_dropped_packets {
      type oc-yang:counter64;
      description
        "RX port cgm ostc3 partial drops counter. Counts packets that were partially dropped and will be seen on RX side.";
    }
    leaf counters_slice1_ifg1_ifgb_rx_port_24_cgm_tc0_dropped_packets {
      type oc-yang:counter64;
      description
        "RX port cgm ostc0 drops counter. Counts packets that were totally dropped and will not be seen on RX side.";
    }
    leaf counters_slice1_ifg1_ifgb_rx_port_24_cgm_tc0_partially_dropped_packets {
      type oc-yang:counter64;
      description
        "RX port cgm ostc0 partial drops counter. Counts packets that were partially dropped and will be seen on RX side.";
    }
    leaf counters_slice1_ifg1_ifgb_rx_port_24_cgm_tc1_dropped_packets {
      type oc-yang:counter64;
      description
        "RX port cgm ostc1 drops counter. Counts packets that were totally dropped and will not be seen on RX side.";
    }
    leaf counters_slice1_ifg1_ifgb_rx_port_24_cgm_tc1_partially_dropped_packets {
      type oc-yang:counter64;
      description
        "RX port cgm ostc1 partial drops counter. Counts packets that were partially dropped and will be seen on RX side.";
    }
    leaf counters_slice1_ifg1_ifgb_rx_port_24_cgm_tc2_dropped_packets {
      type oc-yang:counter64;
      description
        "RX port cgm ostc2 drops counter. Counts packets that were totally dropped and will not be seen on RX side.";
    }
    leaf counters_slice1_ifg1_ifgb_rx_port_24_cgm_tc2_partially_dropped_packets {
      type oc-yang:counter64;
      description
        "RX port cgm ostc2 partial drops counter. Counts packets that were partially dropped and will be seen on RX side.";
    }
    leaf counters_slice1_ifg1_ifgb_rx_port_24_cgm_tc3_dropped_packets {
      type oc-yang:counter64;
      description
        "RX port cgm ostc3 drops counter. Counts packets that were totally dropped and will not be seen on RX side.";
    }
    leaf counters_slice1_ifg1_ifgb_rx_port_24_cgm_tc3_partially_dropped_packets {
      type oc-yang:counter64;
      description
        "RX port cgm ostc3 partial drops counter. Counts packets that were partially dropped and will be seen on RX side.";
    }
    leaf counters_slice1_ifg1_ifgb_rx_port_25_cgm_tc0_dropped_packets {
      type oc-yang:counter64;
      description
        "RX port cgm ostc0 drops counter. Counts packets that were totally dropped and will not be seen on RX side.";
    }
    leaf counters_slice1_ifg1_ifgb_rx_port_25_cgm_tc0_partially_dropped_packets {
      type oc-yang:counter64;
      description
        "RX port cgm ostc0 partial drops counter. Counts packets that were partially dropped and will be seen on RX side.";
    }
    leaf counters_slice1_ifg1_ifgb_rx_port_25_cgm_tc1_dropped_packets {
      type oc-yang:counter64;
      description
        "RX port cgm ostc1 drops counter. Counts packets that were totally dropped and will not be seen on RX side.";
    }
    leaf counters_slice1_ifg1_ifgb_rx_port_25_cgm_tc1_partially_dropped_packets {
      type oc-yang:counter64;
      description
        "RX port cgm ostc1 partial drops counter. Counts packets that were partially dropped and will be seen on RX side.";
    }
    leaf counters_slice1_ifg1_ifgb_rx_port_25_cgm_tc2_dropped_packets {
      type oc-yang:counter64;
      description
        "RX port cgm ostc2 drops counter. Counts packets that were totally dropped and will not be seen on RX side.";
    }
    leaf counters_slice1_ifg1_ifgb_rx_port_25_cgm_tc2_partially_dropped_packets {
      type oc-yang:counter64;
      description
        "RX port cgm ostc2 partial drops counter. Counts packets that were partially dropped and will be seen on RX side.";
    }
    leaf counters_slice1_ifg1_ifgb_rx_port_25_cgm_tc3_dropped_packets {
      type oc-yang:counter64;
      description
        "RX port cgm ostc3 drops counter. Counts packets that were totally dropped and will not be seen on RX side.";
    }
    leaf counters_slice1_ifg1_ifgb_rx_port_25_cgm_tc3_partially_dropped_packets {
      type oc-yang:counter64;
      description
        "RX port cgm ostc3 partial drops counter. Counts packets that were partially dropped and will be seen on RX side.";
    }
    leaf counters_slice1_ifg1_ifgb_rx_port_26_cgm_tc0_dropped_packets {
      type oc-yang:counter64;
      description
        "RX port cgm ostc0 drops counter. Counts packets that were totally dropped and will not be seen on RX side.";
    }
    leaf counters_slice1_ifg1_ifgb_rx_port_26_cgm_tc0_partially_dropped_packets {
      type oc-yang:counter64;
      description
        "RX port cgm ostc0 partial drops counter. Counts packets that were partially dropped and will be seen on RX side.";
    }
    leaf counters_slice1_ifg1_ifgb_rx_port_26_cgm_tc1_dropped_packets {
      type oc-yang:counter64;
      description
        "RX port cgm ostc1 drops counter. Counts packets that were totally dropped and will not be seen on RX side.";
    }
    leaf counters_slice1_ifg1_ifgb_rx_port_26_cgm_tc1_partially_dropped_packets {
      type oc-yang:counter64;
      description
        "RX port cgm ostc1 partial drops counter. Counts packets that were partially dropped and will be seen on RX side.";
    }
    leaf counters_slice1_ifg1_ifgb_rx_port_26_cgm_tc2_dropped_packets {
      type oc-yang:counter64;
      description
        "RX port cgm ostc2 drops counter. Counts packets that were totally dropped and will not be seen on RX side.";
    }
    leaf counters_slice1_ifg1_ifgb_rx_port_26_cgm_tc2_partially_dropped_packets {
      type oc-yang:counter64;
      description
        "RX port cgm ostc2 partial drops counter. Counts packets that were partially dropped and will be seen on RX side.";
    }
    leaf counters_slice1_ifg1_ifgb_rx_port_26_cgm_tc3_dropped_packets {
      type oc-yang:counter64;
      description
        "RX port cgm ostc3 drops counter. Counts packets that were totally dropped and will not be seen on RX side.";
    }
    leaf counters_slice1_ifg1_ifgb_rx_port_26_cgm_tc3_partially_dropped_packets {
      type oc-yang:counter64;
      description
        "RX port cgm ostc3 partial drops counter. Counts packets that were partially dropped and will be seen on RX side.";
    }
    leaf counters_slice1_ifg1_ifgb_rx_port_27_cgm_tc0_dropped_packets {
      type oc-yang:counter64;
      description
        "RX port cgm ostc0 drops counter. Counts packets that were totally dropped and will not be seen on RX side.";
    }
    leaf counters_slice1_ifg1_ifgb_rx_port_27_cgm_tc0_partially_dropped_packets {
      type oc-yang:counter64;
      description
        "RX port cgm ostc0 partial drops counter. Counts packets that were partially dropped and will be seen on RX side.";
    }
    leaf counters_slice1_ifg1_ifgb_rx_port_27_cgm_tc1_dropped_packets {
      type oc-yang:counter64;
      description
        "RX port cgm ostc1 drops counter. Counts packets that were totally dropped and will not be seen on RX side.";
    }
    leaf counters_slice1_ifg1_ifgb_rx_port_27_cgm_tc1_partially_dropped_packets {
      type oc-yang:counter64;
      description
        "RX port cgm ostc1 partial drops counter. Counts packets that were partially dropped and will be seen on RX side.";
    }
    leaf counters_slice1_ifg1_ifgb_rx_port_27_cgm_tc2_dropped_packets {
      type oc-yang:counter64;
      description
        "RX port cgm ostc2 drops counter. Counts packets that were totally dropped and will not be seen on RX side.";
    }
    leaf counters_slice1_ifg1_ifgb_rx_port_27_cgm_tc2_partially_dropped_packets {
      type oc-yang:counter64;
      description
        "RX port cgm ostc2 partial drops counter. Counts packets that were partially dropped and will be seen on RX side.";
    }
    leaf counters_slice1_ifg1_ifgb_rx_port_27_cgm_tc3_dropped_packets {
      type oc-yang:counter64;
      description
        "RX port cgm ostc3 drops counter. Counts packets that were totally dropped and will not be seen on RX side.";
    }
    leaf counters_slice1_ifg1_ifgb_rx_port_27_cgm_tc3_partially_dropped_packets {
      type oc-yang:counter64;
      description
        "RX port cgm ostc3 partial drops counter. Counts packets that were partially dropped and will be seen on RX side.";
    }
    leaf counters_slice1_ifg1_ifgb_rx_port_28_cgm_tc0_dropped_packets {
      type oc-yang:counter64;
      description
        "RX port cgm ostc0 drops counter. Counts packets that were totally dropped and will not be seen on RX side.";
    }
    leaf counters_slice1_ifg1_ifgb_rx_port_28_cgm_tc0_partially_dropped_packets {
      type oc-yang:counter64;
      description
        "RX port cgm ostc0 partial drops counter. Counts packets that were partially dropped and will be seen on RX side.";
    }
    leaf counters_slice1_ifg1_ifgb_rx_port_28_cgm_tc1_dropped_packets {
      type oc-yang:counter64;
      description
        "RX port cgm ostc1 drops counter. Counts packets that were totally dropped and will not be seen on RX side.";
    }
    leaf counters_slice1_ifg1_ifgb_rx_port_28_cgm_tc1_partially_dropped_packets {
      type oc-yang:counter64;
      description
        "RX port cgm ostc1 partial drops counter. Counts packets that were partially dropped and will be seen on RX side.";
    }
    leaf counters_slice1_ifg1_ifgb_rx_port_28_cgm_tc2_dropped_packets {
      type oc-yang:counter64;
      description
        "RX port cgm ostc2 drops counter. Counts packets that were totally dropped and will not be seen on RX side.";
    }
    leaf counters_slice1_ifg1_ifgb_rx_port_28_cgm_tc2_partially_dropped_packets {
      type oc-yang:counter64;
      description
        "RX port cgm ostc2 partial drops counter. Counts packets that were partially dropped and will be seen on RX side.";
    }
    leaf counters_slice1_ifg1_ifgb_rx_port_28_cgm_tc3_dropped_packets {
      type oc-yang:counter64;
      description
        "RX port cgm ostc3 drops counter. Counts packets that were totally dropped and will not be seen on RX side.";
    }
    leaf counters_slice1_ifg1_ifgb_rx_port_28_cgm_tc3_partially_dropped_packets {
      type oc-yang:counter64;
      description
        "RX port cgm ostc3 partial drops counter. Counts packets that were partially dropped and will be seen on RX side.";
    }
    leaf counters_slice1_ifg1_ifgb_rx_port_29_cgm_tc0_dropped_packets {
      type oc-yang:counter64;
      description
        "RX port cgm ostc0 drops counter. Counts packets that were totally dropped and will not be seen on RX side.";
    }
    leaf counters_slice1_ifg1_ifgb_rx_port_29_cgm_tc0_partially_dropped_packets {
      type oc-yang:counter64;
      description
        "RX port cgm ostc0 partial drops counter. Counts packets that were partially dropped and will be seen on RX side.";
    }
    leaf counters_slice1_ifg1_ifgb_rx_port_29_cgm_tc1_dropped_packets {
      type oc-yang:counter64;
      description
        "RX port cgm ostc1 drops counter. Counts packets that were totally dropped and will not be seen on RX side.";
    }
    leaf counters_slice1_ifg1_ifgb_rx_port_29_cgm_tc1_partially_dropped_packets {
      type oc-yang:counter64;
      description
        "RX port cgm ostc1 partial drops counter. Counts packets that were partially dropped and will be seen on RX side.";
    }
    leaf counters_slice1_ifg1_ifgb_rx_port_29_cgm_tc2_dropped_packets {
      type oc-yang:counter64;
      description
        "RX port cgm ostc2 drops counter. Counts packets that were totally dropped and will not be seen on RX side.";
    }
    leaf counters_slice1_ifg1_ifgb_rx_port_29_cgm_tc2_partially_dropped_packets {
      type oc-yang:counter64;
      description
        "RX port cgm ostc2 partial drops counter. Counts packets that were partially dropped and will be seen on RX side.";
    }
    leaf counters_slice1_ifg1_ifgb_rx_port_29_cgm_tc3_dropped_packets {
      type oc-yang:counter64;
      description
        "RX port cgm ostc3 drops counter. Counts packets that were totally dropped and will not be seen on RX side.";
    }
    leaf counters_slice1_ifg1_ifgb_rx_port_29_cgm_tc3_partially_dropped_packets {
      type oc-yang:counter64;
      description
        "RX port cgm ostc3 partial drops counter. Counts packets that were partially dropped and will be seen on RX side.";
    }
    leaf counters_slice1_ifg1_ifgb_rx_port_3_cgm_tc0_dropped_packets {
      type oc-yang:counter64;
      description
        "RX port cgm ostc0 drops counter. Counts packets that were totally dropped and will not be seen on RX side.";
    }
    leaf counters_slice1_ifg1_ifgb_rx_port_3_cgm_tc0_partially_dropped_packets {
      type oc-yang:counter64;
      description
        "RX port cgm ostc0 partial drops counter. Counts packets that were partially dropped and will be seen on RX side.";
    }
    leaf counters_slice1_ifg1_ifgb_rx_port_3_cgm_tc1_dropped_packets {
      type oc-yang:counter64;
      description
        "RX port cgm ostc1 drops counter. Counts packets that were totally dropped and will not be seen on RX side.";
    }
    leaf counters_slice1_ifg1_ifgb_rx_port_3_cgm_tc1_partially_dropped_packets {
      type oc-yang:counter64;
      description
        "RX port cgm ostc1 partial drops counter. Counts packets that were partially dropped and will be seen on RX side.";
    }
    leaf counters_slice1_ifg1_ifgb_rx_port_3_cgm_tc2_dropped_packets {
      type oc-yang:counter64;
      description
        "RX port cgm ostc2 drops counter. Counts packets that were totally dropped and will not be seen on RX side.";
    }
    leaf counters_slice1_ifg1_ifgb_rx_port_3_cgm_tc2_partially_dropped_packets {
      type oc-yang:counter64;
      description
        "RX port cgm ostc2 partial drops counter. Counts packets that were partially dropped and will be seen on RX side.";
    }
    leaf counters_slice1_ifg1_ifgb_rx_port_3_cgm_tc3_dropped_packets {
      type oc-yang:counter64;
      description
        "RX port cgm ostc3 drops counter. Counts packets that were totally dropped and will not be seen on RX side.";
    }
    leaf counters_slice1_ifg1_ifgb_rx_port_3_cgm_tc3_partially_dropped_packets {
      type oc-yang:counter64;
      description
        "RX port cgm ostc3 partial drops counter. Counts packets that were partially dropped and will be seen on RX side.";
    }
    leaf counters_slice1_ifg1_ifgb_rx_port_30_cgm_tc0_dropped_packets {
      type oc-yang:counter64;
      description
        "RX port cgm ostc0 drops counter. Counts packets that were totally dropped and will not be seen on RX side.";
    }
    leaf counters_slice1_ifg1_ifgb_rx_port_30_cgm_tc0_partially_dropped_packets {
      type oc-yang:counter64;
      description
        "RX port cgm ostc0 partial drops counter. Counts packets that were partially dropped and will be seen on RX side.";
    }
    leaf counters_slice1_ifg1_ifgb_rx_port_30_cgm_tc1_dropped_packets {
      type oc-yang:counter64;
      description
        "RX port cgm ostc1 drops counter. Counts packets that were totally dropped and will not be seen on RX side.";
    }
    leaf counters_slice1_ifg1_ifgb_rx_port_30_cgm_tc1_partially_dropped_packets {
      type oc-yang:counter64;
      description
        "RX port cgm ostc1 partial drops counter. Counts packets that were partially dropped and will be seen on RX side.";
    }
    leaf counters_slice1_ifg1_ifgb_rx_port_30_cgm_tc2_dropped_packets {
      type oc-yang:counter64;
      description
        "RX port cgm ostc2 drops counter. Counts packets that were totally dropped and will not be seen on RX side.";
    }
    leaf counters_slice1_ifg1_ifgb_rx_port_30_cgm_tc2_partially_dropped_packets {
      type oc-yang:counter64;
      description
        "RX port cgm ostc2 partial drops counter. Counts packets that were partially dropped and will be seen on RX side.";
    }
    leaf counters_slice1_ifg1_ifgb_rx_port_30_cgm_tc3_dropped_packets {
      type oc-yang:counter64;
      description
        "RX port cgm ostc3 drops counter. Counts packets that were totally dropped and will not be seen on RX side.";
    }
    leaf counters_slice1_ifg1_ifgb_rx_port_30_cgm_tc3_partially_dropped_packets {
      type oc-yang:counter64;
      description
        "RX port cgm ostc3 partial drops counter. Counts packets that were partially dropped and will be seen on RX side.";
    }
    leaf counters_slice1_ifg1_ifgb_rx_port_31_cgm_tc0_dropped_packets {
      type oc-yang:counter64;
      description
        "RX port cgm ostc0 drops counter. Counts packets that were totally dropped and will not be seen on RX side.";
    }
    leaf counters_slice1_ifg1_ifgb_rx_port_31_cgm_tc0_partially_dropped_packets {
      type oc-yang:counter64;
      description
        "RX port cgm ostc0 partial drops counter. Counts packets that were partially dropped and will be seen on RX side.";
    }
    leaf counters_slice1_ifg1_ifgb_rx_port_31_cgm_tc1_dropped_packets {
      type oc-yang:counter64;
      description
        "RX port cgm ostc1 drops counter. Counts packets that were totally dropped and will not be seen on RX side.";
    }
    leaf counters_slice1_ifg1_ifgb_rx_port_31_cgm_tc1_partially_dropped_packets {
      type oc-yang:counter64;
      description
        "RX port cgm ostc1 partial drops counter. Counts packets that were partially dropped and will be seen on RX side.";
    }
    leaf counters_slice1_ifg1_ifgb_rx_port_31_cgm_tc2_dropped_packets {
      type oc-yang:counter64;
      description
        "RX port cgm ostc2 drops counter. Counts packets that were totally dropped and will not be seen on RX side.";
    }
    leaf counters_slice1_ifg1_ifgb_rx_port_31_cgm_tc2_partially_dropped_packets {
      type oc-yang:counter64;
      description
        "RX port cgm ostc2 partial drops counter. Counts packets that were partially dropped and will be seen on RX side.";
    }
    leaf counters_slice1_ifg1_ifgb_rx_port_31_cgm_tc3_dropped_packets {
      type oc-yang:counter64;
      description
        "RX port cgm ostc3 drops counter. Counts packets that were totally dropped and will not be seen on RX side.";
    }
    leaf counters_slice1_ifg1_ifgb_rx_port_31_cgm_tc3_partially_dropped_packets {
      type oc-yang:counter64;
      description
        "RX port cgm ostc3 partial drops counter. Counts packets that were partially dropped and will be seen on RX side.";
    }
    leaf counters_slice1_ifg1_ifgb_rx_port_4_cgm_tc0_dropped_packets {
      type oc-yang:counter64;
      description
        "RX port cgm ostc0 drops counter. Counts packets that were totally dropped and will not be seen on RX side.";
    }
    leaf counters_slice1_ifg1_ifgb_rx_port_4_cgm_tc0_partially_dropped_packets {
      type oc-yang:counter64;
      description
        "RX port cgm ostc0 partial drops counter. Counts packets that were partially dropped and will be seen on RX side.";
    }
    leaf counters_slice1_ifg1_ifgb_rx_port_4_cgm_tc1_dropped_packets {
      type oc-yang:counter64;
      description
        "RX port cgm ostc1 drops counter. Counts packets that were totally dropped and will not be seen on RX side.";
    }
    leaf counters_slice1_ifg1_ifgb_rx_port_4_cgm_tc1_partially_dropped_packets {
      type oc-yang:counter64;
      description
        "RX port cgm ostc1 partial drops counter. Counts packets that were partially dropped and will be seen on RX side.";
    }
    leaf counters_slice1_ifg1_ifgb_rx_port_4_cgm_tc2_dropped_packets {
      type oc-yang:counter64;
      description
        "RX port cgm ostc2 drops counter. Counts packets that were totally dropped and will not be seen on RX side.";
    }
    leaf counters_slice1_ifg1_ifgb_rx_port_4_cgm_tc2_partially_dropped_packets {
      type oc-yang:counter64;
      description
        "RX port cgm ostc2 partial drops counter. Counts packets that were partially dropped and will be seen on RX side.";
    }
    leaf counters_slice1_ifg1_ifgb_rx_port_4_cgm_tc3_dropped_packets {
      type oc-yang:counter64;
      description
        "RX port cgm ostc3 drops counter. Counts packets that were totally dropped and will not be seen on RX side.";
    }
    leaf counters_slice1_ifg1_ifgb_rx_port_4_cgm_tc3_partially_dropped_packets {
      type oc-yang:counter64;
      description
        "RX port cgm ostc3 partial drops counter. Counts packets that were partially dropped and will be seen on RX side.";
    }
    leaf counters_slice1_ifg1_ifgb_rx_port_5_cgm_tc0_dropped_packets {
      type oc-yang:counter64;
      description
        "RX port cgm ostc0 drops counter. Counts packets that were totally dropped and will not be seen on RX side.";
    }
    leaf counters_slice1_ifg1_ifgb_rx_port_5_cgm_tc0_partially_dropped_packets {
      type oc-yang:counter64;
      description
        "RX port cgm ostc0 partial drops counter. Counts packets that were partially dropped and will be seen on RX side.";
    }
    leaf counters_slice1_ifg1_ifgb_rx_port_5_cgm_tc1_dropped_packets {
      type oc-yang:counter64;
      description
        "RX port cgm ostc1 drops counter. Counts packets that were totally dropped and will not be seen on RX side.";
    }
    leaf counters_slice1_ifg1_ifgb_rx_port_5_cgm_tc1_partially_dropped_packets {
      type oc-yang:counter64;
      description
        "RX port cgm ostc1 partial drops counter. Counts packets that were partially dropped and will be seen on RX side.";
    }
    leaf counters_slice1_ifg1_ifgb_rx_port_5_cgm_tc2_dropped_packets {
      type oc-yang:counter64;
      description
        "RX port cgm ostc2 drops counter. Counts packets that were totally dropped and will not be seen on RX side.";
    }
    leaf counters_slice1_ifg1_ifgb_rx_port_5_cgm_tc2_partially_dropped_packets {
      type oc-yang:counter64;
      description
        "RX port cgm ostc2 partial drops counter. Counts packets that were partially dropped and will be seen on RX side.";
    }
    leaf counters_slice1_ifg1_ifgb_rx_port_5_cgm_tc3_dropped_packets {
      type oc-yang:counter64;
      description
        "RX port cgm ostc3 drops counter. Counts packets that were totally dropped and will not be seen on RX side.";
    }
    leaf counters_slice1_ifg1_ifgb_rx_port_5_cgm_tc3_partially_dropped_packets {
      type oc-yang:counter64;
      description
        "RX port cgm ostc3 partial drops counter. Counts packets that were partially dropped and will be seen on RX side.";
    }
    leaf counters_slice1_ifg1_ifgb_rx_port_6_cgm_tc0_dropped_packets {
      type oc-yang:counter64;
      description
        "RX port cgm ostc0 drops counter. Counts packets that were totally dropped and will not be seen on RX side.";
    }
    leaf counters_slice1_ifg1_ifgb_rx_port_6_cgm_tc0_partially_dropped_packets {
      type oc-yang:counter64;
      description
        "RX port cgm ostc0 partial drops counter. Counts packets that were partially dropped and will be seen on RX side.";
    }
    leaf counters_slice1_ifg1_ifgb_rx_port_6_cgm_tc1_dropped_packets {
      type oc-yang:counter64;
      description
        "RX port cgm ostc1 drops counter. Counts packets that were totally dropped and will not be seen on RX side.";
    }
    leaf counters_slice1_ifg1_ifgb_rx_port_6_cgm_tc1_partially_dropped_packets {
      type oc-yang:counter64;
      description
        "RX port cgm ostc1 partial drops counter. Counts packets that were partially dropped and will be seen on RX side.";
    }
    leaf counters_slice1_ifg1_ifgb_rx_port_6_cgm_tc2_dropped_packets {
      type oc-yang:counter64;
      description
        "RX port cgm ostc2 drops counter. Counts packets that were totally dropped and will not be seen on RX side.";
    }
    leaf counters_slice1_ifg1_ifgb_rx_port_6_cgm_tc2_partially_dropped_packets {
      type oc-yang:counter64;
      description
        "RX port cgm ostc2 partial drops counter. Counts packets that were partially dropped and will be seen on RX side.";
    }
    leaf counters_slice1_ifg1_ifgb_rx_port_6_cgm_tc3_dropped_packets {
      type oc-yang:counter64;
      description
        "RX port cgm ostc3 drops counter. Counts packets that were totally dropped and will not be seen on RX side.";
    }
    leaf counters_slice1_ifg1_ifgb_rx_port_6_cgm_tc3_partially_dropped_packets {
      type oc-yang:counter64;
      description
        "RX port cgm ostc3 partial drops counter. Counts packets that were partially dropped and will be seen on RX side.";
    }
    leaf counters_slice1_ifg1_ifgb_rx_port_7_cgm_tc0_dropped_packets {
      type oc-yang:counter64;
      description
        "RX port cgm ostc0 drops counter. Counts packets that were totally dropped and will not be seen on RX side.";
    }
    leaf counters_slice1_ifg1_ifgb_rx_port_7_cgm_tc0_partially_dropped_packets {
      type oc-yang:counter64;
      description
        "RX port cgm ostc0 partial drops counter. Counts packets that were partially dropped and will be seen on RX side.";
    }
    leaf counters_slice1_ifg1_ifgb_rx_port_7_cgm_tc1_dropped_packets {
      type oc-yang:counter64;
      description
        "RX port cgm ostc1 drops counter. Counts packets that were totally dropped and will not be seen on RX side.";
    }
    leaf counters_slice1_ifg1_ifgb_rx_port_7_cgm_tc1_partially_dropped_packets {
      type oc-yang:counter64;
      description
        "RX port cgm ostc1 partial drops counter. Counts packets that were partially dropped and will be seen on RX side.";
    }
    leaf counters_slice1_ifg1_ifgb_rx_port_7_cgm_tc2_dropped_packets {
      type oc-yang:counter64;
      description
        "RX port cgm ostc2 drops counter. Counts packets that were totally dropped and will not be seen on RX side.";
    }
    leaf counters_slice1_ifg1_ifgb_rx_port_7_cgm_tc2_partially_dropped_packets {
      type oc-yang:counter64;
      description
        "RX port cgm ostc2 partial drops counter. Counts packets that were partially dropped and will be seen on RX side.";
    }
    leaf counters_slice1_ifg1_ifgb_rx_port_7_cgm_tc3_dropped_packets {
      type oc-yang:counter64;
      description
        "RX port cgm ostc3 drops counter. Counts packets that were totally dropped and will not be seen on RX side.";
    }
    leaf counters_slice1_ifg1_ifgb_rx_port_7_cgm_tc3_partially_dropped_packets {
      type oc-yang:counter64;
      description
        "RX port cgm ostc3 partial drops counter. Counts packets that were partially dropped and will be seen on RX side.";
    }
    leaf counters_slice1_ifg1_ifgb_rx_port_8_cgm_tc0_dropped_packets {
      type oc-yang:counter64;
      description
        "RX port cgm ostc0 drops counter. Counts packets that were totally dropped and will not be seen on RX side.";
    }
    leaf counters_slice1_ifg1_ifgb_rx_port_8_cgm_tc0_partially_dropped_packets {
      type oc-yang:counter64;
      description
        "RX port cgm ostc0 partial drops counter. Counts packets that were partially dropped and will be seen on RX side.";
    }
    leaf counters_slice1_ifg1_ifgb_rx_port_8_cgm_tc1_dropped_packets {
      type oc-yang:counter64;
      description
        "RX port cgm ostc1 drops counter. Counts packets that were totally dropped and will not be seen on RX side.";
    }
    leaf counters_slice1_ifg1_ifgb_rx_port_8_cgm_tc1_partially_dropped_packets {
      type oc-yang:counter64;
      description
        "RX port cgm ostc1 partial drops counter. Counts packets that were partially dropped and will be seen on RX side.";
    }
    leaf counters_slice1_ifg1_ifgb_rx_port_8_cgm_tc2_dropped_packets {
      type oc-yang:counter64;
      description
        "RX port cgm ostc2 drops counter. Counts packets that were totally dropped and will not be seen on RX side.";
    }
    leaf counters_slice1_ifg1_ifgb_rx_port_8_cgm_tc2_partially_dropped_packets {
      type oc-yang:counter64;
      description
        "RX port cgm ostc2 partial drops counter. Counts packets that were partially dropped and will be seen on RX side.";
    }
    leaf counters_slice1_ifg1_ifgb_rx_port_8_cgm_tc3_dropped_packets {
      type oc-yang:counter64;
      description
        "RX port cgm ostc3 drops counter. Counts packets that were totally dropped and will not be seen on RX side.";
    }
    leaf counters_slice1_ifg1_ifgb_rx_port_8_cgm_tc3_partially_dropped_packets {
      type oc-yang:counter64;
      description
        "RX port cgm ostc3 partial drops counter. Counts packets that were partially dropped and will be seen on RX side.";
    }
    leaf counters_slice1_ifg1_ifgb_rx_port_9_cgm_tc0_dropped_packets {
      type oc-yang:counter64;
      description
        "RX port cgm ostc0 drops counter. Counts packets that were totally dropped and will not be seen on RX side.";
    }
    leaf counters_slice1_ifg1_ifgb_rx_port_9_cgm_tc0_partially_dropped_packets {
      type oc-yang:counter64;
      description
        "RX port cgm ostc0 partial drops counter. Counts packets that were partially dropped and will be seen on RX side.";
    }
    leaf counters_slice1_ifg1_ifgb_rx_port_9_cgm_tc1_dropped_packets {
      type oc-yang:counter64;
      description
        "RX port cgm ostc1 drops counter. Counts packets that were totally dropped and will not be seen on RX side.";
    }
    leaf counters_slice1_ifg1_ifgb_rx_port_9_cgm_tc1_partially_dropped_packets {
      type oc-yang:counter64;
      description
        "RX port cgm ostc1 partial drops counter. Counts packets that were partially dropped and will be seen on RX side.";
    }
    leaf counters_slice1_ifg1_ifgb_rx_port_9_cgm_tc2_dropped_packets {
      type oc-yang:counter64;
      description
        "RX port cgm ostc2 drops counter. Counts packets that were totally dropped and will not be seen on RX side.";
    }
    leaf counters_slice1_ifg1_ifgb_rx_port_9_cgm_tc2_partially_dropped_packets {
      type oc-yang:counter64;
      description
        "RX port cgm ostc2 partial drops counter. Counts packets that were partially dropped and will be seen on RX side.";
    }
    leaf counters_slice1_ifg1_ifgb_rx_port_9_cgm_tc3_dropped_packets {
      type oc-yang:counter64;
      description
        "RX port cgm ostc3 drops counter. Counts packets that were totally dropped and will not be seen on RX side.";
    }
    leaf counters_slice1_ifg1_ifgb_rx_port_9_cgm_tc3_partially_dropped_packets {
      type oc-yang:counter64;
      description
        "RX port cgm ostc3 partial drops counter. Counts packets that were partially dropped and will be seen on RX side.";
    }
    leaf counters_slice1_tx_cgm_dropped_packets_due_to_max_allowed_qsize {
      type oc-yang:counter64;
      description
        "Counts number of dropped packets by max allowed threshold";
    }
    leaf counters_slice1_tx_cgm_local_sch_uc_buffer_c_dropped_packets {
      type oc-yang:counter64;
      description
        "Counts number of dropped packets by counter C";
    }
    leaf counters_slice1_tx_cgm_mc_silently_dropped_packets {
      type oc-yang:counter64;
      description
        "Counter of dropped MC packets that were silently dropped";
    }
    leaf counters_slice1_tx_cgm_sch_uc_buffers_cd_dropped_packets {
      type oc-yang:counter64;
      description
        "Counts number of dropped packets by counter C+D";
    }
    leaf counters_slice1_tx_cgm_sch_uc_counter_z_dropped_packets {
      type oc-yang:counter64;
      description
        "Counts number of dropped packets by counter Z";
    }
    leaf counters_slice1_tx_cgm_total_dropped_packets {
      type oc-yang:counter64;
      description
        "Counts number of dropped in TxCGM only packets";
    }
    leaf counters_slice1_tx_cgm_uc_oq_test_dropped_packets {
      type oc-yang:counter64;
      description
        "Counts number of dropped by UC OQ test";
    }
    leaf counters_slice1_tx_cgm_uc_oqg_dropped_packets {
      type oc-yang:counter64;
      description
        "Counts number of dropped by UC OQG test";
    }
    leaf counters_slice1_tx_cgm_unsch_counter_w_dropped_packets {
      type oc-yang:counter64;
      description
        "Counts number of dropped packets by counter W";
    }
    leaf counters_slice1_tx_cgm_green_mc_oq_bytes_test_dropped_packets {
      type oc-yang:counter64;
      description
        "Counts number of dropped packets by OQ MC green bytes test";
    }
    leaf counters_slice1_tx_cgm_green_mc_oq_pds_test_dropped_packets {
      type oc-yang:counter64;
      description
        "Counts number of dropped packets by OQ MC green PDs test";
    }
    leaf counters_slice1_tx_cgm_mc_color_test0_dropped_packets {
      type oc-yang:counter64;
      description
        "Counts number of dropped packet by MC color test for:0 - Green1 - Yellow2 - Red3 - Other";
    }
    leaf counters_slice1_tx_cgm_mc_color_test1_dropped_packets {
      type oc-yang:counter64;
      description
        "Counts number of dropped packet by MC color test for:0 - Green1 - Yellow2 - Red3 - Other";
    }
    leaf counters_slice1_tx_cgm_mc_color_test2_dropped_packets {
      type oc-yang:counter64;
      description
        "Counts number of dropped packet by MC color test for:0 - Green1 - Yellow2 - Red3 - Other";
    }
    leaf counters_slice1_tx_cgm_mc_color_test3_dropped_packets {
      type oc-yang:counter64;
      description
        "Counts number of dropped packet by MC color test for:0 - Green1 - Yellow2 - Red3 - Other";
    }
    leaf counters_slice1_tx_cgm_mc_set0_dropped_bytes {
      type oc-yang:counter64;
      description
        "Counts MC dropped bytes";
    }
    leaf counters_slice1_tx_cgm_mc_set0_dropped_packets {
      type oc-yang:counter64;
      description
        "Counts MC dropped packets";
    }
    leaf counters_slice1_tx_cgm_mc_set1_dropped_bytes {
      type oc-yang:counter64;
      description
        "Counts MC dropped bytes";
    }
    leaf counters_slice1_tx_cgm_mc_set1_dropped_packets {
      type oc-yang:counter64;
      description
        "Counts MC dropped packets";
    }
    leaf counters_slice1_tx_cgm_mc_set2_dropped_bytes {
      type oc-yang:counter64;
      description
        "Counts MC dropped bytes";
    }
    leaf counters_slice1_tx_cgm_mc_set2_dropped_packets {
      type oc-yang:counter64;
      description
        "Counts MC dropped packets";
    }
    leaf counters_slice1_tx_cgm_mc_set3_dropped_bytes {
      type oc-yang:counter64;
      description
        "Counts MC dropped bytes";
    }
    leaf counters_slice1_tx_cgm_mc_set3_dropped_packets {
      type oc-yang:counter64;
      description
        "Counts MC dropped packets";
    }
    leaf counters_slice1_tx_cgm_uc_color_test0_dropped_packets {
      type oc-yang:counter64;
      description
        "Counts number of dropped packet by UC color test for:0 - Green1 - Yellow2 - Red3 - Other";
    }
    leaf counters_slice1_tx_cgm_uc_color_test1_dropped_packets {
      type oc-yang:counter64;
      description
        "Counts number of dropped packet by UC color test for:0 - Green1 - Yellow2 - Red3 - Other";
    }
    leaf counters_slice1_tx_cgm_uc_color_test2_dropped_packets {
      type oc-yang:counter64;
      description
        "Counts number of dropped packet by UC color test for:0 - Green1 - Yellow2 - Red3 - Other";
    }
    leaf counters_slice1_tx_cgm_uc_color_test3_dropped_packets {
      type oc-yang:counter64;
      description
        "Counts number of dropped packet by UC color test for:0 - Green1 - Yellow2 - Red3 - Other";
    }
    leaf counters_slice1_tx_cgm_uc_set0_dropped_bytes {
      type oc-yang:counter64;
      description
        "Counts UC dropped bytes";
    }
    leaf counters_slice1_tx_cgm_uc_set0_dropped_packets {
      type oc-yang:counter64;
      description
        "Counts UC dropped packets";
    }
    leaf counters_slice1_tx_cgm_uc_set1_dropped_bytes {
      type oc-yang:counter64;
      description
        "Counts UC dropped bytes";
    }
    leaf counters_slice1_tx_cgm_uc_set1_dropped_packets {
      type oc-yang:counter64;
      description
        "Counts UC dropped packets";
    }
    leaf counters_slice1_tx_cgm_uc_set2_dropped_bytes {
      type oc-yang:counter64;
      description
        "Counts UC dropped bytes";
    }
    leaf counters_slice1_tx_cgm_uc_set2_dropped_packets {
      type oc-yang:counter64;
      description
        "Counts UC dropped packets";
    }
    leaf counters_slice1_tx_cgm_uc_set3_dropped_bytes {
      type oc-yang:counter64;
      description
        "Counts UC dropped bytes";
    }
    leaf counters_slice1_tx_cgm_uc_set3_dropped_packets {
      type oc-yang:counter64;
      description
        "Counts UC dropped packets";
    }
    leaf counters_slice1_tx_cgm_yellow_mc_oq_bytes_test_dropped_packets {
      type oc-yang:counter64;
      description
        "Counts number of dropped packets by OQ MC yellow bytes test";
    }
    leaf counters_slice1_tx_cgm_yellow_mc_oq_pds_test_dropped_packets {
      type oc-yang:counter64;
      description
        "Counts number of dropped packets by OQ MC yellow PDs test";
    }
    leaf counters_slice1_tx_pdr_txrq_full_egress_rep_dropped_packets {
      type oc-yang:counter64;
      description
        "Number of dropped packets";
    }
    leaf counters_slice1_tx_pdr_txrq_overload_egress_rep_dropped_packets {
      type oc-yang:counter64;
      description
        "Number of dropped packets";
    }
    leaf counters_slice1_tx_pdr_txrq0_full_egress_rep_dropped_packets {
      type oc-yang:counter64;
      description
        "Number of dropped packets";
    }
    leaf counters_slice1_tx_pdr_txrq0_threshold0_deq_dropped_packets {
      type oc-yang:counter64;
      description
        "Number of dropped packets in TXRQ deq";
    }
    leaf counters_slice1_tx_pdr_txrq0_threshold0_enq_dropped_packets {
      type oc-yang:counter64;
      description
        "Number of dropped packets in TXRQ enq";
    }
    leaf counters_slice1_tx_pdr_txrq0_threshold0_unscheduled_cgm_drops {
      type oc-yang:counter64;
      description
        "nan";
    }
    leaf counters_slice1_tx_pdr_txrq0_threshold1_deq_dropped_packets {
      type oc-yang:counter64;
      description
        "Number of dropped packets in TXRQ deq";
    }
    leaf counters_slice1_tx_pdr_txrq0_threshold1_enq_dropped_packets {
      type oc-yang:counter64;
      description
        "Number of dropped packets in TXRQ enq";
    }
    leaf counters_slice1_tx_pdr_txrq0_threshold1_unscheduled_cgm_drops {
      type oc-yang:counter64;
      description
        "nan";
    }
    leaf counters_slice1_tx_pdr_txrq1_full_egress_rep_dropped_packets {
      type oc-yang:counter64;
      description
        "Number of dropped packets";
    }
    leaf counters_slice1_tx_pdr_txrq1_threshold0_deq_dropped_packets {
      type oc-yang:counter64;
      description
        "Number of dropped packets in TXRQ deq";
    }
    leaf counters_slice1_tx_pdr_txrq1_threshold0_enq_dropped_packets {
      type oc-yang:counter64;
      description
        "Number of dropped packets in TXRQ enq";
    }
    leaf counters_slice1_tx_pdr_txrq1_threshold0_unscheduled_cgm_drops {
      type oc-yang:counter64;
      description
        "nan";
    }
    leaf counters_slice1_tx_pdr_txrq1_threshold1_deq_dropped_packets {
      type oc-yang:counter64;
      description
        "Number of dropped packets in TXRQ deq";
    }
    leaf counters_slice1_tx_pdr_txrq1_threshold1_enq_dropped_packets {
      type oc-yang:counter64;
      description
        "Number of dropped packets in TXRQ enq";
    }
    leaf counters_slice1_tx_pdr_txrq1_threshold1_unscheduled_cgm_drops {
      type oc-yang:counter64;
      description
        "nan";
    }
    leaf counters_slice1_tx_pdr_txrq2_full_egress_rep_dropped_packets {
      type oc-yang:counter64;
      description
        "Number of dropped packets";
    }
    leaf counters_slice1_tx_pdr_txrq2_threshold0_deq_dropped_packets {
      type oc-yang:counter64;
      description
        "Number of dropped packets in TXRQ deq";
    }
    leaf counters_slice1_tx_pdr_txrq2_threshold0_enq_dropped_packets {
      type oc-yang:counter64;
      description
        "Number of dropped packets in TXRQ enq";
    }
    leaf counters_slice1_tx_pdr_txrq2_threshold1_deq_dropped_packets {
      type oc-yang:counter64;
      description
        "Number of dropped packets in TXRQ deq";
    }
    leaf counters_slice1_tx_pdr_txrq2_threshold1_enq_dropped_packets {
      type oc-yang:counter64;
      description
        "Number of dropped packets in TXRQ enq";
    }
    leaf counters_slice1_tx_pdr_txrq3_full_egress_rep_dropped_packets {
      type oc-yang:counter64;
      description
        "Number of dropped packets";
    }
    leaf counters_slice1_tx_pdr_txrq3_threshold0_deq_dropped_packets {
      type oc-yang:counter64;
      description
        "Number of dropped packets in TXRQ deq";
    }
    leaf counters_slice1_tx_pdr_txrq3_threshold0_enq_dropped_packets {
      type oc-yang:counter64;
      description
        "Number of dropped packets in TXRQ enq";
    }
    leaf counters_slice1_tx_pdr_txrq3_threshold1_deq_dropped_packets {
      type oc-yang:counter64;
      description
        "Number of dropped packets in TXRQ deq";
    }
    leaf counters_slice1_tx_pdr_txrq3_threshold1_enq_dropped_packets {
      type oc-yang:counter64;
      description
        "Number of dropped packets in TXRQ enq";
    }
    leaf counters_slice2_ifg0_ifgb_rx_port_0_cgm_tc0_dropped_packets {
      type oc-yang:counter64;
      description
        "RX port cgm ostc0 drops counter. Counts packets that were totally dropped and will not be seen on RX side.";
    }
    leaf counters_slice2_ifg0_ifgb_rx_port_0_cgm_tc0_partially_dropped_packets {
      type oc-yang:counter64;
      description
        "RX port cgm ostc0 partial drops counter. Counts packets that were partially dropped and will be seen on RX side.";
    }
    leaf counters_slice2_ifg0_ifgb_rx_port_0_cgm_tc1_dropped_packets {
      type oc-yang:counter64;
      description
        "RX port cgm ostc1 drops counter. Counts packets that were totally dropped and will not be seen on RX side.";
    }
    leaf counters_slice2_ifg0_ifgb_rx_port_0_cgm_tc1_partially_dropped_packets {
      type oc-yang:counter64;
      description
        "RX port cgm ostc1 partial drops counter. Counts packets that were partially dropped and will be seen on RX side.";
    }
    leaf counters_slice2_ifg0_ifgb_rx_port_0_cgm_tc2_dropped_packets {
      type oc-yang:counter64;
      description
        "RX port cgm ostc2 drops counter. Counts packets that were totally dropped and will not be seen on RX side.";
    }
    leaf counters_slice2_ifg0_ifgb_rx_port_0_cgm_tc2_partially_dropped_packets {
      type oc-yang:counter64;
      description
        "RX port cgm ostc2 partial drops counter. Counts packets that were partially dropped and will be seen on RX side.";
    }
    leaf counters_slice2_ifg0_ifgb_rx_port_0_cgm_tc3_dropped_packets {
      type oc-yang:counter64;
      description
        "RX port cgm ostc3 drops counter. Counts packets that were totally dropped and will not be seen on RX side.";
    }
    leaf counters_slice2_ifg0_ifgb_rx_port_0_cgm_tc3_partially_dropped_packets {
      type oc-yang:counter64;
      description
        "RX port cgm ostc3 partial drops counter. Counts packets that were partially dropped and will be seen on RX side.";
    }
    leaf counters_slice2_ifg0_ifgb_rx_port_1_cgm_tc0_dropped_packets {
      type oc-yang:counter64;
      description
        "RX port cgm ostc0 drops counter. Counts packets that were totally dropped and will not be seen on RX side.";
    }
    leaf counters_slice2_ifg0_ifgb_rx_port_1_cgm_tc0_partially_dropped_packets {
      type oc-yang:counter64;
      description
        "RX port cgm ostc0 partial drops counter. Counts packets that were partially dropped and will be seen on RX side.";
    }
    leaf counters_slice2_ifg0_ifgb_rx_port_1_cgm_tc1_dropped_packets {
      type oc-yang:counter64;
      description
        "RX port cgm ostc1 drops counter. Counts packets that were totally dropped and will not be seen on RX side.";
    }
    leaf counters_slice2_ifg0_ifgb_rx_port_1_cgm_tc1_partially_dropped_packets {
      type oc-yang:counter64;
      description
        "RX port cgm ostc1 partial drops counter. Counts packets that were partially dropped and will be seen on RX side.";
    }
    leaf counters_slice2_ifg0_ifgb_rx_port_1_cgm_tc2_dropped_packets {
      type oc-yang:counter64;
      description
        "RX port cgm ostc2 drops counter. Counts packets that were totally dropped and will not be seen on RX side.";
    }
    leaf counters_slice2_ifg0_ifgb_rx_port_1_cgm_tc2_partially_dropped_packets {
      type oc-yang:counter64;
      description
        "RX port cgm ostc2 partial drops counter. Counts packets that were partially dropped and will be seen on RX side.";
    }
    leaf counters_slice2_ifg0_ifgb_rx_port_1_cgm_tc3_dropped_packets {
      type oc-yang:counter64;
      description
        "RX port cgm ostc3 drops counter. Counts packets that were totally dropped and will not be seen on RX side.";
    }
    leaf counters_slice2_ifg0_ifgb_rx_port_1_cgm_tc3_partially_dropped_packets {
      type oc-yang:counter64;
      description
        "RX port cgm ostc3 partial drops counter. Counts packets that were partially dropped and will be seen on RX side.";
    }
    leaf counters_slice2_ifg0_ifgb_rx_port_10_cgm_tc0_dropped_packets {
      type oc-yang:counter64;
      description
        "RX port cgm ostc0 drops counter. Counts packets that were totally dropped and will not be seen on RX side.";
    }
    leaf counters_slice2_ifg0_ifgb_rx_port_10_cgm_tc0_partially_dropped_packets {
      type oc-yang:counter64;
      description
        "RX port cgm ostc0 partial drops counter. Counts packets that were partially dropped and will be seen on RX side.";
    }
    leaf counters_slice2_ifg0_ifgb_rx_port_10_cgm_tc1_dropped_packets {
      type oc-yang:counter64;
      description
        "RX port cgm ostc1 drops counter. Counts packets that were totally dropped and will not be seen on RX side.";
    }
    leaf counters_slice2_ifg0_ifgb_rx_port_10_cgm_tc1_partially_dropped_packets {
      type oc-yang:counter64;
      description
        "RX port cgm ostc1 partial drops counter. Counts packets that were partially dropped and will be seen on RX side.";
    }
    leaf counters_slice2_ifg0_ifgb_rx_port_10_cgm_tc2_dropped_packets {
      type oc-yang:counter64;
      description
        "RX port cgm ostc2 drops counter. Counts packets that were totally dropped and will not be seen on RX side.";
    }
    leaf counters_slice2_ifg0_ifgb_rx_port_10_cgm_tc2_partially_dropped_packets {
      type oc-yang:counter64;
      description
        "RX port cgm ostc2 partial drops counter. Counts packets that were partially dropped and will be seen on RX side.";
    }
    leaf counters_slice2_ifg0_ifgb_rx_port_10_cgm_tc3_dropped_packets {
      type oc-yang:counter64;
      description
        "RX port cgm ostc3 drops counter. Counts packets that were totally dropped and will not be seen on RX side.";
    }
    leaf counters_slice2_ifg0_ifgb_rx_port_10_cgm_tc3_partially_dropped_packets {
      type oc-yang:counter64;
      description
        "RX port cgm ostc3 partial drops counter. Counts packets that were partially dropped and will be seen on RX side.";
    }
    leaf counters_slice2_ifg0_ifgb_rx_port_11_cgm_tc0_dropped_packets {
      type oc-yang:counter64;
      description
        "RX port cgm ostc0 drops counter. Counts packets that were totally dropped and will not be seen on RX side.";
    }
    leaf counters_slice2_ifg0_ifgb_rx_port_11_cgm_tc0_partially_dropped_packets {
      type oc-yang:counter64;
      description
        "RX port cgm ostc0 partial drops counter. Counts packets that were partially dropped and will be seen on RX side.";
    }
    leaf counters_slice2_ifg0_ifgb_rx_port_11_cgm_tc1_dropped_packets {
      type oc-yang:counter64;
      description
        "RX port cgm ostc1 drops counter. Counts packets that were totally dropped and will not be seen on RX side.";
    }
    leaf counters_slice2_ifg0_ifgb_rx_port_11_cgm_tc1_partially_dropped_packets {
      type oc-yang:counter64;
      description
        "RX port cgm ostc1 partial drops counter. Counts packets that were partially dropped and will be seen on RX side.";
    }
    leaf counters_slice2_ifg0_ifgb_rx_port_11_cgm_tc2_dropped_packets {
      type oc-yang:counter64;
      description
        "RX port cgm ostc2 drops counter. Counts packets that were totally dropped and will not be seen on RX side.";
    }
    leaf counters_slice2_ifg0_ifgb_rx_port_11_cgm_tc2_partially_dropped_packets {
      type oc-yang:counter64;
      description
        "RX port cgm ostc2 partial drops counter. Counts packets that were partially dropped and will be seen on RX side.";
    }
    leaf counters_slice2_ifg0_ifgb_rx_port_11_cgm_tc3_dropped_packets {
      type oc-yang:counter64;
      description
        "RX port cgm ostc3 drops counter. Counts packets that were totally dropped and will not be seen on RX side.";
    }
    leaf counters_slice2_ifg0_ifgb_rx_port_11_cgm_tc3_partially_dropped_packets {
      type oc-yang:counter64;
      description
        "RX port cgm ostc3 partial drops counter. Counts packets that were partially dropped and will be seen on RX side.";
    }
    leaf counters_slice2_ifg0_ifgb_rx_port_12_cgm_tc0_dropped_packets {
      type oc-yang:counter64;
      description
        "RX port cgm ostc0 drops counter. Counts packets that were totally dropped and will not be seen on RX side.";
    }
    leaf counters_slice2_ifg0_ifgb_rx_port_12_cgm_tc0_partially_dropped_packets {
      type oc-yang:counter64;
      description
        "RX port cgm ostc0 partial drops counter. Counts packets that were partially dropped and will be seen on RX side.";
    }
    leaf counters_slice2_ifg0_ifgb_rx_port_12_cgm_tc1_dropped_packets {
      type oc-yang:counter64;
      description
        "RX port cgm ostc1 drops counter. Counts packets that were totally dropped and will not be seen on RX side.";
    }
    leaf counters_slice2_ifg0_ifgb_rx_port_12_cgm_tc1_partially_dropped_packets {
      type oc-yang:counter64;
      description
        "RX port cgm ostc1 partial drops counter. Counts packets that were partially dropped and will be seen on RX side.";
    }
    leaf counters_slice2_ifg0_ifgb_rx_port_12_cgm_tc2_dropped_packets {
      type oc-yang:counter64;
      description
        "RX port cgm ostc2 drops counter. Counts packets that were totally dropped and will not be seen on RX side.";
    }
    leaf counters_slice2_ifg0_ifgb_rx_port_12_cgm_tc2_partially_dropped_packets {
      type oc-yang:counter64;
      description
        "RX port cgm ostc2 partial drops counter. Counts packets that were partially dropped and will be seen on RX side.";
    }
    leaf counters_slice2_ifg0_ifgb_rx_port_12_cgm_tc3_dropped_packets {
      type oc-yang:counter64;
      description
        "RX port cgm ostc3 drops counter. Counts packets that were totally dropped and will not be seen on RX side.";
    }
    leaf counters_slice2_ifg0_ifgb_rx_port_12_cgm_tc3_partially_dropped_packets {
      type oc-yang:counter64;
      description
        "RX port cgm ostc3 partial drops counter. Counts packets that were partially dropped and will be seen on RX side.";
    }
    leaf counters_slice2_ifg0_ifgb_rx_port_13_cgm_tc0_dropped_packets {
      type oc-yang:counter64;
      description
        "RX port cgm ostc0 drops counter. Counts packets that were totally dropped and will not be seen on RX side.";
    }
    leaf counters_slice2_ifg0_ifgb_rx_port_13_cgm_tc0_partially_dropped_packets {
      type oc-yang:counter64;
      description
        "RX port cgm ostc0 partial drops counter. Counts packets that were partially dropped and will be seen on RX side.";
    }
    leaf counters_slice2_ifg0_ifgb_rx_port_13_cgm_tc1_dropped_packets {
      type oc-yang:counter64;
      description
        "RX port cgm ostc1 drops counter. Counts packets that were totally dropped and will not be seen on RX side.";
    }
    leaf counters_slice2_ifg0_ifgb_rx_port_13_cgm_tc1_partially_dropped_packets {
      type oc-yang:counter64;
      description
        "RX port cgm ostc1 partial drops counter. Counts packets that were partially dropped and will be seen on RX side.";
    }
    leaf counters_slice2_ifg0_ifgb_rx_port_13_cgm_tc2_dropped_packets {
      type oc-yang:counter64;
      description
        "RX port cgm ostc2 drops counter. Counts packets that were totally dropped and will not be seen on RX side.";
    }
    leaf counters_slice2_ifg0_ifgb_rx_port_13_cgm_tc2_partially_dropped_packets {
      type oc-yang:counter64;
      description
        "RX port cgm ostc2 partial drops counter. Counts packets that were partially dropped and will be seen on RX side.";
    }
    leaf counters_slice2_ifg0_ifgb_rx_port_13_cgm_tc3_dropped_packets {
      type oc-yang:counter64;
      description
        "RX port cgm ostc3 drops counter. Counts packets that were totally dropped and will not be seen on RX side.";
    }
    leaf counters_slice2_ifg0_ifgb_rx_port_13_cgm_tc3_partially_dropped_packets {
      type oc-yang:counter64;
      description
        "RX port cgm ostc3 partial drops counter. Counts packets that were partially dropped and will be seen on RX side.";
    }
    leaf counters_slice2_ifg0_ifgb_rx_port_14_cgm_tc0_dropped_packets {
      type oc-yang:counter64;
      description
        "RX port cgm ostc0 drops counter. Counts packets that were totally dropped and will not be seen on RX side.";
    }
    leaf counters_slice2_ifg0_ifgb_rx_port_14_cgm_tc0_partially_dropped_packets {
      type oc-yang:counter64;
      description
        "RX port cgm ostc0 partial drops counter. Counts packets that were partially dropped and will be seen on RX side.";
    }
    leaf counters_slice2_ifg0_ifgb_rx_port_14_cgm_tc1_dropped_packets {
      type oc-yang:counter64;
      description
        "RX port cgm ostc1 drops counter. Counts packets that were totally dropped and will not be seen on RX side.";
    }
    leaf counters_slice2_ifg0_ifgb_rx_port_14_cgm_tc1_partially_dropped_packets {
      type oc-yang:counter64;
      description
        "RX port cgm ostc1 partial drops counter. Counts packets that were partially dropped and will be seen on RX side.";
    }
    leaf counters_slice2_ifg0_ifgb_rx_port_14_cgm_tc2_dropped_packets {
      type oc-yang:counter64;
      description
        "RX port cgm ostc2 drops counter. Counts packets that were totally dropped and will not be seen on RX side.";
    }
    leaf counters_slice2_ifg0_ifgb_rx_port_14_cgm_tc2_partially_dropped_packets {
      type oc-yang:counter64;
      description
        "RX port cgm ostc2 partial drops counter. Counts packets that were partially dropped and will be seen on RX side.";
    }
    leaf counters_slice2_ifg0_ifgb_rx_port_14_cgm_tc3_dropped_packets {
      type oc-yang:counter64;
      description
        "RX port cgm ostc3 drops counter. Counts packets that were totally dropped and will not be seen on RX side.";
    }
    leaf counters_slice2_ifg0_ifgb_rx_port_14_cgm_tc3_partially_dropped_packets {
      type oc-yang:counter64;
      description
        "RX port cgm ostc3 partial drops counter. Counts packets that were partially dropped and will be seen on RX side.";
    }
    leaf counters_slice2_ifg0_ifgb_rx_port_15_cgm_tc0_dropped_packets {
      type oc-yang:counter64;
      description
        "RX port cgm ostc0 drops counter. Counts packets that were totally dropped and will not be seen on RX side.";
    }
    leaf counters_slice2_ifg0_ifgb_rx_port_15_cgm_tc0_partially_dropped_packets {
      type oc-yang:counter64;
      description
        "RX port cgm ostc0 partial drops counter. Counts packets that were partially dropped and will be seen on RX side.";
    }
    leaf counters_slice2_ifg0_ifgb_rx_port_15_cgm_tc1_dropped_packets {
      type oc-yang:counter64;
      description
        "RX port cgm ostc1 drops counter. Counts packets that were totally dropped and will not be seen on RX side.";
    }
    leaf counters_slice2_ifg0_ifgb_rx_port_15_cgm_tc1_partially_dropped_packets {
      type oc-yang:counter64;
      description
        "RX port cgm ostc1 partial drops counter. Counts packets that were partially dropped and will be seen on RX side.";
    }
    leaf counters_slice2_ifg0_ifgb_rx_port_15_cgm_tc2_dropped_packets {
      type oc-yang:counter64;
      description
        "RX port cgm ostc2 drops counter. Counts packets that were totally dropped and will not be seen on RX side.";
    }
    leaf counters_slice2_ifg0_ifgb_rx_port_15_cgm_tc2_partially_dropped_packets {
      type oc-yang:counter64;
      description
        "RX port cgm ostc2 partial drops counter. Counts packets that were partially dropped and will be seen on RX side.";
    }
    leaf counters_slice2_ifg0_ifgb_rx_port_15_cgm_tc3_dropped_packets {
      type oc-yang:counter64;
      description
        "RX port cgm ostc3 drops counter. Counts packets that were totally dropped and will not be seen on RX side.";
    }
    leaf counters_slice2_ifg0_ifgb_rx_port_15_cgm_tc3_partially_dropped_packets {
      type oc-yang:counter64;
      description
        "RX port cgm ostc3 partial drops counter. Counts packets that were partially dropped and will be seen on RX side.";
    }
    leaf counters_slice2_ifg0_ifgb_rx_port_16_cgm_tc0_dropped_packets {
      type oc-yang:counter64;
      description
        "RX port cgm ostc0 drops counter. Counts packets that were totally dropped and will not be seen on RX side.";
    }
    leaf counters_slice2_ifg0_ifgb_rx_port_16_cgm_tc0_partially_dropped_packets {
      type oc-yang:counter64;
      description
        "RX port cgm ostc0 partial drops counter. Counts packets that were partially dropped and will be seen on RX side.";
    }
    leaf counters_slice2_ifg0_ifgb_rx_port_16_cgm_tc1_dropped_packets {
      type oc-yang:counter64;
      description
        "RX port cgm ostc1 drops counter. Counts packets that were totally dropped and will not be seen on RX side.";
    }
    leaf counters_slice2_ifg0_ifgb_rx_port_16_cgm_tc1_partially_dropped_packets {
      type oc-yang:counter64;
      description
        "RX port cgm ostc1 partial drops counter. Counts packets that were partially dropped and will be seen on RX side.";
    }
    leaf counters_slice2_ifg0_ifgb_rx_port_16_cgm_tc2_dropped_packets {
      type oc-yang:counter64;
      description
        "RX port cgm ostc2 drops counter. Counts packets that were totally dropped and will not be seen on RX side.";
    }
    leaf counters_slice2_ifg0_ifgb_rx_port_16_cgm_tc2_partially_dropped_packets {
      type oc-yang:counter64;
      description
        "RX port cgm ostc2 partial drops counter. Counts packets that were partially dropped and will be seen on RX side.";
    }
    leaf counters_slice2_ifg0_ifgb_rx_port_16_cgm_tc3_dropped_packets {
      type oc-yang:counter64;
      description
        "RX port cgm ostc3 drops counter. Counts packets that were totally dropped and will not be seen on RX side.";
    }
    leaf counters_slice2_ifg0_ifgb_rx_port_16_cgm_tc3_partially_dropped_packets {
      type oc-yang:counter64;
      description
        "RX port cgm ostc3 partial drops counter. Counts packets that were partially dropped and will be seen on RX side.";
    }
    leaf counters_slice2_ifg0_ifgb_rx_port_17_cgm_tc0_dropped_packets {
      type oc-yang:counter64;
      description
        "RX port cgm ostc0 drops counter. Counts packets that were totally dropped and will not be seen on RX side.";
    }
    leaf counters_slice2_ifg0_ifgb_rx_port_17_cgm_tc0_partially_dropped_packets {
      type oc-yang:counter64;
      description
        "RX port cgm ostc0 partial drops counter. Counts packets that were partially dropped and will be seen on RX side.";
    }
    leaf counters_slice2_ifg0_ifgb_rx_port_17_cgm_tc1_dropped_packets {
      type oc-yang:counter64;
      description
        "RX port cgm ostc1 drops counter. Counts packets that were totally dropped and will not be seen on RX side.";
    }
    leaf counters_slice2_ifg0_ifgb_rx_port_17_cgm_tc1_partially_dropped_packets {
      type oc-yang:counter64;
      description
        "RX port cgm ostc1 partial drops counter. Counts packets that were partially dropped and will be seen on RX side.";
    }
    leaf counters_slice2_ifg0_ifgb_rx_port_17_cgm_tc2_dropped_packets {
      type oc-yang:counter64;
      description
        "RX port cgm ostc2 drops counter. Counts packets that were totally dropped and will not be seen on RX side.";
    }
    leaf counters_slice2_ifg0_ifgb_rx_port_17_cgm_tc2_partially_dropped_packets {
      type oc-yang:counter64;
      description
        "RX port cgm ostc2 partial drops counter. Counts packets that were partially dropped and will be seen on RX side.";
    }
    leaf counters_slice2_ifg0_ifgb_rx_port_17_cgm_tc3_dropped_packets {
      type oc-yang:counter64;
      description
        "RX port cgm ostc3 drops counter. Counts packets that were totally dropped and will not be seen on RX side.";
    }
    leaf counters_slice2_ifg0_ifgb_rx_port_17_cgm_tc3_partially_dropped_packets {
      type oc-yang:counter64;
      description
        "RX port cgm ostc3 partial drops counter. Counts packets that were partially dropped and will be seen on RX side.";
    }
    leaf counters_slice2_ifg0_ifgb_rx_port_18_cgm_tc0_dropped_packets {
      type oc-yang:counter64;
      description
        "RX port cgm ostc0 drops counter. Counts packets that were totally dropped and will not be seen on RX side.";
    }
    leaf counters_slice2_ifg0_ifgb_rx_port_18_cgm_tc0_partially_dropped_packets {
      type oc-yang:counter64;
      description
        "RX port cgm ostc0 partial drops counter. Counts packets that were partially dropped and will be seen on RX side.";
    }
    leaf counters_slice2_ifg0_ifgb_rx_port_18_cgm_tc1_dropped_packets {
      type oc-yang:counter64;
      description
        "RX port cgm ostc1 drops counter. Counts packets that were totally dropped and will not be seen on RX side.";
    }
    leaf counters_slice2_ifg0_ifgb_rx_port_18_cgm_tc1_partially_dropped_packets {
      type oc-yang:counter64;
      description
        "RX port cgm ostc1 partial drops counter. Counts packets that were partially dropped and will be seen on RX side.";
    }
    leaf counters_slice2_ifg0_ifgb_rx_port_18_cgm_tc2_dropped_packets {
      type oc-yang:counter64;
      description
        "RX port cgm ostc2 drops counter. Counts packets that were totally dropped and will not be seen on RX side.";
    }
    leaf counters_slice2_ifg0_ifgb_rx_port_18_cgm_tc2_partially_dropped_packets {
      type oc-yang:counter64;
      description
        "RX port cgm ostc2 partial drops counter. Counts packets that were partially dropped and will be seen on RX side.";
    }
    leaf counters_slice2_ifg0_ifgb_rx_port_18_cgm_tc3_dropped_packets {
      type oc-yang:counter64;
      description
        "RX port cgm ostc3 drops counter. Counts packets that were totally dropped and will not be seen on RX side.";
    }
    leaf counters_slice2_ifg0_ifgb_rx_port_18_cgm_tc3_partially_dropped_packets {
      type oc-yang:counter64;
      description
        "RX port cgm ostc3 partial drops counter. Counts packets that were partially dropped and will be seen on RX side.";
    }
    leaf counters_slice2_ifg0_ifgb_rx_port_19_cgm_tc0_dropped_packets {
      type oc-yang:counter64;
      description
        "RX port cgm ostc0 drops counter. Counts packets that were totally dropped and will not be seen on RX side.";
    }
    leaf counters_slice2_ifg0_ifgb_rx_port_19_cgm_tc0_partially_dropped_packets {
      type oc-yang:counter64;
      description
        "RX port cgm ostc0 partial drops counter. Counts packets that were partially dropped and will be seen on RX side.";
    }
    leaf counters_slice2_ifg0_ifgb_rx_port_19_cgm_tc1_dropped_packets {
      type oc-yang:counter64;
      description
        "RX port cgm ostc1 drops counter. Counts packets that were totally dropped and will not be seen on RX side.";
    }
    leaf counters_slice2_ifg0_ifgb_rx_port_19_cgm_tc1_partially_dropped_packets {
      type oc-yang:counter64;
      description
        "RX port cgm ostc1 partial drops counter. Counts packets that were partially dropped and will be seen on RX side.";
    }
    leaf counters_slice2_ifg0_ifgb_rx_port_19_cgm_tc2_dropped_packets {
      type oc-yang:counter64;
      description
        "RX port cgm ostc2 drops counter. Counts packets that were totally dropped and will not be seen on RX side.";
    }
    leaf counters_slice2_ifg0_ifgb_rx_port_19_cgm_tc2_partially_dropped_packets {
      type oc-yang:counter64;
      description
        "RX port cgm ostc2 partial drops counter. Counts packets that were partially dropped and will be seen on RX side.";
    }
    leaf counters_slice2_ifg0_ifgb_rx_port_19_cgm_tc3_dropped_packets {
      type oc-yang:counter64;
      description
        "RX port cgm ostc3 drops counter. Counts packets that were totally dropped and will not be seen on RX side.";
    }
    leaf counters_slice2_ifg0_ifgb_rx_port_19_cgm_tc3_partially_dropped_packets {
      type oc-yang:counter64;
      description
        "RX port cgm ostc3 partial drops counter. Counts packets that were partially dropped and will be seen on RX side.";
    }
    leaf counters_slice2_ifg0_ifgb_rx_port_2_cgm_tc0_dropped_packets {
      type oc-yang:counter64;
      description
        "RX port cgm ostc0 drops counter. Counts packets that were totally dropped and will not be seen on RX side.";
    }
    leaf counters_slice2_ifg0_ifgb_rx_port_2_cgm_tc0_partially_dropped_packets {
      type oc-yang:counter64;
      description
        "RX port cgm ostc0 partial drops counter. Counts packets that were partially dropped and will be seen on RX side.";
    }
    leaf counters_slice2_ifg0_ifgb_rx_port_2_cgm_tc1_dropped_packets {
      type oc-yang:counter64;
      description
        "RX port cgm ostc1 drops counter. Counts packets that were totally dropped and will not be seen on RX side.";
    }
    leaf counters_slice2_ifg0_ifgb_rx_port_2_cgm_tc1_partially_dropped_packets {
      type oc-yang:counter64;
      description
        "RX port cgm ostc1 partial drops counter. Counts packets that were partially dropped and will be seen on RX side.";
    }
    leaf counters_slice2_ifg0_ifgb_rx_port_2_cgm_tc2_dropped_packets {
      type oc-yang:counter64;
      description
        "RX port cgm ostc2 drops counter. Counts packets that were totally dropped and will not be seen on RX side.";
    }
    leaf counters_slice2_ifg0_ifgb_rx_port_2_cgm_tc2_partially_dropped_packets {
      type oc-yang:counter64;
      description
        "RX port cgm ostc2 partial drops counter. Counts packets that were partially dropped and will be seen on RX side.";
    }
    leaf counters_slice2_ifg0_ifgb_rx_port_2_cgm_tc3_dropped_packets {
      type oc-yang:counter64;
      description
        "RX port cgm ostc3 drops counter. Counts packets that were totally dropped and will not be seen on RX side.";
    }
    leaf counters_slice2_ifg0_ifgb_rx_port_2_cgm_tc3_partially_dropped_packets {
      type oc-yang:counter64;
      description
        "RX port cgm ostc3 partial drops counter. Counts packets that were partially dropped and will be seen on RX side.";
    }
    leaf counters_slice2_ifg0_ifgb_rx_port_20_cgm_tc0_dropped_packets {
      type oc-yang:counter64;
      description
        "RX port cgm ostc0 drops counter. Counts packets that were totally dropped and will not be seen on RX side.";
    }
    leaf counters_slice2_ifg0_ifgb_rx_port_20_cgm_tc0_partially_dropped_packets {
      type oc-yang:counter64;
      description
        "RX port cgm ostc0 partial drops counter. Counts packets that were partially dropped and will be seen on RX side.";
    }
    leaf counters_slice2_ifg0_ifgb_rx_port_20_cgm_tc1_dropped_packets {
      type oc-yang:counter64;
      description
        "RX port cgm ostc1 drops counter. Counts packets that were totally dropped and will not be seen on RX side.";
    }
    leaf counters_slice2_ifg0_ifgb_rx_port_20_cgm_tc1_partially_dropped_packets {
      type oc-yang:counter64;
      description
        "RX port cgm ostc1 partial drops counter. Counts packets that were partially dropped and will be seen on RX side.";
    }
    leaf counters_slice2_ifg0_ifgb_rx_port_20_cgm_tc2_dropped_packets {
      type oc-yang:counter64;
      description
        "RX port cgm ostc2 drops counter. Counts packets that were totally dropped and will not be seen on RX side.";
    }
    leaf counters_slice2_ifg0_ifgb_rx_port_20_cgm_tc2_partially_dropped_packets {
      type oc-yang:counter64;
      description
        "RX port cgm ostc2 partial drops counter. Counts packets that were partially dropped and will be seen on RX side.";
    }
    leaf counters_slice2_ifg0_ifgb_rx_port_20_cgm_tc3_dropped_packets {
      type oc-yang:counter64;
      description
        "RX port cgm ostc3 drops counter. Counts packets that were totally dropped and will not be seen on RX side.";
    }
    leaf counters_slice2_ifg0_ifgb_rx_port_20_cgm_tc3_partially_dropped_packets {
      type oc-yang:counter64;
      description
        "RX port cgm ostc3 partial drops counter. Counts packets that were partially dropped and will be seen on RX side.";
    }
    leaf counters_slice2_ifg0_ifgb_rx_port_21_cgm_tc0_dropped_packets {
      type oc-yang:counter64;
      description
        "RX port cgm ostc0 drops counter. Counts packets that were totally dropped and will not be seen on RX side.";
    }
    leaf counters_slice2_ifg0_ifgb_rx_port_21_cgm_tc0_partially_dropped_packets {
      type oc-yang:counter64;
      description
        "RX port cgm ostc0 partial drops counter. Counts packets that were partially dropped and will be seen on RX side.";
    }
    leaf counters_slice2_ifg0_ifgb_rx_port_21_cgm_tc1_dropped_packets {
      type oc-yang:counter64;
      description
        "RX port cgm ostc1 drops counter. Counts packets that were totally dropped and will not be seen on RX side.";
    }
    leaf counters_slice2_ifg0_ifgb_rx_port_21_cgm_tc1_partially_dropped_packets {
      type oc-yang:counter64;
      description
        "RX port cgm ostc1 partial drops counter. Counts packets that were partially dropped and will be seen on RX side.";
    }
    leaf counters_slice2_ifg0_ifgb_rx_port_21_cgm_tc2_dropped_packets {
      type oc-yang:counter64;
      description
        "RX port cgm ostc2 drops counter. Counts packets that were totally dropped and will not be seen on RX side.";
    }
    leaf counters_slice2_ifg0_ifgb_rx_port_21_cgm_tc2_partially_dropped_packets {
      type oc-yang:counter64;
      description
        "RX port cgm ostc2 partial drops counter. Counts packets that were partially dropped and will be seen on RX side.";
    }
    leaf counters_slice2_ifg0_ifgb_rx_port_21_cgm_tc3_dropped_packets {
      type oc-yang:counter64;
      description
        "RX port cgm ostc3 drops counter. Counts packets that were totally dropped and will not be seen on RX side.";
    }
    leaf counters_slice2_ifg0_ifgb_rx_port_21_cgm_tc3_partially_dropped_packets {
      type oc-yang:counter64;
      description
        "RX port cgm ostc3 partial drops counter. Counts packets that were partially dropped and will be seen on RX side.";
    }
    leaf counters_slice2_ifg0_ifgb_rx_port_22_cgm_tc0_dropped_packets {
      type oc-yang:counter64;
      description
        "RX port cgm ostc0 drops counter. Counts packets that were totally dropped and will not be seen on RX side.";
    }
    leaf counters_slice2_ifg0_ifgb_rx_port_22_cgm_tc0_partially_dropped_packets {
      type oc-yang:counter64;
      description
        "RX port cgm ostc0 partial drops counter. Counts packets that were partially dropped and will be seen on RX side.";
    }
    leaf counters_slice2_ifg0_ifgb_rx_port_22_cgm_tc1_dropped_packets {
      type oc-yang:counter64;
      description
        "RX port cgm ostc1 drops counter. Counts packets that were totally dropped and will not be seen on RX side.";
    }
    leaf counters_slice2_ifg0_ifgb_rx_port_22_cgm_tc1_partially_dropped_packets {
      type oc-yang:counter64;
      description
        "RX port cgm ostc1 partial drops counter. Counts packets that were partially dropped and will be seen on RX side.";
    }
    leaf counters_slice2_ifg0_ifgb_rx_port_22_cgm_tc2_dropped_packets {
      type oc-yang:counter64;
      description
        "RX port cgm ostc2 drops counter. Counts packets that were totally dropped and will not be seen on RX side.";
    }
    leaf counters_slice2_ifg0_ifgb_rx_port_22_cgm_tc2_partially_dropped_packets {
      type oc-yang:counter64;
      description
        "RX port cgm ostc2 partial drops counter. Counts packets that were partially dropped and will be seen on RX side.";
    }
    leaf counters_slice2_ifg0_ifgb_rx_port_22_cgm_tc3_dropped_packets {
      type oc-yang:counter64;
      description
        "RX port cgm ostc3 drops counter. Counts packets that were totally dropped and will not be seen on RX side.";
    }
    leaf counters_slice2_ifg0_ifgb_rx_port_22_cgm_tc3_partially_dropped_packets {
      type oc-yang:counter64;
      description
        "RX port cgm ostc3 partial drops counter. Counts packets that were partially dropped and will be seen on RX side.";
    }
    leaf counters_slice2_ifg0_ifgb_rx_port_23_cgm_tc0_dropped_packets {
      type oc-yang:counter64;
      description
        "RX port cgm ostc0 drops counter. Counts packets that were totally dropped and will not be seen on RX side.";
    }
    leaf counters_slice2_ifg0_ifgb_rx_port_23_cgm_tc0_partially_dropped_packets {
      type oc-yang:counter64;
      description
        "RX port cgm ostc0 partial drops counter. Counts packets that were partially dropped and will be seen on RX side.";
    }
    leaf counters_slice2_ifg0_ifgb_rx_port_23_cgm_tc1_dropped_packets {
      type oc-yang:counter64;
      description
        "RX port cgm ostc1 drops counter. Counts packets that were totally dropped and will not be seen on RX side.";
    }
    leaf counters_slice2_ifg0_ifgb_rx_port_23_cgm_tc1_partially_dropped_packets {
      type oc-yang:counter64;
      description
        "RX port cgm ostc1 partial drops counter. Counts packets that were partially dropped and will be seen on RX side.";
    }
    leaf counters_slice2_ifg0_ifgb_rx_port_23_cgm_tc2_dropped_packets {
      type oc-yang:counter64;
      description
        "RX port cgm ostc2 drops counter. Counts packets that were totally dropped and will not be seen on RX side.";
    }
    leaf counters_slice2_ifg0_ifgb_rx_port_23_cgm_tc2_partially_dropped_packets {
      type oc-yang:counter64;
      description
        "RX port cgm ostc2 partial drops counter. Counts packets that were partially dropped and will be seen on RX side.";
    }
    leaf counters_slice2_ifg0_ifgb_rx_port_23_cgm_tc3_dropped_packets {
      type oc-yang:counter64;
      description
        "RX port cgm ostc3 drops counter. Counts packets that were totally dropped and will not be seen on RX side.";
    }
    leaf counters_slice2_ifg0_ifgb_rx_port_23_cgm_tc3_partially_dropped_packets {
      type oc-yang:counter64;
      description
        "RX port cgm ostc3 partial drops counter. Counts packets that were partially dropped and will be seen on RX side.";
    }
    leaf counters_slice2_ifg0_ifgb_rx_port_24_cgm_tc0_dropped_packets {
      type oc-yang:counter64;
      description
        "RX port cgm ostc0 drops counter. Counts packets that were totally dropped and will not be seen on RX side.";
    }
    leaf counters_slice2_ifg0_ifgb_rx_port_24_cgm_tc0_partially_dropped_packets {
      type oc-yang:counter64;
      description
        "RX port cgm ostc0 partial drops counter. Counts packets that were partially dropped and will be seen on RX side.";
    }
    leaf counters_slice2_ifg0_ifgb_rx_port_24_cgm_tc1_dropped_packets {
      type oc-yang:counter64;
      description
        "RX port cgm ostc1 drops counter. Counts packets that were totally dropped and will not be seen on RX side.";
    }
    leaf counters_slice2_ifg0_ifgb_rx_port_24_cgm_tc1_partially_dropped_packets {
      type oc-yang:counter64;
      description
        "RX port cgm ostc1 partial drops counter. Counts packets that were partially dropped and will be seen on RX side.";
    }
    leaf counters_slice2_ifg0_ifgb_rx_port_24_cgm_tc2_dropped_packets {
      type oc-yang:counter64;
      description
        "RX port cgm ostc2 drops counter. Counts packets that were totally dropped and will not be seen on RX side.";
    }
    leaf counters_slice2_ifg0_ifgb_rx_port_24_cgm_tc2_partially_dropped_packets {
      type oc-yang:counter64;
      description
        "RX port cgm ostc2 partial drops counter. Counts packets that were partially dropped and will be seen on RX side.";
    }
    leaf counters_slice2_ifg0_ifgb_rx_port_24_cgm_tc3_dropped_packets {
      type oc-yang:counter64;
      description
        "RX port cgm ostc3 drops counter. Counts packets that were totally dropped and will not be seen on RX side.";
    }
    leaf counters_slice2_ifg0_ifgb_rx_port_24_cgm_tc3_partially_dropped_packets {
      type oc-yang:counter64;
      description
        "RX port cgm ostc3 partial drops counter. Counts packets that were partially dropped and will be seen on RX side.";
    }
    leaf counters_slice2_ifg0_ifgb_rx_port_25_cgm_tc0_dropped_packets {
      type oc-yang:counter64;
      description
        "RX port cgm ostc0 drops counter. Counts packets that were totally dropped and will not be seen on RX side.";
    }
    leaf counters_slice2_ifg0_ifgb_rx_port_25_cgm_tc0_partially_dropped_packets {
      type oc-yang:counter64;
      description
        "RX port cgm ostc0 partial drops counter. Counts packets that were partially dropped and will be seen on RX side.";
    }
    leaf counters_slice2_ifg0_ifgb_rx_port_25_cgm_tc1_dropped_packets {
      type oc-yang:counter64;
      description
        "RX port cgm ostc1 drops counter. Counts packets that were totally dropped and will not be seen on RX side.";
    }
    leaf counters_slice2_ifg0_ifgb_rx_port_25_cgm_tc1_partially_dropped_packets {
      type oc-yang:counter64;
      description
        "RX port cgm ostc1 partial drops counter. Counts packets that were partially dropped and will be seen on RX side.";
    }
    leaf counters_slice2_ifg0_ifgb_rx_port_25_cgm_tc2_dropped_packets {
      type oc-yang:counter64;
      description
        "RX port cgm ostc2 drops counter. Counts packets that were totally dropped and will not be seen on RX side.";
    }
    leaf counters_slice2_ifg0_ifgb_rx_port_25_cgm_tc2_partially_dropped_packets {
      type oc-yang:counter64;
      description
        "RX port cgm ostc2 partial drops counter. Counts packets that were partially dropped and will be seen on RX side.";
    }
    leaf counters_slice2_ifg0_ifgb_rx_port_25_cgm_tc3_dropped_packets {
      type oc-yang:counter64;
      description
        "RX port cgm ostc3 drops counter. Counts packets that were totally dropped and will not be seen on RX side.";
    }
    leaf counters_slice2_ifg0_ifgb_rx_port_25_cgm_tc3_partially_dropped_packets {
      type oc-yang:counter64;
      description
        "RX port cgm ostc3 partial drops counter. Counts packets that were partially dropped and will be seen on RX side.";
    }
    leaf counters_slice2_ifg0_ifgb_rx_port_26_cgm_tc0_dropped_packets {
      type oc-yang:counter64;
      description
        "RX port cgm ostc0 drops counter. Counts packets that were totally dropped and will not be seen on RX side.";
    }
    leaf counters_slice2_ifg0_ifgb_rx_port_26_cgm_tc0_partially_dropped_packets {
      type oc-yang:counter64;
      description
        "RX port cgm ostc0 partial drops counter. Counts packets that were partially dropped and will be seen on RX side.";
    }
    leaf counters_slice2_ifg0_ifgb_rx_port_26_cgm_tc1_dropped_packets {
      type oc-yang:counter64;
      description
        "RX port cgm ostc1 drops counter. Counts packets that were totally dropped and will not be seen on RX side.";
    }
    leaf counters_slice2_ifg0_ifgb_rx_port_26_cgm_tc1_partially_dropped_packets {
      type oc-yang:counter64;
      description
        "RX port cgm ostc1 partial drops counter. Counts packets that were partially dropped and will be seen on RX side.";
    }
    leaf counters_slice2_ifg0_ifgb_rx_port_26_cgm_tc2_dropped_packets {
      type oc-yang:counter64;
      description
        "RX port cgm ostc2 drops counter. Counts packets that were totally dropped and will not be seen on RX side.";
    }
    leaf counters_slice2_ifg0_ifgb_rx_port_26_cgm_tc2_partially_dropped_packets {
      type oc-yang:counter64;
      description
        "RX port cgm ostc2 partial drops counter. Counts packets that were partially dropped and will be seen on RX side.";
    }
    leaf counters_slice2_ifg0_ifgb_rx_port_26_cgm_tc3_dropped_packets {
      type oc-yang:counter64;
      description
        "RX port cgm ostc3 drops counter. Counts packets that were totally dropped and will not be seen on RX side.";
    }
    leaf counters_slice2_ifg0_ifgb_rx_port_26_cgm_tc3_partially_dropped_packets {
      type oc-yang:counter64;
      description
        "RX port cgm ostc3 partial drops counter. Counts packets that were partially dropped and will be seen on RX side.";
    }
    leaf counters_slice2_ifg0_ifgb_rx_port_27_cgm_tc0_dropped_packets {
      type oc-yang:counter64;
      description
        "RX port cgm ostc0 drops counter. Counts packets that were totally dropped and will not be seen on RX side.";
    }
    leaf counters_slice2_ifg0_ifgb_rx_port_27_cgm_tc0_partially_dropped_packets {
      type oc-yang:counter64;
      description
        "RX port cgm ostc0 partial drops counter. Counts packets that were partially dropped and will be seen on RX side.";
    }
    leaf counters_slice2_ifg0_ifgb_rx_port_27_cgm_tc1_dropped_packets {
      type oc-yang:counter64;
      description
        "RX port cgm ostc1 drops counter. Counts packets that were totally dropped and will not be seen on RX side.";
    }
    leaf counters_slice2_ifg0_ifgb_rx_port_27_cgm_tc1_partially_dropped_packets {
      type oc-yang:counter64;
      description
        "RX port cgm ostc1 partial drops counter. Counts packets that were partially dropped and will be seen on RX side.";
    }
    leaf counters_slice2_ifg0_ifgb_rx_port_27_cgm_tc2_dropped_packets {
      type oc-yang:counter64;
      description
        "RX port cgm ostc2 drops counter. Counts packets that were totally dropped and will not be seen on RX side.";
    }
    leaf counters_slice2_ifg0_ifgb_rx_port_27_cgm_tc2_partially_dropped_packets {
      type oc-yang:counter64;
      description
        "RX port cgm ostc2 partial drops counter. Counts packets that were partially dropped and will be seen on RX side.";
    }
    leaf counters_slice2_ifg0_ifgb_rx_port_27_cgm_tc3_dropped_packets {
      type oc-yang:counter64;
      description
        "RX port cgm ostc3 drops counter. Counts packets that were totally dropped and will not be seen on RX side.";
    }
    leaf counters_slice2_ifg0_ifgb_rx_port_27_cgm_tc3_partially_dropped_packets {
      type oc-yang:counter64;
      description
        "RX port cgm ostc3 partial drops counter. Counts packets that were partially dropped and will be seen on RX side.";
    }
    leaf counters_slice2_ifg0_ifgb_rx_port_28_cgm_tc0_dropped_packets {
      type oc-yang:counter64;
      description
        "RX port cgm ostc0 drops counter. Counts packets that were totally dropped and will not be seen on RX side.";
    }
    leaf counters_slice2_ifg0_ifgb_rx_port_28_cgm_tc0_partially_dropped_packets {
      type oc-yang:counter64;
      description
        "RX port cgm ostc0 partial drops counter. Counts packets that were partially dropped and will be seen on RX side.";
    }
    leaf counters_slice2_ifg0_ifgb_rx_port_28_cgm_tc1_dropped_packets {
      type oc-yang:counter64;
      description
        "RX port cgm ostc1 drops counter. Counts packets that were totally dropped and will not be seen on RX side.";
    }
    leaf counters_slice2_ifg0_ifgb_rx_port_28_cgm_tc1_partially_dropped_packets {
      type oc-yang:counter64;
      description
        "RX port cgm ostc1 partial drops counter. Counts packets that were partially dropped and will be seen on RX side.";
    }
    leaf counters_slice2_ifg0_ifgb_rx_port_28_cgm_tc2_dropped_packets {
      type oc-yang:counter64;
      description
        "RX port cgm ostc2 drops counter. Counts packets that were totally dropped and will not be seen on RX side.";
    }
    leaf counters_slice2_ifg0_ifgb_rx_port_28_cgm_tc2_partially_dropped_packets {
      type oc-yang:counter64;
      description
        "RX port cgm ostc2 partial drops counter. Counts packets that were partially dropped and will be seen on RX side.";
    }
    leaf counters_slice2_ifg0_ifgb_rx_port_28_cgm_tc3_dropped_packets {
      type oc-yang:counter64;
      description
        "RX port cgm ostc3 drops counter. Counts packets that were totally dropped and will not be seen on RX side.";
    }
    leaf counters_slice2_ifg0_ifgb_rx_port_28_cgm_tc3_partially_dropped_packets {
      type oc-yang:counter64;
      description
        "RX port cgm ostc3 partial drops counter. Counts packets that were partially dropped and will be seen on RX side.";
    }
    leaf counters_slice2_ifg0_ifgb_rx_port_29_cgm_tc0_dropped_packets {
      type oc-yang:counter64;
      description
        "RX port cgm ostc0 drops counter. Counts packets that were totally dropped and will not be seen on RX side.";
    }
    leaf counters_slice2_ifg0_ifgb_rx_port_29_cgm_tc0_partially_dropped_packets {
      type oc-yang:counter64;
      description
        "RX port cgm ostc0 partial drops counter. Counts packets that were partially dropped and will be seen on RX side.";
    }
    leaf counters_slice2_ifg0_ifgb_rx_port_29_cgm_tc1_dropped_packets {
      type oc-yang:counter64;
      description
        "RX port cgm ostc1 drops counter. Counts packets that were totally dropped and will not be seen on RX side.";
    }
    leaf counters_slice2_ifg0_ifgb_rx_port_29_cgm_tc1_partially_dropped_packets {
      type oc-yang:counter64;
      description
        "RX port cgm ostc1 partial drops counter. Counts packets that were partially dropped and will be seen on RX side.";
    }
    leaf counters_slice2_ifg0_ifgb_rx_port_29_cgm_tc2_dropped_packets {
      type oc-yang:counter64;
      description
        "RX port cgm ostc2 drops counter. Counts packets that were totally dropped and will not be seen on RX side.";
    }
    leaf counters_slice2_ifg0_ifgb_rx_port_29_cgm_tc2_partially_dropped_packets {
      type oc-yang:counter64;
      description
        "RX port cgm ostc2 partial drops counter. Counts packets that were partially dropped and will be seen on RX side.";
    }
    leaf counters_slice2_ifg0_ifgb_rx_port_29_cgm_tc3_dropped_packets {
      type oc-yang:counter64;
      description
        "RX port cgm ostc3 drops counter. Counts packets that were totally dropped and will not be seen on RX side.";
    }
    leaf counters_slice2_ifg0_ifgb_rx_port_29_cgm_tc3_partially_dropped_packets {
      type oc-yang:counter64;
      description
        "RX port cgm ostc3 partial drops counter. Counts packets that were partially dropped and will be seen on RX side.";
    }
    leaf counters_slice2_ifg0_ifgb_rx_port_3_cgm_tc0_dropped_packets {
      type oc-yang:counter64;
      description
        "RX port cgm ostc0 drops counter. Counts packets that were totally dropped and will not be seen on RX side.";
    }
    leaf counters_slice2_ifg0_ifgb_rx_port_3_cgm_tc0_partially_dropped_packets {
      type oc-yang:counter64;
      description
        "RX port cgm ostc0 partial drops counter. Counts packets that were partially dropped and will be seen on RX side.";
    }
    leaf counters_slice2_ifg0_ifgb_rx_port_3_cgm_tc1_dropped_packets {
      type oc-yang:counter64;
      description
        "RX port cgm ostc1 drops counter. Counts packets that were totally dropped and will not be seen on RX side.";
    }
    leaf counters_slice2_ifg0_ifgb_rx_port_3_cgm_tc1_partially_dropped_packets {
      type oc-yang:counter64;
      description
        "RX port cgm ostc1 partial drops counter. Counts packets that were partially dropped and will be seen on RX side.";
    }
    leaf counters_slice2_ifg0_ifgb_rx_port_3_cgm_tc2_dropped_packets {
      type oc-yang:counter64;
      description
        "RX port cgm ostc2 drops counter. Counts packets that were totally dropped and will not be seen on RX side.";
    }
    leaf counters_slice2_ifg0_ifgb_rx_port_3_cgm_tc2_partially_dropped_packets {
      type oc-yang:counter64;
      description
        "RX port cgm ostc2 partial drops counter. Counts packets that were partially dropped and will be seen on RX side.";
    }
    leaf counters_slice2_ifg0_ifgb_rx_port_3_cgm_tc3_dropped_packets {
      type oc-yang:counter64;
      description
        "RX port cgm ostc3 drops counter. Counts packets that were totally dropped and will not be seen on RX side.";
    }
    leaf counters_slice2_ifg0_ifgb_rx_port_3_cgm_tc3_partially_dropped_packets {
      type oc-yang:counter64;
      description
        "RX port cgm ostc3 partial drops counter. Counts packets that were partially dropped and will be seen on RX side.";
    }
    leaf counters_slice2_ifg0_ifgb_rx_port_30_cgm_tc0_dropped_packets {
      type oc-yang:counter64;
      description
        "RX port cgm ostc0 drops counter. Counts packets that were totally dropped and will not be seen on RX side.";
    }
    leaf counters_slice2_ifg0_ifgb_rx_port_30_cgm_tc0_partially_dropped_packets {
      type oc-yang:counter64;
      description
        "RX port cgm ostc0 partial drops counter. Counts packets that were partially dropped and will be seen on RX side.";
    }
    leaf counters_slice2_ifg0_ifgb_rx_port_30_cgm_tc1_dropped_packets {
      type oc-yang:counter64;
      description
        "RX port cgm ostc1 drops counter. Counts packets that were totally dropped and will not be seen on RX side.";
    }
    leaf counters_slice2_ifg0_ifgb_rx_port_30_cgm_tc1_partially_dropped_packets {
      type oc-yang:counter64;
      description
        "RX port cgm ostc1 partial drops counter. Counts packets that were partially dropped and will be seen on RX side.";
    }
    leaf counters_slice2_ifg0_ifgb_rx_port_30_cgm_tc2_dropped_packets {
      type oc-yang:counter64;
      description
        "RX port cgm ostc2 drops counter. Counts packets that were totally dropped and will not be seen on RX side.";
    }
    leaf counters_slice2_ifg0_ifgb_rx_port_30_cgm_tc2_partially_dropped_packets {
      type oc-yang:counter64;
      description
        "RX port cgm ostc2 partial drops counter. Counts packets that were partially dropped and will be seen on RX side.";
    }
    leaf counters_slice2_ifg0_ifgb_rx_port_30_cgm_tc3_dropped_packets {
      type oc-yang:counter64;
      description
        "RX port cgm ostc3 drops counter. Counts packets that were totally dropped and will not be seen on RX side.";
    }
    leaf counters_slice2_ifg0_ifgb_rx_port_30_cgm_tc3_partially_dropped_packets {
      type oc-yang:counter64;
      description
        "RX port cgm ostc3 partial drops counter. Counts packets that were partially dropped and will be seen on RX side.";
    }
    leaf counters_slice2_ifg0_ifgb_rx_port_31_cgm_tc0_dropped_packets {
      type oc-yang:counter64;
      description
        "RX port cgm ostc0 drops counter. Counts packets that were totally dropped and will not be seen on RX side.";
    }
    leaf counters_slice2_ifg0_ifgb_rx_port_31_cgm_tc0_partially_dropped_packets {
      type oc-yang:counter64;
      description
        "RX port cgm ostc0 partial drops counter. Counts packets that were partially dropped and will be seen on RX side.";
    }
    leaf counters_slice2_ifg0_ifgb_rx_port_31_cgm_tc1_dropped_packets {
      type oc-yang:counter64;
      description
        "RX port cgm ostc1 drops counter. Counts packets that were totally dropped and will not be seen on RX side.";
    }
    leaf counters_slice2_ifg0_ifgb_rx_port_31_cgm_tc1_partially_dropped_packets {
      type oc-yang:counter64;
      description
        "RX port cgm ostc1 partial drops counter. Counts packets that were partially dropped and will be seen on RX side.";
    }
    leaf counters_slice2_ifg0_ifgb_rx_port_31_cgm_tc2_dropped_packets {
      type oc-yang:counter64;
      description
        "RX port cgm ostc2 drops counter. Counts packets that were totally dropped and will not be seen on RX side.";
    }
    leaf counters_slice2_ifg0_ifgb_rx_port_31_cgm_tc2_partially_dropped_packets {
      type oc-yang:counter64;
      description
        "RX port cgm ostc2 partial drops counter. Counts packets that were partially dropped and will be seen on RX side.";
    }
    leaf counters_slice2_ifg0_ifgb_rx_port_31_cgm_tc3_dropped_packets {
      type oc-yang:counter64;
      description
        "RX port cgm ostc3 drops counter. Counts packets that were totally dropped and will not be seen on RX side.";
    }
    leaf counters_slice2_ifg0_ifgb_rx_port_31_cgm_tc3_partially_dropped_packets {
      type oc-yang:counter64;
      description
        "RX port cgm ostc3 partial drops counter. Counts packets that were partially dropped and will be seen on RX side.";
    }
    leaf counters_slice2_ifg0_ifgb_rx_port_4_cgm_tc0_dropped_packets {
      type oc-yang:counter64;
      description
        "RX port cgm ostc0 drops counter. Counts packets that were totally dropped and will not be seen on RX side.";
    }
    leaf counters_slice2_ifg0_ifgb_rx_port_4_cgm_tc0_partially_dropped_packets {
      type oc-yang:counter64;
      description
        "RX port cgm ostc0 partial drops counter. Counts packets that were partially dropped and will be seen on RX side.";
    }
    leaf counters_slice2_ifg0_ifgb_rx_port_4_cgm_tc1_dropped_packets {
      type oc-yang:counter64;
      description
        "RX port cgm ostc1 drops counter. Counts packets that were totally dropped and will not be seen on RX side.";
    }
    leaf counters_slice2_ifg0_ifgb_rx_port_4_cgm_tc1_partially_dropped_packets {
      type oc-yang:counter64;
      description
        "RX port cgm ostc1 partial drops counter. Counts packets that were partially dropped and will be seen on RX side.";
    }
    leaf counters_slice2_ifg0_ifgb_rx_port_4_cgm_tc2_dropped_packets {
      type oc-yang:counter64;
      description
        "RX port cgm ostc2 drops counter. Counts packets that were totally dropped and will not be seen on RX side.";
    }
    leaf counters_slice2_ifg0_ifgb_rx_port_4_cgm_tc2_partially_dropped_packets {
      type oc-yang:counter64;
      description
        "RX port cgm ostc2 partial drops counter. Counts packets that were partially dropped and will be seen on RX side.";
    }
    leaf counters_slice2_ifg0_ifgb_rx_port_4_cgm_tc3_dropped_packets {
      type oc-yang:counter64;
      description
        "RX port cgm ostc3 drops counter. Counts packets that were totally dropped and will not be seen on RX side.";
    }
    leaf counters_slice2_ifg0_ifgb_rx_port_4_cgm_tc3_partially_dropped_packets {
      type oc-yang:counter64;
      description
        "RX port cgm ostc3 partial drops counter. Counts packets that were partially dropped and will be seen on RX side.";
    }
    leaf counters_slice2_ifg0_ifgb_rx_port_5_cgm_tc0_dropped_packets {
      type oc-yang:counter64;
      description
        "RX port cgm ostc0 drops counter. Counts packets that were totally dropped and will not be seen on RX side.";
    }
    leaf counters_slice2_ifg0_ifgb_rx_port_5_cgm_tc0_partially_dropped_packets {
      type oc-yang:counter64;
      description
        "RX port cgm ostc0 partial drops counter. Counts packets that were partially dropped and will be seen on RX side.";
    }
    leaf counters_slice2_ifg0_ifgb_rx_port_5_cgm_tc1_dropped_packets {
      type oc-yang:counter64;
      description
        "RX port cgm ostc1 drops counter. Counts packets that were totally dropped and will not be seen on RX side.";
    }
    leaf counters_slice2_ifg0_ifgb_rx_port_5_cgm_tc1_partially_dropped_packets {
      type oc-yang:counter64;
      description
        "RX port cgm ostc1 partial drops counter. Counts packets that were partially dropped and will be seen on RX side.";
    }
    leaf counters_slice2_ifg0_ifgb_rx_port_5_cgm_tc2_dropped_packets {
      type oc-yang:counter64;
      description
        "RX port cgm ostc2 drops counter. Counts packets that were totally dropped and will not be seen on RX side.";
    }
    leaf counters_slice2_ifg0_ifgb_rx_port_5_cgm_tc2_partially_dropped_packets {
      type oc-yang:counter64;
      description
        "RX port cgm ostc2 partial drops counter. Counts packets that were partially dropped and will be seen on RX side.";
    }
    leaf counters_slice2_ifg0_ifgb_rx_port_5_cgm_tc3_dropped_packets {
      type oc-yang:counter64;
      description
        "RX port cgm ostc3 drops counter. Counts packets that were totally dropped and will not be seen on RX side.";
    }
    leaf counters_slice2_ifg0_ifgb_rx_port_5_cgm_tc3_partially_dropped_packets {
      type oc-yang:counter64;
      description
        "RX port cgm ostc3 partial drops counter. Counts packets that were partially dropped and will be seen on RX side.";
    }
    leaf counters_slice2_ifg0_ifgb_rx_port_6_cgm_tc0_dropped_packets {
      type oc-yang:counter64;
      description
        "RX port cgm ostc0 drops counter. Counts packets that were totally dropped and will not be seen on RX side.";
    }
    leaf counters_slice2_ifg0_ifgb_rx_port_6_cgm_tc0_partially_dropped_packets {
      type oc-yang:counter64;
      description
        "RX port cgm ostc0 partial drops counter. Counts packets that were partially dropped and will be seen on RX side.";
    }
    leaf counters_slice2_ifg0_ifgb_rx_port_6_cgm_tc1_dropped_packets {
      type oc-yang:counter64;
      description
        "RX port cgm ostc1 drops counter. Counts packets that were totally dropped and will not be seen on RX side.";
    }
    leaf counters_slice2_ifg0_ifgb_rx_port_6_cgm_tc1_partially_dropped_packets {
      type oc-yang:counter64;
      description
        "RX port cgm ostc1 partial drops counter. Counts packets that were partially dropped and will be seen on RX side.";
    }
    leaf counters_slice2_ifg0_ifgb_rx_port_6_cgm_tc2_dropped_packets {
      type oc-yang:counter64;
      description
        "RX port cgm ostc2 drops counter. Counts packets that were totally dropped and will not be seen on RX side.";
    }
    leaf counters_slice2_ifg0_ifgb_rx_port_6_cgm_tc2_partially_dropped_packets {
      type oc-yang:counter64;
      description
        "RX port cgm ostc2 partial drops counter. Counts packets that were partially dropped and will be seen on RX side.";
    }
    leaf counters_slice2_ifg0_ifgb_rx_port_6_cgm_tc3_dropped_packets {
      type oc-yang:counter64;
      description
        "RX port cgm ostc3 drops counter. Counts packets that were totally dropped and will not be seen on RX side.";
    }
    leaf counters_slice2_ifg0_ifgb_rx_port_6_cgm_tc3_partially_dropped_packets {
      type oc-yang:counter64;
      description
        "RX port cgm ostc3 partial drops counter. Counts packets that were partially dropped and will be seen on RX side.";
    }
    leaf counters_slice2_ifg0_ifgb_rx_port_7_cgm_tc0_dropped_packets {
      type oc-yang:counter64;
      description
        "RX port cgm ostc0 drops counter. Counts packets that were totally dropped and will not be seen on RX side.";
    }
    leaf counters_slice2_ifg0_ifgb_rx_port_7_cgm_tc0_partially_dropped_packets {
      type oc-yang:counter64;
      description
        "RX port cgm ostc0 partial drops counter. Counts packets that were partially dropped and will be seen on RX side.";
    }
    leaf counters_slice2_ifg0_ifgb_rx_port_7_cgm_tc1_dropped_packets {
      type oc-yang:counter64;
      description
        "RX port cgm ostc1 drops counter. Counts packets that were totally dropped and will not be seen on RX side.";
    }
    leaf counters_slice2_ifg0_ifgb_rx_port_7_cgm_tc1_partially_dropped_packets {
      type oc-yang:counter64;
      description
        "RX port cgm ostc1 partial drops counter. Counts packets that were partially dropped and will be seen on RX side.";
    }
    leaf counters_slice2_ifg0_ifgb_rx_port_7_cgm_tc2_dropped_packets {
      type oc-yang:counter64;
      description
        "RX port cgm ostc2 drops counter. Counts packets that were totally dropped and will not be seen on RX side.";
    }
    leaf counters_slice2_ifg0_ifgb_rx_port_7_cgm_tc2_partially_dropped_packets {
      type oc-yang:counter64;
      description
        "RX port cgm ostc2 partial drops counter. Counts packets that were partially dropped and will be seen on RX side.";
    }
    leaf counters_slice2_ifg0_ifgb_rx_port_7_cgm_tc3_dropped_packets {
      type oc-yang:counter64;
      description
        "RX port cgm ostc3 drops counter. Counts packets that were totally dropped and will not be seen on RX side.";
    }
    leaf counters_slice2_ifg0_ifgb_rx_port_7_cgm_tc3_partially_dropped_packets {
      type oc-yang:counter64;
      description
        "RX port cgm ostc3 partial drops counter. Counts packets that were partially dropped and will be seen on RX side.";
    }
    leaf counters_slice2_ifg0_ifgb_rx_port_8_cgm_tc0_dropped_packets {
      type oc-yang:counter64;
      description
        "RX port cgm ostc0 drops counter. Counts packets that were totally dropped and will not be seen on RX side.";
    }
    leaf counters_slice2_ifg0_ifgb_rx_port_8_cgm_tc0_partially_dropped_packets {
      type oc-yang:counter64;
      description
        "RX port cgm ostc0 partial drops counter. Counts packets that were partially dropped and will be seen on RX side.";
    }
    leaf counters_slice2_ifg0_ifgb_rx_port_8_cgm_tc1_dropped_packets {
      type oc-yang:counter64;
      description
        "RX port cgm ostc1 drops counter. Counts packets that were totally dropped and will not be seen on RX side.";
    }
    leaf counters_slice2_ifg0_ifgb_rx_port_8_cgm_tc1_partially_dropped_packets {
      type oc-yang:counter64;
      description
        "RX port cgm ostc1 partial drops counter. Counts packets that were partially dropped and will be seen on RX side.";
    }
    leaf counters_slice2_ifg0_ifgb_rx_port_8_cgm_tc2_dropped_packets {
      type oc-yang:counter64;
      description
        "RX port cgm ostc2 drops counter. Counts packets that were totally dropped and will not be seen on RX side.";
    }
    leaf counters_slice2_ifg0_ifgb_rx_port_8_cgm_tc2_partially_dropped_packets {
      type oc-yang:counter64;
      description
        "RX port cgm ostc2 partial drops counter. Counts packets that were partially dropped and will be seen on RX side.";
    }
    leaf counters_slice2_ifg0_ifgb_rx_port_8_cgm_tc3_dropped_packets {
      type oc-yang:counter64;
      description
        "RX port cgm ostc3 drops counter. Counts packets that were totally dropped and will not be seen on RX side.";
    }
    leaf counters_slice2_ifg0_ifgb_rx_port_8_cgm_tc3_partially_dropped_packets {
      type oc-yang:counter64;
      description
        "RX port cgm ostc3 partial drops counter. Counts packets that were partially dropped and will be seen on RX side.";
    }
    leaf counters_slice2_ifg0_ifgb_rx_port_9_cgm_tc0_dropped_packets {
      type oc-yang:counter64;
      description
        "RX port cgm ostc0 drops counter. Counts packets that were totally dropped and will not be seen on RX side.";
    }
    leaf counters_slice2_ifg0_ifgb_rx_port_9_cgm_tc0_partially_dropped_packets {
      type oc-yang:counter64;
      description
        "RX port cgm ostc0 partial drops counter. Counts packets that were partially dropped and will be seen on RX side.";
    }
    leaf counters_slice2_ifg0_ifgb_rx_port_9_cgm_tc1_dropped_packets {
      type oc-yang:counter64;
      description
        "RX port cgm ostc1 drops counter. Counts packets that were totally dropped and will not be seen on RX side.";
    }
    leaf counters_slice2_ifg0_ifgb_rx_port_9_cgm_tc1_partially_dropped_packets {
      type oc-yang:counter64;
      description
        "RX port cgm ostc1 partial drops counter. Counts packets that were partially dropped and will be seen on RX side.";
    }
    leaf counters_slice2_ifg0_ifgb_rx_port_9_cgm_tc2_dropped_packets {
      type oc-yang:counter64;
      description
        "RX port cgm ostc2 drops counter. Counts packets that were totally dropped and will not be seen on RX side.";
    }
    leaf counters_slice2_ifg0_ifgb_rx_port_9_cgm_tc2_partially_dropped_packets {
      type oc-yang:counter64;
      description
        "RX port cgm ostc2 partial drops counter. Counts packets that were partially dropped and will be seen on RX side.";
    }
    leaf counters_slice2_ifg0_ifgb_rx_port_9_cgm_tc3_dropped_packets {
      type oc-yang:counter64;
      description
        "RX port cgm ostc3 drops counter. Counts packets that were totally dropped and will not be seen on RX side.";
    }
    leaf counters_slice2_ifg0_ifgb_rx_port_9_cgm_tc3_partially_dropped_packets {
      type oc-yang:counter64;
      description
        "RX port cgm ostc3 partial drops counter. Counts packets that were partially dropped and will be seen on RX side.";
    }
    leaf counters_slice2_ifg1_ifgb_rx_port_0_cgm_tc0_dropped_packets {
      type oc-yang:counter64;
      description
        "RX port cgm ostc0 drops counter. Counts packets that were totally dropped and will not be seen on RX side.";
    }
    leaf counters_slice2_ifg1_ifgb_rx_port_0_cgm_tc0_partially_dropped_packets {
      type oc-yang:counter64;
      description
        "RX port cgm ostc0 partial drops counter. Counts packets that were partially dropped and will be seen on RX side.";
    }
    leaf counters_slice2_ifg1_ifgb_rx_port_0_cgm_tc1_dropped_packets {
      type oc-yang:counter64;
      description
        "RX port cgm ostc1 drops counter. Counts packets that were totally dropped and will not be seen on RX side.";
    }
    leaf counters_slice2_ifg1_ifgb_rx_port_0_cgm_tc1_partially_dropped_packets {
      type oc-yang:counter64;
      description
        "RX port cgm ostc1 partial drops counter. Counts packets that were partially dropped and will be seen on RX side.";
    }
    leaf counters_slice2_ifg1_ifgb_rx_port_0_cgm_tc2_dropped_packets {
      type oc-yang:counter64;
      description
        "RX port cgm ostc2 drops counter. Counts packets that were totally dropped and will not be seen on RX side.";
    }
    leaf counters_slice2_ifg1_ifgb_rx_port_0_cgm_tc2_partially_dropped_packets {
      type oc-yang:counter64;
      description
        "RX port cgm ostc2 partial drops counter. Counts packets that were partially dropped and will be seen on RX side.";
    }
    leaf counters_slice2_ifg1_ifgb_rx_port_0_cgm_tc3_dropped_packets {
      type oc-yang:counter64;
      description
        "RX port cgm ostc3 drops counter. Counts packets that were totally dropped and will not be seen on RX side.";
    }
    leaf counters_slice2_ifg1_ifgb_rx_port_0_cgm_tc3_partially_dropped_packets {
      type oc-yang:counter64;
      description
        "RX port cgm ostc3 partial drops counter. Counts packets that were partially dropped and will be seen on RX side.";
    }
    leaf counters_slice2_ifg1_ifgb_rx_port_1_cgm_tc0_dropped_packets {
      type oc-yang:counter64;
      description
        "RX port cgm ostc0 drops counter. Counts packets that were totally dropped and will not be seen on RX side.";
    }
    leaf counters_slice2_ifg1_ifgb_rx_port_1_cgm_tc0_partially_dropped_packets {
      type oc-yang:counter64;
      description
        "RX port cgm ostc0 partial drops counter. Counts packets that were partially dropped and will be seen on RX side.";
    }
    leaf counters_slice2_ifg1_ifgb_rx_port_1_cgm_tc1_dropped_packets {
      type oc-yang:counter64;
      description
        "RX port cgm ostc1 drops counter. Counts packets that were totally dropped and will not be seen on RX side.";
    }
    leaf counters_slice2_ifg1_ifgb_rx_port_1_cgm_tc1_partially_dropped_packets {
      type oc-yang:counter64;
      description
        "RX port cgm ostc1 partial drops counter. Counts packets that were partially dropped and will be seen on RX side.";
    }
    leaf counters_slice2_ifg1_ifgb_rx_port_1_cgm_tc2_dropped_packets {
      type oc-yang:counter64;
      description
        "RX port cgm ostc2 drops counter. Counts packets that were totally dropped and will not be seen on RX side.";
    }
    leaf counters_slice2_ifg1_ifgb_rx_port_1_cgm_tc2_partially_dropped_packets {
      type oc-yang:counter64;
      description
        "RX port cgm ostc2 partial drops counter. Counts packets that were partially dropped and will be seen on RX side.";
    }
    leaf counters_slice2_ifg1_ifgb_rx_port_1_cgm_tc3_dropped_packets {
      type oc-yang:counter64;
      description
        "RX port cgm ostc3 drops counter. Counts packets that were totally dropped and will not be seen on RX side.";
    }
    leaf counters_slice2_ifg1_ifgb_rx_port_1_cgm_tc3_partially_dropped_packets {
      type oc-yang:counter64;
      description
        "RX port cgm ostc3 partial drops counter. Counts packets that were partially dropped and will be seen on RX side.";
    }
    leaf counters_slice2_ifg1_ifgb_rx_port_10_cgm_tc0_dropped_packets {
      type oc-yang:counter64;
      description
        "RX port cgm ostc0 drops counter. Counts packets that were totally dropped and will not be seen on RX side.";
    }
    leaf counters_slice2_ifg1_ifgb_rx_port_10_cgm_tc0_partially_dropped_packets {
      type oc-yang:counter64;
      description
        "RX port cgm ostc0 partial drops counter. Counts packets that were partially dropped and will be seen on RX side.";
    }
    leaf counters_slice2_ifg1_ifgb_rx_port_10_cgm_tc1_dropped_packets {
      type oc-yang:counter64;
      description
        "RX port cgm ostc1 drops counter. Counts packets that were totally dropped and will not be seen on RX side.";
    }
    leaf counters_slice2_ifg1_ifgb_rx_port_10_cgm_tc1_partially_dropped_packets {
      type oc-yang:counter64;
      description
        "RX port cgm ostc1 partial drops counter. Counts packets that were partially dropped and will be seen on RX side.";
    }
    leaf counters_slice2_ifg1_ifgb_rx_port_10_cgm_tc2_dropped_packets {
      type oc-yang:counter64;
      description
        "RX port cgm ostc2 drops counter. Counts packets that were totally dropped and will not be seen on RX side.";
    }
    leaf counters_slice2_ifg1_ifgb_rx_port_10_cgm_tc2_partially_dropped_packets {
      type oc-yang:counter64;
      description
        "RX port cgm ostc2 partial drops counter. Counts packets that were partially dropped and will be seen on RX side.";
    }
    leaf counters_slice2_ifg1_ifgb_rx_port_10_cgm_tc3_dropped_packets {
      type oc-yang:counter64;
      description
        "RX port cgm ostc3 drops counter. Counts packets that were totally dropped and will not be seen on RX side.";
    }
    leaf counters_slice2_ifg1_ifgb_rx_port_10_cgm_tc3_partially_dropped_packets {
      type oc-yang:counter64;
      description
        "RX port cgm ostc3 partial drops counter. Counts packets that were partially dropped and will be seen on RX side.";
    }
    leaf counters_slice2_ifg1_ifgb_rx_port_11_cgm_tc0_dropped_packets {
      type oc-yang:counter64;
      description
        "RX port cgm ostc0 drops counter. Counts packets that were totally dropped and will not be seen on RX side.";
    }
    leaf counters_slice2_ifg1_ifgb_rx_port_11_cgm_tc0_partially_dropped_packets {
      type oc-yang:counter64;
      description
        "RX port cgm ostc0 partial drops counter. Counts packets that were partially dropped and will be seen on RX side.";
    }
    leaf counters_slice2_ifg1_ifgb_rx_port_11_cgm_tc1_dropped_packets {
      type oc-yang:counter64;
      description
        "RX port cgm ostc1 drops counter. Counts packets that were totally dropped and will not be seen on RX side.";
    }
    leaf counters_slice2_ifg1_ifgb_rx_port_11_cgm_tc1_partially_dropped_packets {
      type oc-yang:counter64;
      description
        "RX port cgm ostc1 partial drops counter. Counts packets that were partially dropped and will be seen on RX side.";
    }
    leaf counters_slice2_ifg1_ifgb_rx_port_11_cgm_tc2_dropped_packets {
      type oc-yang:counter64;
      description
        "RX port cgm ostc2 drops counter. Counts packets that were totally dropped and will not be seen on RX side.";
    }
    leaf counters_slice2_ifg1_ifgb_rx_port_11_cgm_tc2_partially_dropped_packets {
      type oc-yang:counter64;
      description
        "RX port cgm ostc2 partial drops counter. Counts packets that were partially dropped and will be seen on RX side.";
    }
    leaf counters_slice2_ifg1_ifgb_rx_port_11_cgm_tc3_dropped_packets {
      type oc-yang:counter64;
      description
        "RX port cgm ostc3 drops counter. Counts packets that were totally dropped and will not be seen on RX side.";
    }
    leaf counters_slice2_ifg1_ifgb_rx_port_11_cgm_tc3_partially_dropped_packets {
      type oc-yang:counter64;
      description
        "RX port cgm ostc3 partial drops counter. Counts packets that were partially dropped and will be seen on RX side.";
    }
    leaf counters_slice2_ifg1_ifgb_rx_port_12_cgm_tc0_dropped_packets {
      type oc-yang:counter64;
      description
        "RX port cgm ostc0 drops counter. Counts packets that were totally dropped and will not be seen on RX side.";
    }
    leaf counters_slice2_ifg1_ifgb_rx_port_12_cgm_tc0_partially_dropped_packets {
      type oc-yang:counter64;
      description
        "RX port cgm ostc0 partial drops counter. Counts packets that were partially dropped and will be seen on RX side.";
    }
    leaf counters_slice2_ifg1_ifgb_rx_port_12_cgm_tc1_dropped_packets {
      type oc-yang:counter64;
      description
        "RX port cgm ostc1 drops counter. Counts packets that were totally dropped and will not be seen on RX side.";
    }
    leaf counters_slice2_ifg1_ifgb_rx_port_12_cgm_tc1_partially_dropped_packets {
      type oc-yang:counter64;
      description
        "RX port cgm ostc1 partial drops counter. Counts packets that were partially dropped and will be seen on RX side.";
    }
    leaf counters_slice2_ifg1_ifgb_rx_port_12_cgm_tc2_dropped_packets {
      type oc-yang:counter64;
      description
        "RX port cgm ostc2 drops counter. Counts packets that were totally dropped and will not be seen on RX side.";
    }
    leaf counters_slice2_ifg1_ifgb_rx_port_12_cgm_tc2_partially_dropped_packets {
      type oc-yang:counter64;
      description
        "RX port cgm ostc2 partial drops counter. Counts packets that were partially dropped and will be seen on RX side.";
    }
    leaf counters_slice2_ifg1_ifgb_rx_port_12_cgm_tc3_dropped_packets {
      type oc-yang:counter64;
      description
        "RX port cgm ostc3 drops counter. Counts packets that were totally dropped and will not be seen on RX side.";
    }
    leaf counters_slice2_ifg1_ifgb_rx_port_12_cgm_tc3_partially_dropped_packets {
      type oc-yang:counter64;
      description
        "RX port cgm ostc3 partial drops counter. Counts packets that were partially dropped and will be seen on RX side.";
    }
    leaf counters_slice2_ifg1_ifgb_rx_port_13_cgm_tc0_dropped_packets {
      type oc-yang:counter64;
      description
        "RX port cgm ostc0 drops counter. Counts packets that were totally dropped and will not be seen on RX side.";
    }
    leaf counters_slice2_ifg1_ifgb_rx_port_13_cgm_tc0_partially_dropped_packets {
      type oc-yang:counter64;
      description
        "RX port cgm ostc0 partial drops counter. Counts packets that were partially dropped and will be seen on RX side.";
    }
    leaf counters_slice2_ifg1_ifgb_rx_port_13_cgm_tc1_dropped_packets {
      type oc-yang:counter64;
      description
        "RX port cgm ostc1 drops counter. Counts packets that were totally dropped and will not be seen on RX side.";
    }
    leaf counters_slice2_ifg1_ifgb_rx_port_13_cgm_tc1_partially_dropped_packets {
      type oc-yang:counter64;
      description
        "RX port cgm ostc1 partial drops counter. Counts packets that were partially dropped and will be seen on RX side.";
    }
    leaf counters_slice2_ifg1_ifgb_rx_port_13_cgm_tc2_dropped_packets {
      type oc-yang:counter64;
      description
        "RX port cgm ostc2 drops counter. Counts packets that were totally dropped and will not be seen on RX side.";
    }
    leaf counters_slice2_ifg1_ifgb_rx_port_13_cgm_tc2_partially_dropped_packets {
      type oc-yang:counter64;
      description
        "RX port cgm ostc2 partial drops counter. Counts packets that were partially dropped and will be seen on RX side.";
    }
    leaf counters_slice2_ifg1_ifgb_rx_port_13_cgm_tc3_dropped_packets {
      type oc-yang:counter64;
      description
        "RX port cgm ostc3 drops counter. Counts packets that were totally dropped and will not be seen on RX side.";
    }
    leaf counters_slice2_ifg1_ifgb_rx_port_13_cgm_tc3_partially_dropped_packets {
      type oc-yang:counter64;
      description
        "RX port cgm ostc3 partial drops counter. Counts packets that were partially dropped and will be seen on RX side.";
    }
    leaf counters_slice2_ifg1_ifgb_rx_port_14_cgm_tc0_dropped_packets {
      type oc-yang:counter64;
      description
        "RX port cgm ostc0 drops counter. Counts packets that were totally dropped and will not be seen on RX side.";
    }
    leaf counters_slice2_ifg1_ifgb_rx_port_14_cgm_tc0_partially_dropped_packets {
      type oc-yang:counter64;
      description
        "RX port cgm ostc0 partial drops counter. Counts packets that were partially dropped and will be seen on RX side.";
    }
    leaf counters_slice2_ifg1_ifgb_rx_port_14_cgm_tc1_dropped_packets {
      type oc-yang:counter64;
      description
        "RX port cgm ostc1 drops counter. Counts packets that were totally dropped and will not be seen on RX side.";
    }
    leaf counters_slice2_ifg1_ifgb_rx_port_14_cgm_tc1_partially_dropped_packets {
      type oc-yang:counter64;
      description
        "RX port cgm ostc1 partial drops counter. Counts packets that were partially dropped and will be seen on RX side.";
    }
    leaf counters_slice2_ifg1_ifgb_rx_port_14_cgm_tc2_dropped_packets {
      type oc-yang:counter64;
      description
        "RX port cgm ostc2 drops counter. Counts packets that were totally dropped and will not be seen on RX side.";
    }
    leaf counters_slice2_ifg1_ifgb_rx_port_14_cgm_tc2_partially_dropped_packets {
      type oc-yang:counter64;
      description
        "RX port cgm ostc2 partial drops counter. Counts packets that were partially dropped and will be seen on RX side.";
    }
    leaf counters_slice2_ifg1_ifgb_rx_port_14_cgm_tc3_dropped_packets {
      type oc-yang:counter64;
      description
        "RX port cgm ostc3 drops counter. Counts packets that were totally dropped and will not be seen on RX side.";
    }
    leaf counters_slice2_ifg1_ifgb_rx_port_14_cgm_tc3_partially_dropped_packets {
      type oc-yang:counter64;
      description
        "RX port cgm ostc3 partial drops counter. Counts packets that were partially dropped and will be seen on RX side.";
    }
    leaf counters_slice2_ifg1_ifgb_rx_port_15_cgm_tc0_dropped_packets {
      type oc-yang:counter64;
      description
        "RX port cgm ostc0 drops counter. Counts packets that were totally dropped and will not be seen on RX side.";
    }
    leaf counters_slice2_ifg1_ifgb_rx_port_15_cgm_tc0_partially_dropped_packets {
      type oc-yang:counter64;
      description
        "RX port cgm ostc0 partial drops counter. Counts packets that were partially dropped and will be seen on RX side.";
    }
    leaf counters_slice2_ifg1_ifgb_rx_port_15_cgm_tc1_dropped_packets {
      type oc-yang:counter64;
      description
        "RX port cgm ostc1 drops counter. Counts packets that were totally dropped and will not be seen on RX side.";
    }
    leaf counters_slice2_ifg1_ifgb_rx_port_15_cgm_tc1_partially_dropped_packets {
      type oc-yang:counter64;
      description
        "RX port cgm ostc1 partial drops counter. Counts packets that were partially dropped and will be seen on RX side.";
    }
    leaf counters_slice2_ifg1_ifgb_rx_port_15_cgm_tc2_dropped_packets {
      type oc-yang:counter64;
      description
        "RX port cgm ostc2 drops counter. Counts packets that were totally dropped and will not be seen on RX side.";
    }
    leaf counters_slice2_ifg1_ifgb_rx_port_15_cgm_tc2_partially_dropped_packets {
      type oc-yang:counter64;
      description
        "RX port cgm ostc2 partial drops counter. Counts packets that were partially dropped and will be seen on RX side.";
    }
    leaf counters_slice2_ifg1_ifgb_rx_port_15_cgm_tc3_dropped_packets {
      type oc-yang:counter64;
      description
        "RX port cgm ostc3 drops counter. Counts packets that were totally dropped and will not be seen on RX side.";
    }
    leaf counters_slice2_ifg1_ifgb_rx_port_15_cgm_tc3_partially_dropped_packets {
      type oc-yang:counter64;
      description
        "RX port cgm ostc3 partial drops counter. Counts packets that were partially dropped and will be seen on RX side.";
    }
    leaf counters_slice2_ifg1_ifgb_rx_port_16_cgm_tc0_dropped_packets {
      type oc-yang:counter64;
      description
        "RX port cgm ostc0 drops counter. Counts packets that were totally dropped and will not be seen on RX side.";
    }
    leaf counters_slice2_ifg1_ifgb_rx_port_16_cgm_tc0_partially_dropped_packets {
      type oc-yang:counter64;
      description
        "RX port cgm ostc0 partial drops counter. Counts packets that were partially dropped and will be seen on RX side.";
    }
    leaf counters_slice2_ifg1_ifgb_rx_port_16_cgm_tc1_dropped_packets {
      type oc-yang:counter64;
      description
        "RX port cgm ostc1 drops counter. Counts packets that were totally dropped and will not be seen on RX side.";
    }
    leaf counters_slice2_ifg1_ifgb_rx_port_16_cgm_tc1_partially_dropped_packets {
      type oc-yang:counter64;
      description
        "RX port cgm ostc1 partial drops counter. Counts packets that were partially dropped and will be seen on RX side.";
    }
    leaf counters_slice2_ifg1_ifgb_rx_port_16_cgm_tc2_dropped_packets {
      type oc-yang:counter64;
      description
        "RX port cgm ostc2 drops counter. Counts packets that were totally dropped and will not be seen on RX side.";
    }
    leaf counters_slice2_ifg1_ifgb_rx_port_16_cgm_tc2_partially_dropped_packets {
      type oc-yang:counter64;
      description
        "RX port cgm ostc2 partial drops counter. Counts packets that were partially dropped and will be seen on RX side.";
    }
    leaf counters_slice2_ifg1_ifgb_rx_port_16_cgm_tc3_dropped_packets {
      type oc-yang:counter64;
      description
        "RX port cgm ostc3 drops counter. Counts packets that were totally dropped and will not be seen on RX side.";
    }
    leaf counters_slice2_ifg1_ifgb_rx_port_16_cgm_tc3_partially_dropped_packets {
      type oc-yang:counter64;
      description
        "RX port cgm ostc3 partial drops counter. Counts packets that were partially dropped and will be seen on RX side.";
    }
    leaf counters_slice2_ifg1_ifgb_rx_port_17_cgm_tc0_dropped_packets {
      type oc-yang:counter64;
      description
        "RX port cgm ostc0 drops counter. Counts packets that were totally dropped and will not be seen on RX side.";
    }
    leaf counters_slice2_ifg1_ifgb_rx_port_17_cgm_tc0_partially_dropped_packets {
      type oc-yang:counter64;
      description
        "RX port cgm ostc0 partial drops counter. Counts packets that were partially dropped and will be seen on RX side.";
    }
    leaf counters_slice2_ifg1_ifgb_rx_port_17_cgm_tc1_dropped_packets {
      type oc-yang:counter64;
      description
        "RX port cgm ostc1 drops counter. Counts packets that were totally dropped and will not be seen on RX side.";
    }
    leaf counters_slice2_ifg1_ifgb_rx_port_17_cgm_tc1_partially_dropped_packets {
      type oc-yang:counter64;
      description
        "RX port cgm ostc1 partial drops counter. Counts packets that were partially dropped and will be seen on RX side.";
    }
    leaf counters_slice2_ifg1_ifgb_rx_port_17_cgm_tc2_dropped_packets {
      type oc-yang:counter64;
      description
        "RX port cgm ostc2 drops counter. Counts packets that were totally dropped and will not be seen on RX side.";
    }
    leaf counters_slice2_ifg1_ifgb_rx_port_17_cgm_tc2_partially_dropped_packets {
      type oc-yang:counter64;
      description
        "RX port cgm ostc2 partial drops counter. Counts packets that were partially dropped and will be seen on RX side.";
    }
    leaf counters_slice2_ifg1_ifgb_rx_port_17_cgm_tc3_dropped_packets {
      type oc-yang:counter64;
      description
        "RX port cgm ostc3 drops counter. Counts packets that were totally dropped and will not be seen on RX side.";
    }
    leaf counters_slice2_ifg1_ifgb_rx_port_17_cgm_tc3_partially_dropped_packets {
      type oc-yang:counter64;
      description
        "RX port cgm ostc3 partial drops counter. Counts packets that were partially dropped and will be seen on RX side.";
    }
    leaf counters_slice2_ifg1_ifgb_rx_port_18_cgm_tc0_dropped_packets {
      type oc-yang:counter64;
      description
        "RX port cgm ostc0 drops counter. Counts packets that were totally dropped and will not be seen on RX side.";
    }
    leaf counters_slice2_ifg1_ifgb_rx_port_18_cgm_tc0_partially_dropped_packets {
      type oc-yang:counter64;
      description
        "RX port cgm ostc0 partial drops counter. Counts packets that were partially dropped and will be seen on RX side.";
    }
    leaf counters_slice2_ifg1_ifgb_rx_port_18_cgm_tc1_dropped_packets {
      type oc-yang:counter64;
      description
        "RX port cgm ostc1 drops counter. Counts packets that were totally dropped and will not be seen on RX side.";
    }
    leaf counters_slice2_ifg1_ifgb_rx_port_18_cgm_tc1_partially_dropped_packets {
      type oc-yang:counter64;
      description
        "RX port cgm ostc1 partial drops counter. Counts packets that were partially dropped and will be seen on RX side.";
    }
    leaf counters_slice2_ifg1_ifgb_rx_port_18_cgm_tc2_dropped_packets {
      type oc-yang:counter64;
      description
        "RX port cgm ostc2 drops counter. Counts packets that were totally dropped and will not be seen on RX side.";
    }
    leaf counters_slice2_ifg1_ifgb_rx_port_18_cgm_tc2_partially_dropped_packets {
      type oc-yang:counter64;
      description
        "RX port cgm ostc2 partial drops counter. Counts packets that were partially dropped and will be seen on RX side.";
    }
    leaf counters_slice2_ifg1_ifgb_rx_port_18_cgm_tc3_dropped_packets {
      type oc-yang:counter64;
      description
        "RX port cgm ostc3 drops counter. Counts packets that were totally dropped and will not be seen on RX side.";
    }
    leaf counters_slice2_ifg1_ifgb_rx_port_18_cgm_tc3_partially_dropped_packets {
      type oc-yang:counter64;
      description
        "RX port cgm ostc3 partial drops counter. Counts packets that were partially dropped and will be seen on RX side.";
    }
    leaf counters_slice2_ifg1_ifgb_rx_port_19_cgm_tc0_dropped_packets {
      type oc-yang:counter64;
      description
        "RX port cgm ostc0 drops counter. Counts packets that were totally dropped and will not be seen on RX side.";
    }
    leaf counters_slice2_ifg1_ifgb_rx_port_19_cgm_tc0_partially_dropped_packets {
      type oc-yang:counter64;
      description
        "RX port cgm ostc0 partial drops counter. Counts packets that were partially dropped and will be seen on RX side.";
    }
    leaf counters_slice2_ifg1_ifgb_rx_port_19_cgm_tc1_dropped_packets {
      type oc-yang:counter64;
      description
        "RX port cgm ostc1 drops counter. Counts packets that were totally dropped and will not be seen on RX side.";
    }
    leaf counters_slice2_ifg1_ifgb_rx_port_19_cgm_tc1_partially_dropped_packets {
      type oc-yang:counter64;
      description
        "RX port cgm ostc1 partial drops counter. Counts packets that were partially dropped and will be seen on RX side.";
    }
    leaf counters_slice2_ifg1_ifgb_rx_port_19_cgm_tc2_dropped_packets {
      type oc-yang:counter64;
      description
        "RX port cgm ostc2 drops counter. Counts packets that were totally dropped and will not be seen on RX side.";
    }
    leaf counters_slice2_ifg1_ifgb_rx_port_19_cgm_tc2_partially_dropped_packets {
      type oc-yang:counter64;
      description
        "RX port cgm ostc2 partial drops counter. Counts packets that were partially dropped and will be seen on RX side.";
    }
    leaf counters_slice2_ifg1_ifgb_rx_port_19_cgm_tc3_dropped_packets {
      type oc-yang:counter64;
      description
        "RX port cgm ostc3 drops counter. Counts packets that were totally dropped and will not be seen on RX side.";
    }
    leaf counters_slice2_ifg1_ifgb_rx_port_19_cgm_tc3_partially_dropped_packets {
      type oc-yang:counter64;
      description
        "RX port cgm ostc3 partial drops counter. Counts packets that were partially dropped and will be seen on RX side.";
    }
    leaf counters_slice2_ifg1_ifgb_rx_port_2_cgm_tc0_dropped_packets {
      type oc-yang:counter64;
      description
        "RX port cgm ostc0 drops counter. Counts packets that were totally dropped and will not be seen on RX side.";
    }
    leaf counters_slice2_ifg1_ifgb_rx_port_2_cgm_tc0_partially_dropped_packets {
      type oc-yang:counter64;
      description
        "RX port cgm ostc0 partial drops counter. Counts packets that were partially dropped and will be seen on RX side.";
    }
    leaf counters_slice2_ifg1_ifgb_rx_port_2_cgm_tc1_dropped_packets {
      type oc-yang:counter64;
      description
        "RX port cgm ostc1 drops counter. Counts packets that were totally dropped and will not be seen on RX side.";
    }
    leaf counters_slice2_ifg1_ifgb_rx_port_2_cgm_tc1_partially_dropped_packets {
      type oc-yang:counter64;
      description
        "RX port cgm ostc1 partial drops counter. Counts packets that were partially dropped and will be seen on RX side.";
    }
    leaf counters_slice2_ifg1_ifgb_rx_port_2_cgm_tc2_dropped_packets {
      type oc-yang:counter64;
      description
        "RX port cgm ostc2 drops counter. Counts packets that were totally dropped and will not be seen on RX side.";
    }
    leaf counters_slice2_ifg1_ifgb_rx_port_2_cgm_tc2_partially_dropped_packets {
      type oc-yang:counter64;
      description
        "RX port cgm ostc2 partial drops counter. Counts packets that were partially dropped and will be seen on RX side.";
    }
    leaf counters_slice2_ifg1_ifgb_rx_port_2_cgm_tc3_dropped_packets {
      type oc-yang:counter64;
      description
        "RX port cgm ostc3 drops counter. Counts packets that were totally dropped and will not be seen on RX side.";
    }
    leaf counters_slice2_ifg1_ifgb_rx_port_2_cgm_tc3_partially_dropped_packets {
      type oc-yang:counter64;
      description
        "RX port cgm ostc3 partial drops counter. Counts packets that were partially dropped and will be seen on RX side.";
    }
    leaf counters_slice2_ifg1_ifgb_rx_port_20_cgm_tc0_dropped_packets {
      type oc-yang:counter64;
      description
        "RX port cgm ostc0 drops counter. Counts packets that were totally dropped and will not be seen on RX side.";
    }
    leaf counters_slice2_ifg1_ifgb_rx_port_20_cgm_tc0_partially_dropped_packets {
      type oc-yang:counter64;
      description
        "RX port cgm ostc0 partial drops counter. Counts packets that were partially dropped and will be seen on RX side.";
    }
    leaf counters_slice2_ifg1_ifgb_rx_port_20_cgm_tc1_dropped_packets {
      type oc-yang:counter64;
      description
        "RX port cgm ostc1 drops counter. Counts packets that were totally dropped and will not be seen on RX side.";
    }
    leaf counters_slice2_ifg1_ifgb_rx_port_20_cgm_tc1_partially_dropped_packets {
      type oc-yang:counter64;
      description
        "RX port cgm ostc1 partial drops counter. Counts packets that were partially dropped and will be seen on RX side.";
    }
    leaf counters_slice2_ifg1_ifgb_rx_port_20_cgm_tc2_dropped_packets {
      type oc-yang:counter64;
      description
        "RX port cgm ostc2 drops counter. Counts packets that were totally dropped and will not be seen on RX side.";
    }
    leaf counters_slice2_ifg1_ifgb_rx_port_20_cgm_tc2_partially_dropped_packets {
      type oc-yang:counter64;
      description
        "RX port cgm ostc2 partial drops counter. Counts packets that were partially dropped and will be seen on RX side.";
    }
    leaf counters_slice2_ifg1_ifgb_rx_port_20_cgm_tc3_dropped_packets {
      type oc-yang:counter64;
      description
        "RX port cgm ostc3 drops counter. Counts packets that were totally dropped and will not be seen on RX side.";
    }
    leaf counters_slice2_ifg1_ifgb_rx_port_20_cgm_tc3_partially_dropped_packets {
      type oc-yang:counter64;
      description
        "RX port cgm ostc3 partial drops counter. Counts packets that were partially dropped and will be seen on RX side.";
    }
    leaf counters_slice2_ifg1_ifgb_rx_port_21_cgm_tc0_dropped_packets {
      type oc-yang:counter64;
      description
        "RX port cgm ostc0 drops counter. Counts packets that were totally dropped and will not be seen on RX side.";
    }
    leaf counters_slice2_ifg1_ifgb_rx_port_21_cgm_tc0_partially_dropped_packets {
      type oc-yang:counter64;
      description
        "RX port cgm ostc0 partial drops counter. Counts packets that were partially dropped and will be seen on RX side.";
    }
    leaf counters_slice2_ifg1_ifgb_rx_port_21_cgm_tc1_dropped_packets {
      type oc-yang:counter64;
      description
        "RX port cgm ostc1 drops counter. Counts packets that were totally dropped and will not be seen on RX side.";
    }
    leaf counters_slice2_ifg1_ifgb_rx_port_21_cgm_tc1_partially_dropped_packets {
      type oc-yang:counter64;
      description
        "RX port cgm ostc1 partial drops counter. Counts packets that were partially dropped and will be seen on RX side.";
    }
    leaf counters_slice2_ifg1_ifgb_rx_port_21_cgm_tc2_dropped_packets {
      type oc-yang:counter64;
      description
        "RX port cgm ostc2 drops counter. Counts packets that were totally dropped and will not be seen on RX side.";
    }
    leaf counters_slice2_ifg1_ifgb_rx_port_21_cgm_tc2_partially_dropped_packets {
      type oc-yang:counter64;
      description
        "RX port cgm ostc2 partial drops counter. Counts packets that were partially dropped and will be seen on RX side.";
    }
    leaf counters_slice2_ifg1_ifgb_rx_port_21_cgm_tc3_dropped_packets {
      type oc-yang:counter64;
      description
        "RX port cgm ostc3 drops counter. Counts packets that were totally dropped and will not be seen on RX side.";
    }
    leaf counters_slice2_ifg1_ifgb_rx_port_21_cgm_tc3_partially_dropped_packets {
      type oc-yang:counter64;
      description
        "RX port cgm ostc3 partial drops counter. Counts packets that were partially dropped and will be seen on RX side.";
    }
    leaf counters_slice2_ifg1_ifgb_rx_port_22_cgm_tc0_dropped_packets {
      type oc-yang:counter64;
      description
        "RX port cgm ostc0 drops counter. Counts packets that were totally dropped and will not be seen on RX side.";
    }
    leaf counters_slice2_ifg1_ifgb_rx_port_22_cgm_tc0_partially_dropped_packets {
      type oc-yang:counter64;
      description
        "RX port cgm ostc0 partial drops counter. Counts packets that were partially dropped and will be seen on RX side.";
    }
    leaf counters_slice2_ifg1_ifgb_rx_port_22_cgm_tc1_dropped_packets {
      type oc-yang:counter64;
      description
        "RX port cgm ostc1 drops counter. Counts packets that were totally dropped and will not be seen on RX side.";
    }
    leaf counters_slice2_ifg1_ifgb_rx_port_22_cgm_tc1_partially_dropped_packets {
      type oc-yang:counter64;
      description
        "RX port cgm ostc1 partial drops counter. Counts packets that were partially dropped and will be seen on RX side.";
    }
    leaf counters_slice2_ifg1_ifgb_rx_port_22_cgm_tc2_dropped_packets {
      type oc-yang:counter64;
      description
        "RX port cgm ostc2 drops counter. Counts packets that were totally dropped and will not be seen on RX side.";
    }
    leaf counters_slice2_ifg1_ifgb_rx_port_22_cgm_tc2_partially_dropped_packets {
      type oc-yang:counter64;
      description
        "RX port cgm ostc2 partial drops counter. Counts packets that were partially dropped and will be seen on RX side.";
    }
    leaf counters_slice2_ifg1_ifgb_rx_port_22_cgm_tc3_dropped_packets {
      type oc-yang:counter64;
      description
        "RX port cgm ostc3 drops counter. Counts packets that were totally dropped and will not be seen on RX side.";
    }
    leaf counters_slice2_ifg1_ifgb_rx_port_22_cgm_tc3_partially_dropped_packets {
      type oc-yang:counter64;
      description
        "RX port cgm ostc3 partial drops counter. Counts packets that were partially dropped and will be seen on RX side.";
    }
    leaf counters_slice2_ifg1_ifgb_rx_port_23_cgm_tc0_dropped_packets {
      type oc-yang:counter64;
      description
        "RX port cgm ostc0 drops counter. Counts packets that were totally dropped and will not be seen on RX side.";
    }
    leaf counters_slice2_ifg1_ifgb_rx_port_23_cgm_tc0_partially_dropped_packets {
      type oc-yang:counter64;
      description
        "RX port cgm ostc0 partial drops counter. Counts packets that were partially dropped and will be seen on RX side.";
    }
    leaf counters_slice2_ifg1_ifgb_rx_port_23_cgm_tc1_dropped_packets {
      type oc-yang:counter64;
      description
        "RX port cgm ostc1 drops counter. Counts packets that were totally dropped and will not be seen on RX side.";
    }
    leaf counters_slice2_ifg1_ifgb_rx_port_23_cgm_tc1_partially_dropped_packets {
      type oc-yang:counter64;
      description
        "RX port cgm ostc1 partial drops counter. Counts packets that were partially dropped and will be seen on RX side.";
    }
    leaf counters_slice2_ifg1_ifgb_rx_port_23_cgm_tc2_dropped_packets {
      type oc-yang:counter64;
      description
        "RX port cgm ostc2 drops counter. Counts packets that were totally dropped and will not be seen on RX side.";
    }
    leaf counters_slice2_ifg1_ifgb_rx_port_23_cgm_tc2_partially_dropped_packets {
      type oc-yang:counter64;
      description
        "RX port cgm ostc2 partial drops counter. Counts packets that were partially dropped and will be seen on RX side.";
    }
    leaf counters_slice2_ifg1_ifgb_rx_port_23_cgm_tc3_dropped_packets {
      type oc-yang:counter64;
      description
        "RX port cgm ostc3 drops counter. Counts packets that were totally dropped and will not be seen on RX side.";
    }
    leaf counters_slice2_ifg1_ifgb_rx_port_23_cgm_tc3_partially_dropped_packets {
      type oc-yang:counter64;
      description
        "RX port cgm ostc3 partial drops counter. Counts packets that were partially dropped and will be seen on RX side.";
    }
    leaf counters_slice2_ifg1_ifgb_rx_port_24_cgm_tc0_dropped_packets {
      type oc-yang:counter64;
      description
        "RX port cgm ostc0 drops counter. Counts packets that were totally dropped and will not be seen on RX side.";
    }
    leaf counters_slice2_ifg1_ifgb_rx_port_24_cgm_tc0_partially_dropped_packets {
      type oc-yang:counter64;
      description
        "RX port cgm ostc0 partial drops counter. Counts packets that were partially dropped and will be seen on RX side.";
    }
    leaf counters_slice2_ifg1_ifgb_rx_port_24_cgm_tc1_dropped_packets {
      type oc-yang:counter64;
      description
        "RX port cgm ostc1 drops counter. Counts packets that were totally dropped and will not be seen on RX side.";
    }
    leaf counters_slice2_ifg1_ifgb_rx_port_24_cgm_tc1_partially_dropped_packets {
      type oc-yang:counter64;
      description
        "RX port cgm ostc1 partial drops counter. Counts packets that were partially dropped and will be seen on RX side.";
    }
    leaf counters_slice2_ifg1_ifgb_rx_port_24_cgm_tc2_dropped_packets {
      type oc-yang:counter64;
      description
        "RX port cgm ostc2 drops counter. Counts packets that were totally dropped and will not be seen on RX side.";
    }
    leaf counters_slice2_ifg1_ifgb_rx_port_24_cgm_tc2_partially_dropped_packets {
      type oc-yang:counter64;
      description
        "RX port cgm ostc2 partial drops counter. Counts packets that were partially dropped and will be seen on RX side.";
    }
    leaf counters_slice2_ifg1_ifgb_rx_port_24_cgm_tc3_dropped_packets {
      type oc-yang:counter64;
      description
        "RX port cgm ostc3 drops counter. Counts packets that were totally dropped and will not be seen on RX side.";
    }
    leaf counters_slice2_ifg1_ifgb_rx_port_24_cgm_tc3_partially_dropped_packets {
      type oc-yang:counter64;
      description
        "RX port cgm ostc3 partial drops counter. Counts packets that were partially dropped and will be seen on RX side.";
    }
    leaf counters_slice2_ifg1_ifgb_rx_port_25_cgm_tc0_dropped_packets {
      type oc-yang:counter64;
      description
        "RX port cgm ostc0 drops counter. Counts packets that were totally dropped and will not be seen on RX side.";
    }
    leaf counters_slice2_ifg1_ifgb_rx_port_25_cgm_tc0_partially_dropped_packets {
      type oc-yang:counter64;
      description
        "RX port cgm ostc0 partial drops counter. Counts packets that were partially dropped and will be seen on RX side.";
    }
    leaf counters_slice2_ifg1_ifgb_rx_port_25_cgm_tc1_dropped_packets {
      type oc-yang:counter64;
      description
        "RX port cgm ostc1 drops counter. Counts packets that were totally dropped and will not be seen on RX side.";
    }
    leaf counters_slice2_ifg1_ifgb_rx_port_25_cgm_tc1_partially_dropped_packets {
      type oc-yang:counter64;
      description
        "RX port cgm ostc1 partial drops counter. Counts packets that were partially dropped and will be seen on RX side.";
    }
    leaf counters_slice2_ifg1_ifgb_rx_port_25_cgm_tc2_dropped_packets {
      type oc-yang:counter64;
      description
        "RX port cgm ostc2 drops counter. Counts packets that were totally dropped and will not be seen on RX side.";
    }
    leaf counters_slice2_ifg1_ifgb_rx_port_25_cgm_tc2_partially_dropped_packets {
      type oc-yang:counter64;
      description
        "RX port cgm ostc2 partial drops counter. Counts packets that were partially dropped and will be seen on RX side.";
    }
    leaf counters_slice2_ifg1_ifgb_rx_port_25_cgm_tc3_dropped_packets {
      type oc-yang:counter64;
      description
        "RX port cgm ostc3 drops counter. Counts packets that were totally dropped and will not be seen on RX side.";
    }
    leaf counters_slice2_ifg1_ifgb_rx_port_25_cgm_tc3_partially_dropped_packets {
      type oc-yang:counter64;
      description
        "RX port cgm ostc3 partial drops counter. Counts packets that were partially dropped and will be seen on RX side.";
    }
    leaf counters_slice2_ifg1_ifgb_rx_port_26_cgm_tc0_dropped_packets {
      type oc-yang:counter64;
      description
        "RX port cgm ostc0 drops counter. Counts packets that were totally dropped and will not be seen on RX side.";
    }
    leaf counters_slice2_ifg1_ifgb_rx_port_26_cgm_tc0_partially_dropped_packets {
      type oc-yang:counter64;
      description
        "RX port cgm ostc0 partial drops counter. Counts packets that were partially dropped and will be seen on RX side.";
    }
    leaf counters_slice2_ifg1_ifgb_rx_port_26_cgm_tc1_dropped_packets {
      type oc-yang:counter64;
      description
        "RX port cgm ostc1 drops counter. Counts packets that were totally dropped and will not be seen on RX side.";
    }
    leaf counters_slice2_ifg1_ifgb_rx_port_26_cgm_tc1_partially_dropped_packets {
      type oc-yang:counter64;
      description
        "RX port cgm ostc1 partial drops counter. Counts packets that were partially dropped and will be seen on RX side.";
    }
    leaf counters_slice2_ifg1_ifgb_rx_port_26_cgm_tc2_dropped_packets {
      type oc-yang:counter64;
      description
        "RX port cgm ostc2 drops counter. Counts packets that were totally dropped and will not be seen on RX side.";
    }
    leaf counters_slice2_ifg1_ifgb_rx_port_26_cgm_tc2_partially_dropped_packets {
      type oc-yang:counter64;
      description
        "RX port cgm ostc2 partial drops counter. Counts packets that were partially dropped and will be seen on RX side.";
    }
    leaf counters_slice2_ifg1_ifgb_rx_port_26_cgm_tc3_dropped_packets {
      type oc-yang:counter64;
      description
        "RX port cgm ostc3 drops counter. Counts packets that were totally dropped and will not be seen on RX side.";
    }
    leaf counters_slice2_ifg1_ifgb_rx_port_26_cgm_tc3_partially_dropped_packets {
      type oc-yang:counter64;
      description
        "RX port cgm ostc3 partial drops counter. Counts packets that were partially dropped and will be seen on RX side.";
    }
    leaf counters_slice2_ifg1_ifgb_rx_port_27_cgm_tc0_dropped_packets {
      type oc-yang:counter64;
      description
        "RX port cgm ostc0 drops counter. Counts packets that were totally dropped and will not be seen on RX side.";
    }
    leaf counters_slice2_ifg1_ifgb_rx_port_27_cgm_tc0_partially_dropped_packets {
      type oc-yang:counter64;
      description
        "RX port cgm ostc0 partial drops counter. Counts packets that were partially dropped and will be seen on RX side.";
    }
    leaf counters_slice2_ifg1_ifgb_rx_port_27_cgm_tc1_dropped_packets {
      type oc-yang:counter64;
      description
        "RX port cgm ostc1 drops counter. Counts packets that were totally dropped and will not be seen on RX side.";
    }
    leaf counters_slice2_ifg1_ifgb_rx_port_27_cgm_tc1_partially_dropped_packets {
      type oc-yang:counter64;
      description
        "RX port cgm ostc1 partial drops counter. Counts packets that were partially dropped and will be seen on RX side.";
    }
    leaf counters_slice2_ifg1_ifgb_rx_port_27_cgm_tc2_dropped_packets {
      type oc-yang:counter64;
      description
        "RX port cgm ostc2 drops counter. Counts packets that were totally dropped and will not be seen on RX side.";
    }
    leaf counters_slice2_ifg1_ifgb_rx_port_27_cgm_tc2_partially_dropped_packets {
      type oc-yang:counter64;
      description
        "RX port cgm ostc2 partial drops counter. Counts packets that were partially dropped and will be seen on RX side.";
    }
    leaf counters_slice2_ifg1_ifgb_rx_port_27_cgm_tc3_dropped_packets {
      type oc-yang:counter64;
      description
        "RX port cgm ostc3 drops counter. Counts packets that were totally dropped and will not be seen on RX side.";
    }
    leaf counters_slice2_ifg1_ifgb_rx_port_27_cgm_tc3_partially_dropped_packets {
      type oc-yang:counter64;
      description
        "RX port cgm ostc3 partial drops counter. Counts packets that were partially dropped and will be seen on RX side.";
    }
    leaf counters_slice2_ifg1_ifgb_rx_port_28_cgm_tc0_dropped_packets {
      type oc-yang:counter64;
      description
        "RX port cgm ostc0 drops counter. Counts packets that were totally dropped and will not be seen on RX side.";
    }
    leaf counters_slice2_ifg1_ifgb_rx_port_28_cgm_tc0_partially_dropped_packets {
      type oc-yang:counter64;
      description
        "RX port cgm ostc0 partial drops counter. Counts packets that were partially dropped and will be seen on RX side.";
    }
    leaf counters_slice2_ifg1_ifgb_rx_port_28_cgm_tc1_dropped_packets {
      type oc-yang:counter64;
      description
        "RX port cgm ostc1 drops counter. Counts packets that were totally dropped and will not be seen on RX side.";
    }
    leaf counters_slice2_ifg1_ifgb_rx_port_28_cgm_tc1_partially_dropped_packets {
      type oc-yang:counter64;
      description
        "RX port cgm ostc1 partial drops counter. Counts packets that were partially dropped and will be seen on RX side.";
    }
    leaf counters_slice2_ifg1_ifgb_rx_port_28_cgm_tc2_dropped_packets {
      type oc-yang:counter64;
      description
        "RX port cgm ostc2 drops counter. Counts packets that were totally dropped and will not be seen on RX side.";
    }
    leaf counters_slice2_ifg1_ifgb_rx_port_28_cgm_tc2_partially_dropped_packets {
      type oc-yang:counter64;
      description
        "RX port cgm ostc2 partial drops counter. Counts packets that were partially dropped and will be seen on RX side.";
    }
    leaf counters_slice2_ifg1_ifgb_rx_port_28_cgm_tc3_dropped_packets {
      type oc-yang:counter64;
      description
        "RX port cgm ostc3 drops counter. Counts packets that were totally dropped and will not be seen on RX side.";
    }
    leaf counters_slice2_ifg1_ifgb_rx_port_28_cgm_tc3_partially_dropped_packets {
      type oc-yang:counter64;
      description
        "RX port cgm ostc3 partial drops counter. Counts packets that were partially dropped and will be seen on RX side.";
    }
    leaf counters_slice2_ifg1_ifgb_rx_port_29_cgm_tc0_dropped_packets {
      type oc-yang:counter64;
      description
        "RX port cgm ostc0 drops counter. Counts packets that were totally dropped and will not be seen on RX side.";
    }
    leaf counters_slice2_ifg1_ifgb_rx_port_29_cgm_tc0_partially_dropped_packets {
      type oc-yang:counter64;
      description
        "RX port cgm ostc0 partial drops counter. Counts packets that were partially dropped and will be seen on RX side.";
    }
    leaf counters_slice2_ifg1_ifgb_rx_port_29_cgm_tc1_dropped_packets {
      type oc-yang:counter64;
      description
        "RX port cgm ostc1 drops counter. Counts packets that were totally dropped and will not be seen on RX side.";
    }
    leaf counters_slice2_ifg1_ifgb_rx_port_29_cgm_tc1_partially_dropped_packets {
      type oc-yang:counter64;
      description
        "RX port cgm ostc1 partial drops counter. Counts packets that were partially dropped and will be seen on RX side.";
    }
    leaf counters_slice2_ifg1_ifgb_rx_port_29_cgm_tc2_dropped_packets {
      type oc-yang:counter64;
      description
        "RX port cgm ostc2 drops counter. Counts packets that were totally dropped and will not be seen on RX side.";
    }
    leaf counters_slice2_ifg1_ifgb_rx_port_29_cgm_tc2_partially_dropped_packets {
      type oc-yang:counter64;
      description
        "RX port cgm ostc2 partial drops counter. Counts packets that were partially dropped and will be seen on RX side.";
    }
    leaf counters_slice2_ifg1_ifgb_rx_port_29_cgm_tc3_dropped_packets {
      type oc-yang:counter64;
      description
        "RX port cgm ostc3 drops counter. Counts packets that were totally dropped and will not be seen on RX side.";
    }
    leaf counters_slice2_ifg1_ifgb_rx_port_29_cgm_tc3_partially_dropped_packets {
      type oc-yang:counter64;
      description
        "RX port cgm ostc3 partial drops counter. Counts packets that were partially dropped and will be seen on RX side.";
    }
    leaf counters_slice2_ifg1_ifgb_rx_port_3_cgm_tc0_dropped_packets {
      type oc-yang:counter64;
      description
        "RX port cgm ostc0 drops counter. Counts packets that were totally dropped and will not be seen on RX side.";
    }
    leaf counters_slice2_ifg1_ifgb_rx_port_3_cgm_tc0_partially_dropped_packets {
      type oc-yang:counter64;
      description
        "RX port cgm ostc0 partial drops counter. Counts packets that were partially dropped and will be seen on RX side.";
    }
    leaf counters_slice2_ifg1_ifgb_rx_port_3_cgm_tc1_dropped_packets {
      type oc-yang:counter64;
      description
        "RX port cgm ostc1 drops counter. Counts packets that were totally dropped and will not be seen on RX side.";
    }
    leaf counters_slice2_ifg1_ifgb_rx_port_3_cgm_tc1_partially_dropped_packets {
      type oc-yang:counter64;
      description
        "RX port cgm ostc1 partial drops counter. Counts packets that were partially dropped and will be seen on RX side.";
    }
    leaf counters_slice2_ifg1_ifgb_rx_port_3_cgm_tc2_dropped_packets {
      type oc-yang:counter64;
      description
        "RX port cgm ostc2 drops counter. Counts packets that were totally dropped and will not be seen on RX side.";
    }
    leaf counters_slice2_ifg1_ifgb_rx_port_3_cgm_tc2_partially_dropped_packets {
      type oc-yang:counter64;
      description
        "RX port cgm ostc2 partial drops counter. Counts packets that were partially dropped and will be seen on RX side.";
    }
    leaf counters_slice2_ifg1_ifgb_rx_port_3_cgm_tc3_dropped_packets {
      type oc-yang:counter64;
      description
        "RX port cgm ostc3 drops counter. Counts packets that were totally dropped and will not be seen on RX side.";
    }
    leaf counters_slice2_ifg1_ifgb_rx_port_3_cgm_tc3_partially_dropped_packets {
      type oc-yang:counter64;
      description
        "RX port cgm ostc3 partial drops counter. Counts packets that were partially dropped and will be seen on RX side.";
    }
    leaf counters_slice2_ifg1_ifgb_rx_port_30_cgm_tc0_dropped_packets {
      type oc-yang:counter64;
      description
        "RX port cgm ostc0 drops counter. Counts packets that were totally dropped and will not be seen on RX side.";
    }
    leaf counters_slice2_ifg1_ifgb_rx_port_30_cgm_tc0_partially_dropped_packets {
      type oc-yang:counter64;
      description
        "RX port cgm ostc0 partial drops counter. Counts packets that were partially dropped and will be seen on RX side.";
    }
    leaf counters_slice2_ifg1_ifgb_rx_port_30_cgm_tc1_dropped_packets {
      type oc-yang:counter64;
      description
        "RX port cgm ostc1 drops counter. Counts packets that were totally dropped and will not be seen on RX side.";
    }
    leaf counters_slice2_ifg1_ifgb_rx_port_30_cgm_tc1_partially_dropped_packets {
      type oc-yang:counter64;
      description
        "RX port cgm ostc1 partial drops counter. Counts packets that were partially dropped and will be seen on RX side.";
    }
    leaf counters_slice2_ifg1_ifgb_rx_port_30_cgm_tc2_dropped_packets {
      type oc-yang:counter64;
      description
        "RX port cgm ostc2 drops counter. Counts packets that were totally dropped and will not be seen on RX side.";
    }
    leaf counters_slice2_ifg1_ifgb_rx_port_30_cgm_tc2_partially_dropped_packets {
      type oc-yang:counter64;
      description
        "RX port cgm ostc2 partial drops counter. Counts packets that were partially dropped and will be seen on RX side.";
    }
    leaf counters_slice2_ifg1_ifgb_rx_port_30_cgm_tc3_dropped_packets {
      type oc-yang:counter64;
      description
        "RX port cgm ostc3 drops counter. Counts packets that were totally dropped and will not be seen on RX side.";
    }
    leaf counters_slice2_ifg1_ifgb_rx_port_30_cgm_tc3_partially_dropped_packets {
      type oc-yang:counter64;
      description
        "RX port cgm ostc3 partial drops counter. Counts packets that were partially dropped and will be seen on RX side.";
    }
    leaf counters_slice2_ifg1_ifgb_rx_port_31_cgm_tc0_dropped_packets {
      type oc-yang:counter64;
      description
        "RX port cgm ostc0 drops counter. Counts packets that were totally dropped and will not be seen on RX side.";
    }
    leaf counters_slice2_ifg1_ifgb_rx_port_31_cgm_tc0_partially_dropped_packets {
      type oc-yang:counter64;
      description
        "RX port cgm ostc0 partial drops counter. Counts packets that were partially dropped and will be seen on RX side.";
    }
    leaf counters_slice2_ifg1_ifgb_rx_port_31_cgm_tc1_dropped_packets {
      type oc-yang:counter64;
      description
        "RX port cgm ostc1 drops counter. Counts packets that were totally dropped and will not be seen on RX side.";
    }
    leaf counters_slice2_ifg1_ifgb_rx_port_31_cgm_tc1_partially_dropped_packets {
      type oc-yang:counter64;
      description
        "RX port cgm ostc1 partial drops counter. Counts packets that were partially dropped and will be seen on RX side.";
    }
    leaf counters_slice2_ifg1_ifgb_rx_port_31_cgm_tc2_dropped_packets {
      type oc-yang:counter64;
      description
        "RX port cgm ostc2 drops counter. Counts packets that were totally dropped and will not be seen on RX side.";
    }
    leaf counters_slice2_ifg1_ifgb_rx_port_31_cgm_tc2_partially_dropped_packets {
      type oc-yang:counter64;
      description
        "RX port cgm ostc2 partial drops counter. Counts packets that were partially dropped and will be seen on RX side.";
    }
    leaf counters_slice2_ifg1_ifgb_rx_port_31_cgm_tc3_dropped_packets {
      type oc-yang:counter64;
      description
        "RX port cgm ostc3 drops counter. Counts packets that were totally dropped and will not be seen on RX side.";
    }
    leaf counters_slice2_ifg1_ifgb_rx_port_31_cgm_tc3_partially_dropped_packets {
      type oc-yang:counter64;
      description
        "RX port cgm ostc3 partial drops counter. Counts packets that were partially dropped and will be seen on RX side.";
    }
    leaf counters_slice2_ifg1_ifgb_rx_port_4_cgm_tc0_dropped_packets {
      type oc-yang:counter64;
      description
        "RX port cgm ostc0 drops counter. Counts packets that were totally dropped and will not be seen on RX side.";
    }
    leaf counters_slice2_ifg1_ifgb_rx_port_4_cgm_tc0_partially_dropped_packets {
      type oc-yang:counter64;
      description
        "RX port cgm ostc0 partial drops counter. Counts packets that were partially dropped and will be seen on RX side.";
    }
    leaf counters_slice2_ifg1_ifgb_rx_port_4_cgm_tc1_dropped_packets {
      type oc-yang:counter64;
      description
        "RX port cgm ostc1 drops counter. Counts packets that were totally dropped and will not be seen on RX side.";
    }
    leaf counters_slice2_ifg1_ifgb_rx_port_4_cgm_tc1_partially_dropped_packets {
      type oc-yang:counter64;
      description
        "RX port cgm ostc1 partial drops counter. Counts packets that were partially dropped and will be seen on RX side.";
    }
    leaf counters_slice2_ifg1_ifgb_rx_port_4_cgm_tc2_dropped_packets {
      type oc-yang:counter64;
      description
        "RX port cgm ostc2 drops counter. Counts packets that were totally dropped and will not be seen on RX side.";
    }
    leaf counters_slice2_ifg1_ifgb_rx_port_4_cgm_tc2_partially_dropped_packets {
      type oc-yang:counter64;
      description
        "RX port cgm ostc2 partial drops counter. Counts packets that were partially dropped and will be seen on RX side.";
    }
    leaf counters_slice2_ifg1_ifgb_rx_port_4_cgm_tc3_dropped_packets {
      type oc-yang:counter64;
      description
        "RX port cgm ostc3 drops counter. Counts packets that were totally dropped and will not be seen on RX side.";
    }
    leaf counters_slice2_ifg1_ifgb_rx_port_4_cgm_tc3_partially_dropped_packets {
      type oc-yang:counter64;
      description
        "RX port cgm ostc3 partial drops counter. Counts packets that were partially dropped and will be seen on RX side.";
    }
    leaf counters_slice2_ifg1_ifgb_rx_port_5_cgm_tc0_dropped_packets {
      type oc-yang:counter64;
      description
        "RX port cgm ostc0 drops counter. Counts packets that were totally dropped and will not be seen on RX side.";
    }
    leaf counters_slice2_ifg1_ifgb_rx_port_5_cgm_tc0_partially_dropped_packets {
      type oc-yang:counter64;
      description
        "RX port cgm ostc0 partial drops counter. Counts packets that were partially dropped and will be seen on RX side.";
    }
    leaf counters_slice2_ifg1_ifgb_rx_port_5_cgm_tc1_dropped_packets {
      type oc-yang:counter64;
      description
        "RX port cgm ostc1 drops counter. Counts packets that were totally dropped and will not be seen on RX side.";
    }
    leaf counters_slice2_ifg1_ifgb_rx_port_5_cgm_tc1_partially_dropped_packets {
      type oc-yang:counter64;
      description
        "RX port cgm ostc1 partial drops counter. Counts packets that were partially dropped and will be seen on RX side.";
    }
    leaf counters_slice2_ifg1_ifgb_rx_port_5_cgm_tc2_dropped_packets {
      type oc-yang:counter64;
      description
        "RX port cgm ostc2 drops counter. Counts packets that were totally dropped and will not be seen on RX side.";
    }
    leaf counters_slice2_ifg1_ifgb_rx_port_5_cgm_tc2_partially_dropped_packets {
      type oc-yang:counter64;
      description
        "RX port cgm ostc2 partial drops counter. Counts packets that were partially dropped and will be seen on RX side.";
    }
    leaf counters_slice2_ifg1_ifgb_rx_port_5_cgm_tc3_dropped_packets {
      type oc-yang:counter64;
      description
        "RX port cgm ostc3 drops counter. Counts packets that were totally dropped and will not be seen on RX side.";
    }
    leaf counters_slice2_ifg1_ifgb_rx_port_5_cgm_tc3_partially_dropped_packets {
      type oc-yang:counter64;
      description
        "RX port cgm ostc3 partial drops counter. Counts packets that were partially dropped and will be seen on RX side.";
    }
    leaf counters_slice2_ifg1_ifgb_rx_port_6_cgm_tc0_dropped_packets {
      type oc-yang:counter64;
      description
        "RX port cgm ostc0 drops counter. Counts packets that were totally dropped and will not be seen on RX side.";
    }
    leaf counters_slice2_ifg1_ifgb_rx_port_6_cgm_tc0_partially_dropped_packets {
      type oc-yang:counter64;
      description
        "RX port cgm ostc0 partial drops counter. Counts packets that were partially dropped and will be seen on RX side.";
    }
    leaf counters_slice2_ifg1_ifgb_rx_port_6_cgm_tc1_dropped_packets {
      type oc-yang:counter64;
      description
        "RX port cgm ostc1 drops counter. Counts packets that were totally dropped and will not be seen on RX side.";
    }
    leaf counters_slice2_ifg1_ifgb_rx_port_6_cgm_tc1_partially_dropped_packets {
      type oc-yang:counter64;
      description
        "RX port cgm ostc1 partial drops counter. Counts packets that were partially dropped and will be seen on RX side.";
    }
    leaf counters_slice2_ifg1_ifgb_rx_port_6_cgm_tc2_dropped_packets {
      type oc-yang:counter64;
      description
        "RX port cgm ostc2 drops counter. Counts packets that were totally dropped and will not be seen on RX side.";
    }
    leaf counters_slice2_ifg1_ifgb_rx_port_6_cgm_tc2_partially_dropped_packets {
      type oc-yang:counter64;
      description
        "RX port cgm ostc2 partial drops counter. Counts packets that were partially dropped and will be seen on RX side.";
    }
    leaf counters_slice2_ifg1_ifgb_rx_port_6_cgm_tc3_dropped_packets {
      type oc-yang:counter64;
      description
        "RX port cgm ostc3 drops counter. Counts packets that were totally dropped and will not be seen on RX side.";
    }
    leaf counters_slice2_ifg1_ifgb_rx_port_6_cgm_tc3_partially_dropped_packets {
      type oc-yang:counter64;
      description
        "RX port cgm ostc3 partial drops counter. Counts packets that were partially dropped and will be seen on RX side.";
    }
    leaf counters_slice2_ifg1_ifgb_rx_port_7_cgm_tc0_dropped_packets {
      type oc-yang:counter64;
      description
        "RX port cgm ostc0 drops counter. Counts packets that were totally dropped and will not be seen on RX side.";
    }
    leaf counters_slice2_ifg1_ifgb_rx_port_7_cgm_tc0_partially_dropped_packets {
      type oc-yang:counter64;
      description
        "RX port cgm ostc0 partial drops counter. Counts packets that were partially dropped and will be seen on RX side.";
    }
    leaf counters_slice2_ifg1_ifgb_rx_port_7_cgm_tc1_dropped_packets {
      type oc-yang:counter64;
      description
        "RX port cgm ostc1 drops counter. Counts packets that were totally dropped and will not be seen on RX side.";
    }
    leaf counters_slice2_ifg1_ifgb_rx_port_7_cgm_tc1_partially_dropped_packets {
      type oc-yang:counter64;
      description
        "RX port cgm ostc1 partial drops counter. Counts packets that were partially dropped and will be seen on RX side.";
    }
    leaf counters_slice2_ifg1_ifgb_rx_port_7_cgm_tc2_dropped_packets {
      type oc-yang:counter64;
      description
        "RX port cgm ostc2 drops counter. Counts packets that were totally dropped and will not be seen on RX side.";
    }
    leaf counters_slice2_ifg1_ifgb_rx_port_7_cgm_tc2_partially_dropped_packets {
      type oc-yang:counter64;
      description
        "RX port cgm ostc2 partial drops counter. Counts packets that were partially dropped and will be seen on RX side.";
    }
    leaf counters_slice2_ifg1_ifgb_rx_port_7_cgm_tc3_dropped_packets {
      type oc-yang:counter64;
      description
        "RX port cgm ostc3 drops counter. Counts packets that were totally dropped and will not be seen on RX side.";
    }
    leaf counters_slice2_ifg1_ifgb_rx_port_7_cgm_tc3_partially_dropped_packets {
      type oc-yang:counter64;
      description
        "RX port cgm ostc3 partial drops counter. Counts packets that were partially dropped and will be seen on RX side.";
    }
    leaf counters_slice2_ifg1_ifgb_rx_port_8_cgm_tc0_dropped_packets {
      type oc-yang:counter64;
      description
        "RX port cgm ostc0 drops counter. Counts packets that were totally dropped and will not be seen on RX side.";
    }
    leaf counters_slice2_ifg1_ifgb_rx_port_8_cgm_tc0_partially_dropped_packets {
      type oc-yang:counter64;
      description
        "RX port cgm ostc0 partial drops counter. Counts packets that were partially dropped and will be seen on RX side.";
    }
    leaf counters_slice2_ifg1_ifgb_rx_port_8_cgm_tc1_dropped_packets {
      type oc-yang:counter64;
      description
        "RX port cgm ostc1 drops counter. Counts packets that were totally dropped and will not be seen on RX side.";
    }
    leaf counters_slice2_ifg1_ifgb_rx_port_8_cgm_tc1_partially_dropped_packets {
      type oc-yang:counter64;
      description
        "RX port cgm ostc1 partial drops counter. Counts packets that were partially dropped and will be seen on RX side.";
    }
    leaf counters_slice2_ifg1_ifgb_rx_port_8_cgm_tc2_dropped_packets {
      type oc-yang:counter64;
      description
        "RX port cgm ostc2 drops counter. Counts packets that were totally dropped and will not be seen on RX side.";
    }
    leaf counters_slice2_ifg1_ifgb_rx_port_8_cgm_tc2_partially_dropped_packets {
      type oc-yang:counter64;
      description
        "RX port cgm ostc2 partial drops counter. Counts packets that were partially dropped and will be seen on RX side.";
    }
    leaf counters_slice2_ifg1_ifgb_rx_port_8_cgm_tc3_dropped_packets {
      type oc-yang:counter64;
      description
        "RX port cgm ostc3 drops counter. Counts packets that were totally dropped and will not be seen on RX side.";
    }
    leaf counters_slice2_ifg1_ifgb_rx_port_8_cgm_tc3_partially_dropped_packets {
      type oc-yang:counter64;
      description
        "RX port cgm ostc3 partial drops counter. Counts packets that were partially dropped and will be seen on RX side.";
    }
    leaf counters_slice2_ifg1_ifgb_rx_port_9_cgm_tc0_dropped_packets {
      type oc-yang:counter64;
      description
        "RX port cgm ostc0 drops counter. Counts packets that were totally dropped and will not be seen on RX side.";
    }
    leaf counters_slice2_ifg1_ifgb_rx_port_9_cgm_tc0_partially_dropped_packets {
      type oc-yang:counter64;
      description
        "RX port cgm ostc0 partial drops counter. Counts packets that were partially dropped and will be seen on RX side.";
    }
    leaf counters_slice2_ifg1_ifgb_rx_port_9_cgm_tc1_dropped_packets {
      type oc-yang:counter64;
      description
        "RX port cgm ostc1 drops counter. Counts packets that were totally dropped and will not be seen on RX side.";
    }
    leaf counters_slice2_ifg1_ifgb_rx_port_9_cgm_tc1_partially_dropped_packets {
      type oc-yang:counter64;
      description
        "RX port cgm ostc1 partial drops counter. Counts packets that were partially dropped and will be seen on RX side.";
    }
    leaf counters_slice2_ifg1_ifgb_rx_port_9_cgm_tc2_dropped_packets {
      type oc-yang:counter64;
      description
        "RX port cgm ostc2 drops counter. Counts packets that were totally dropped and will not be seen on RX side.";
    }
    leaf counters_slice2_ifg1_ifgb_rx_port_9_cgm_tc2_partially_dropped_packets {
      type oc-yang:counter64;
      description
        "RX port cgm ostc2 partial drops counter. Counts packets that were partially dropped and will be seen on RX side.";
    }
    leaf counters_slice2_ifg1_ifgb_rx_port_9_cgm_tc3_dropped_packets {
      type oc-yang:counter64;
      description
        "RX port cgm ostc3 drops counter. Counts packets that were totally dropped and will not be seen on RX side.";
    }
    leaf counters_slice2_ifg1_ifgb_rx_port_9_cgm_tc3_partially_dropped_packets {
      type oc-yang:counter64;
      description
        "RX port cgm ostc3 partial drops counter. Counts packets that were partially dropped and will be seen on RX side.";
    }
    leaf counters_slice2_tx_cgm_dropped_packets_due_to_max_allowed_qsize {
      type oc-yang:counter64;
      description
        "Counts number of dropped packets by max allowed threshold";
    }
    leaf counters_slice2_tx_cgm_local_sch_uc_buffer_c_dropped_packets {
      type oc-yang:counter64;
      description
        "Counts number of dropped packets by counter C";
    }
    leaf counters_slice2_tx_cgm_mc_silently_dropped_packets {
      type oc-yang:counter64;
      description
        "Counter of dropped MC packets that were silently dropped";
    }
    leaf counters_slice2_tx_cgm_sch_uc_buffers_cd_dropped_packets {
      type oc-yang:counter64;
      description
        "Counts number of dropped packets by counter C+D";
    }
    leaf counters_slice2_tx_cgm_sch_uc_counter_z_dropped_packets {
      type oc-yang:counter64;
      description
        "Counts number of dropped packets by counter Z";
    }
    leaf counters_slice2_tx_cgm_total_dropped_packets {
      type oc-yang:counter64;
      description
        "Counts number of dropped in TxCGM only packets";
    }
    leaf counters_slice2_tx_cgm_uc_oq_test_dropped_packets {
      type oc-yang:counter64;
      description
        "Counts number of dropped by UC OQ test";
    }
    leaf counters_slice2_tx_cgm_uc_oqg_dropped_packets {
      type oc-yang:counter64;
      description
        "Counts number of dropped by UC OQG test";
    }
    leaf counters_slice2_tx_cgm_unsch_counter_w_dropped_packets {
      type oc-yang:counter64;
      description
        "Counts number of dropped packets by counter W";
    }
    leaf counters_slice2_tx_cgm_green_mc_oq_bytes_test_dropped_packets {
      type oc-yang:counter64;
      description
        "Counts number of dropped packets by OQ MC green bytes test";
    }
    leaf counters_slice2_tx_cgm_green_mc_oq_pds_test_dropped_packets {
      type oc-yang:counter64;
      description
        "Counts number of dropped packets by OQ MC green PDs test";
    }
    leaf counters_slice2_tx_cgm_mc_color_test0_dropped_packets {
      type oc-yang:counter64;
      description
        "Counts number of dropped packet by MC color test for:0 - Green1 - Yellow2 - Red3 - Other";
    }
    leaf counters_slice2_tx_cgm_mc_color_test1_dropped_packets {
      type oc-yang:counter64;
      description
        "Counts number of dropped packet by MC color test for:0 - Green1 - Yellow2 - Red3 - Other";
    }
    leaf counters_slice2_tx_cgm_mc_color_test2_dropped_packets {
      type oc-yang:counter64;
      description
        "Counts number of dropped packet by MC color test for:0 - Green1 - Yellow2 - Red3 - Other";
    }
    leaf counters_slice2_tx_cgm_mc_color_test3_dropped_packets {
      type oc-yang:counter64;
      description
        "Counts number of dropped packet by MC color test for:0 - Green1 - Yellow2 - Red3 - Other";
    }
    leaf counters_slice2_tx_cgm_mc_set0_dropped_bytes {
      type oc-yang:counter64;
      description
        "Counts MC dropped bytes";
    }
    leaf counters_slice2_tx_cgm_mc_set0_dropped_packets {
      type oc-yang:counter64;
      description
        "Counts MC dropped packets";
    }
    leaf counters_slice2_tx_cgm_mc_set1_dropped_bytes {
      type oc-yang:counter64;
      description
        "Counts MC dropped bytes";
    }
    leaf counters_slice2_tx_cgm_mc_set1_dropped_packets {
      type oc-yang:counter64;
      description
        "Counts MC dropped packets";
    }
    leaf counters_slice2_tx_cgm_mc_set2_dropped_bytes {
      type oc-yang:counter64;
      description
        "Counts MC dropped bytes";
    }
    leaf counters_slice2_tx_cgm_mc_set2_dropped_packets {
      type oc-yang:counter64;
      description
        "Counts MC dropped packets";
    }
    leaf counters_slice2_tx_cgm_mc_set3_dropped_bytes {
      type oc-yang:counter64;
      description
        "Counts MC dropped bytes";
    }
    leaf counters_slice2_tx_cgm_mc_set3_dropped_packets {
      type oc-yang:counter64;
      description
        "Counts MC dropped packets";
    }
    leaf counters_slice2_tx_cgm_uc_color_test0_dropped_packets {
      type oc-yang:counter64;
      description
        "Counts number of dropped packet by UC color test for:0 - Green1 - Yellow2 - Red3 - Other";
    }
    leaf counters_slice2_tx_cgm_uc_color_test1_dropped_packets {
      type oc-yang:counter64;
      description
        "Counts number of dropped packet by UC color test for:0 - Green1 - Yellow2 - Red3 - Other";
    }
    leaf counters_slice2_tx_cgm_uc_color_test2_dropped_packets {
      type oc-yang:counter64;
      description
        "Counts number of dropped packet by UC color test for:0 - Green1 - Yellow2 - Red3 - Other";
    }
    leaf counters_slice2_tx_cgm_uc_color_test3_dropped_packets {
      type oc-yang:counter64;
      description
        "Counts number of dropped packet by UC color test for:0 - Green1 - Yellow2 - Red3 - Other";
    }
    leaf counters_slice2_tx_cgm_uc_set0_dropped_bytes {
      type oc-yang:counter64;
      description
        "Counts UC dropped bytes";
    }
    leaf counters_slice2_tx_cgm_uc_set0_dropped_packets {
      type oc-yang:counter64;
      description
        "Counts UC dropped packets";
    }
    leaf counters_slice2_tx_cgm_uc_set1_dropped_bytes {
      type oc-yang:counter64;
      description
        "Counts UC dropped bytes";
    }
    leaf counters_slice2_tx_cgm_uc_set1_dropped_packets {
      type oc-yang:counter64;
      description
        "Counts UC dropped packets";
    }
    leaf counters_slice2_tx_cgm_uc_set2_dropped_bytes {
      type oc-yang:counter64;
      description
        "Counts UC dropped bytes";
    }
    leaf counters_slice2_tx_cgm_uc_set2_dropped_packets {
      type oc-yang:counter64;
      description
        "Counts UC dropped packets";
    }
    leaf counters_slice2_tx_cgm_uc_set3_dropped_bytes {
      type oc-yang:counter64;
      description
        "Counts UC dropped bytes";
    }
    leaf counters_slice2_tx_cgm_uc_set3_dropped_packets {
      type oc-yang:counter64;
      description
        "Counts UC dropped packets";
    }
    leaf counters_slice2_tx_cgm_yellow_mc_oq_bytes_test_dropped_packets {
      type oc-yang:counter64;
      description
        "Counts number of dropped packets by OQ MC yellow bytes test";
    }
    leaf counters_slice2_tx_cgm_yellow_mc_oq_pds_test_dropped_packets {
      type oc-yang:counter64;
      description
        "Counts number of dropped packets by OQ MC yellow PDs test";
    }
    leaf counters_slice2_tx_pdr_txrq_full_egress_rep_dropped_packets {
      type oc-yang:counter64;
      description
        "Number of dropped packets";
    }
    leaf counters_slice2_tx_pdr_txrq_overload_egress_rep_dropped_packets {
      type oc-yang:counter64;
      description
        "Number of dropped packets";
    }
    leaf counters_slice2_tx_pdr_txrq0_full_egress_rep_dropped_packets {
      type oc-yang:counter64;
      description
        "Number of dropped packets";
    }
    leaf counters_slice2_tx_pdr_txrq0_threshold0_deq_dropped_packets {
      type oc-yang:counter64;
      description
        "Number of dropped packets in TXRQ deq";
    }
    leaf counters_slice2_tx_pdr_txrq0_threshold0_enq_dropped_packets {
      type oc-yang:counter64;
      description
        "Number of dropped packets in TXRQ enq";
    }
    leaf counters_slice2_tx_pdr_txrq0_threshold0_unscheduled_cgm_drops {
      type oc-yang:counter64;
      description
        "nan";
    }
    leaf counters_slice2_tx_pdr_txrq0_threshold1_deq_dropped_packets {
      type oc-yang:counter64;
      description
        "Number of dropped packets in TXRQ deq";
    }
    leaf counters_slice2_tx_pdr_txrq0_threshold1_enq_dropped_packets {
      type oc-yang:counter64;
      description
        "Number of dropped packets in TXRQ enq";
    }
    leaf counters_slice2_tx_pdr_txrq0_threshold1_unscheduled_cgm_drops {
      type oc-yang:counter64;
      description
        "nan";
    }
    leaf counters_slice2_tx_pdr_txrq1_full_egress_rep_dropped_packets {
      type oc-yang:counter64;
      description
        "Number of dropped packets";
    }
    leaf counters_slice2_tx_pdr_txrq1_threshold0_deq_dropped_packets {
      type oc-yang:counter64;
      description
        "Number of dropped packets in TXRQ deq";
    }
    leaf counters_slice2_tx_pdr_txrq1_threshold0_enq_dropped_packets {
      type oc-yang:counter64;
      description
        "Number of dropped packets in TXRQ enq";
    }
    leaf counters_slice2_tx_pdr_txrq1_threshold0_unscheduled_cgm_drops {
      type oc-yang:counter64;
      description
        "nan";
    }
    leaf counters_slice2_tx_pdr_txrq1_threshold1_deq_dropped_packets {
      type oc-yang:counter64;
      description
        "Number of dropped packets in TXRQ deq";
    }
    leaf counters_slice2_tx_pdr_txrq1_threshold1_enq_dropped_packets {
      type oc-yang:counter64;
      description
        "Number of dropped packets in TXRQ enq";
    }
    leaf counters_slice2_tx_pdr_txrq1_threshold1_unscheduled_cgm_drops {
      type oc-yang:counter64;
      description
        "nan";
    }
    leaf counters_slice2_tx_pdr_txrq2_full_egress_rep_dropped_packets {
      type oc-yang:counter64;
      description
        "Number of dropped packets";
    }
    leaf counters_slice2_tx_pdr_txrq2_threshold0_deq_dropped_packets {
      type oc-yang:counter64;
      description
        "Number of dropped packets in TXRQ deq";
    }
    leaf counters_slice2_tx_pdr_txrq2_threshold0_enq_dropped_packets {
      type oc-yang:counter64;
      description
        "Number of dropped packets in TXRQ enq";
    }
    leaf counters_slice2_tx_pdr_txrq2_threshold1_deq_dropped_packets {
      type oc-yang:counter64;
      description
        "Number of dropped packets in TXRQ deq";
    }
    leaf counters_slice2_tx_pdr_txrq2_threshold1_enq_dropped_packets {
      type oc-yang:counter64;
      description
        "Number of dropped packets in TXRQ enq";
    }
    leaf counters_slice2_tx_pdr_txrq3_full_egress_rep_dropped_packets {
      type oc-yang:counter64;
      description
        "Number of dropped packets";
    }
    leaf counters_slice2_tx_pdr_txrq3_threshold0_deq_dropped_packets {
      type oc-yang:counter64;
      description
        "Number of dropped packets in TXRQ deq";
    }
    leaf counters_slice2_tx_pdr_txrq3_threshold0_enq_dropped_packets {
      type oc-yang:counter64;
      description
        "Number of dropped packets in TXRQ enq";
    }
    leaf counters_slice2_tx_pdr_txrq3_threshold1_deq_dropped_packets {
      type oc-yang:counter64;
      description
        "Number of dropped packets in TXRQ deq";
    }
    leaf counters_slice2_tx_pdr_txrq3_threshold1_enq_dropped_packets {
      type oc-yang:counter64;
      description
        "Number of dropped packets in TXRQ enq";
    }
    leaf counters_slice3_ifg0_ifgb_rx_port_0_cgm_tc0_dropped_packets {
      type oc-yang:counter64;
      description
        "RX port cgm ostc0 drops counter. Counts packets that were totally dropped and will not be seen on RX side.";
    }
    leaf counters_slice3_ifg0_ifgb_rx_port_0_cgm_tc0_partially_dropped_packets {
      type oc-yang:counter64;
      description
        "RX port cgm ostc0 partial drops counter. Counts packets that were partially dropped and will be seen on RX side.";
    }
    leaf counters_slice3_ifg0_ifgb_rx_port_0_cgm_tc1_dropped_packets {
      type oc-yang:counter64;
      description
        "RX port cgm ostc1 drops counter. Counts packets that were totally dropped and will not be seen on RX side.";
    }
    leaf counters_slice3_ifg0_ifgb_rx_port_0_cgm_tc1_partially_dropped_packets {
      type oc-yang:counter64;
      description
        "RX port cgm ostc1 partial drops counter. Counts packets that were partially dropped and will be seen on RX side.";
    }
    leaf counters_slice3_ifg0_ifgb_rx_port_0_cgm_tc2_dropped_packets {
      type oc-yang:counter64;
      description
        "RX port cgm ostc2 drops counter. Counts packets that were totally dropped and will not be seen on RX side.";
    }
    leaf counters_slice3_ifg0_ifgb_rx_port_0_cgm_tc2_partially_dropped_packets {
      type oc-yang:counter64;
      description
        "RX port cgm ostc2 partial drops counter. Counts packets that were partially dropped and will be seen on RX side.";
    }
    leaf counters_slice3_ifg0_ifgb_rx_port_0_cgm_tc3_dropped_packets {
      type oc-yang:counter64;
      description
        "RX port cgm ostc3 drops counter. Counts packets that were totally dropped and will not be seen on RX side.";
    }
    leaf counters_slice3_ifg0_ifgb_rx_port_0_cgm_tc3_partially_dropped_packets {
      type oc-yang:counter64;
      description
        "RX port cgm ostc3 partial drops counter. Counts packets that were partially dropped and will be seen on RX side.";
    }
    leaf counters_slice3_ifg0_ifgb_rx_port_1_cgm_tc0_dropped_packets {
      type oc-yang:counter64;
      description
        "RX port cgm ostc0 drops counter. Counts packets that were totally dropped and will not be seen on RX side.";
    }
    leaf counters_slice3_ifg0_ifgb_rx_port_1_cgm_tc0_partially_dropped_packets {
      type oc-yang:counter64;
      description
        "RX port cgm ostc0 partial drops counter. Counts packets that were partially dropped and will be seen on RX side.";
    }
    leaf counters_slice3_ifg0_ifgb_rx_port_1_cgm_tc1_dropped_packets {
      type oc-yang:counter64;
      description
        "RX port cgm ostc1 drops counter. Counts packets that were totally dropped and will not be seen on RX side.";
    }
    leaf counters_slice3_ifg0_ifgb_rx_port_1_cgm_tc1_partially_dropped_packets {
      type oc-yang:counter64;
      description
        "RX port cgm ostc1 partial drops counter. Counts packets that were partially dropped and will be seen on RX side.";
    }
    leaf counters_slice3_ifg0_ifgb_rx_port_1_cgm_tc2_dropped_packets {
      type oc-yang:counter64;
      description
        "RX port cgm ostc2 drops counter. Counts packets that were totally dropped and will not be seen on RX side.";
    }
    leaf counters_slice3_ifg0_ifgb_rx_port_1_cgm_tc2_partially_dropped_packets {
      type oc-yang:counter64;
      description
        "RX port cgm ostc2 partial drops counter. Counts packets that were partially dropped and will be seen on RX side.";
    }
    leaf counters_slice3_ifg0_ifgb_rx_port_1_cgm_tc3_dropped_packets {
      type oc-yang:counter64;
      description
        "RX port cgm ostc3 drops counter. Counts packets that were totally dropped and will not be seen on RX side.";
    }
    leaf counters_slice3_ifg0_ifgb_rx_port_1_cgm_tc3_partially_dropped_packets {
      type oc-yang:counter64;
      description
        "RX port cgm ostc3 partial drops counter. Counts packets that were partially dropped and will be seen on RX side.";
    }
    leaf counters_slice3_ifg0_ifgb_rx_port_10_cgm_tc0_dropped_packets {
      type oc-yang:counter64;
      description
        "RX port cgm ostc0 drops counter. Counts packets that were totally dropped and will not be seen on RX side.";
    }
    leaf counters_slice3_ifg0_ifgb_rx_port_10_cgm_tc0_partially_dropped_packets {
      type oc-yang:counter64;
      description
        "RX port cgm ostc0 partial drops counter. Counts packets that were partially dropped and will be seen on RX side.";
    }
    leaf counters_slice3_ifg0_ifgb_rx_port_10_cgm_tc1_dropped_packets {
      type oc-yang:counter64;
      description
        "RX port cgm ostc1 drops counter. Counts packets that were totally dropped and will not be seen on RX side.";
    }
    leaf counters_slice3_ifg0_ifgb_rx_port_10_cgm_tc1_partially_dropped_packets {
      type oc-yang:counter64;
      description
        "RX port cgm ostc1 partial drops counter. Counts packets that were partially dropped and will be seen on RX side.";
    }
    leaf counters_slice3_ifg0_ifgb_rx_port_10_cgm_tc2_dropped_packets {
      type oc-yang:counter64;
      description
        "RX port cgm ostc2 drops counter. Counts packets that were totally dropped and will not be seen on RX side.";
    }
    leaf counters_slice3_ifg0_ifgb_rx_port_10_cgm_tc2_partially_dropped_packets {
      type oc-yang:counter64;
      description
        "RX port cgm ostc2 partial drops counter. Counts packets that were partially dropped and will be seen on RX side.";
    }
    leaf counters_slice3_ifg0_ifgb_rx_port_10_cgm_tc3_dropped_packets {
      type oc-yang:counter64;
      description
        "RX port cgm ostc3 drops counter. Counts packets that were totally dropped and will not be seen on RX side.";
    }
    leaf counters_slice3_ifg0_ifgb_rx_port_10_cgm_tc3_partially_dropped_packets {
      type oc-yang:counter64;
      description
        "RX port cgm ostc3 partial drops counter. Counts packets that were partially dropped and will be seen on RX side.";
    }
    leaf counters_slice3_ifg0_ifgb_rx_port_11_cgm_tc0_dropped_packets {
      type oc-yang:counter64;
      description
        "RX port cgm ostc0 drops counter. Counts packets that were totally dropped and will not be seen on RX side.";
    }
    leaf counters_slice3_ifg0_ifgb_rx_port_11_cgm_tc0_partially_dropped_packets {
      type oc-yang:counter64;
      description
        "RX port cgm ostc0 partial drops counter. Counts packets that were partially dropped and will be seen on RX side.";
    }
    leaf counters_slice3_ifg0_ifgb_rx_port_11_cgm_tc1_dropped_packets {
      type oc-yang:counter64;
      description
        "RX port cgm ostc1 drops counter. Counts packets that were totally dropped and will not be seen on RX side.";
    }
    leaf counters_slice3_ifg0_ifgb_rx_port_11_cgm_tc1_partially_dropped_packets {
      type oc-yang:counter64;
      description
        "RX port cgm ostc1 partial drops counter. Counts packets that were partially dropped and will be seen on RX side.";
    }
    leaf counters_slice3_ifg0_ifgb_rx_port_11_cgm_tc2_dropped_packets {
      type oc-yang:counter64;
      description
        "RX port cgm ostc2 drops counter. Counts packets that were totally dropped and will not be seen on RX side.";
    }
    leaf counters_slice3_ifg0_ifgb_rx_port_11_cgm_tc2_partially_dropped_packets {
      type oc-yang:counter64;
      description
        "RX port cgm ostc2 partial drops counter. Counts packets that were partially dropped and will be seen on RX side.";
    }
    leaf counters_slice3_ifg0_ifgb_rx_port_11_cgm_tc3_dropped_packets {
      type oc-yang:counter64;
      description
        "RX port cgm ostc3 drops counter. Counts packets that were totally dropped and will not be seen on RX side.";
    }
    leaf counters_slice3_ifg0_ifgb_rx_port_11_cgm_tc3_partially_dropped_packets {
      type oc-yang:counter64;
      description
        "RX port cgm ostc3 partial drops counter. Counts packets that were partially dropped and will be seen on RX side.";
    }
    leaf counters_slice3_ifg0_ifgb_rx_port_12_cgm_tc0_dropped_packets {
      type oc-yang:counter64;
      description
        "RX port cgm ostc0 drops counter. Counts packets that were totally dropped and will not be seen on RX side.";
    }
    leaf counters_slice3_ifg0_ifgb_rx_port_12_cgm_tc0_partially_dropped_packets {
      type oc-yang:counter64;
      description
        "RX port cgm ostc0 partial drops counter. Counts packets that were partially dropped and will be seen on RX side.";
    }
    leaf counters_slice3_ifg0_ifgb_rx_port_12_cgm_tc1_dropped_packets {
      type oc-yang:counter64;
      description
        "RX port cgm ostc1 drops counter. Counts packets that were totally dropped and will not be seen on RX side.";
    }
    leaf counters_slice3_ifg0_ifgb_rx_port_12_cgm_tc1_partially_dropped_packets {
      type oc-yang:counter64;
      description
        "RX port cgm ostc1 partial drops counter. Counts packets that were partially dropped and will be seen on RX side.";
    }
    leaf counters_slice3_ifg0_ifgb_rx_port_12_cgm_tc2_dropped_packets {
      type oc-yang:counter64;
      description
        "RX port cgm ostc2 drops counter. Counts packets that were totally dropped and will not be seen on RX side.";
    }
    leaf counters_slice3_ifg0_ifgb_rx_port_12_cgm_tc2_partially_dropped_packets {
      type oc-yang:counter64;
      description
        "RX port cgm ostc2 partial drops counter. Counts packets that were partially dropped and will be seen on RX side.";
    }
    leaf counters_slice3_ifg0_ifgb_rx_port_12_cgm_tc3_dropped_packets {
      type oc-yang:counter64;
      description
        "RX port cgm ostc3 drops counter. Counts packets that were totally dropped and will not be seen on RX side.";
    }
    leaf counters_slice3_ifg0_ifgb_rx_port_12_cgm_tc3_partially_dropped_packets {
      type oc-yang:counter64;
      description
        "RX port cgm ostc3 partial drops counter. Counts packets that were partially dropped and will be seen on RX side.";
    }
    leaf counters_slice3_ifg0_ifgb_rx_port_13_cgm_tc0_dropped_packets {
      type oc-yang:counter64;
      description
        "RX port cgm ostc0 drops counter. Counts packets that were totally dropped and will not be seen on RX side.";
    }
    leaf counters_slice3_ifg0_ifgb_rx_port_13_cgm_tc0_partially_dropped_packets {
      type oc-yang:counter64;
      description
        "RX port cgm ostc0 partial drops counter. Counts packets that were partially dropped and will be seen on RX side.";
    }
    leaf counters_slice3_ifg0_ifgb_rx_port_13_cgm_tc1_dropped_packets {
      type oc-yang:counter64;
      description
        "RX port cgm ostc1 drops counter. Counts packets that were totally dropped and will not be seen on RX side.";
    }
    leaf counters_slice3_ifg0_ifgb_rx_port_13_cgm_tc1_partially_dropped_packets {
      type oc-yang:counter64;
      description
        "RX port cgm ostc1 partial drops counter. Counts packets that were partially dropped and will be seen on RX side.";
    }
    leaf counters_slice3_ifg0_ifgb_rx_port_13_cgm_tc2_dropped_packets {
      type oc-yang:counter64;
      description
        "RX port cgm ostc2 drops counter. Counts packets that were totally dropped and will not be seen on RX side.";
    }
    leaf counters_slice3_ifg0_ifgb_rx_port_13_cgm_tc2_partially_dropped_packets {
      type oc-yang:counter64;
      description
        "RX port cgm ostc2 partial drops counter. Counts packets that were partially dropped and will be seen on RX side.";
    }
    leaf counters_slice3_ifg0_ifgb_rx_port_13_cgm_tc3_dropped_packets {
      type oc-yang:counter64;
      description
        "RX port cgm ostc3 drops counter. Counts packets that were totally dropped and will not be seen on RX side.";
    }
    leaf counters_slice3_ifg0_ifgb_rx_port_13_cgm_tc3_partially_dropped_packets {
      type oc-yang:counter64;
      description
        "RX port cgm ostc3 partial drops counter. Counts packets that were partially dropped and will be seen on RX side.";
    }
    leaf counters_slice3_ifg0_ifgb_rx_port_14_cgm_tc0_dropped_packets {
      type oc-yang:counter64;
      description
        "RX port cgm ostc0 drops counter. Counts packets that were totally dropped and will not be seen on RX side.";
    }
    leaf counters_slice3_ifg0_ifgb_rx_port_14_cgm_tc0_partially_dropped_packets {
      type oc-yang:counter64;
      description
        "RX port cgm ostc0 partial drops counter. Counts packets that were partially dropped and will be seen on RX side.";
    }
    leaf counters_slice3_ifg0_ifgb_rx_port_14_cgm_tc1_dropped_packets {
      type oc-yang:counter64;
      description
        "RX port cgm ostc1 drops counter. Counts packets that were totally dropped and will not be seen on RX side.";
    }
    leaf counters_slice3_ifg0_ifgb_rx_port_14_cgm_tc1_partially_dropped_packets {
      type oc-yang:counter64;
      description
        "RX port cgm ostc1 partial drops counter. Counts packets that were partially dropped and will be seen on RX side.";
    }
    leaf counters_slice3_ifg0_ifgb_rx_port_14_cgm_tc2_dropped_packets {
      type oc-yang:counter64;
      description
        "RX port cgm ostc2 drops counter. Counts packets that were totally dropped and will not be seen on RX side.";
    }
    leaf counters_slice3_ifg0_ifgb_rx_port_14_cgm_tc2_partially_dropped_packets {
      type oc-yang:counter64;
      description
        "RX port cgm ostc2 partial drops counter. Counts packets that were partially dropped and will be seen on RX side.";
    }
    leaf counters_slice3_ifg0_ifgb_rx_port_14_cgm_tc3_dropped_packets {
      type oc-yang:counter64;
      description
        "RX port cgm ostc3 drops counter. Counts packets that were totally dropped and will not be seen on RX side.";
    }
    leaf counters_slice3_ifg0_ifgb_rx_port_14_cgm_tc3_partially_dropped_packets {
      type oc-yang:counter64;
      description
        "RX port cgm ostc3 partial drops counter. Counts packets that were partially dropped and will be seen on RX side.";
    }
    leaf counters_slice3_ifg0_ifgb_rx_port_15_cgm_tc0_dropped_packets {
      type oc-yang:counter64;
      description
        "RX port cgm ostc0 drops counter. Counts packets that were totally dropped and will not be seen on RX side.";
    }
    leaf counters_slice3_ifg0_ifgb_rx_port_15_cgm_tc0_partially_dropped_packets {
      type oc-yang:counter64;
      description
        "RX port cgm ostc0 partial drops counter. Counts packets that were partially dropped and will be seen on RX side.";
    }
    leaf counters_slice3_ifg0_ifgb_rx_port_15_cgm_tc1_dropped_packets {
      type oc-yang:counter64;
      description
        "RX port cgm ostc1 drops counter. Counts packets that were totally dropped and will not be seen on RX side.";
    }
    leaf counters_slice3_ifg0_ifgb_rx_port_15_cgm_tc1_partially_dropped_packets {
      type oc-yang:counter64;
      description
        "RX port cgm ostc1 partial drops counter. Counts packets that were partially dropped and will be seen on RX side.";
    }
    leaf counters_slice3_ifg0_ifgb_rx_port_15_cgm_tc2_dropped_packets {
      type oc-yang:counter64;
      description
        "RX port cgm ostc2 drops counter. Counts packets that were totally dropped and will not be seen on RX side.";
    }
    leaf counters_slice3_ifg0_ifgb_rx_port_15_cgm_tc2_partially_dropped_packets {
      type oc-yang:counter64;
      description
        "RX port cgm ostc2 partial drops counter. Counts packets that were partially dropped and will be seen on RX side.";
    }
    leaf counters_slice3_ifg0_ifgb_rx_port_15_cgm_tc3_dropped_packets {
      type oc-yang:counter64;
      description
        "RX port cgm ostc3 drops counter. Counts packets that were totally dropped and will not be seen on RX side.";
    }
    leaf counters_slice3_ifg0_ifgb_rx_port_15_cgm_tc3_partially_dropped_packets {
      type oc-yang:counter64;
      description
        "RX port cgm ostc3 partial drops counter. Counts packets that were partially dropped and will be seen on RX side.";
    }
    leaf counters_slice3_ifg0_ifgb_rx_port_16_cgm_tc0_dropped_packets {
      type oc-yang:counter64;
      description
        "RX port cgm ostc0 drops counter. Counts packets that were totally dropped and will not be seen on RX side.";
    }
    leaf counters_slice3_ifg0_ifgb_rx_port_16_cgm_tc0_partially_dropped_packets {
      type oc-yang:counter64;
      description
        "RX port cgm ostc0 partial drops counter. Counts packets that were partially dropped and will be seen on RX side.";
    }
    leaf counters_slice3_ifg0_ifgb_rx_port_16_cgm_tc1_dropped_packets {
      type oc-yang:counter64;
      description
        "RX port cgm ostc1 drops counter. Counts packets that were totally dropped and will not be seen on RX side.";
    }
    leaf counters_slice3_ifg0_ifgb_rx_port_16_cgm_tc1_partially_dropped_packets {
      type oc-yang:counter64;
      description
        "RX port cgm ostc1 partial drops counter. Counts packets that were partially dropped and will be seen on RX side.";
    }
    leaf counters_slice3_ifg0_ifgb_rx_port_16_cgm_tc2_dropped_packets {
      type oc-yang:counter64;
      description
        "RX port cgm ostc2 drops counter. Counts packets that were totally dropped and will not be seen on RX side.";
    }
    leaf counters_slice3_ifg0_ifgb_rx_port_16_cgm_tc2_partially_dropped_packets {
      type oc-yang:counter64;
      description
        "RX port cgm ostc2 partial drops counter. Counts packets that were partially dropped and will be seen on RX side.";
    }
    leaf counters_slice3_ifg0_ifgb_rx_port_16_cgm_tc3_dropped_packets {
      type oc-yang:counter64;
      description
        "RX port cgm ostc3 drops counter. Counts packets that were totally dropped and will not be seen on RX side.";
    }
    leaf counters_slice3_ifg0_ifgb_rx_port_16_cgm_tc3_partially_dropped_packets {
      type oc-yang:counter64;
      description
        "RX port cgm ostc3 partial drops counter. Counts packets that were partially dropped and will be seen on RX side.";
    }
    leaf counters_slice3_ifg0_ifgb_rx_port_17_cgm_tc0_dropped_packets {
      type oc-yang:counter64;
      description
        "RX port cgm ostc0 drops counter. Counts packets that were totally dropped and will not be seen on RX side.";
    }
    leaf counters_slice3_ifg0_ifgb_rx_port_17_cgm_tc0_partially_dropped_packets {
      type oc-yang:counter64;
      description
        "RX port cgm ostc0 partial drops counter. Counts packets that were partially dropped and will be seen on RX side.";
    }
    leaf counters_slice3_ifg0_ifgb_rx_port_17_cgm_tc1_dropped_packets {
      type oc-yang:counter64;
      description
        "RX port cgm ostc1 drops counter. Counts packets that were totally dropped and will not be seen on RX side.";
    }
    leaf counters_slice3_ifg0_ifgb_rx_port_17_cgm_tc1_partially_dropped_packets {
      type oc-yang:counter64;
      description
        "RX port cgm ostc1 partial drops counter. Counts packets that were partially dropped and will be seen on RX side.";
    }
    leaf counters_slice3_ifg0_ifgb_rx_port_17_cgm_tc2_dropped_packets {
      type oc-yang:counter64;
      description
        "RX port cgm ostc2 drops counter. Counts packets that were totally dropped and will not be seen on RX side.";
    }
    leaf counters_slice3_ifg0_ifgb_rx_port_17_cgm_tc2_partially_dropped_packets {
      type oc-yang:counter64;
      description
        "RX port cgm ostc2 partial drops counter. Counts packets that were partially dropped and will be seen on RX side.";
    }
    leaf counters_slice3_ifg0_ifgb_rx_port_17_cgm_tc3_dropped_packets {
      type oc-yang:counter64;
      description
        "RX port cgm ostc3 drops counter. Counts packets that were totally dropped and will not be seen on RX side.";
    }
    leaf counters_slice3_ifg0_ifgb_rx_port_17_cgm_tc3_partially_dropped_packets {
      type oc-yang:counter64;
      description
        "RX port cgm ostc3 partial drops counter. Counts packets that were partially dropped and will be seen on RX side.";
    }
    leaf counters_slice3_ifg0_ifgb_rx_port_18_cgm_tc0_dropped_packets {
      type oc-yang:counter64;
      description
        "RX port cgm ostc0 drops counter. Counts packets that were totally dropped and will not be seen on RX side.";
    }
    leaf counters_slice3_ifg0_ifgb_rx_port_18_cgm_tc0_partially_dropped_packets {
      type oc-yang:counter64;
      description
        "RX port cgm ostc0 partial drops counter. Counts packets that were partially dropped and will be seen on RX side.";
    }
    leaf counters_slice3_ifg0_ifgb_rx_port_18_cgm_tc1_dropped_packets {
      type oc-yang:counter64;
      description
        "RX port cgm ostc1 drops counter. Counts packets that were totally dropped and will not be seen on RX side.";
    }
    leaf counters_slice3_ifg0_ifgb_rx_port_18_cgm_tc1_partially_dropped_packets {
      type oc-yang:counter64;
      description
        "RX port cgm ostc1 partial drops counter. Counts packets that were partially dropped and will be seen on RX side.";
    }
    leaf counters_slice3_ifg0_ifgb_rx_port_18_cgm_tc2_dropped_packets {
      type oc-yang:counter64;
      description
        "RX port cgm ostc2 drops counter. Counts packets that were totally dropped and will not be seen on RX side.";
    }
    leaf counters_slice3_ifg0_ifgb_rx_port_18_cgm_tc2_partially_dropped_packets {
      type oc-yang:counter64;
      description
        "RX port cgm ostc2 partial drops counter. Counts packets that were partially dropped and will be seen on RX side.";
    }
    leaf counters_slice3_ifg0_ifgb_rx_port_18_cgm_tc3_dropped_packets {
      type oc-yang:counter64;
      description
        "RX port cgm ostc3 drops counter. Counts packets that were totally dropped and will not be seen on RX side.";
    }
    leaf counters_slice3_ifg0_ifgb_rx_port_18_cgm_tc3_partially_dropped_packets {
      type oc-yang:counter64;
      description
        "RX port cgm ostc3 partial drops counter. Counts packets that were partially dropped and will be seen on RX side.";
    }
    leaf counters_slice3_ifg0_ifgb_rx_port_19_cgm_tc0_dropped_packets {
      type oc-yang:counter64;
      description
        "RX port cgm ostc0 drops counter. Counts packets that were totally dropped and will not be seen on RX side.";
    }
    leaf counters_slice3_ifg0_ifgb_rx_port_19_cgm_tc0_partially_dropped_packets {
      type oc-yang:counter64;
      description
        "RX port cgm ostc0 partial drops counter. Counts packets that were partially dropped and will be seen on RX side.";
    }
    leaf counters_slice3_ifg0_ifgb_rx_port_19_cgm_tc1_dropped_packets {
      type oc-yang:counter64;
      description
        "RX port cgm ostc1 drops counter. Counts packets that were totally dropped and will not be seen on RX side.";
    }
    leaf counters_slice3_ifg0_ifgb_rx_port_19_cgm_tc1_partially_dropped_packets {
      type oc-yang:counter64;
      description
        "RX port cgm ostc1 partial drops counter. Counts packets that were partially dropped and will be seen on RX side.";
    }
    leaf counters_slice3_ifg0_ifgb_rx_port_19_cgm_tc2_dropped_packets {
      type oc-yang:counter64;
      description
        "RX port cgm ostc2 drops counter. Counts packets that were totally dropped and will not be seen on RX side.";
    }
    leaf counters_slice3_ifg0_ifgb_rx_port_19_cgm_tc2_partially_dropped_packets {
      type oc-yang:counter64;
      description
        "RX port cgm ostc2 partial drops counter. Counts packets that were partially dropped and will be seen on RX side.";
    }
    leaf counters_slice3_ifg0_ifgb_rx_port_19_cgm_tc3_dropped_packets {
      type oc-yang:counter64;
      description
        "RX port cgm ostc3 drops counter. Counts packets that were totally dropped and will not be seen on RX side.";
    }
    leaf counters_slice3_ifg0_ifgb_rx_port_19_cgm_tc3_partially_dropped_packets {
      type oc-yang:counter64;
      description
        "RX port cgm ostc3 partial drops counter. Counts packets that were partially dropped and will be seen on RX side.";
    }
    leaf counters_slice3_ifg0_ifgb_rx_port_2_cgm_tc0_dropped_packets {
      type oc-yang:counter64;
      description
        "RX port cgm ostc0 drops counter. Counts packets that were totally dropped and will not be seen on RX side.";
    }
    leaf counters_slice3_ifg0_ifgb_rx_port_2_cgm_tc0_partially_dropped_packets {
      type oc-yang:counter64;
      description
        "RX port cgm ostc0 partial drops counter. Counts packets that were partially dropped and will be seen on RX side.";
    }
    leaf counters_slice3_ifg0_ifgb_rx_port_2_cgm_tc1_dropped_packets {
      type oc-yang:counter64;
      description
        "RX port cgm ostc1 drops counter. Counts packets that were totally dropped and will not be seen on RX side.";
    }
    leaf counters_slice3_ifg0_ifgb_rx_port_2_cgm_tc1_partially_dropped_packets {
      type oc-yang:counter64;
      description
        "RX port cgm ostc1 partial drops counter. Counts packets that were partially dropped and will be seen on RX side.";
    }
    leaf counters_slice3_ifg0_ifgb_rx_port_2_cgm_tc2_dropped_packets {
      type oc-yang:counter64;
      description
        "RX port cgm ostc2 drops counter. Counts packets that were totally dropped and will not be seen on RX side.";
    }
    leaf counters_slice3_ifg0_ifgb_rx_port_2_cgm_tc2_partially_dropped_packets {
      type oc-yang:counter64;
      description
        "RX port cgm ostc2 partial drops counter. Counts packets that were partially dropped and will be seen on RX side.";
    }
    leaf counters_slice3_ifg0_ifgb_rx_port_2_cgm_tc3_dropped_packets {
      type oc-yang:counter64;
      description
        "RX port cgm ostc3 drops counter. Counts packets that were totally dropped and will not be seen on RX side.";
    }
    leaf counters_slice3_ifg0_ifgb_rx_port_2_cgm_tc3_partially_dropped_packets {
      type oc-yang:counter64;
      description
        "RX port cgm ostc3 partial drops counter. Counts packets that were partially dropped and will be seen on RX side.";
    }
    leaf counters_slice3_ifg0_ifgb_rx_port_20_cgm_tc0_dropped_packets {
      type oc-yang:counter64;
      description
        "RX port cgm ostc0 drops counter. Counts packets that were totally dropped and will not be seen on RX side.";
    }
    leaf counters_slice3_ifg0_ifgb_rx_port_20_cgm_tc0_partially_dropped_packets {
      type oc-yang:counter64;
      description
        "RX port cgm ostc0 partial drops counter. Counts packets that were partially dropped and will be seen on RX side.";
    }
    leaf counters_slice3_ifg0_ifgb_rx_port_20_cgm_tc1_dropped_packets {
      type oc-yang:counter64;
      description
        "RX port cgm ostc1 drops counter. Counts packets that were totally dropped and will not be seen on RX side.";
    }
    leaf counters_slice3_ifg0_ifgb_rx_port_20_cgm_tc1_partially_dropped_packets {
      type oc-yang:counter64;
      description
        "RX port cgm ostc1 partial drops counter. Counts packets that were partially dropped and will be seen on RX side.";
    }
    leaf counters_slice3_ifg0_ifgb_rx_port_20_cgm_tc2_dropped_packets {
      type oc-yang:counter64;
      description
        "RX port cgm ostc2 drops counter. Counts packets that were totally dropped and will not be seen on RX side.";
    }
    leaf counters_slice3_ifg0_ifgb_rx_port_20_cgm_tc2_partially_dropped_packets {
      type oc-yang:counter64;
      description
        "RX port cgm ostc2 partial drops counter. Counts packets that were partially dropped and will be seen on RX side.";
    }
    leaf counters_slice3_ifg0_ifgb_rx_port_20_cgm_tc3_dropped_packets {
      type oc-yang:counter64;
      description
        "RX port cgm ostc3 drops counter. Counts packets that were totally dropped and will not be seen on RX side.";
    }
    leaf counters_slice3_ifg0_ifgb_rx_port_20_cgm_tc3_partially_dropped_packets {
      type oc-yang:counter64;
      description
        "RX port cgm ostc3 partial drops counter. Counts packets that were partially dropped and will be seen on RX side.";
    }
    leaf counters_slice3_ifg0_ifgb_rx_port_21_cgm_tc0_dropped_packets {
      type oc-yang:counter64;
      description
        "RX port cgm ostc0 drops counter. Counts packets that were totally dropped and will not be seen on RX side.";
    }
    leaf counters_slice3_ifg0_ifgb_rx_port_21_cgm_tc0_partially_dropped_packets {
      type oc-yang:counter64;
      description
        "RX port cgm ostc0 partial drops counter. Counts packets that were partially dropped and will be seen on RX side.";
    }
    leaf counters_slice3_ifg0_ifgb_rx_port_21_cgm_tc1_dropped_packets {
      type oc-yang:counter64;
      description
        "RX port cgm ostc1 drops counter. Counts packets that were totally dropped and will not be seen on RX side.";
    }
    leaf counters_slice3_ifg0_ifgb_rx_port_21_cgm_tc1_partially_dropped_packets {
      type oc-yang:counter64;
      description
        "RX port cgm ostc1 partial drops counter. Counts packets that were partially dropped and will be seen on RX side.";
    }
    leaf counters_slice3_ifg0_ifgb_rx_port_21_cgm_tc2_dropped_packets {
      type oc-yang:counter64;
      description
        "RX port cgm ostc2 drops counter. Counts packets that were totally dropped and will not be seen on RX side.";
    }
    leaf counters_slice3_ifg0_ifgb_rx_port_21_cgm_tc2_partially_dropped_packets {
      type oc-yang:counter64;
      description
        "RX port cgm ostc2 partial drops counter. Counts packets that were partially dropped and will be seen on RX side.";
    }
    leaf counters_slice3_ifg0_ifgb_rx_port_21_cgm_tc3_dropped_packets {
      type oc-yang:counter64;
      description
        "RX port cgm ostc3 drops counter. Counts packets that were totally dropped and will not be seen on RX side.";
    }
    leaf counters_slice3_ifg0_ifgb_rx_port_21_cgm_tc3_partially_dropped_packets {
      type oc-yang:counter64;
      description
        "RX port cgm ostc3 partial drops counter. Counts packets that were partially dropped and will be seen on RX side.";
    }
    leaf counters_slice3_ifg0_ifgb_rx_port_22_cgm_tc0_dropped_packets {
      type oc-yang:counter64;
      description
        "RX port cgm ostc0 drops counter. Counts packets that were totally dropped and will not be seen on RX side.";
    }
    leaf counters_slice3_ifg0_ifgb_rx_port_22_cgm_tc0_partially_dropped_packets {
      type oc-yang:counter64;
      description
        "RX port cgm ostc0 partial drops counter. Counts packets that were partially dropped and will be seen on RX side.";
    }
    leaf counters_slice3_ifg0_ifgb_rx_port_22_cgm_tc1_dropped_packets {
      type oc-yang:counter64;
      description
        "RX port cgm ostc1 drops counter. Counts packets that were totally dropped and will not be seen on RX side.";
    }
    leaf counters_slice3_ifg0_ifgb_rx_port_22_cgm_tc1_partially_dropped_packets {
      type oc-yang:counter64;
      description
        "RX port cgm ostc1 partial drops counter. Counts packets that were partially dropped and will be seen on RX side.";
    }
    leaf counters_slice3_ifg0_ifgb_rx_port_22_cgm_tc2_dropped_packets {
      type oc-yang:counter64;
      description
        "RX port cgm ostc2 drops counter. Counts packets that were totally dropped and will not be seen on RX side.";
    }
    leaf counters_slice3_ifg0_ifgb_rx_port_22_cgm_tc2_partially_dropped_packets {
      type oc-yang:counter64;
      description
        "RX port cgm ostc2 partial drops counter. Counts packets that were partially dropped and will be seen on RX side.";
    }
    leaf counters_slice3_ifg0_ifgb_rx_port_22_cgm_tc3_dropped_packets {
      type oc-yang:counter64;
      description
        "RX port cgm ostc3 drops counter. Counts packets that were totally dropped and will not be seen on RX side.";
    }
    leaf counters_slice3_ifg0_ifgb_rx_port_22_cgm_tc3_partially_dropped_packets {
      type oc-yang:counter64;
      description
        "RX port cgm ostc3 partial drops counter. Counts packets that were partially dropped and will be seen on RX side.";
    }
    leaf counters_slice3_ifg0_ifgb_rx_port_23_cgm_tc0_dropped_packets {
      type oc-yang:counter64;
      description
        "RX port cgm ostc0 drops counter. Counts packets that were totally dropped and will not be seen on RX side.";
    }
    leaf counters_slice3_ifg0_ifgb_rx_port_23_cgm_tc0_partially_dropped_packets {
      type oc-yang:counter64;
      description
        "RX port cgm ostc0 partial drops counter. Counts packets that were partially dropped and will be seen on RX side.";
    }
    leaf counters_slice3_ifg0_ifgb_rx_port_23_cgm_tc1_dropped_packets {
      type oc-yang:counter64;
      description
        "RX port cgm ostc1 drops counter. Counts packets that were totally dropped and will not be seen on RX side.";
    }
    leaf counters_slice3_ifg0_ifgb_rx_port_23_cgm_tc1_partially_dropped_packets {
      type oc-yang:counter64;
      description
        "RX port cgm ostc1 partial drops counter. Counts packets that were partially dropped and will be seen on RX side.";
    }
    leaf counters_slice3_ifg0_ifgb_rx_port_23_cgm_tc2_dropped_packets {
      type oc-yang:counter64;
      description
        "RX port cgm ostc2 drops counter. Counts packets that were totally dropped and will not be seen on RX side.";
    }
    leaf counters_slice3_ifg0_ifgb_rx_port_23_cgm_tc2_partially_dropped_packets {
      type oc-yang:counter64;
      description
        "RX port cgm ostc2 partial drops counter. Counts packets that were partially dropped and will be seen on RX side.";
    }
    leaf counters_slice3_ifg0_ifgb_rx_port_23_cgm_tc3_dropped_packets {
      type oc-yang:counter64;
      description
        "RX port cgm ostc3 drops counter. Counts packets that were totally dropped and will not be seen on RX side.";
    }
    leaf counters_slice3_ifg0_ifgb_rx_port_23_cgm_tc3_partially_dropped_packets {
      type oc-yang:counter64;
      description
        "RX port cgm ostc3 partial drops counter. Counts packets that were partially dropped and will be seen on RX side.";
    }
    leaf counters_slice3_ifg0_ifgb_rx_port_24_cgm_tc0_dropped_packets {
      type oc-yang:counter64;
      description
        "RX port cgm ostc0 drops counter. Counts packets that were totally dropped and will not be seen on RX side.";
    }
    leaf counters_slice3_ifg0_ifgb_rx_port_24_cgm_tc0_partially_dropped_packets {
      type oc-yang:counter64;
      description
        "RX port cgm ostc0 partial drops counter. Counts packets that were partially dropped and will be seen on RX side.";
    }
    leaf counters_slice3_ifg0_ifgb_rx_port_24_cgm_tc1_dropped_packets {
      type oc-yang:counter64;
      description
        "RX port cgm ostc1 drops counter. Counts packets that were totally dropped and will not be seen on RX side.";
    }
    leaf counters_slice3_ifg0_ifgb_rx_port_24_cgm_tc1_partially_dropped_packets {
      type oc-yang:counter64;
      description
        "RX port cgm ostc1 partial drops counter. Counts packets that were partially dropped and will be seen on RX side.";
    }
    leaf counters_slice3_ifg0_ifgb_rx_port_24_cgm_tc2_dropped_packets {
      type oc-yang:counter64;
      description
        "RX port cgm ostc2 drops counter. Counts packets that were totally dropped and will not be seen on RX side.";
    }
    leaf counters_slice3_ifg0_ifgb_rx_port_24_cgm_tc2_partially_dropped_packets {
      type oc-yang:counter64;
      description
        "RX port cgm ostc2 partial drops counter. Counts packets that were partially dropped and will be seen on RX side.";
    }
    leaf counters_slice3_ifg0_ifgb_rx_port_24_cgm_tc3_dropped_packets {
      type oc-yang:counter64;
      description
        "RX port cgm ostc3 drops counter. Counts packets that were totally dropped and will not be seen on RX side.";
    }
    leaf counters_slice3_ifg0_ifgb_rx_port_24_cgm_tc3_partially_dropped_packets {
      type oc-yang:counter64;
      description
        "RX port cgm ostc3 partial drops counter. Counts packets that were partially dropped and will be seen on RX side.";
    }
    leaf counters_slice3_ifg0_ifgb_rx_port_25_cgm_tc0_dropped_packets {
      type oc-yang:counter64;
      description
        "RX port cgm ostc0 drops counter. Counts packets that were totally dropped and will not be seen on RX side.";
    }
    leaf counters_slice3_ifg0_ifgb_rx_port_25_cgm_tc0_partially_dropped_packets {
      type oc-yang:counter64;
      description
        "RX port cgm ostc0 partial drops counter. Counts packets that were partially dropped and will be seen on RX side.";
    }
    leaf counters_slice3_ifg0_ifgb_rx_port_25_cgm_tc1_dropped_packets {
      type oc-yang:counter64;
      description
        "RX port cgm ostc1 drops counter. Counts packets that were totally dropped and will not be seen on RX side.";
    }
    leaf counters_slice3_ifg0_ifgb_rx_port_25_cgm_tc1_partially_dropped_packets {
      type oc-yang:counter64;
      description
        "RX port cgm ostc1 partial drops counter. Counts packets that were partially dropped and will be seen on RX side.";
    }
    leaf counters_slice3_ifg0_ifgb_rx_port_25_cgm_tc2_dropped_packets {
      type oc-yang:counter64;
      description
        "RX port cgm ostc2 drops counter. Counts packets that were totally dropped and will not be seen on RX side.";
    }
    leaf counters_slice3_ifg0_ifgb_rx_port_25_cgm_tc2_partially_dropped_packets {
      type oc-yang:counter64;
      description
        "RX port cgm ostc2 partial drops counter. Counts packets that were partially dropped and will be seen on RX side.";
    }
    leaf counters_slice3_ifg0_ifgb_rx_port_25_cgm_tc3_dropped_packets {
      type oc-yang:counter64;
      description
        "RX port cgm ostc3 drops counter. Counts packets that were totally dropped and will not be seen on RX side.";
    }
    leaf counters_slice3_ifg0_ifgb_rx_port_25_cgm_tc3_partially_dropped_packets {
      type oc-yang:counter64;
      description
        "RX port cgm ostc3 partial drops counter. Counts packets that were partially dropped and will be seen on RX side.";
    }
    leaf counters_slice3_ifg0_ifgb_rx_port_26_cgm_tc0_dropped_packets {
      type oc-yang:counter64;
      description
        "RX port cgm ostc0 drops counter. Counts packets that were totally dropped and will not be seen on RX side.";
    }
    leaf counters_slice3_ifg0_ifgb_rx_port_26_cgm_tc0_partially_dropped_packets {
      type oc-yang:counter64;
      description
        "RX port cgm ostc0 partial drops counter. Counts packets that were partially dropped and will be seen on RX side.";
    }
    leaf counters_slice3_ifg0_ifgb_rx_port_26_cgm_tc1_dropped_packets {
      type oc-yang:counter64;
      description
        "RX port cgm ostc1 drops counter. Counts packets that were totally dropped and will not be seen on RX side.";
    }
    leaf counters_slice3_ifg0_ifgb_rx_port_26_cgm_tc1_partially_dropped_packets {
      type oc-yang:counter64;
      description
        "RX port cgm ostc1 partial drops counter. Counts packets that were partially dropped and will be seen on RX side.";
    }
    leaf counters_slice3_ifg0_ifgb_rx_port_26_cgm_tc2_dropped_packets {
      type oc-yang:counter64;
      description
        "RX port cgm ostc2 drops counter. Counts packets that were totally dropped and will not be seen on RX side.";
    }
    leaf counters_slice3_ifg0_ifgb_rx_port_26_cgm_tc2_partially_dropped_packets {
      type oc-yang:counter64;
      description
        "RX port cgm ostc2 partial drops counter. Counts packets that were partially dropped and will be seen on RX side.";
    }
    leaf counters_slice3_ifg0_ifgb_rx_port_26_cgm_tc3_dropped_packets {
      type oc-yang:counter64;
      description
        "RX port cgm ostc3 drops counter. Counts packets that were totally dropped and will not be seen on RX side.";
    }
    leaf counters_slice3_ifg0_ifgb_rx_port_26_cgm_tc3_partially_dropped_packets {
      type oc-yang:counter64;
      description
        "RX port cgm ostc3 partial drops counter. Counts packets that were partially dropped and will be seen on RX side.";
    }
    leaf counters_slice3_ifg0_ifgb_rx_port_27_cgm_tc0_dropped_packets {
      type oc-yang:counter64;
      description
        "RX port cgm ostc0 drops counter. Counts packets that were totally dropped and will not be seen on RX side.";
    }
    leaf counters_slice3_ifg0_ifgb_rx_port_27_cgm_tc0_partially_dropped_packets {
      type oc-yang:counter64;
      description
        "RX port cgm ostc0 partial drops counter. Counts packets that were partially dropped and will be seen on RX side.";
    }
    leaf counters_slice3_ifg0_ifgb_rx_port_27_cgm_tc1_dropped_packets {
      type oc-yang:counter64;
      description
        "RX port cgm ostc1 drops counter. Counts packets that were totally dropped and will not be seen on RX side.";
    }
    leaf counters_slice3_ifg0_ifgb_rx_port_27_cgm_tc1_partially_dropped_packets {
      type oc-yang:counter64;
      description
        "RX port cgm ostc1 partial drops counter. Counts packets that were partially dropped and will be seen on RX side.";
    }
    leaf counters_slice3_ifg0_ifgb_rx_port_27_cgm_tc2_dropped_packets {
      type oc-yang:counter64;
      description
        "RX port cgm ostc2 drops counter. Counts packets that were totally dropped and will not be seen on RX side.";
    }
    leaf counters_slice3_ifg0_ifgb_rx_port_27_cgm_tc2_partially_dropped_packets {
      type oc-yang:counter64;
      description
        "RX port cgm ostc2 partial drops counter. Counts packets that were partially dropped and will be seen on RX side.";
    }
    leaf counters_slice3_ifg0_ifgb_rx_port_27_cgm_tc3_dropped_packets {
      type oc-yang:counter64;
      description
        "RX port cgm ostc3 drops counter. Counts packets that were totally dropped and will not be seen on RX side.";
    }
    leaf counters_slice3_ifg0_ifgb_rx_port_27_cgm_tc3_partially_dropped_packets {
      type oc-yang:counter64;
      description
        "RX port cgm ostc3 partial drops counter. Counts packets that were partially dropped and will be seen on RX side.";
    }
    leaf counters_slice3_ifg0_ifgb_rx_port_28_cgm_tc0_dropped_packets {
      type oc-yang:counter64;
      description
        "RX port cgm ostc0 drops counter. Counts packets that were totally dropped and will not be seen on RX side.";
    }
    leaf counters_slice3_ifg0_ifgb_rx_port_28_cgm_tc0_partially_dropped_packets {
      type oc-yang:counter64;
      description
        "RX port cgm ostc0 partial drops counter. Counts packets that were partially dropped and will be seen on RX side.";
    }
    leaf counters_slice3_ifg0_ifgb_rx_port_28_cgm_tc1_dropped_packets {
      type oc-yang:counter64;
      description
        "RX port cgm ostc1 drops counter. Counts packets that were totally dropped and will not be seen on RX side.";
    }
    leaf counters_slice3_ifg0_ifgb_rx_port_28_cgm_tc1_partially_dropped_packets {
      type oc-yang:counter64;
      description
        "RX port cgm ostc1 partial drops counter. Counts packets that were partially dropped and will be seen on RX side.";
    }
    leaf counters_slice3_ifg0_ifgb_rx_port_28_cgm_tc2_dropped_packets {
      type oc-yang:counter64;
      description
        "RX port cgm ostc2 drops counter. Counts packets that were totally dropped and will not be seen on RX side.";
    }
    leaf counters_slice3_ifg0_ifgb_rx_port_28_cgm_tc2_partially_dropped_packets {
      type oc-yang:counter64;
      description
        "RX port cgm ostc2 partial drops counter. Counts packets that were partially dropped and will be seen on RX side.";
    }
    leaf counters_slice3_ifg0_ifgb_rx_port_28_cgm_tc3_dropped_packets {
      type oc-yang:counter64;
      description
        "RX port cgm ostc3 drops counter. Counts packets that were totally dropped and will not be seen on RX side.";
    }
    leaf counters_slice3_ifg0_ifgb_rx_port_28_cgm_tc3_partially_dropped_packets {
      type oc-yang:counter64;
      description
        "RX port cgm ostc3 partial drops counter. Counts packets that were partially dropped and will be seen on RX side.";
    }
    leaf counters_slice3_ifg0_ifgb_rx_port_29_cgm_tc0_dropped_packets {
      type oc-yang:counter64;
      description
        "RX port cgm ostc0 drops counter. Counts packets that were totally dropped and will not be seen on RX side.";
    }
    leaf counters_slice3_ifg0_ifgb_rx_port_29_cgm_tc0_partially_dropped_packets {
      type oc-yang:counter64;
      description
        "RX port cgm ostc0 partial drops counter. Counts packets that were partially dropped and will be seen on RX side.";
    }
    leaf counters_slice3_ifg0_ifgb_rx_port_29_cgm_tc1_dropped_packets {
      type oc-yang:counter64;
      description
        "RX port cgm ostc1 drops counter. Counts packets that were totally dropped and will not be seen on RX side.";
    }
    leaf counters_slice3_ifg0_ifgb_rx_port_29_cgm_tc1_partially_dropped_packets {
      type oc-yang:counter64;
      description
        "RX port cgm ostc1 partial drops counter. Counts packets that were partially dropped and will be seen on RX side.";
    }
    leaf counters_slice3_ifg0_ifgb_rx_port_29_cgm_tc2_dropped_packets {
      type oc-yang:counter64;
      description
        "RX port cgm ostc2 drops counter. Counts packets that were totally dropped and will not be seen on RX side.";
    }
    leaf counters_slice3_ifg0_ifgb_rx_port_29_cgm_tc2_partially_dropped_packets {
      type oc-yang:counter64;
      description
        "RX port cgm ostc2 partial drops counter. Counts packets that were partially dropped and will be seen on RX side.";
    }
    leaf counters_slice3_ifg0_ifgb_rx_port_29_cgm_tc3_dropped_packets {
      type oc-yang:counter64;
      description
        "RX port cgm ostc3 drops counter. Counts packets that were totally dropped and will not be seen on RX side.";
    }
    leaf counters_slice3_ifg0_ifgb_rx_port_29_cgm_tc3_partially_dropped_packets {
      type oc-yang:counter64;
      description
        "RX port cgm ostc3 partial drops counter. Counts packets that were partially dropped and will be seen on RX side.";
    }
    leaf counters_slice3_ifg0_ifgb_rx_port_3_cgm_tc0_dropped_packets {
      type oc-yang:counter64;
      description
        "RX port cgm ostc0 drops counter. Counts packets that were totally dropped and will not be seen on RX side.";
    }
    leaf counters_slice3_ifg0_ifgb_rx_port_3_cgm_tc0_partially_dropped_packets {
      type oc-yang:counter64;
      description
        "RX port cgm ostc0 partial drops counter. Counts packets that were partially dropped and will be seen on RX side.";
    }
    leaf counters_slice3_ifg0_ifgb_rx_port_3_cgm_tc1_dropped_packets {
      type oc-yang:counter64;
      description
        "RX port cgm ostc1 drops counter. Counts packets that were totally dropped and will not be seen on RX side.";
    }
    leaf counters_slice3_ifg0_ifgb_rx_port_3_cgm_tc1_partially_dropped_packets {
      type oc-yang:counter64;
      description
        "RX port cgm ostc1 partial drops counter. Counts packets that were partially dropped and will be seen on RX side.";
    }
    leaf counters_slice3_ifg0_ifgb_rx_port_3_cgm_tc2_dropped_packets {
      type oc-yang:counter64;
      description
        "RX port cgm ostc2 drops counter. Counts packets that were totally dropped and will not be seen on RX side.";
    }
    leaf counters_slice3_ifg0_ifgb_rx_port_3_cgm_tc2_partially_dropped_packets {
      type oc-yang:counter64;
      description
        "RX port cgm ostc2 partial drops counter. Counts packets that were partially dropped and will be seen on RX side.";
    }
    leaf counters_slice3_ifg0_ifgb_rx_port_3_cgm_tc3_dropped_packets {
      type oc-yang:counter64;
      description
        "RX port cgm ostc3 drops counter. Counts packets that were totally dropped and will not be seen on RX side.";
    }
    leaf counters_slice3_ifg0_ifgb_rx_port_3_cgm_tc3_partially_dropped_packets {
      type oc-yang:counter64;
      description
        "RX port cgm ostc3 partial drops counter. Counts packets that were partially dropped and will be seen on RX side.";
    }
    leaf counters_slice3_ifg0_ifgb_rx_port_30_cgm_tc0_dropped_packets {
      type oc-yang:counter64;
      description
        "RX port cgm ostc0 drops counter. Counts packets that were totally dropped and will not be seen on RX side.";
    }
    leaf counters_slice3_ifg0_ifgb_rx_port_30_cgm_tc0_partially_dropped_packets {
      type oc-yang:counter64;
      description
        "RX port cgm ostc0 partial drops counter. Counts packets that were partially dropped and will be seen on RX side.";
    }
    leaf counters_slice3_ifg0_ifgb_rx_port_30_cgm_tc1_dropped_packets {
      type oc-yang:counter64;
      description
        "RX port cgm ostc1 drops counter. Counts packets that were totally dropped and will not be seen on RX side.";
    }
    leaf counters_slice3_ifg0_ifgb_rx_port_30_cgm_tc1_partially_dropped_packets {
      type oc-yang:counter64;
      description
        "RX port cgm ostc1 partial drops counter. Counts packets that were partially dropped and will be seen on RX side.";
    }
    leaf counters_slice3_ifg0_ifgb_rx_port_30_cgm_tc2_dropped_packets {
      type oc-yang:counter64;
      description
        "RX port cgm ostc2 drops counter. Counts packets that were totally dropped and will not be seen on RX side.";
    }
    leaf counters_slice3_ifg0_ifgb_rx_port_30_cgm_tc2_partially_dropped_packets {
      type oc-yang:counter64;
      description
        "RX port cgm ostc2 partial drops counter. Counts packets that were partially dropped and will be seen on RX side.";
    }
    leaf counters_slice3_ifg0_ifgb_rx_port_30_cgm_tc3_dropped_packets {
      type oc-yang:counter64;
      description
        "RX port cgm ostc3 drops counter. Counts packets that were totally dropped and will not be seen on RX side.";
    }
    leaf counters_slice3_ifg0_ifgb_rx_port_30_cgm_tc3_partially_dropped_packets {
      type oc-yang:counter64;
      description
        "RX port cgm ostc3 partial drops counter. Counts packets that were partially dropped and will be seen on RX side.";
    }
    leaf counters_slice3_ifg0_ifgb_rx_port_31_cgm_tc0_dropped_packets {
      type oc-yang:counter64;
      description
        "RX port cgm ostc0 drops counter. Counts packets that were totally dropped and will not be seen on RX side.";
    }
    leaf counters_slice3_ifg0_ifgb_rx_port_31_cgm_tc0_partially_dropped_packets {
      type oc-yang:counter64;
      description
        "RX port cgm ostc0 partial drops counter. Counts packets that were partially dropped and will be seen on RX side.";
    }
    leaf counters_slice3_ifg0_ifgb_rx_port_31_cgm_tc1_dropped_packets {
      type oc-yang:counter64;
      description
        "RX port cgm ostc1 drops counter. Counts packets that were totally dropped and will not be seen on RX side.";
    }
    leaf counters_slice3_ifg0_ifgb_rx_port_31_cgm_tc1_partially_dropped_packets {
      type oc-yang:counter64;
      description
        "RX port cgm ostc1 partial drops counter. Counts packets that were partially dropped and will be seen on RX side.";
    }
    leaf counters_slice3_ifg0_ifgb_rx_port_31_cgm_tc2_dropped_packets {
      type oc-yang:counter64;
      description
        "RX port cgm ostc2 drops counter. Counts packets that were totally dropped and will not be seen on RX side.";
    }
    leaf counters_slice3_ifg0_ifgb_rx_port_31_cgm_tc2_partially_dropped_packets {
      type oc-yang:counter64;
      description
        "RX port cgm ostc2 partial drops counter. Counts packets that were partially dropped and will be seen on RX side.";
    }
    leaf counters_slice3_ifg0_ifgb_rx_port_31_cgm_tc3_dropped_packets {
      type oc-yang:counter64;
      description
        "RX port cgm ostc3 drops counter. Counts packets that were totally dropped and will not be seen on RX side.";
    }
    leaf counters_slice3_ifg0_ifgb_rx_port_31_cgm_tc3_partially_dropped_packets {
      type oc-yang:counter64;
      description
        "RX port cgm ostc3 partial drops counter. Counts packets that were partially dropped and will be seen on RX side.";
    }
    leaf counters_slice3_ifg0_ifgb_rx_port_4_cgm_tc0_dropped_packets {
      type oc-yang:counter64;
      description
        "RX port cgm ostc0 drops counter. Counts packets that were totally dropped and will not be seen on RX side.";
    }
    leaf counters_slice3_ifg0_ifgb_rx_port_4_cgm_tc0_partially_dropped_packets {
      type oc-yang:counter64;
      description
        "RX port cgm ostc0 partial drops counter. Counts packets that were partially dropped and will be seen on RX side.";
    }
    leaf counters_slice3_ifg0_ifgb_rx_port_4_cgm_tc1_dropped_packets {
      type oc-yang:counter64;
      description
        "RX port cgm ostc1 drops counter. Counts packets that were totally dropped and will not be seen on RX side.";
    }
    leaf counters_slice3_ifg0_ifgb_rx_port_4_cgm_tc1_partially_dropped_packets {
      type oc-yang:counter64;
      description
        "RX port cgm ostc1 partial drops counter. Counts packets that were partially dropped and will be seen on RX side.";
    }
    leaf counters_slice3_ifg0_ifgb_rx_port_4_cgm_tc2_dropped_packets {
      type oc-yang:counter64;
      description
        "RX port cgm ostc2 drops counter. Counts packets that were totally dropped and will not be seen on RX side.";
    }
    leaf counters_slice3_ifg0_ifgb_rx_port_4_cgm_tc2_partially_dropped_packets {
      type oc-yang:counter64;
      description
        "RX port cgm ostc2 partial drops counter. Counts packets that were partially dropped and will be seen on RX side.";
    }
    leaf counters_slice3_ifg0_ifgb_rx_port_4_cgm_tc3_dropped_packets {
      type oc-yang:counter64;
      description
        "RX port cgm ostc3 drops counter. Counts packets that were totally dropped and will not be seen on RX side.";
    }
    leaf counters_slice3_ifg0_ifgb_rx_port_4_cgm_tc3_partially_dropped_packets {
      type oc-yang:counter64;
      description
        "RX port cgm ostc3 partial drops counter. Counts packets that were partially dropped and will be seen on RX side.";
    }
    leaf counters_slice3_ifg0_ifgb_rx_port_5_cgm_tc0_dropped_packets {
      type oc-yang:counter64;
      description
        "RX port cgm ostc0 drops counter. Counts packets that were totally dropped and will not be seen on RX side.";
    }
    leaf counters_slice3_ifg0_ifgb_rx_port_5_cgm_tc0_partially_dropped_packets {
      type oc-yang:counter64;
      description
        "RX port cgm ostc0 partial drops counter. Counts packets that were partially dropped and will be seen on RX side.";
    }
    leaf counters_slice3_ifg0_ifgb_rx_port_5_cgm_tc1_dropped_packets {
      type oc-yang:counter64;
      description
        "RX port cgm ostc1 drops counter. Counts packets that were totally dropped and will not be seen on RX side.";
    }
    leaf counters_slice3_ifg0_ifgb_rx_port_5_cgm_tc1_partially_dropped_packets {
      type oc-yang:counter64;
      description
        "RX port cgm ostc1 partial drops counter. Counts packets that were partially dropped and will be seen on RX side.";
    }
    leaf counters_slice3_ifg0_ifgb_rx_port_5_cgm_tc2_dropped_packets {
      type oc-yang:counter64;
      description
        "RX port cgm ostc2 drops counter. Counts packets that were totally dropped and will not be seen on RX side.";
    }
    leaf counters_slice3_ifg0_ifgb_rx_port_5_cgm_tc2_partially_dropped_packets {
      type oc-yang:counter64;
      description
        "RX port cgm ostc2 partial drops counter. Counts packets that were partially dropped and will be seen on RX side.";
    }
    leaf counters_slice3_ifg0_ifgb_rx_port_5_cgm_tc3_dropped_packets {
      type oc-yang:counter64;
      description
        "RX port cgm ostc3 drops counter. Counts packets that were totally dropped and will not be seen on RX side.";
    }
    leaf counters_slice3_ifg0_ifgb_rx_port_5_cgm_tc3_partially_dropped_packets {
      type oc-yang:counter64;
      description
        "RX port cgm ostc3 partial drops counter. Counts packets that were partially dropped and will be seen on RX side.";
    }
    leaf counters_slice3_ifg0_ifgb_rx_port_6_cgm_tc0_dropped_packets {
      type oc-yang:counter64;
      description
        "RX port cgm ostc0 drops counter. Counts packets that were totally dropped and will not be seen on RX side.";
    }
    leaf counters_slice3_ifg0_ifgb_rx_port_6_cgm_tc0_partially_dropped_packets {
      type oc-yang:counter64;
      description
        "RX port cgm ostc0 partial drops counter. Counts packets that were partially dropped and will be seen on RX side.";
    }
    leaf counters_slice3_ifg0_ifgb_rx_port_6_cgm_tc1_dropped_packets {
      type oc-yang:counter64;
      description
        "RX port cgm ostc1 drops counter. Counts packets that were totally dropped and will not be seen on RX side.";
    }
    leaf counters_slice3_ifg0_ifgb_rx_port_6_cgm_tc1_partially_dropped_packets {
      type oc-yang:counter64;
      description
        "RX port cgm ostc1 partial drops counter. Counts packets that were partially dropped and will be seen on RX side.";
    }
    leaf counters_slice3_ifg0_ifgb_rx_port_6_cgm_tc2_dropped_packets {
      type oc-yang:counter64;
      description
        "RX port cgm ostc2 drops counter. Counts packets that were totally dropped and will not be seen on RX side.";
    }
    leaf counters_slice3_ifg0_ifgb_rx_port_6_cgm_tc2_partially_dropped_packets {
      type oc-yang:counter64;
      description
        "RX port cgm ostc2 partial drops counter. Counts packets that were partially dropped and will be seen on RX side.";
    }
    leaf counters_slice3_ifg0_ifgb_rx_port_6_cgm_tc3_dropped_packets {
      type oc-yang:counter64;
      description
        "RX port cgm ostc3 drops counter. Counts packets that were totally dropped and will not be seen on RX side.";
    }
    leaf counters_slice3_ifg0_ifgb_rx_port_6_cgm_tc3_partially_dropped_packets {
      type oc-yang:counter64;
      description
        "RX port cgm ostc3 partial drops counter. Counts packets that were partially dropped and will be seen on RX side.";
    }
    leaf counters_slice3_ifg0_ifgb_rx_port_7_cgm_tc0_dropped_packets {
      type oc-yang:counter64;
      description
        "RX port cgm ostc0 drops counter. Counts packets that were totally dropped and will not be seen on RX side.";
    }
    leaf counters_slice3_ifg0_ifgb_rx_port_7_cgm_tc0_partially_dropped_packets {
      type oc-yang:counter64;
      description
        "RX port cgm ostc0 partial drops counter. Counts packets that were partially dropped and will be seen on RX side.";
    }
    leaf counters_slice3_ifg0_ifgb_rx_port_7_cgm_tc1_dropped_packets {
      type oc-yang:counter64;
      description
        "RX port cgm ostc1 drops counter. Counts packets that were totally dropped and will not be seen on RX side.";
    }
    leaf counters_slice3_ifg0_ifgb_rx_port_7_cgm_tc1_partially_dropped_packets {
      type oc-yang:counter64;
      description
        "RX port cgm ostc1 partial drops counter. Counts packets that were partially dropped and will be seen on RX side.";
    }
    leaf counters_slice3_ifg0_ifgb_rx_port_7_cgm_tc2_dropped_packets {
      type oc-yang:counter64;
      description
        "RX port cgm ostc2 drops counter. Counts packets that were totally dropped and will not be seen on RX side.";
    }
    leaf counters_slice3_ifg0_ifgb_rx_port_7_cgm_tc2_partially_dropped_packets {
      type oc-yang:counter64;
      description
        "RX port cgm ostc2 partial drops counter. Counts packets that were partially dropped and will be seen on RX side.";
    }
    leaf counters_slice3_ifg0_ifgb_rx_port_7_cgm_tc3_dropped_packets {
      type oc-yang:counter64;
      description
        "RX port cgm ostc3 drops counter. Counts packets that were totally dropped and will not be seen on RX side.";
    }
    leaf counters_slice3_ifg0_ifgb_rx_port_7_cgm_tc3_partially_dropped_packets {
      type oc-yang:counter64;
      description
        "RX port cgm ostc3 partial drops counter. Counts packets that were partially dropped and will be seen on RX side.";
    }
    leaf counters_slice3_ifg0_ifgb_rx_port_8_cgm_tc0_dropped_packets {
      type oc-yang:counter64;
      description
        "RX port cgm ostc0 drops counter. Counts packets that were totally dropped and will not be seen on RX side.";
    }
    leaf counters_slice3_ifg0_ifgb_rx_port_8_cgm_tc0_partially_dropped_packets {
      type oc-yang:counter64;
      description
        "RX port cgm ostc0 partial drops counter. Counts packets that were partially dropped and will be seen on RX side.";
    }
    leaf counters_slice3_ifg0_ifgb_rx_port_8_cgm_tc1_dropped_packets {
      type oc-yang:counter64;
      description
        "RX port cgm ostc1 drops counter. Counts packets that were totally dropped and will not be seen on RX side.";
    }
    leaf counters_slice3_ifg0_ifgb_rx_port_8_cgm_tc1_partially_dropped_packets {
      type oc-yang:counter64;
      description
        "RX port cgm ostc1 partial drops counter. Counts packets that were partially dropped and will be seen on RX side.";
    }
    leaf counters_slice3_ifg0_ifgb_rx_port_8_cgm_tc2_dropped_packets {
      type oc-yang:counter64;
      description
        "RX port cgm ostc2 drops counter. Counts packets that were totally dropped and will not be seen on RX side.";
    }
    leaf counters_slice3_ifg0_ifgb_rx_port_8_cgm_tc2_partially_dropped_packets {
      type oc-yang:counter64;
      description
        "RX port cgm ostc2 partial drops counter. Counts packets that were partially dropped and will be seen on RX side.";
    }
    leaf counters_slice3_ifg0_ifgb_rx_port_8_cgm_tc3_dropped_packets {
      type oc-yang:counter64;
      description
        "RX port cgm ostc3 drops counter. Counts packets that were totally dropped and will not be seen on RX side.";
    }
    leaf counters_slice3_ifg0_ifgb_rx_port_8_cgm_tc3_partially_dropped_packets {
      type oc-yang:counter64;
      description
        "RX port cgm ostc3 partial drops counter. Counts packets that were partially dropped and will be seen on RX side.";
    }
    leaf counters_slice3_ifg0_ifgb_rx_port_9_cgm_tc0_dropped_packets {
      type oc-yang:counter64;
      description
        "RX port cgm ostc0 drops counter. Counts packets that were totally dropped and will not be seen on RX side.";
    }
    leaf counters_slice3_ifg0_ifgb_rx_port_9_cgm_tc0_partially_dropped_packets {
      type oc-yang:counter64;
      description
        "RX port cgm ostc0 partial drops counter. Counts packets that were partially dropped and will be seen on RX side.";
    }
    leaf counters_slice3_ifg0_ifgb_rx_port_9_cgm_tc1_dropped_packets {
      type oc-yang:counter64;
      description
        "RX port cgm ostc1 drops counter. Counts packets that were totally dropped and will not be seen on RX side.";
    }
    leaf counters_slice3_ifg0_ifgb_rx_port_9_cgm_tc1_partially_dropped_packets {
      type oc-yang:counter64;
      description
        "RX port cgm ostc1 partial drops counter. Counts packets that were partially dropped and will be seen on RX side.";
    }
    leaf counters_slice3_ifg0_ifgb_rx_port_9_cgm_tc2_dropped_packets {
      type oc-yang:counter64;
      description
        "RX port cgm ostc2 drops counter. Counts packets that were totally dropped and will not be seen on RX side.";
    }
    leaf counters_slice3_ifg0_ifgb_rx_port_9_cgm_tc2_partially_dropped_packets {
      type oc-yang:counter64;
      description
        "RX port cgm ostc2 partial drops counter. Counts packets that were partially dropped and will be seen on RX side.";
    }
    leaf counters_slice3_ifg0_ifgb_rx_port_9_cgm_tc3_dropped_packets {
      type oc-yang:counter64;
      description
        "RX port cgm ostc3 drops counter. Counts packets that were totally dropped and will not be seen on RX side.";
    }
    leaf counters_slice3_ifg0_ifgb_rx_port_9_cgm_tc3_partially_dropped_packets {
      type oc-yang:counter64;
      description
        "RX port cgm ostc3 partial drops counter. Counts packets that were partially dropped and will be seen on RX side.";
    }
    leaf counters_slice3_ifg1_ifgb_rx_port_0_cgm_tc0_dropped_packets {
      type oc-yang:counter64;
      description
        "RX port cgm ostc0 drops counter. Counts packets that were totally dropped and will not be seen on RX side.";
    }
    leaf counters_slice3_ifg1_ifgb_rx_port_0_cgm_tc0_partially_dropped_packets {
      type oc-yang:counter64;
      description
        "RX port cgm ostc0 partial drops counter. Counts packets that were partially dropped and will be seen on RX side.";
    }
    leaf counters_slice3_ifg1_ifgb_rx_port_0_cgm_tc1_dropped_packets {
      type oc-yang:counter64;
      description
        "RX port cgm ostc1 drops counter. Counts packets that were totally dropped and will not be seen on RX side.";
    }
    leaf counters_slice3_ifg1_ifgb_rx_port_0_cgm_tc1_partially_dropped_packets {
      type oc-yang:counter64;
      description
        "RX port cgm ostc1 partial drops counter. Counts packets that were partially dropped and will be seen on RX side.";
    }
    leaf counters_slice3_ifg1_ifgb_rx_port_0_cgm_tc2_dropped_packets {
      type oc-yang:counter64;
      description
        "RX port cgm ostc2 drops counter. Counts packets that were totally dropped and will not be seen on RX side.";
    }
    leaf counters_slice3_ifg1_ifgb_rx_port_0_cgm_tc2_partially_dropped_packets {
      type oc-yang:counter64;
      description
        "RX port cgm ostc2 partial drops counter. Counts packets that were partially dropped and will be seen on RX side.";
    }
    leaf counters_slice3_ifg1_ifgb_rx_port_0_cgm_tc3_dropped_packets {
      type oc-yang:counter64;
      description
        "RX port cgm ostc3 drops counter. Counts packets that were totally dropped and will not be seen on RX side.";
    }
    leaf counters_slice3_ifg1_ifgb_rx_port_0_cgm_tc3_partially_dropped_packets {
      type oc-yang:counter64;
      description
        "RX port cgm ostc3 partial drops counter. Counts packets that were partially dropped and will be seen on RX side.";
    }
    leaf counters_slice3_ifg1_ifgb_rx_port_1_cgm_tc0_dropped_packets {
      type oc-yang:counter64;
      description
        "RX port cgm ostc0 drops counter. Counts packets that were totally dropped and will not be seen on RX side.";
    }
    leaf counters_slice3_ifg1_ifgb_rx_port_1_cgm_tc0_partially_dropped_packets {
      type oc-yang:counter64;
      description
        "RX port cgm ostc0 partial drops counter. Counts packets that were partially dropped and will be seen on RX side.";
    }
    leaf counters_slice3_ifg1_ifgb_rx_port_1_cgm_tc1_dropped_packets {
      type oc-yang:counter64;
      description
        "RX port cgm ostc1 drops counter. Counts packets that were totally dropped and will not be seen on RX side.";
    }
    leaf counters_slice3_ifg1_ifgb_rx_port_1_cgm_tc1_partially_dropped_packets {
      type oc-yang:counter64;
      description
        "RX port cgm ostc1 partial drops counter. Counts packets that were partially dropped and will be seen on RX side.";
    }
    leaf counters_slice3_ifg1_ifgb_rx_port_1_cgm_tc2_dropped_packets {
      type oc-yang:counter64;
      description
        "RX port cgm ostc2 drops counter. Counts packets that were totally dropped and will not be seen on RX side.";
    }
    leaf counters_slice3_ifg1_ifgb_rx_port_1_cgm_tc2_partially_dropped_packets {
      type oc-yang:counter64;
      description
        "RX port cgm ostc2 partial drops counter. Counts packets that were partially dropped and will be seen on RX side.";
    }
    leaf counters_slice3_ifg1_ifgb_rx_port_1_cgm_tc3_dropped_packets {
      type oc-yang:counter64;
      description
        "RX port cgm ostc3 drops counter. Counts packets that were totally dropped and will not be seen on RX side.";
    }
    leaf counters_slice3_ifg1_ifgb_rx_port_1_cgm_tc3_partially_dropped_packets {
      type oc-yang:counter64;
      description
        "RX port cgm ostc3 partial drops counter. Counts packets that were partially dropped and will be seen on RX side.";
    }
    leaf counters_slice3_ifg1_ifgb_rx_port_10_cgm_tc0_dropped_packets {
      type oc-yang:counter64;
      description
        "RX port cgm ostc0 drops counter. Counts packets that were totally dropped and will not be seen on RX side.";
    }
    leaf counters_slice3_ifg1_ifgb_rx_port_10_cgm_tc0_partially_dropped_packets {
      type oc-yang:counter64;
      description
        "RX port cgm ostc0 partial drops counter. Counts packets that were partially dropped and will be seen on RX side.";
    }
    leaf counters_slice3_ifg1_ifgb_rx_port_10_cgm_tc1_dropped_packets {
      type oc-yang:counter64;
      description
        "RX port cgm ostc1 drops counter. Counts packets that were totally dropped and will not be seen on RX side.";
    }
    leaf counters_slice3_ifg1_ifgb_rx_port_10_cgm_tc1_partially_dropped_packets {
      type oc-yang:counter64;
      description
        "RX port cgm ostc1 partial drops counter. Counts packets that were partially dropped and will be seen on RX side.";
    }
    leaf counters_slice3_ifg1_ifgb_rx_port_10_cgm_tc2_dropped_packets {
      type oc-yang:counter64;
      description
        "RX port cgm ostc2 drops counter. Counts packets that were totally dropped and will not be seen on RX side.";
    }
    leaf counters_slice3_ifg1_ifgb_rx_port_10_cgm_tc2_partially_dropped_packets {
      type oc-yang:counter64;
      description
        "RX port cgm ostc2 partial drops counter. Counts packets that were partially dropped and will be seen on RX side.";
    }
    leaf counters_slice3_ifg1_ifgb_rx_port_10_cgm_tc3_dropped_packets {
      type oc-yang:counter64;
      description
        "RX port cgm ostc3 drops counter. Counts packets that were totally dropped and will not be seen on RX side.";
    }
    leaf counters_slice3_ifg1_ifgb_rx_port_10_cgm_tc3_partially_dropped_packets {
      type oc-yang:counter64;
      description
        "RX port cgm ostc3 partial drops counter. Counts packets that were partially dropped and will be seen on RX side.";
    }
    leaf counters_slice3_ifg1_ifgb_rx_port_11_cgm_tc0_dropped_packets {
      type oc-yang:counter64;
      description
        "RX port cgm ostc0 drops counter. Counts packets that were totally dropped and will not be seen on RX side.";
    }
    leaf counters_slice3_ifg1_ifgb_rx_port_11_cgm_tc0_partially_dropped_packets {
      type oc-yang:counter64;
      description
        "RX port cgm ostc0 partial drops counter. Counts packets that were partially dropped and will be seen on RX side.";
    }
    leaf counters_slice3_ifg1_ifgb_rx_port_11_cgm_tc1_dropped_packets {
      type oc-yang:counter64;
      description
        "RX port cgm ostc1 drops counter. Counts packets that were totally dropped and will not be seen on RX side.";
    }
    leaf counters_slice3_ifg1_ifgb_rx_port_11_cgm_tc1_partially_dropped_packets {
      type oc-yang:counter64;
      description
        "RX port cgm ostc1 partial drops counter. Counts packets that were partially dropped and will be seen on RX side.";
    }
    leaf counters_slice3_ifg1_ifgb_rx_port_11_cgm_tc2_dropped_packets {
      type oc-yang:counter64;
      description
        "RX port cgm ostc2 drops counter. Counts packets that were totally dropped and will not be seen on RX side.";
    }
    leaf counters_slice3_ifg1_ifgb_rx_port_11_cgm_tc2_partially_dropped_packets {
      type oc-yang:counter64;
      description
        "RX port cgm ostc2 partial drops counter. Counts packets that were partially dropped and will be seen on RX side.";
    }
    leaf counters_slice3_ifg1_ifgb_rx_port_11_cgm_tc3_dropped_packets {
      type oc-yang:counter64;
      description
        "RX port cgm ostc3 drops counter. Counts packets that were totally dropped and will not be seen on RX side.";
    }
    leaf counters_slice3_ifg1_ifgb_rx_port_11_cgm_tc3_partially_dropped_packets {
      type oc-yang:counter64;
      description
        "RX port cgm ostc3 partial drops counter. Counts packets that were partially dropped and will be seen on RX side.";
    }
    leaf counters_slice3_ifg1_ifgb_rx_port_12_cgm_tc0_dropped_packets {
      type oc-yang:counter64;
      description
        "RX port cgm ostc0 drops counter. Counts packets that were totally dropped and will not be seen on RX side.";
    }
    leaf counters_slice3_ifg1_ifgb_rx_port_12_cgm_tc0_partially_dropped_packets {
      type oc-yang:counter64;
      description
        "RX port cgm ostc0 partial drops counter. Counts packets that were partially dropped and will be seen on RX side.";
    }
    leaf counters_slice3_ifg1_ifgb_rx_port_12_cgm_tc1_dropped_packets {
      type oc-yang:counter64;
      description
        "RX port cgm ostc1 drops counter. Counts packets that were totally dropped and will not be seen on RX side.";
    }
    leaf counters_slice3_ifg1_ifgb_rx_port_12_cgm_tc1_partially_dropped_packets {
      type oc-yang:counter64;
      description
        "RX port cgm ostc1 partial drops counter. Counts packets that were partially dropped and will be seen on RX side.";
    }
    leaf counters_slice3_ifg1_ifgb_rx_port_12_cgm_tc2_dropped_packets {
      type oc-yang:counter64;
      description
        "RX port cgm ostc2 drops counter. Counts packets that were totally dropped and will not be seen on RX side.";
    }
    leaf counters_slice3_ifg1_ifgb_rx_port_12_cgm_tc2_partially_dropped_packets {
      type oc-yang:counter64;
      description
        "RX port cgm ostc2 partial drops counter. Counts packets that were partially dropped and will be seen on RX side.";
    }
    leaf counters_slice3_ifg1_ifgb_rx_port_12_cgm_tc3_dropped_packets {
      type oc-yang:counter64;
      description
        "RX port cgm ostc3 drops counter. Counts packets that were totally dropped and will not be seen on RX side.";
    }
    leaf counters_slice3_ifg1_ifgb_rx_port_12_cgm_tc3_partially_dropped_packets {
      type oc-yang:counter64;
      description
        "RX port cgm ostc3 partial drops counter. Counts packets that were partially dropped and will be seen on RX side.";
    }
    leaf counters_slice3_ifg1_ifgb_rx_port_13_cgm_tc0_dropped_packets {
      type oc-yang:counter64;
      description
        "RX port cgm ostc0 drops counter. Counts packets that were totally dropped and will not be seen on RX side.";
    }
    leaf counters_slice3_ifg1_ifgb_rx_port_13_cgm_tc0_partially_dropped_packets {
      type oc-yang:counter64;
      description
        "RX port cgm ostc0 partial drops counter. Counts packets that were partially dropped and will be seen on RX side.";
    }
    leaf counters_slice3_ifg1_ifgb_rx_port_13_cgm_tc1_dropped_packets {
      type oc-yang:counter64;
      description
        "RX port cgm ostc1 drops counter. Counts packets that were totally dropped and will not be seen on RX side.";
    }
    leaf counters_slice3_ifg1_ifgb_rx_port_13_cgm_tc1_partially_dropped_packets {
      type oc-yang:counter64;
      description
        "RX port cgm ostc1 partial drops counter. Counts packets that were partially dropped and will be seen on RX side.";
    }
    leaf counters_slice3_ifg1_ifgb_rx_port_13_cgm_tc2_dropped_packets {
      type oc-yang:counter64;
      description
        "RX port cgm ostc2 drops counter. Counts packets that were totally dropped and will not be seen on RX side.";
    }
    leaf counters_slice3_ifg1_ifgb_rx_port_13_cgm_tc2_partially_dropped_packets {
      type oc-yang:counter64;
      description
        "RX port cgm ostc2 partial drops counter. Counts packets that were partially dropped and will be seen on RX side.";
    }
    leaf counters_slice3_ifg1_ifgb_rx_port_13_cgm_tc3_dropped_packets {
      type oc-yang:counter64;
      description
        "RX port cgm ostc3 drops counter. Counts packets that were totally dropped and will not be seen on RX side.";
    }
    leaf counters_slice3_ifg1_ifgb_rx_port_13_cgm_tc3_partially_dropped_packets {
      type oc-yang:counter64;
      description
        "RX port cgm ostc3 partial drops counter. Counts packets that were partially dropped and will be seen on RX side.";
    }
    leaf counters_slice3_ifg1_ifgb_rx_port_14_cgm_tc0_dropped_packets {
      type oc-yang:counter64;
      description
        "RX port cgm ostc0 drops counter. Counts packets that were totally dropped and will not be seen on RX side.";
    }
    leaf counters_slice3_ifg1_ifgb_rx_port_14_cgm_tc0_partially_dropped_packets {
      type oc-yang:counter64;
      description
        "RX port cgm ostc0 partial drops counter. Counts packets that were partially dropped and will be seen on RX side.";
    }
    leaf counters_slice3_ifg1_ifgb_rx_port_14_cgm_tc1_dropped_packets {
      type oc-yang:counter64;
      description
        "RX port cgm ostc1 drops counter. Counts packets that were totally dropped and will not be seen on RX side.";
    }
    leaf counters_slice3_ifg1_ifgb_rx_port_14_cgm_tc1_partially_dropped_packets {
      type oc-yang:counter64;
      description
        "RX port cgm ostc1 partial drops counter. Counts packets that were partially dropped and will be seen on RX side.";
    }
    leaf counters_slice3_ifg1_ifgb_rx_port_14_cgm_tc2_dropped_packets {
      type oc-yang:counter64;
      description
        "RX port cgm ostc2 drops counter. Counts packets that were totally dropped and will not be seen on RX side.";
    }
    leaf counters_slice3_ifg1_ifgb_rx_port_14_cgm_tc2_partially_dropped_packets {
      type oc-yang:counter64;
      description
        "RX port cgm ostc2 partial drops counter. Counts packets that were partially dropped and will be seen on RX side.";
    }
    leaf counters_slice3_ifg1_ifgb_rx_port_14_cgm_tc3_dropped_packets {
      type oc-yang:counter64;
      description
        "RX port cgm ostc3 drops counter. Counts packets that were totally dropped and will not be seen on RX side.";
    }
    leaf counters_slice3_ifg1_ifgb_rx_port_14_cgm_tc3_partially_dropped_packets {
      type oc-yang:counter64;
      description
        "RX port cgm ostc3 partial drops counter. Counts packets that were partially dropped and will be seen on RX side.";
    }
    leaf counters_slice3_ifg1_ifgb_rx_port_15_cgm_tc0_dropped_packets {
      type oc-yang:counter64;
      description
        "RX port cgm ostc0 drops counter. Counts packets that were totally dropped and will not be seen on RX side.";
    }
    leaf counters_slice3_ifg1_ifgb_rx_port_15_cgm_tc0_partially_dropped_packets {
      type oc-yang:counter64;
      description
        "RX port cgm ostc0 partial drops counter. Counts packets that were partially dropped and will be seen on RX side.";
    }
    leaf counters_slice3_ifg1_ifgb_rx_port_15_cgm_tc1_dropped_packets {
      type oc-yang:counter64;
      description
        "RX port cgm ostc1 drops counter. Counts packets that were totally dropped and will not be seen on RX side.";
    }
    leaf counters_slice3_ifg1_ifgb_rx_port_15_cgm_tc1_partially_dropped_packets {
      type oc-yang:counter64;
      description
        "RX port cgm ostc1 partial drops counter. Counts packets that were partially dropped and will be seen on RX side.";
    }
    leaf counters_slice3_ifg1_ifgb_rx_port_15_cgm_tc2_dropped_packets {
      type oc-yang:counter64;
      description
        "RX port cgm ostc2 drops counter. Counts packets that were totally dropped and will not be seen on RX side.";
    }
    leaf counters_slice3_ifg1_ifgb_rx_port_15_cgm_tc2_partially_dropped_packets {
      type oc-yang:counter64;
      description
        "RX port cgm ostc2 partial drops counter. Counts packets that were partially dropped and will be seen on RX side.";
    }
    leaf counters_slice3_ifg1_ifgb_rx_port_15_cgm_tc3_dropped_packets {
      type oc-yang:counter64;
      description
        "RX port cgm ostc3 drops counter. Counts packets that were totally dropped and will not be seen on RX side.";
    }
    leaf counters_slice3_ifg1_ifgb_rx_port_15_cgm_tc3_partially_dropped_packets {
      type oc-yang:counter64;
      description
        "RX port cgm ostc3 partial drops counter. Counts packets that were partially dropped and will be seen on RX side.";
    }
    leaf counters_slice3_ifg1_ifgb_rx_port_16_cgm_tc0_dropped_packets {
      type oc-yang:counter64;
      description
        "RX port cgm ostc0 drops counter. Counts packets that were totally dropped and will not be seen on RX side.";
    }
    leaf counters_slice3_ifg1_ifgb_rx_port_16_cgm_tc0_partially_dropped_packets {
      type oc-yang:counter64;
      description
        "RX port cgm ostc0 partial drops counter. Counts packets that were partially dropped and will be seen on RX side.";
    }
    leaf counters_slice3_ifg1_ifgb_rx_port_16_cgm_tc1_dropped_packets {
      type oc-yang:counter64;
      description
        "RX port cgm ostc1 drops counter. Counts packets that were totally dropped and will not be seen on RX side.";
    }
    leaf counters_slice3_ifg1_ifgb_rx_port_16_cgm_tc1_partially_dropped_packets {
      type oc-yang:counter64;
      description
        "RX port cgm ostc1 partial drops counter. Counts packets that were partially dropped and will be seen on RX side.";
    }
    leaf counters_slice3_ifg1_ifgb_rx_port_16_cgm_tc2_dropped_packets {
      type oc-yang:counter64;
      description
        "RX port cgm ostc2 drops counter. Counts packets that were totally dropped and will not be seen on RX side.";
    }
    leaf counters_slice3_ifg1_ifgb_rx_port_16_cgm_tc2_partially_dropped_packets {
      type oc-yang:counter64;
      description
        "RX port cgm ostc2 partial drops counter. Counts packets that were partially dropped and will be seen on RX side.";
    }
    leaf counters_slice3_ifg1_ifgb_rx_port_16_cgm_tc3_dropped_packets {
      type oc-yang:counter64;
      description
        "RX port cgm ostc3 drops counter. Counts packets that were totally dropped and will not be seen on RX side.";
    }
    leaf counters_slice3_ifg1_ifgb_rx_port_16_cgm_tc3_partially_dropped_packets {
      type oc-yang:counter64;
      description
        "RX port cgm ostc3 partial drops counter. Counts packets that were partially dropped and will be seen on RX side.";
    }
    leaf counters_slice3_ifg1_ifgb_rx_port_17_cgm_tc0_dropped_packets {
      type oc-yang:counter64;
      description
        "RX port cgm ostc0 drops counter. Counts packets that were totally dropped and will not be seen on RX side.";
    }
    leaf counters_slice3_ifg1_ifgb_rx_port_17_cgm_tc0_partially_dropped_packets {
      type oc-yang:counter64;
      description
        "RX port cgm ostc0 partial drops counter. Counts packets that were partially dropped and will be seen on RX side.";
    }
    leaf counters_slice3_ifg1_ifgb_rx_port_17_cgm_tc1_dropped_packets {
      type oc-yang:counter64;
      description
        "RX port cgm ostc1 drops counter. Counts packets that were totally dropped and will not be seen on RX side.";
    }
    leaf counters_slice3_ifg1_ifgb_rx_port_17_cgm_tc1_partially_dropped_packets {
      type oc-yang:counter64;
      description
        "RX port cgm ostc1 partial drops counter. Counts packets that were partially dropped and will be seen on RX side.";
    }
    leaf counters_slice3_ifg1_ifgb_rx_port_17_cgm_tc2_dropped_packets {
      type oc-yang:counter64;
      description
        "RX port cgm ostc2 drops counter. Counts packets that were totally dropped and will not be seen on RX side.";
    }
    leaf counters_slice3_ifg1_ifgb_rx_port_17_cgm_tc2_partially_dropped_packets {
      type oc-yang:counter64;
      description
        "RX port cgm ostc2 partial drops counter. Counts packets that were partially dropped and will be seen on RX side.";
    }
    leaf counters_slice3_ifg1_ifgb_rx_port_17_cgm_tc3_dropped_packets {
      type oc-yang:counter64;
      description
        "RX port cgm ostc3 drops counter. Counts packets that were totally dropped and will not be seen on RX side.";
    }
    leaf counters_slice3_ifg1_ifgb_rx_port_17_cgm_tc3_partially_dropped_packets {
      type oc-yang:counter64;
      description
        "RX port cgm ostc3 partial drops counter. Counts packets that were partially dropped and will be seen on RX side.";
    }
    leaf counters_slice3_ifg1_ifgb_rx_port_18_cgm_tc0_dropped_packets {
      type oc-yang:counter64;
      description
        "RX port cgm ostc0 drops counter. Counts packets that were totally dropped and will not be seen on RX side.";
    }
    leaf counters_slice3_ifg1_ifgb_rx_port_18_cgm_tc0_partially_dropped_packets {
      type oc-yang:counter64;
      description
        "RX port cgm ostc0 partial drops counter. Counts packets that were partially dropped and will be seen on RX side.";
    }
    leaf counters_slice3_ifg1_ifgb_rx_port_18_cgm_tc1_dropped_packets {
      type oc-yang:counter64;
      description
        "RX port cgm ostc1 drops counter. Counts packets that were totally dropped and will not be seen on RX side.";
    }
    leaf counters_slice3_ifg1_ifgb_rx_port_18_cgm_tc1_partially_dropped_packets {
      type oc-yang:counter64;
      description
        "RX port cgm ostc1 partial drops counter. Counts packets that were partially dropped and will be seen on RX side.";
    }
    leaf counters_slice3_ifg1_ifgb_rx_port_18_cgm_tc2_dropped_packets {
      type oc-yang:counter64;
      description
        "RX port cgm ostc2 drops counter. Counts packets that were totally dropped and will not be seen on RX side.";
    }
    leaf counters_slice3_ifg1_ifgb_rx_port_18_cgm_tc2_partially_dropped_packets {
      type oc-yang:counter64;
      description
        "RX port cgm ostc2 partial drops counter. Counts packets that were partially dropped and will be seen on RX side.";
    }
    leaf counters_slice3_ifg1_ifgb_rx_port_18_cgm_tc3_dropped_packets {
      type oc-yang:counter64;
      description
        "RX port cgm ostc3 drops counter. Counts packets that were totally dropped and will not be seen on RX side.";
    }
    leaf counters_slice3_ifg1_ifgb_rx_port_18_cgm_tc3_partially_dropped_packets {
      type oc-yang:counter64;
      description
        "RX port cgm ostc3 partial drops counter. Counts packets that were partially dropped and will be seen on RX side.";
    }
    leaf counters_slice3_ifg1_ifgb_rx_port_19_cgm_tc0_dropped_packets {
      type oc-yang:counter64;
      description
        "RX port cgm ostc0 drops counter. Counts packets that were totally dropped and will not be seen on RX side.";
    }
    leaf counters_slice3_ifg1_ifgb_rx_port_19_cgm_tc0_partially_dropped_packets {
      type oc-yang:counter64;
      description
        "RX port cgm ostc0 partial drops counter. Counts packets that were partially dropped and will be seen on RX side.";
    }
    leaf counters_slice3_ifg1_ifgb_rx_port_19_cgm_tc1_dropped_packets {
      type oc-yang:counter64;
      description
        "RX port cgm ostc1 drops counter. Counts packets that were totally dropped and will not be seen on RX side.";
    }
    leaf counters_slice3_ifg1_ifgb_rx_port_19_cgm_tc1_partially_dropped_packets {
      type oc-yang:counter64;
      description
        "RX port cgm ostc1 partial drops counter. Counts packets that were partially dropped and will be seen on RX side.";
    }
    leaf counters_slice3_ifg1_ifgb_rx_port_19_cgm_tc2_dropped_packets {
      type oc-yang:counter64;
      description
        "RX port cgm ostc2 drops counter. Counts packets that were totally dropped and will not be seen on RX side.";
    }
    leaf counters_slice3_ifg1_ifgb_rx_port_19_cgm_tc2_partially_dropped_packets {
      type oc-yang:counter64;
      description
        "RX port cgm ostc2 partial drops counter. Counts packets that were partially dropped and will be seen on RX side.";
    }
    leaf counters_slice3_ifg1_ifgb_rx_port_19_cgm_tc3_dropped_packets {
      type oc-yang:counter64;
      description
        "RX port cgm ostc3 drops counter. Counts packets that were totally dropped and will not be seen on RX side.";
    }
    leaf counters_slice3_ifg1_ifgb_rx_port_19_cgm_tc3_partially_dropped_packets {
      type oc-yang:counter64;
      description
        "RX port cgm ostc3 partial drops counter. Counts packets that were partially dropped and will be seen on RX side.";
    }
    leaf counters_slice3_ifg1_ifgb_rx_port_2_cgm_tc0_dropped_packets {
      type oc-yang:counter64;
      description
        "RX port cgm ostc0 drops counter. Counts packets that were totally dropped and will not be seen on RX side.";
    }
    leaf counters_slice3_ifg1_ifgb_rx_port_2_cgm_tc0_partially_dropped_packets {
      type oc-yang:counter64;
      description
        "RX port cgm ostc0 partial drops counter. Counts packets that were partially dropped and will be seen on RX side.";
    }
    leaf counters_slice3_ifg1_ifgb_rx_port_2_cgm_tc1_dropped_packets {
      type oc-yang:counter64;
      description
        "RX port cgm ostc1 drops counter. Counts packets that were totally dropped and will not be seen on RX side.";
    }
    leaf counters_slice3_ifg1_ifgb_rx_port_2_cgm_tc1_partially_dropped_packets {
      type oc-yang:counter64;
      description
        "RX port cgm ostc1 partial drops counter. Counts packets that were partially dropped and will be seen on RX side.";
    }
    leaf counters_slice3_ifg1_ifgb_rx_port_2_cgm_tc2_dropped_packets {
      type oc-yang:counter64;
      description
        "RX port cgm ostc2 drops counter. Counts packets that were totally dropped and will not be seen on RX side.";
    }
    leaf counters_slice3_ifg1_ifgb_rx_port_2_cgm_tc2_partially_dropped_packets {
      type oc-yang:counter64;
      description
        "RX port cgm ostc2 partial drops counter. Counts packets that were partially dropped and will be seen on RX side.";
    }
    leaf counters_slice3_ifg1_ifgb_rx_port_2_cgm_tc3_dropped_packets {
      type oc-yang:counter64;
      description
        "RX port cgm ostc3 drops counter. Counts packets that were totally dropped and will not be seen on RX side.";
    }
    leaf counters_slice3_ifg1_ifgb_rx_port_2_cgm_tc3_partially_dropped_packets {
      type oc-yang:counter64;
      description
        "RX port cgm ostc3 partial drops counter. Counts packets that were partially dropped and will be seen on RX side.";
    }
    leaf counters_slice3_ifg1_ifgb_rx_port_20_cgm_tc0_dropped_packets {
      type oc-yang:counter64;
      description
        "RX port cgm ostc0 drops counter. Counts packets that were totally dropped and will not be seen on RX side.";
    }
    leaf counters_slice3_ifg1_ifgb_rx_port_20_cgm_tc0_partially_dropped_packets {
      type oc-yang:counter64;
      description
        "RX port cgm ostc0 partial drops counter. Counts packets that were partially dropped and will be seen on RX side.";
    }
    leaf counters_slice3_ifg1_ifgb_rx_port_20_cgm_tc1_dropped_packets {
      type oc-yang:counter64;
      description
        "RX port cgm ostc1 drops counter. Counts packets that were totally dropped and will not be seen on RX side.";
    }
    leaf counters_slice3_ifg1_ifgb_rx_port_20_cgm_tc1_partially_dropped_packets {
      type oc-yang:counter64;
      description
        "RX port cgm ostc1 partial drops counter. Counts packets that were partially dropped and will be seen on RX side.";
    }
    leaf counters_slice3_ifg1_ifgb_rx_port_20_cgm_tc2_dropped_packets {
      type oc-yang:counter64;
      description
        "RX port cgm ostc2 drops counter. Counts packets that were totally dropped and will not be seen on RX side.";
    }
    leaf counters_slice3_ifg1_ifgb_rx_port_20_cgm_tc2_partially_dropped_packets {
      type oc-yang:counter64;
      description
        "RX port cgm ostc2 partial drops counter. Counts packets that were partially dropped and will be seen on RX side.";
    }
    leaf counters_slice3_ifg1_ifgb_rx_port_20_cgm_tc3_dropped_packets {
      type oc-yang:counter64;
      description
        "RX port cgm ostc3 drops counter. Counts packets that were totally dropped and will not be seen on RX side.";
    }
    leaf counters_slice3_ifg1_ifgb_rx_port_20_cgm_tc3_partially_dropped_packets {
      type oc-yang:counter64;
      description
        "RX port cgm ostc3 partial drops counter. Counts packets that were partially dropped and will be seen on RX side.";
    }
    leaf counters_slice3_ifg1_ifgb_rx_port_21_cgm_tc0_dropped_packets {
      type oc-yang:counter64;
      description
        "RX port cgm ostc0 drops counter. Counts packets that were totally dropped and will not be seen on RX side.";
    }
    leaf counters_slice3_ifg1_ifgb_rx_port_21_cgm_tc0_partially_dropped_packets {
      type oc-yang:counter64;
      description
        "RX port cgm ostc0 partial drops counter. Counts packets that were partially dropped and will be seen on RX side.";
    }
    leaf counters_slice3_ifg1_ifgb_rx_port_21_cgm_tc1_dropped_packets {
      type oc-yang:counter64;
      description
        "RX port cgm ostc1 drops counter. Counts packets that were totally dropped and will not be seen on RX side.";
    }
    leaf counters_slice3_ifg1_ifgb_rx_port_21_cgm_tc1_partially_dropped_packets {
      type oc-yang:counter64;
      description
        "RX port cgm ostc1 partial drops counter. Counts packets that were partially dropped and will be seen on RX side.";
    }
    leaf counters_slice3_ifg1_ifgb_rx_port_21_cgm_tc2_dropped_packets {
      type oc-yang:counter64;
      description
        "RX port cgm ostc2 drops counter. Counts packets that were totally dropped and will not be seen on RX side.";
    }
    leaf counters_slice3_ifg1_ifgb_rx_port_21_cgm_tc2_partially_dropped_packets {
      type oc-yang:counter64;
      description
        "RX port cgm ostc2 partial drops counter. Counts packets that were partially dropped and will be seen on RX side.";
    }
    leaf counters_slice3_ifg1_ifgb_rx_port_21_cgm_tc3_dropped_packets {
      type oc-yang:counter64;
      description
        "RX port cgm ostc3 drops counter. Counts packets that were totally dropped and will not be seen on RX side.";
    }
    leaf counters_slice3_ifg1_ifgb_rx_port_21_cgm_tc3_partially_dropped_packets {
      type oc-yang:counter64;
      description
        "RX port cgm ostc3 partial drops counter. Counts packets that were partially dropped and will be seen on RX side.";
    }
    leaf counters_slice3_ifg1_ifgb_rx_port_22_cgm_tc0_dropped_packets {
      type oc-yang:counter64;
      description
        "RX port cgm ostc0 drops counter. Counts packets that were totally dropped and will not be seen on RX side.";
    }
    leaf counters_slice3_ifg1_ifgb_rx_port_22_cgm_tc0_partially_dropped_packets {
      type oc-yang:counter64;
      description
        "RX port cgm ostc0 partial drops counter. Counts packets that were partially dropped and will be seen on RX side.";
    }
    leaf counters_slice3_ifg1_ifgb_rx_port_22_cgm_tc1_dropped_packets {
      type oc-yang:counter64;
      description
        "RX port cgm ostc1 drops counter. Counts packets that were totally dropped and will not be seen on RX side.";
    }
    leaf counters_slice3_ifg1_ifgb_rx_port_22_cgm_tc1_partially_dropped_packets {
      type oc-yang:counter64;
      description
        "RX port cgm ostc1 partial drops counter. Counts packets that were partially dropped and will be seen on RX side.";
    }
    leaf counters_slice3_ifg1_ifgb_rx_port_22_cgm_tc2_dropped_packets {
      type oc-yang:counter64;
      description
        "RX port cgm ostc2 drops counter. Counts packets that were totally dropped and will not be seen on RX side.";
    }
    leaf counters_slice3_ifg1_ifgb_rx_port_22_cgm_tc2_partially_dropped_packets {
      type oc-yang:counter64;
      description
        "RX port cgm ostc2 partial drops counter. Counts packets that were partially dropped and will be seen on RX side.";
    }
    leaf counters_slice3_ifg1_ifgb_rx_port_22_cgm_tc3_dropped_packets {
      type oc-yang:counter64;
      description
        "RX port cgm ostc3 drops counter. Counts packets that were totally dropped and will not be seen on RX side.";
    }
    leaf counters_slice3_ifg1_ifgb_rx_port_22_cgm_tc3_partially_dropped_packets {
      type oc-yang:counter64;
      description
        "RX port cgm ostc3 partial drops counter. Counts packets that were partially dropped and will be seen on RX side.";
    }
    leaf counters_slice3_ifg1_ifgb_rx_port_23_cgm_tc0_dropped_packets {
      type oc-yang:counter64;
      description
        "RX port cgm ostc0 drops counter. Counts packets that were totally dropped and will not be seen on RX side.";
    }
    leaf counters_slice3_ifg1_ifgb_rx_port_23_cgm_tc0_partially_dropped_packets {
      type oc-yang:counter64;
      description
        "RX port cgm ostc0 partial drops counter. Counts packets that were partially dropped and will be seen on RX side.";
    }
    leaf counters_slice3_ifg1_ifgb_rx_port_23_cgm_tc1_dropped_packets {
      type oc-yang:counter64;
      description
        "RX port cgm ostc1 drops counter. Counts packets that were totally dropped and will not be seen on RX side.";
    }
    leaf counters_slice3_ifg1_ifgb_rx_port_23_cgm_tc1_partially_dropped_packets {
      type oc-yang:counter64;
      description
        "RX port cgm ostc1 partial drops counter. Counts packets that were partially dropped and will be seen on RX side.";
    }
    leaf counters_slice3_ifg1_ifgb_rx_port_23_cgm_tc2_dropped_packets {
      type oc-yang:counter64;
      description
        "RX port cgm ostc2 drops counter. Counts packets that were totally dropped and will not be seen on RX side.";
    }
    leaf counters_slice3_ifg1_ifgb_rx_port_23_cgm_tc2_partially_dropped_packets {
      type oc-yang:counter64;
      description
        "RX port cgm ostc2 partial drops counter. Counts packets that were partially dropped and will be seen on RX side.";
    }
    leaf counters_slice3_ifg1_ifgb_rx_port_23_cgm_tc3_dropped_packets {
      type oc-yang:counter64;
      description
        "RX port cgm ostc3 drops counter. Counts packets that were totally dropped and will not be seen on RX side.";
    }
    leaf counters_slice3_ifg1_ifgb_rx_port_23_cgm_tc3_partially_dropped_packets {
      type oc-yang:counter64;
      description
        "RX port cgm ostc3 partial drops counter. Counts packets that were partially dropped and will be seen on RX side.";
    }
    leaf counters_slice3_ifg1_ifgb_rx_port_24_cgm_tc0_dropped_packets {
      type oc-yang:counter64;
      description
        "RX port cgm ostc0 drops counter. Counts packets that were totally dropped and will not be seen on RX side.";
    }
    leaf counters_slice3_ifg1_ifgb_rx_port_24_cgm_tc0_partially_dropped_packets {
      type oc-yang:counter64;
      description
        "RX port cgm ostc0 partial drops counter. Counts packets that were partially dropped and will be seen on RX side.";
    }
    leaf counters_slice3_ifg1_ifgb_rx_port_24_cgm_tc1_dropped_packets {
      type oc-yang:counter64;
      description
        "RX port cgm ostc1 drops counter. Counts packets that were totally dropped and will not be seen on RX side.";
    }
    leaf counters_slice3_ifg1_ifgb_rx_port_24_cgm_tc1_partially_dropped_packets {
      type oc-yang:counter64;
      description
        "RX port cgm ostc1 partial drops counter. Counts packets that were partially dropped and will be seen on RX side.";
    }
    leaf counters_slice3_ifg1_ifgb_rx_port_24_cgm_tc2_dropped_packets {
      type oc-yang:counter64;
      description
        "RX port cgm ostc2 drops counter. Counts packets that were totally dropped and will not be seen on RX side.";
    }
    leaf counters_slice3_ifg1_ifgb_rx_port_24_cgm_tc2_partially_dropped_packets {
      type oc-yang:counter64;
      description
        "RX port cgm ostc2 partial drops counter. Counts packets that were partially dropped and will be seen on RX side.";
    }
    leaf counters_slice3_ifg1_ifgb_rx_port_24_cgm_tc3_dropped_packets {
      type oc-yang:counter64;
      description
        "RX port cgm ostc3 drops counter. Counts packets that were totally dropped and will not be seen on RX side.";
    }
    leaf counters_slice3_ifg1_ifgb_rx_port_24_cgm_tc3_partially_dropped_packets {
      type oc-yang:counter64;
      description
        "RX port cgm ostc3 partial drops counter. Counts packets that were partially dropped and will be seen on RX side.";
    }
    leaf counters_slice3_ifg1_ifgb_rx_port_25_cgm_tc0_dropped_packets {
      type oc-yang:counter64;
      description
        "RX port cgm ostc0 drops counter. Counts packets that were totally dropped and will not be seen on RX side.";
    }
    leaf counters_slice3_ifg1_ifgb_rx_port_25_cgm_tc0_partially_dropped_packets {
      type oc-yang:counter64;
      description
        "RX port cgm ostc0 partial drops counter. Counts packets that were partially dropped and will be seen on RX side.";
    }
    leaf counters_slice3_ifg1_ifgb_rx_port_25_cgm_tc1_dropped_packets {
      type oc-yang:counter64;
      description
        "RX port cgm ostc1 drops counter. Counts packets that were totally dropped and will not be seen on RX side.";
    }
    leaf counters_slice3_ifg1_ifgb_rx_port_25_cgm_tc1_partially_dropped_packets {
      type oc-yang:counter64;
      description
        "RX port cgm ostc1 partial drops counter. Counts packets that were partially dropped and will be seen on RX side.";
    }
    leaf counters_slice3_ifg1_ifgb_rx_port_25_cgm_tc2_dropped_packets {
      type oc-yang:counter64;
      description
        "RX port cgm ostc2 drops counter. Counts packets that were totally dropped and will not be seen on RX side.";
    }
    leaf counters_slice3_ifg1_ifgb_rx_port_25_cgm_tc2_partially_dropped_packets {
      type oc-yang:counter64;
      description
        "RX port cgm ostc2 partial drops counter. Counts packets that were partially dropped and will be seen on RX side.";
    }
    leaf counters_slice3_ifg1_ifgb_rx_port_25_cgm_tc3_dropped_packets {
      type oc-yang:counter64;
      description
        "RX port cgm ostc3 drops counter. Counts packets that were totally dropped and will not be seen on RX side.";
    }
    leaf counters_slice3_ifg1_ifgb_rx_port_25_cgm_tc3_partially_dropped_packets {
      type oc-yang:counter64;
      description
        "RX port cgm ostc3 partial drops counter. Counts packets that were partially dropped and will be seen on RX side.";
    }
    leaf counters_slice3_ifg1_ifgb_rx_port_26_cgm_tc0_dropped_packets {
      type oc-yang:counter64;
      description
        "RX port cgm ostc0 drops counter. Counts packets that were totally dropped and will not be seen on RX side.";
    }
    leaf counters_slice3_ifg1_ifgb_rx_port_26_cgm_tc0_partially_dropped_packets {
      type oc-yang:counter64;
      description
        "RX port cgm ostc0 partial drops counter. Counts packets that were partially dropped and will be seen on RX side.";
    }
    leaf counters_slice3_ifg1_ifgb_rx_port_26_cgm_tc1_dropped_packets {
      type oc-yang:counter64;
      description
        "RX port cgm ostc1 drops counter. Counts packets that were totally dropped and will not be seen on RX side.";
    }
    leaf counters_slice3_ifg1_ifgb_rx_port_26_cgm_tc1_partially_dropped_packets {
      type oc-yang:counter64;
      description
        "RX port cgm ostc1 partial drops counter. Counts packets that were partially dropped and will be seen on RX side.";
    }
    leaf counters_slice3_ifg1_ifgb_rx_port_26_cgm_tc2_dropped_packets {
      type oc-yang:counter64;
      description
        "RX port cgm ostc2 drops counter. Counts packets that were totally dropped and will not be seen on RX side.";
    }
    leaf counters_slice3_ifg1_ifgb_rx_port_26_cgm_tc2_partially_dropped_packets {
      type oc-yang:counter64;
      description
        "RX port cgm ostc2 partial drops counter. Counts packets that were partially dropped and will be seen on RX side.";
    }
    leaf counters_slice3_ifg1_ifgb_rx_port_26_cgm_tc3_dropped_packets {
      type oc-yang:counter64;
      description
        "RX port cgm ostc3 drops counter. Counts packets that were totally dropped and will not be seen on RX side.";
    }
    leaf counters_slice3_ifg1_ifgb_rx_port_26_cgm_tc3_partially_dropped_packets {
      type oc-yang:counter64;
      description
        "RX port cgm ostc3 partial drops counter. Counts packets that were partially dropped and will be seen on RX side.";
    }
    leaf counters_slice3_ifg1_ifgb_rx_port_27_cgm_tc0_dropped_packets {
      type oc-yang:counter64;
      description
        "RX port cgm ostc0 drops counter. Counts packets that were totally dropped and will not be seen on RX side.";
    }
    leaf counters_slice3_ifg1_ifgb_rx_port_27_cgm_tc0_partially_dropped_packets {
      type oc-yang:counter64;
      description
        "RX port cgm ostc0 partial drops counter. Counts packets that were partially dropped and will be seen on RX side.";
    }
    leaf counters_slice3_ifg1_ifgb_rx_port_27_cgm_tc1_dropped_packets {
      type oc-yang:counter64;
      description
        "RX port cgm ostc1 drops counter. Counts packets that were totally dropped and will not be seen on RX side.";
    }
    leaf counters_slice3_ifg1_ifgb_rx_port_27_cgm_tc1_partially_dropped_packets {
      type oc-yang:counter64;
      description
        "RX port cgm ostc1 partial drops counter. Counts packets that were partially dropped and will be seen on RX side.";
    }
    leaf counters_slice3_ifg1_ifgb_rx_port_27_cgm_tc2_dropped_packets {
      type oc-yang:counter64;
      description
        "RX port cgm ostc2 drops counter. Counts packets that were totally dropped and will not be seen on RX side.";
    }
    leaf counters_slice3_ifg1_ifgb_rx_port_27_cgm_tc2_partially_dropped_packets {
      type oc-yang:counter64;
      description
        "RX port cgm ostc2 partial drops counter. Counts packets that were partially dropped and will be seen on RX side.";
    }
    leaf counters_slice3_ifg1_ifgb_rx_port_27_cgm_tc3_dropped_packets {
      type oc-yang:counter64;
      description
        "RX port cgm ostc3 drops counter. Counts packets that were totally dropped and will not be seen on RX side.";
    }
    leaf counters_slice3_ifg1_ifgb_rx_port_27_cgm_tc3_partially_dropped_packets {
      type oc-yang:counter64;
      description
        "RX port cgm ostc3 partial drops counter. Counts packets that were partially dropped and will be seen on RX side.";
    }
    leaf counters_slice3_ifg1_ifgb_rx_port_28_cgm_tc0_dropped_packets {
      type oc-yang:counter64;
      description
        "RX port cgm ostc0 drops counter. Counts packets that were totally dropped and will not be seen on RX side.";
    }
    leaf counters_slice3_ifg1_ifgb_rx_port_28_cgm_tc0_partially_dropped_packets {
      type oc-yang:counter64;
      description
        "RX port cgm ostc0 partial drops counter. Counts packets that were partially dropped and will be seen on RX side.";
    }
    leaf counters_slice3_ifg1_ifgb_rx_port_28_cgm_tc1_dropped_packets {
      type oc-yang:counter64;
      description
        "RX port cgm ostc1 drops counter. Counts packets that were totally dropped and will not be seen on RX side.";
    }
    leaf counters_slice3_ifg1_ifgb_rx_port_28_cgm_tc1_partially_dropped_packets {
      type oc-yang:counter64;
      description
        "RX port cgm ostc1 partial drops counter. Counts packets that were partially dropped and will be seen on RX side.";
    }
    leaf counters_slice3_ifg1_ifgb_rx_port_28_cgm_tc2_dropped_packets {
      type oc-yang:counter64;
      description
        "RX port cgm ostc2 drops counter. Counts packets that were totally dropped and will not be seen on RX side.";
    }
    leaf counters_slice3_ifg1_ifgb_rx_port_28_cgm_tc2_partially_dropped_packets {
      type oc-yang:counter64;
      description
        "RX port cgm ostc2 partial drops counter. Counts packets that were partially dropped and will be seen on RX side.";
    }
    leaf counters_slice3_ifg1_ifgb_rx_port_28_cgm_tc3_dropped_packets {
      type oc-yang:counter64;
      description
        "RX port cgm ostc3 drops counter. Counts packets that were totally dropped and will not be seen on RX side.";
    }
    leaf counters_slice3_ifg1_ifgb_rx_port_28_cgm_tc3_partially_dropped_packets {
      type oc-yang:counter64;
      description
        "RX port cgm ostc3 partial drops counter. Counts packets that were partially dropped and will be seen on RX side.";
    }
    leaf counters_slice3_ifg1_ifgb_rx_port_29_cgm_tc0_dropped_packets {
      type oc-yang:counter64;
      description
        "RX port cgm ostc0 drops counter. Counts packets that were totally dropped and will not be seen on RX side.";
    }
    leaf counters_slice3_ifg1_ifgb_rx_port_29_cgm_tc0_partially_dropped_packets {
      type oc-yang:counter64;
      description
        "RX port cgm ostc0 partial drops counter. Counts packets that were partially dropped and will be seen on RX side.";
    }
    leaf counters_slice3_ifg1_ifgb_rx_port_29_cgm_tc1_dropped_packets {
      type oc-yang:counter64;
      description
        "RX port cgm ostc1 drops counter. Counts packets that were totally dropped and will not be seen on RX side.";
    }
    leaf counters_slice3_ifg1_ifgb_rx_port_29_cgm_tc1_partially_dropped_packets {
      type oc-yang:counter64;
      description
        "RX port cgm ostc1 partial drops counter. Counts packets that were partially dropped and will be seen on RX side.";
    }
    leaf counters_slice3_ifg1_ifgb_rx_port_29_cgm_tc2_dropped_packets {
      type oc-yang:counter64;
      description
        "RX port cgm ostc2 drops counter. Counts packets that were totally dropped and will not be seen on RX side.";
    }
    leaf counters_slice3_ifg1_ifgb_rx_port_29_cgm_tc2_partially_dropped_packets {
      type oc-yang:counter64;
      description
        "RX port cgm ostc2 partial drops counter. Counts packets that were partially dropped and will be seen on RX side.";
    }
    leaf counters_slice3_ifg1_ifgb_rx_port_29_cgm_tc3_dropped_packets {
      type oc-yang:counter64;
      description
        "RX port cgm ostc3 drops counter. Counts packets that were totally dropped and will not be seen on RX side.";
    }
    leaf counters_slice3_ifg1_ifgb_rx_port_29_cgm_tc3_partially_dropped_packets {
      type oc-yang:counter64;
      description
        "RX port cgm ostc3 partial drops counter. Counts packets that were partially dropped and will be seen on RX side.";
    }
    leaf counters_slice3_ifg1_ifgb_rx_port_3_cgm_tc0_dropped_packets {
      type oc-yang:counter64;
      description
        "RX port cgm ostc0 drops counter. Counts packets that were totally dropped and will not be seen on RX side.";
    }
    leaf counters_slice3_ifg1_ifgb_rx_port_3_cgm_tc0_partially_dropped_packets {
      type oc-yang:counter64;
      description
        "RX port cgm ostc0 partial drops counter. Counts packets that were partially dropped and will be seen on RX side.";
    }
    leaf counters_slice3_ifg1_ifgb_rx_port_3_cgm_tc1_dropped_packets {
      type oc-yang:counter64;
      description
        "RX port cgm ostc1 drops counter. Counts packets that were totally dropped and will not be seen on RX side.";
    }
    leaf counters_slice3_ifg1_ifgb_rx_port_3_cgm_tc1_partially_dropped_packets {
      type oc-yang:counter64;
      description
        "RX port cgm ostc1 partial drops counter. Counts packets that were partially dropped and will be seen on RX side.";
    }
    leaf counters_slice3_ifg1_ifgb_rx_port_3_cgm_tc2_dropped_packets {
      type oc-yang:counter64;
      description
        "RX port cgm ostc2 drops counter. Counts packets that were totally dropped and will not be seen on RX side.";
    }
    leaf counters_slice3_ifg1_ifgb_rx_port_3_cgm_tc2_partially_dropped_packets {
      type oc-yang:counter64;
      description
        "RX port cgm ostc2 partial drops counter. Counts packets that were partially dropped and will be seen on RX side.";
    }
    leaf counters_slice3_ifg1_ifgb_rx_port_3_cgm_tc3_dropped_packets {
      type oc-yang:counter64;
      description
        "RX port cgm ostc3 drops counter. Counts packets that were totally dropped and will not be seen on RX side.";
    }
    leaf counters_slice3_ifg1_ifgb_rx_port_3_cgm_tc3_partially_dropped_packets {
      type oc-yang:counter64;
      description
        "RX port cgm ostc3 partial drops counter. Counts packets that were partially dropped and will be seen on RX side.";
    }
    leaf counters_slice3_ifg1_ifgb_rx_port_30_cgm_tc0_dropped_packets {
      type oc-yang:counter64;
      description
        "RX port cgm ostc0 drops counter. Counts packets that were totally dropped and will not be seen on RX side.";
    }
    leaf counters_slice3_ifg1_ifgb_rx_port_30_cgm_tc0_partially_dropped_packets {
      type oc-yang:counter64;
      description
        "RX port cgm ostc0 partial drops counter. Counts packets that were partially dropped and will be seen on RX side.";
    }
    leaf counters_slice3_ifg1_ifgb_rx_port_30_cgm_tc1_dropped_packets {
      type oc-yang:counter64;
      description
        "RX port cgm ostc1 drops counter. Counts packets that were totally dropped and will not be seen on RX side.";
    }
    leaf counters_slice3_ifg1_ifgb_rx_port_30_cgm_tc1_partially_dropped_packets {
      type oc-yang:counter64;
      description
        "RX port cgm ostc1 partial drops counter. Counts packets that were partially dropped and will be seen on RX side.";
    }
    leaf counters_slice3_ifg1_ifgb_rx_port_30_cgm_tc2_dropped_packets {
      type oc-yang:counter64;
      description
        "RX port cgm ostc2 drops counter. Counts packets that were totally dropped and will not be seen on RX side.";
    }
    leaf counters_slice3_ifg1_ifgb_rx_port_30_cgm_tc2_partially_dropped_packets {
      type oc-yang:counter64;
      description
        "RX port cgm ostc2 partial drops counter. Counts packets that were partially dropped and will be seen on RX side.";
    }
    leaf counters_slice3_ifg1_ifgb_rx_port_30_cgm_tc3_dropped_packets {
      type oc-yang:counter64;
      description
        "RX port cgm ostc3 drops counter. Counts packets that were totally dropped and will not be seen on RX side.";
    }
    leaf counters_slice3_ifg1_ifgb_rx_port_30_cgm_tc3_partially_dropped_packets {
      type oc-yang:counter64;
      description
        "RX port cgm ostc3 partial drops counter. Counts packets that were partially dropped and will be seen on RX side.";
    }
    leaf counters_slice3_ifg1_ifgb_rx_port_31_cgm_tc0_dropped_packets {
      type oc-yang:counter64;
      description
        "RX port cgm ostc0 drops counter. Counts packets that were totally dropped and will not be seen on RX side.";
    }
    leaf counters_slice3_ifg1_ifgb_rx_port_31_cgm_tc0_partially_dropped_packets {
      type oc-yang:counter64;
      description
        "RX port cgm ostc0 partial drops counter. Counts packets that were partially dropped and will be seen on RX side.";
    }
    leaf counters_slice3_ifg1_ifgb_rx_port_31_cgm_tc1_dropped_packets {
      type oc-yang:counter64;
      description
        "RX port cgm ostc1 drops counter. Counts packets that were totally dropped and will not be seen on RX side.";
    }
    leaf counters_slice3_ifg1_ifgb_rx_port_31_cgm_tc1_partially_dropped_packets {
      type oc-yang:counter64;
      description
        "RX port cgm ostc1 partial drops counter. Counts packets that were partially dropped and will be seen on RX side.";
    }
    leaf counters_slice3_ifg1_ifgb_rx_port_31_cgm_tc2_dropped_packets {
      type oc-yang:counter64;
      description
        "RX port cgm ostc2 drops counter. Counts packets that were totally dropped and will not be seen on RX side.";
    }
    leaf counters_slice3_ifg1_ifgb_rx_port_31_cgm_tc2_partially_dropped_packets {
      type oc-yang:counter64;
      description
        "RX port cgm ostc2 partial drops counter. Counts packets that were partially dropped and will be seen on RX side.";
    }
    leaf counters_slice3_ifg1_ifgb_rx_port_31_cgm_tc3_dropped_packets {
      type oc-yang:counter64;
      description
        "RX port cgm ostc3 drops counter. Counts packets that were totally dropped and will not be seen on RX side.";
    }
    leaf counters_slice3_ifg1_ifgb_rx_port_31_cgm_tc3_partially_dropped_packets {
      type oc-yang:counter64;
      description
        "RX port cgm ostc3 partial drops counter. Counts packets that were partially dropped and will be seen on RX side.";
    }
    leaf counters_slice3_ifg1_ifgb_rx_port_4_cgm_tc0_dropped_packets {
      type oc-yang:counter64;
      description
        "RX port cgm ostc0 drops counter. Counts packets that were totally dropped and will not be seen on RX side.";
    }
    leaf counters_slice3_ifg1_ifgb_rx_port_4_cgm_tc0_partially_dropped_packets {
      type oc-yang:counter64;
      description
        "RX port cgm ostc0 partial drops counter. Counts packets that were partially dropped and will be seen on RX side.";
    }
    leaf counters_slice3_ifg1_ifgb_rx_port_4_cgm_tc1_dropped_packets {
      type oc-yang:counter64;
      description
        "RX port cgm ostc1 drops counter. Counts packets that were totally dropped and will not be seen on RX side.";
    }
    leaf counters_slice3_ifg1_ifgb_rx_port_4_cgm_tc1_partially_dropped_packets {
      type oc-yang:counter64;
      description
        "RX port cgm ostc1 partial drops counter. Counts packets that were partially dropped and will be seen on RX side.";
    }
    leaf counters_slice3_ifg1_ifgb_rx_port_4_cgm_tc2_dropped_packets {
      type oc-yang:counter64;
      description
        "RX port cgm ostc2 drops counter. Counts packets that were totally dropped and will not be seen on RX side.";
    }
    leaf counters_slice3_ifg1_ifgb_rx_port_4_cgm_tc2_partially_dropped_packets {
      type oc-yang:counter64;
      description
        "RX port cgm ostc2 partial drops counter. Counts packets that were partially dropped and will be seen on RX side.";
    }
    leaf counters_slice3_ifg1_ifgb_rx_port_4_cgm_tc3_dropped_packets {
      type oc-yang:counter64;
      description
        "RX port cgm ostc3 drops counter. Counts packets that were totally dropped and will not be seen on RX side.";
    }
    leaf counters_slice3_ifg1_ifgb_rx_port_4_cgm_tc3_partially_dropped_packets {
      type oc-yang:counter64;
      description
        "RX port cgm ostc3 partial drops counter. Counts packets that were partially dropped and will be seen on RX side.";
    }
    leaf counters_slice3_ifg1_ifgb_rx_port_5_cgm_tc0_dropped_packets {
      type oc-yang:counter64;
      description
        "RX port cgm ostc0 drops counter. Counts packets that were totally dropped and will not be seen on RX side.";
    }
    leaf counters_slice3_ifg1_ifgb_rx_port_5_cgm_tc0_partially_dropped_packets {
      type oc-yang:counter64;
      description
        "RX port cgm ostc0 partial drops counter. Counts packets that were partially dropped and will be seen on RX side.";
    }
    leaf counters_slice3_ifg1_ifgb_rx_port_5_cgm_tc1_dropped_packets {
      type oc-yang:counter64;
      description
        "RX port cgm ostc1 drops counter. Counts packets that were totally dropped and will not be seen on RX side.";
    }
    leaf counters_slice3_ifg1_ifgb_rx_port_5_cgm_tc1_partially_dropped_packets {
      type oc-yang:counter64;
      description
        "RX port cgm ostc1 partial drops counter. Counts packets that were partially dropped and will be seen on RX side.";
    }
    leaf counters_slice3_ifg1_ifgb_rx_port_5_cgm_tc2_dropped_packets {
      type oc-yang:counter64;
      description
        "RX port cgm ostc2 drops counter. Counts packets that were totally dropped and will not be seen on RX side.";
    }
    leaf counters_slice3_ifg1_ifgb_rx_port_5_cgm_tc2_partially_dropped_packets {
      type oc-yang:counter64;
      description
        "RX port cgm ostc2 partial drops counter. Counts packets that were partially dropped and will be seen on RX side.";
    }
    leaf counters_slice3_ifg1_ifgb_rx_port_5_cgm_tc3_dropped_packets {
      type oc-yang:counter64;
      description
        "RX port cgm ostc3 drops counter. Counts packets that were totally dropped and will not be seen on RX side.";
    }
    leaf counters_slice3_ifg1_ifgb_rx_port_5_cgm_tc3_partially_dropped_packets {
      type oc-yang:counter64;
      description
        "RX port cgm ostc3 partial drops counter. Counts packets that were partially dropped and will be seen on RX side.";
    }
    leaf counters_slice3_ifg1_ifgb_rx_port_6_cgm_tc0_dropped_packets {
      type oc-yang:counter64;
      description
        "RX port cgm ostc0 drops counter. Counts packets that were totally dropped and will not be seen on RX side.";
    }
    leaf counters_slice3_ifg1_ifgb_rx_port_6_cgm_tc0_partially_dropped_packets {
      type oc-yang:counter64;
      description
        "RX port cgm ostc0 partial drops counter. Counts packets that were partially dropped and will be seen on RX side.";
    }
    leaf counters_slice3_ifg1_ifgb_rx_port_6_cgm_tc1_dropped_packets {
      type oc-yang:counter64;
      description
        "RX port cgm ostc1 drops counter. Counts packets that were totally dropped and will not be seen on RX side.";
    }
    leaf counters_slice3_ifg1_ifgb_rx_port_6_cgm_tc1_partially_dropped_packets {
      type oc-yang:counter64;
      description
        "RX port cgm ostc1 partial drops counter. Counts packets that were partially dropped and will be seen on RX side.";
    }
    leaf counters_slice3_ifg1_ifgb_rx_port_6_cgm_tc2_dropped_packets {
      type oc-yang:counter64;
      description
        "RX port cgm ostc2 drops counter. Counts packets that were totally dropped and will not be seen on RX side.";
    }
    leaf counters_slice3_ifg1_ifgb_rx_port_6_cgm_tc2_partially_dropped_packets {
      type oc-yang:counter64;
      description
        "RX port cgm ostc2 partial drops counter. Counts packets that were partially dropped and will be seen on RX side.";
    }
    leaf counters_slice3_ifg1_ifgb_rx_port_6_cgm_tc3_dropped_packets {
      type oc-yang:counter64;
      description
        "RX port cgm ostc3 drops counter. Counts packets that were totally dropped and will not be seen on RX side.";
    }
    leaf counters_slice3_ifg1_ifgb_rx_port_6_cgm_tc3_partially_dropped_packets {
      type oc-yang:counter64;
      description
        "RX port cgm ostc3 partial drops counter. Counts packets that were partially dropped and will be seen on RX side.";
    }
    leaf counters_slice3_ifg1_ifgb_rx_port_7_cgm_tc0_dropped_packets {
      type oc-yang:counter64;
      description
        "RX port cgm ostc0 drops counter. Counts packets that were totally dropped and will not be seen on RX side.";
    }
    leaf counters_slice3_ifg1_ifgb_rx_port_7_cgm_tc0_partially_dropped_packets {
      type oc-yang:counter64;
      description
        "RX port cgm ostc0 partial drops counter. Counts packets that were partially dropped and will be seen on RX side.";
    }
    leaf counters_slice3_ifg1_ifgb_rx_port_7_cgm_tc1_dropped_packets {
      type oc-yang:counter64;
      description
        "RX port cgm ostc1 drops counter. Counts packets that were totally dropped and will not be seen on RX side.";
    }
    leaf counters_slice3_ifg1_ifgb_rx_port_7_cgm_tc1_partially_dropped_packets {
      type oc-yang:counter64;
      description
        "RX port cgm ostc1 partial drops counter. Counts packets that were partially dropped and will be seen on RX side.";
    }
    leaf counters_slice3_ifg1_ifgb_rx_port_7_cgm_tc2_dropped_packets {
      type oc-yang:counter64;
      description
        "RX port cgm ostc2 drops counter. Counts packets that were totally dropped and will not be seen on RX side.";
    }
    leaf counters_slice3_ifg1_ifgb_rx_port_7_cgm_tc2_partially_dropped_packets {
      type oc-yang:counter64;
      description
        "RX port cgm ostc2 partial drops counter. Counts packets that were partially dropped and will be seen on RX side.";
    }
    leaf counters_slice3_ifg1_ifgb_rx_port_7_cgm_tc3_dropped_packets {
      type oc-yang:counter64;
      description
        "RX port cgm ostc3 drops counter. Counts packets that were totally dropped and will not be seen on RX side.";
    }
    leaf counters_slice3_ifg1_ifgb_rx_port_7_cgm_tc3_partially_dropped_packets {
      type oc-yang:counter64;
      description
        "RX port cgm ostc3 partial drops counter. Counts packets that were partially dropped and will be seen on RX side.";
    }
    leaf counters_slice3_ifg1_ifgb_rx_port_8_cgm_tc0_dropped_packets {
      type oc-yang:counter64;
      description
        "RX port cgm ostc0 drops counter. Counts packets that were totally dropped and will not be seen on RX side.";
    }
    leaf counters_slice3_ifg1_ifgb_rx_port_8_cgm_tc0_partially_dropped_packets {
      type oc-yang:counter64;
      description
        "RX port cgm ostc0 partial drops counter. Counts packets that were partially dropped and will be seen on RX side.";
    }
    leaf counters_slice3_ifg1_ifgb_rx_port_8_cgm_tc1_dropped_packets {
      type oc-yang:counter64;
      description
        "RX port cgm ostc1 drops counter. Counts packets that were totally dropped and will not be seen on RX side.";
    }
    leaf counters_slice3_ifg1_ifgb_rx_port_8_cgm_tc1_partially_dropped_packets {
      type oc-yang:counter64;
      description
        "RX port cgm ostc1 partial drops counter. Counts packets that were partially dropped and will be seen on RX side.";
    }
    leaf counters_slice3_ifg1_ifgb_rx_port_8_cgm_tc2_dropped_packets {
      type oc-yang:counter64;
      description
        "RX port cgm ostc2 drops counter. Counts packets that were totally dropped and will not be seen on RX side.";
    }
    leaf counters_slice3_ifg1_ifgb_rx_port_8_cgm_tc2_partially_dropped_packets {
      type oc-yang:counter64;
      description
        "RX port cgm ostc2 partial drops counter. Counts packets that were partially dropped and will be seen on RX side.";
    }
    leaf counters_slice3_ifg1_ifgb_rx_port_8_cgm_tc3_dropped_packets {
      type oc-yang:counter64;
      description
        "RX port cgm ostc3 drops counter. Counts packets that were totally dropped and will not be seen on RX side.";
    }
    leaf counters_slice3_ifg1_ifgb_rx_port_8_cgm_tc3_partially_dropped_packets {
      type oc-yang:counter64;
      description
        "RX port cgm ostc3 partial drops counter. Counts packets that were partially dropped and will be seen on RX side.";
    }
    leaf counters_slice3_ifg1_ifgb_rx_port_9_cgm_tc0_dropped_packets {
      type oc-yang:counter64;
      description
        "RX port cgm ostc0 drops counter. Counts packets that were totally dropped and will not be seen on RX side.";
    }
    leaf counters_slice3_ifg1_ifgb_rx_port_9_cgm_tc0_partially_dropped_packets {
      type oc-yang:counter64;
      description
        "RX port cgm ostc0 partial drops counter. Counts packets that were partially dropped and will be seen on RX side.";
    }
    leaf counters_slice3_ifg1_ifgb_rx_port_9_cgm_tc1_dropped_packets {
      type oc-yang:counter64;
      description
        "RX port cgm ostc1 drops counter. Counts packets that were totally dropped and will not be seen on RX side.";
    }
    leaf counters_slice3_ifg1_ifgb_rx_port_9_cgm_tc1_partially_dropped_packets {
      type oc-yang:counter64;
      description
        "RX port cgm ostc1 partial drops counter. Counts packets that were partially dropped and will be seen on RX side.";
    }
    leaf counters_slice3_ifg1_ifgb_rx_port_9_cgm_tc2_dropped_packets {
      type oc-yang:counter64;
      description
        "RX port cgm ostc2 drops counter. Counts packets that were totally dropped and will not be seen on RX side.";
    }
    leaf counters_slice3_ifg1_ifgb_rx_port_9_cgm_tc2_partially_dropped_packets {
      type oc-yang:counter64;
      description
        "RX port cgm ostc2 partial drops counter. Counts packets that were partially dropped and will be seen on RX side.";
    }
    leaf counters_slice3_ifg1_ifgb_rx_port_9_cgm_tc3_dropped_packets {
      type oc-yang:counter64;
      description
        "RX port cgm ostc3 drops counter. Counts packets that were totally dropped and will not be seen on RX side.";
    }
    leaf counters_slice3_ifg1_ifgb_rx_port_9_cgm_tc3_partially_dropped_packets {
      type oc-yang:counter64;
      description
        "RX port cgm ostc3 partial drops counter. Counts packets that were partially dropped and will be seen on RX side.";
    }
    leaf counters_slice3_tx_cgm_dropped_packets_due_to_max_allowed_qsize {
      type oc-yang:counter64;
      description
        "Counts number of dropped packets by max allowed threshold";
    }
    leaf counters_slice3_tx_cgm_local_sch_uc_buffer_c_dropped_packets {
      type oc-yang:counter64;
      description
        "Counts number of dropped packets by counter C";
    }
    leaf counters_slice3_tx_cgm_mc_silently_dropped_packets {
      type oc-yang:counter64;
      description
        "Counter of dropped MC packets that were silently dropped";
    }
    leaf counters_slice3_tx_cgm_sch_uc_buffers_cd_dropped_packets {
      type oc-yang:counter64;
      description
        "Counts number of dropped packets by counter C+D";
    }
    leaf counters_slice3_tx_cgm_sch_uc_counter_z_dropped_packets {
      type oc-yang:counter64;
      description
        "Counts number of dropped packets by counter Z";
    }
    leaf counters_slice3_tx_cgm_total_dropped_packets {
      type oc-yang:counter64;
      description
        "Counts number of dropped in TxCGM only packets";
    }
    leaf counters_slice3_tx_cgm_uc_oq_test_dropped_packets {
      type oc-yang:counter64;
      description
        "Counts number of dropped by UC OQ test";
    }
    leaf counters_slice3_tx_cgm_uc_oqg_dropped_packets {
      type oc-yang:counter64;
      description
        "Counts number of dropped by UC OQG test";
    }
    leaf counters_slice3_tx_cgm_unsch_counter_w_dropped_packets {
      type oc-yang:counter64;
      description
        "Counts number of dropped packets by counter W";
    }
    leaf counters_slice3_tx_cgm_green_mc_oq_bytes_test_dropped_packets {
      type oc-yang:counter64;
      description
        "Counts number of dropped packets by OQ MC green bytes test";
    }
    leaf counters_slice3_tx_cgm_green_mc_oq_pds_test_dropped_packets {
      type oc-yang:counter64;
      description
        "Counts number of dropped packets by OQ MC green PDs test";
    }
    leaf counters_slice3_tx_cgm_mc_color_test0_dropped_packets {
      type oc-yang:counter64;
      description
        "Counts number of dropped packet by MC color test for:0 - Green1 - Yellow2 - Red3 - Other";
    }
    leaf counters_slice3_tx_cgm_mc_color_test1_dropped_packets {
      type oc-yang:counter64;
      description
        "Counts number of dropped packet by MC color test for:0 - Green1 - Yellow2 - Red3 - Other";
    }
    leaf counters_slice3_tx_cgm_mc_color_test2_dropped_packets {
      type oc-yang:counter64;
      description
        "Counts number of dropped packet by MC color test for:0 - Green1 - Yellow2 - Red3 - Other";
    }
    leaf counters_slice3_tx_cgm_mc_color_test3_dropped_packets {
      type oc-yang:counter64;
      description
        "Counts number of dropped packet by MC color test for:0 - Green1 - Yellow2 - Red3 - Other";
    }
    leaf counters_slice3_tx_cgm_mc_set0_dropped_bytes {
      type oc-yang:counter64;
      description
        "Counts MC dropped bytes";
    }
    leaf counters_slice3_tx_cgm_mc_set0_dropped_packets {
      type oc-yang:counter64;
      description
        "Counts MC dropped packets";
    }
    leaf counters_slice3_tx_cgm_mc_set1_dropped_bytes {
      type oc-yang:counter64;
      description
        "Counts MC dropped bytes";
    }
    leaf counters_slice3_tx_cgm_mc_set1_dropped_packets {
      type oc-yang:counter64;
      description
        "Counts MC dropped packets";
    }
    leaf counters_slice3_tx_cgm_mc_set2_dropped_bytes {
      type oc-yang:counter64;
      description
        "Counts MC dropped bytes";
    }
    leaf counters_slice3_tx_cgm_mc_set2_dropped_packets {
      type oc-yang:counter64;
      description
        "Counts MC dropped packets";
    }
    leaf counters_slice3_tx_cgm_mc_set3_dropped_bytes {
      type oc-yang:counter64;
      description
        "Counts MC dropped bytes";
    }
    leaf counters_slice3_tx_cgm_mc_set3_dropped_packets {
      type oc-yang:counter64;
      description
        "Counts MC dropped packets";
    }
    leaf counters_slice3_tx_cgm_uc_color_test0_dropped_packets {
      type oc-yang:counter64;
      description
        "Counts number of dropped packet by UC color test for:0 - Green1 - Yellow2 - Red3 - Other";
    }
    leaf counters_slice3_tx_cgm_uc_color_test1_dropped_packets {
      type oc-yang:counter64;
      description
        "Counts number of dropped packet by UC color test for:0 - Green1 - Yellow2 - Red3 - Other";
    }
    leaf counters_slice3_tx_cgm_uc_color_test2_dropped_packets {
      type oc-yang:counter64;
      description
        "Counts number of dropped packet by UC color test for:0 - Green1 - Yellow2 - Red3 - Other";
    }
    leaf counters_slice3_tx_cgm_uc_color_test3_dropped_packets {
      type oc-yang:counter64;
      description
        "Counts number of dropped packet by UC color test for:0 - Green1 - Yellow2 - Red3 - Other";
    }
    leaf counters_slice3_tx_cgm_uc_set0_dropped_bytes {
      type oc-yang:counter64;
      description
        "Counts UC dropped bytes";
    }
    leaf counters_slice3_tx_cgm_uc_set0_dropped_packets {
      type oc-yang:counter64;
      description
        "Counts UC dropped packets";
    }
    leaf counters_slice3_tx_cgm_uc_set1_dropped_bytes {
      type oc-yang:counter64;
      description
        "Counts UC dropped bytes";
    }
    leaf counters_slice3_tx_cgm_uc_set1_dropped_packets {
      type oc-yang:counter64;
      description
        "Counts UC dropped packets";
    }
    leaf counters_slice3_tx_cgm_uc_set2_dropped_bytes {
      type oc-yang:counter64;
      description
        "Counts UC dropped bytes";
    }
    leaf counters_slice3_tx_cgm_uc_set2_dropped_packets {
      type oc-yang:counter64;
      description
        "Counts UC dropped packets";
    }
    leaf counters_slice3_tx_cgm_uc_set3_dropped_bytes {
      type oc-yang:counter64;
      description
        "Counts UC dropped bytes";
    }
    leaf counters_slice3_tx_cgm_uc_set3_dropped_packets {
      type oc-yang:counter64;
      description
        "Counts UC dropped packets";
    }
    leaf counters_slice3_tx_cgm_yellow_mc_oq_bytes_test_dropped_packets {
      type oc-yang:counter64;
      description
        "Counts number of dropped packets by OQ MC yellow bytes test";
    }
    leaf counters_slice3_tx_cgm_yellow_mc_oq_pds_test_dropped_packets {
      type oc-yang:counter64;
      description
        "Counts number of dropped packets by OQ MC yellow PDs test";
    }
    leaf counters_slice3_tx_pdr_txrq_full_egress_rep_dropped_packets {
      type oc-yang:counter64;
      description
        "Number of dropped packets";
    }
    leaf counters_slice3_tx_pdr_txrq_overload_egress_rep_dropped_packets {
      type oc-yang:counter64;
      description
        "Number of dropped packets";
    }
    leaf counters_slice3_tx_pdr_txrq0_full_egress_rep_dropped_packets {
      type oc-yang:counter64;
      description
        "Number of dropped packets";
    }
    leaf counters_slice3_tx_pdr_txrq0_threshold0_deq_dropped_packets {
      type oc-yang:counter64;
      description
        "Number of dropped packets in TXRQ deq";
    }
    leaf counters_slice3_tx_pdr_txrq0_threshold0_enq_dropped_packets {
      type oc-yang:counter64;
      description
        "Number of dropped packets in TXRQ enq";
    }
    leaf counters_slice3_tx_pdr_txrq0_threshold0_unscheduled_cgm_drops {
      type oc-yang:counter64;
      description
        "nan";
    }
    leaf counters_slice3_tx_pdr_txrq0_threshold1_deq_dropped_packets {
      type oc-yang:counter64;
      description
        "Number of dropped packets in TXRQ deq";
    }
    leaf counters_slice3_tx_pdr_txrq0_threshold1_enq_dropped_packets {
      type oc-yang:counter64;
      description
        "Number of dropped packets in TXRQ enq";
    }
    leaf counters_slice3_tx_pdr_txrq0_threshold1_unscheduled_cgm_drops {
      type oc-yang:counter64;
      description
        "nan";
    }
    leaf counters_slice3_tx_pdr_txrq1_full_egress_rep_dropped_packets {
      type oc-yang:counter64;
      description
        "Number of dropped packets";
    }
    leaf counters_slice3_tx_pdr_txrq1_threshold0_deq_dropped_packets {
      type oc-yang:counter64;
      description
        "Number of dropped packets in TXRQ deq";
    }
    leaf counters_slice3_tx_pdr_txrq1_threshold0_enq_dropped_packets {
      type oc-yang:counter64;
      description
        "Number of dropped packets in TXRQ enq";
    }
    leaf counters_slice3_tx_pdr_txrq1_threshold0_unscheduled_cgm_drops {
      type oc-yang:counter64;
      description
        "nan";
    }
    leaf counters_slice3_tx_pdr_txrq1_threshold1_deq_dropped_packets {
      type oc-yang:counter64;
      description
        "Number of dropped packets in TXRQ deq";
    }
    leaf counters_slice3_tx_pdr_txrq1_threshold1_enq_dropped_packets {
      type oc-yang:counter64;
      description
        "Number of dropped packets in TXRQ enq";
    }
    leaf counters_slice3_tx_pdr_txrq1_threshold1_unscheduled_cgm_drops {
      type oc-yang:counter64;
      description
        "nan";
    }
    leaf counters_slice3_tx_pdr_txrq2_full_egress_rep_dropped_packets {
      type oc-yang:counter64;
      description
        "Number of dropped packets";
    }
    leaf counters_slice3_tx_pdr_txrq2_threshold0_deq_dropped_packets {
      type oc-yang:counter64;
      description
        "Number of dropped packets in TXRQ deq";
    }
    leaf counters_slice3_tx_pdr_txrq2_threshold0_enq_dropped_packets {
      type oc-yang:counter64;
      description
        "Number of dropped packets in TXRQ enq";
    }
    leaf counters_slice3_tx_pdr_txrq2_threshold1_deq_dropped_packets {
      type oc-yang:counter64;
      description
        "Number of dropped packets in TXRQ deq";
    }
    leaf counters_slice3_tx_pdr_txrq2_threshold1_enq_dropped_packets {
      type oc-yang:counter64;
      description
        "Number of dropped packets in TXRQ enq";
    }
    leaf counters_slice3_tx_pdr_txrq3_full_egress_rep_dropped_packets {
      type oc-yang:counter64;
      description
        "Number of dropped packets";
    }
    leaf counters_slice3_tx_pdr_txrq3_threshold0_deq_dropped_packets {
      type oc-yang:counter64;
      description
        "Number of dropped packets in TXRQ deq";
    }
    leaf counters_slice3_tx_pdr_txrq3_threshold0_enq_dropped_packets {
      type oc-yang:counter64;
      description
        "Number of dropped packets in TXRQ enq";
    }
    leaf counters_slice3_tx_pdr_txrq3_threshold1_deq_dropped_packets {
      type oc-yang:counter64;
      description
        "Number of dropped packets in TXRQ deq";
    }
    leaf counters_slice3_tx_pdr_txrq3_threshold1_enq_dropped_packets {
      type oc-yang:counter64;
      description
        "Number of dropped packets in TXRQ enq";
    }
    leaf counters_slice4_ifg0_ifgb_rx_port_0_cgm_tc0_dropped_packets {
      type oc-yang:counter64;
      description
        "RX port cgm ostc0 drops counter. Counts packets that were totally dropped and will not be seen on RX side.";
    }
    leaf counters_slice4_ifg0_ifgb_rx_port_0_cgm_tc0_partially_dropped_packets {
      type oc-yang:counter64;
      description
        "RX port cgm ostc0 partial drops counter. Counts packets that were partially dropped and will be seen on RX side.";
    }
    leaf counters_slice4_ifg0_ifgb_rx_port_0_cgm_tc1_dropped_packets {
      type oc-yang:counter64;
      description
        "RX port cgm ostc1 drops counter. Counts packets that were totally dropped and will not be seen on RX side.";
    }
    leaf counters_slice4_ifg0_ifgb_rx_port_0_cgm_tc1_partially_dropped_packets {
      type oc-yang:counter64;
      description
        "RX port cgm ostc1 partial drops counter. Counts packets that were partially dropped and will be seen on RX side.";
    }
    leaf counters_slice4_ifg0_ifgb_rx_port_0_cgm_tc2_dropped_packets {
      type oc-yang:counter64;
      description
        "RX port cgm ostc2 drops counter. Counts packets that were totally dropped and will not be seen on RX side.";
    }
    leaf counters_slice4_ifg0_ifgb_rx_port_0_cgm_tc2_partially_dropped_packets {
      type oc-yang:counter64;
      description
        "RX port cgm ostc2 partial drops counter. Counts packets that were partially dropped and will be seen on RX side.";
    }
    leaf counters_slice4_ifg0_ifgb_rx_port_0_cgm_tc3_dropped_packets {
      type oc-yang:counter64;
      description
        "RX port cgm ostc3 drops counter. Counts packets that were totally dropped and will not be seen on RX side.";
    }
    leaf counters_slice4_ifg0_ifgb_rx_port_0_cgm_tc3_partially_dropped_packets {
      type oc-yang:counter64;
      description
        "RX port cgm ostc3 partial drops counter. Counts packets that were partially dropped and will be seen on RX side.";
    }
    leaf counters_slice4_ifg0_ifgb_rx_port_1_cgm_tc0_dropped_packets {
      type oc-yang:counter64;
      description
        "RX port cgm ostc0 drops counter. Counts packets that were totally dropped and will not be seen on RX side.";
    }
    leaf counters_slice4_ifg0_ifgb_rx_port_1_cgm_tc0_partially_dropped_packets {
      type oc-yang:counter64;
      description
        "RX port cgm ostc0 partial drops counter. Counts packets that were partially dropped and will be seen on RX side.";
    }
    leaf counters_slice4_ifg0_ifgb_rx_port_1_cgm_tc1_dropped_packets {
      type oc-yang:counter64;
      description
        "RX port cgm ostc1 drops counter. Counts packets that were totally dropped and will not be seen on RX side.";
    }
    leaf counters_slice4_ifg0_ifgb_rx_port_1_cgm_tc1_partially_dropped_packets {
      type oc-yang:counter64;
      description
        "RX port cgm ostc1 partial drops counter. Counts packets that were partially dropped and will be seen on RX side.";
    }
    leaf counters_slice4_ifg0_ifgb_rx_port_1_cgm_tc2_dropped_packets {
      type oc-yang:counter64;
      description
        "RX port cgm ostc2 drops counter. Counts packets that were totally dropped and will not be seen on RX side.";
    }
    leaf counters_slice4_ifg0_ifgb_rx_port_1_cgm_tc2_partially_dropped_packets {
      type oc-yang:counter64;
      description
        "RX port cgm ostc2 partial drops counter. Counts packets that were partially dropped and will be seen on RX side.";
    }
    leaf counters_slice4_ifg0_ifgb_rx_port_1_cgm_tc3_dropped_packets {
      type oc-yang:counter64;
      description
        "RX port cgm ostc3 drops counter. Counts packets that were totally dropped and will not be seen on RX side.";
    }
    leaf counters_slice4_ifg0_ifgb_rx_port_1_cgm_tc3_partially_dropped_packets {
      type oc-yang:counter64;
      description
        "RX port cgm ostc3 partial drops counter. Counts packets that were partially dropped and will be seen on RX side.";
    }
    leaf counters_slice4_ifg0_ifgb_rx_port_10_cgm_tc0_dropped_packets {
      type oc-yang:counter64;
      description
        "RX port cgm ostc0 drops counter. Counts packets that were totally dropped and will not be seen on RX side.";
    }
    leaf counters_slice4_ifg0_ifgb_rx_port_10_cgm_tc0_partially_dropped_packets {
      type oc-yang:counter64;
      description
        "RX port cgm ostc0 partial drops counter. Counts packets that were partially dropped and will be seen on RX side.";
    }
    leaf counters_slice4_ifg0_ifgb_rx_port_10_cgm_tc1_dropped_packets {
      type oc-yang:counter64;
      description
        "RX port cgm ostc1 drops counter. Counts packets that were totally dropped and will not be seen on RX side.";
    }
    leaf counters_slice4_ifg0_ifgb_rx_port_10_cgm_tc1_partially_dropped_packets {
      type oc-yang:counter64;
      description
        "RX port cgm ostc1 partial drops counter. Counts packets that were partially dropped and will be seen on RX side.";
    }
    leaf counters_slice4_ifg0_ifgb_rx_port_10_cgm_tc2_dropped_packets {
      type oc-yang:counter64;
      description
        "RX port cgm ostc2 drops counter. Counts packets that were totally dropped and will not be seen on RX side.";
    }
    leaf counters_slice4_ifg0_ifgb_rx_port_10_cgm_tc2_partially_dropped_packets {
      type oc-yang:counter64;
      description
        "RX port cgm ostc2 partial drops counter. Counts packets that were partially dropped and will be seen on RX side.";
    }
    leaf counters_slice4_ifg0_ifgb_rx_port_10_cgm_tc3_dropped_packets {
      type oc-yang:counter64;
      description
        "RX port cgm ostc3 drops counter. Counts packets that were totally dropped and will not be seen on RX side.";
    }
    leaf counters_slice4_ifg0_ifgb_rx_port_10_cgm_tc3_partially_dropped_packets {
      type oc-yang:counter64;
      description
        "RX port cgm ostc3 partial drops counter. Counts packets that were partially dropped and will be seen on RX side.";
    }
    leaf counters_slice4_ifg0_ifgb_rx_port_11_cgm_tc0_dropped_packets {
      type oc-yang:counter64;
      description
        "RX port cgm ostc0 drops counter. Counts packets that were totally dropped and will not be seen on RX side.";
    }
    leaf counters_slice4_ifg0_ifgb_rx_port_11_cgm_tc0_partially_dropped_packets {
      type oc-yang:counter64;
      description
        "RX port cgm ostc0 partial drops counter. Counts packets that were partially dropped and will be seen on RX side.";
    }
    leaf counters_slice4_ifg0_ifgb_rx_port_11_cgm_tc1_dropped_packets {
      type oc-yang:counter64;
      description
        "RX port cgm ostc1 drops counter. Counts packets that were totally dropped and will not be seen on RX side.";
    }
    leaf counters_slice4_ifg0_ifgb_rx_port_11_cgm_tc1_partially_dropped_packets {
      type oc-yang:counter64;
      description
        "RX port cgm ostc1 partial drops counter. Counts packets that were partially dropped and will be seen on RX side.";
    }
    leaf counters_slice4_ifg0_ifgb_rx_port_11_cgm_tc2_dropped_packets {
      type oc-yang:counter64;
      description
        "RX port cgm ostc2 drops counter. Counts packets that were totally dropped and will not be seen on RX side.";
    }
    leaf counters_slice4_ifg0_ifgb_rx_port_11_cgm_tc2_partially_dropped_packets {
      type oc-yang:counter64;
      description
        "RX port cgm ostc2 partial drops counter. Counts packets that were partially dropped and will be seen on RX side.";
    }
    leaf counters_slice4_ifg0_ifgb_rx_port_11_cgm_tc3_dropped_packets {
      type oc-yang:counter64;
      description
        "RX port cgm ostc3 drops counter. Counts packets that were totally dropped and will not be seen on RX side.";
    }
    leaf counters_slice4_ifg0_ifgb_rx_port_11_cgm_tc3_partially_dropped_packets {
      type oc-yang:counter64;
      description
        "RX port cgm ostc3 partial drops counter. Counts packets that were partially dropped and will be seen on RX side.";
    }
    leaf counters_slice4_ifg0_ifgb_rx_port_12_cgm_tc0_dropped_packets {
      type oc-yang:counter64;
      description
        "RX port cgm ostc0 drops counter. Counts packets that were totally dropped and will not be seen on RX side.";
    }
    leaf counters_slice4_ifg0_ifgb_rx_port_12_cgm_tc0_partially_dropped_packets {
      type oc-yang:counter64;
      description
        "RX port cgm ostc0 partial drops counter. Counts packets that were partially dropped and will be seen on RX side.";
    }
    leaf counters_slice4_ifg0_ifgb_rx_port_12_cgm_tc1_dropped_packets {
      type oc-yang:counter64;
      description
        "RX port cgm ostc1 drops counter. Counts packets that were totally dropped and will not be seen on RX side.";
    }
    leaf counters_slice4_ifg0_ifgb_rx_port_12_cgm_tc1_partially_dropped_packets {
      type oc-yang:counter64;
      description
        "RX port cgm ostc1 partial drops counter. Counts packets that were partially dropped and will be seen on RX side.";
    }
    leaf counters_slice4_ifg0_ifgb_rx_port_12_cgm_tc2_dropped_packets {
      type oc-yang:counter64;
      description
        "RX port cgm ostc2 drops counter. Counts packets that were totally dropped and will not be seen on RX side.";
    }
    leaf counters_slice4_ifg0_ifgb_rx_port_12_cgm_tc2_partially_dropped_packets {
      type oc-yang:counter64;
      description
        "RX port cgm ostc2 partial drops counter. Counts packets that were partially dropped and will be seen on RX side.";
    }
    leaf counters_slice4_ifg0_ifgb_rx_port_12_cgm_tc3_dropped_packets {
      type oc-yang:counter64;
      description
        "RX port cgm ostc3 drops counter. Counts packets that were totally dropped and will not be seen on RX side.";
    }
    leaf counters_slice4_ifg0_ifgb_rx_port_12_cgm_tc3_partially_dropped_packets {
      type oc-yang:counter64;
      description
        "RX port cgm ostc3 partial drops counter. Counts packets that were partially dropped and will be seen on RX side.";
    }
    leaf counters_slice4_ifg0_ifgb_rx_port_13_cgm_tc0_dropped_packets {
      type oc-yang:counter64;
      description
        "RX port cgm ostc0 drops counter. Counts packets that were totally dropped and will not be seen on RX side.";
    }
    leaf counters_slice4_ifg0_ifgb_rx_port_13_cgm_tc0_partially_dropped_packets {
      type oc-yang:counter64;
      description
        "RX port cgm ostc0 partial drops counter. Counts packets that were partially dropped and will be seen on RX side.";
    }
    leaf counters_slice4_ifg0_ifgb_rx_port_13_cgm_tc1_dropped_packets {
      type oc-yang:counter64;
      description
        "RX port cgm ostc1 drops counter. Counts packets that were totally dropped and will not be seen on RX side.";
    }
    leaf counters_slice4_ifg0_ifgb_rx_port_13_cgm_tc1_partially_dropped_packets {
      type oc-yang:counter64;
      description
        "RX port cgm ostc1 partial drops counter. Counts packets that were partially dropped and will be seen on RX side.";
    }
    leaf counters_slice4_ifg0_ifgb_rx_port_13_cgm_tc2_dropped_packets {
      type oc-yang:counter64;
      description
        "RX port cgm ostc2 drops counter. Counts packets that were totally dropped and will not be seen on RX side.";
    }
    leaf counters_slice4_ifg0_ifgb_rx_port_13_cgm_tc2_partially_dropped_packets {
      type oc-yang:counter64;
      description
        "RX port cgm ostc2 partial drops counter. Counts packets that were partially dropped and will be seen on RX side.";
    }
    leaf counters_slice4_ifg0_ifgb_rx_port_13_cgm_tc3_dropped_packets {
      type oc-yang:counter64;
      description
        "RX port cgm ostc3 drops counter. Counts packets that were totally dropped and will not be seen on RX side.";
    }
    leaf counters_slice4_ifg0_ifgb_rx_port_13_cgm_tc3_partially_dropped_packets {
      type oc-yang:counter64;
      description
        "RX port cgm ostc3 partial drops counter. Counts packets that were partially dropped and will be seen on RX side.";
    }
    leaf counters_slice4_ifg0_ifgb_rx_port_14_cgm_tc0_dropped_packets {
      type oc-yang:counter64;
      description
        "RX port cgm ostc0 drops counter. Counts packets that were totally dropped and will not be seen on RX side.";
    }
    leaf counters_slice4_ifg0_ifgb_rx_port_14_cgm_tc0_partially_dropped_packets {
      type oc-yang:counter64;
      description
        "RX port cgm ostc0 partial drops counter. Counts packets that were partially dropped and will be seen on RX side.";
    }
    leaf counters_slice4_ifg0_ifgb_rx_port_14_cgm_tc1_dropped_packets {
      type oc-yang:counter64;
      description
        "RX port cgm ostc1 drops counter. Counts packets that were totally dropped and will not be seen on RX side.";
    }
    leaf counters_slice4_ifg0_ifgb_rx_port_14_cgm_tc1_partially_dropped_packets {
      type oc-yang:counter64;
      description
        "RX port cgm ostc1 partial drops counter. Counts packets that were partially dropped and will be seen on RX side.";
    }
    leaf counters_slice4_ifg0_ifgb_rx_port_14_cgm_tc2_dropped_packets {
      type oc-yang:counter64;
      description
        "RX port cgm ostc2 drops counter. Counts packets that were totally dropped and will not be seen on RX side.";
    }
    leaf counters_slice4_ifg0_ifgb_rx_port_14_cgm_tc2_partially_dropped_packets {
      type oc-yang:counter64;
      description
        "RX port cgm ostc2 partial drops counter. Counts packets that were partially dropped and will be seen on RX side.";
    }
    leaf counters_slice4_ifg0_ifgb_rx_port_14_cgm_tc3_dropped_packets {
      type oc-yang:counter64;
      description
        "RX port cgm ostc3 drops counter. Counts packets that were totally dropped and will not be seen on RX side.";
    }
    leaf counters_slice4_ifg0_ifgb_rx_port_14_cgm_tc3_partially_dropped_packets {
      type oc-yang:counter64;
      description
        "RX port cgm ostc3 partial drops counter. Counts packets that were partially dropped and will be seen on RX side.";
    }
    leaf counters_slice4_ifg0_ifgb_rx_port_15_cgm_tc0_dropped_packets {
      type oc-yang:counter64;
      description
        "RX port cgm ostc0 drops counter. Counts packets that were totally dropped and will not be seen on RX side.";
    }
    leaf counters_slice4_ifg0_ifgb_rx_port_15_cgm_tc0_partially_dropped_packets {
      type oc-yang:counter64;
      description
        "RX port cgm ostc0 partial drops counter. Counts packets that were partially dropped and will be seen on RX side.";
    }
    leaf counters_slice4_ifg0_ifgb_rx_port_15_cgm_tc1_dropped_packets {
      type oc-yang:counter64;
      description
        "RX port cgm ostc1 drops counter. Counts packets that were totally dropped and will not be seen on RX side.";
    }
    leaf counters_slice4_ifg0_ifgb_rx_port_15_cgm_tc1_partially_dropped_packets {
      type oc-yang:counter64;
      description
        "RX port cgm ostc1 partial drops counter. Counts packets that were partially dropped and will be seen on RX side.";
    }
    leaf counters_slice4_ifg0_ifgb_rx_port_15_cgm_tc2_dropped_packets {
      type oc-yang:counter64;
      description
        "RX port cgm ostc2 drops counter. Counts packets that were totally dropped and will not be seen on RX side.";
    }
    leaf counters_slice4_ifg0_ifgb_rx_port_15_cgm_tc2_partially_dropped_packets {
      type oc-yang:counter64;
      description
        "RX port cgm ostc2 partial drops counter. Counts packets that were partially dropped and will be seen on RX side.";
    }
    leaf counters_slice4_ifg0_ifgb_rx_port_15_cgm_tc3_dropped_packets {
      type oc-yang:counter64;
      description
        "RX port cgm ostc3 drops counter. Counts packets that were totally dropped and will not be seen on RX side.";
    }
    leaf counters_slice4_ifg0_ifgb_rx_port_15_cgm_tc3_partially_dropped_packets {
      type oc-yang:counter64;
      description
        "RX port cgm ostc3 partial drops counter. Counts packets that were partially dropped and will be seen on RX side.";
    }
    leaf counters_slice4_ifg0_ifgb_rx_port_16_cgm_tc0_dropped_packets {
      type oc-yang:counter64;
      description
        "RX port cgm ostc0 drops counter. Counts packets that were totally dropped and will not be seen on RX side.";
    }
    leaf counters_slice4_ifg0_ifgb_rx_port_16_cgm_tc0_partially_dropped_packets {
      type oc-yang:counter64;
      description
        "RX port cgm ostc0 partial drops counter. Counts packets that were partially dropped and will be seen on RX side.";
    }
    leaf counters_slice4_ifg0_ifgb_rx_port_16_cgm_tc1_dropped_packets {
      type oc-yang:counter64;
      description
        "RX port cgm ostc1 drops counter. Counts packets that were totally dropped and will not be seen on RX side.";
    }
    leaf counters_slice4_ifg0_ifgb_rx_port_16_cgm_tc1_partially_dropped_packets {
      type oc-yang:counter64;
      description
        "RX port cgm ostc1 partial drops counter. Counts packets that were partially dropped and will be seen on RX side.";
    }
    leaf counters_slice4_ifg0_ifgb_rx_port_16_cgm_tc2_dropped_packets {
      type oc-yang:counter64;
      description
        "RX port cgm ostc2 drops counter. Counts packets that were totally dropped and will not be seen on RX side.";
    }
    leaf counters_slice4_ifg0_ifgb_rx_port_16_cgm_tc2_partially_dropped_packets {
      type oc-yang:counter64;
      description
        "RX port cgm ostc2 partial drops counter. Counts packets that were partially dropped and will be seen on RX side.";
    }
    leaf counters_slice4_ifg0_ifgb_rx_port_16_cgm_tc3_dropped_packets {
      type oc-yang:counter64;
      description
        "RX port cgm ostc3 drops counter. Counts packets that were totally dropped and will not be seen on RX side.";
    }
    leaf counters_slice4_ifg0_ifgb_rx_port_16_cgm_tc3_partially_dropped_packets {
      type oc-yang:counter64;
      description
        "RX port cgm ostc3 partial drops counter. Counts packets that were partially dropped and will be seen on RX side.";
    }
    leaf counters_slice4_ifg0_ifgb_rx_port_17_cgm_tc0_dropped_packets {
      type oc-yang:counter64;
      description
        "RX port cgm ostc0 drops counter. Counts packets that were totally dropped and will not be seen on RX side.";
    }
    leaf counters_slice4_ifg0_ifgb_rx_port_17_cgm_tc0_partially_dropped_packets {
      type oc-yang:counter64;
      description
        "RX port cgm ostc0 partial drops counter. Counts packets that were partially dropped and will be seen on RX side.";
    }
    leaf counters_slice4_ifg0_ifgb_rx_port_17_cgm_tc1_dropped_packets {
      type oc-yang:counter64;
      description
        "RX port cgm ostc1 drops counter. Counts packets that were totally dropped and will not be seen on RX side.";
    }
    leaf counters_slice4_ifg0_ifgb_rx_port_17_cgm_tc1_partially_dropped_packets {
      type oc-yang:counter64;
      description
        "RX port cgm ostc1 partial drops counter. Counts packets that were partially dropped and will be seen on RX side.";
    }
    leaf counters_slice4_ifg0_ifgb_rx_port_17_cgm_tc2_dropped_packets {
      type oc-yang:counter64;
      description
        "RX port cgm ostc2 drops counter. Counts packets that were totally dropped and will not be seen on RX side.";
    }
    leaf counters_slice4_ifg0_ifgb_rx_port_17_cgm_tc2_partially_dropped_packets {
      type oc-yang:counter64;
      description
        "RX port cgm ostc2 partial drops counter. Counts packets that were partially dropped and will be seen on RX side.";
    }
    leaf counters_slice4_ifg0_ifgb_rx_port_17_cgm_tc3_dropped_packets {
      type oc-yang:counter64;
      description
        "RX port cgm ostc3 drops counter. Counts packets that were totally dropped and will not be seen on RX side.";
    }
    leaf counters_slice4_ifg0_ifgb_rx_port_17_cgm_tc3_partially_dropped_packets {
      type oc-yang:counter64;
      description
        "RX port cgm ostc3 partial drops counter. Counts packets that were partially dropped and will be seen on RX side.";
    }
    leaf counters_slice4_ifg0_ifgb_rx_port_18_cgm_tc0_dropped_packets {
      type oc-yang:counter64;
      description
        "RX port cgm ostc0 drops counter. Counts packets that were totally dropped and will not be seen on RX side.";
    }
    leaf counters_slice4_ifg0_ifgb_rx_port_18_cgm_tc0_partially_dropped_packets {
      type oc-yang:counter64;
      description
        "RX port cgm ostc0 partial drops counter. Counts packets that were partially dropped and will be seen on RX side.";
    }
    leaf counters_slice4_ifg0_ifgb_rx_port_18_cgm_tc1_dropped_packets {
      type oc-yang:counter64;
      description
        "RX port cgm ostc1 drops counter. Counts packets that were totally dropped and will not be seen on RX side.";
    }
    leaf counters_slice4_ifg0_ifgb_rx_port_18_cgm_tc1_partially_dropped_packets {
      type oc-yang:counter64;
      description
        "RX port cgm ostc1 partial drops counter. Counts packets that were partially dropped and will be seen on RX side.";
    }
    leaf counters_slice4_ifg0_ifgb_rx_port_18_cgm_tc2_dropped_packets {
      type oc-yang:counter64;
      description
        "RX port cgm ostc2 drops counter. Counts packets that were totally dropped and will not be seen on RX side.";
    }
    leaf counters_slice4_ifg0_ifgb_rx_port_18_cgm_tc2_partially_dropped_packets {
      type oc-yang:counter64;
      description
        "RX port cgm ostc2 partial drops counter. Counts packets that were partially dropped and will be seen on RX side.";
    }
    leaf counters_slice4_ifg0_ifgb_rx_port_18_cgm_tc3_dropped_packets {
      type oc-yang:counter64;
      description
        "RX port cgm ostc3 drops counter. Counts packets that were totally dropped and will not be seen on RX side.";
    }
    leaf counters_slice4_ifg0_ifgb_rx_port_18_cgm_tc3_partially_dropped_packets {
      type oc-yang:counter64;
      description
        "RX port cgm ostc3 partial drops counter. Counts packets that were partially dropped and will be seen on RX side.";
    }
    leaf counters_slice4_ifg0_ifgb_rx_port_19_cgm_tc0_dropped_packets {
      type oc-yang:counter64;
      description
        "RX port cgm ostc0 drops counter. Counts packets that were totally dropped and will not be seen on RX side.";
    }
    leaf counters_slice4_ifg0_ifgb_rx_port_19_cgm_tc0_partially_dropped_packets {
      type oc-yang:counter64;
      description
        "RX port cgm ostc0 partial drops counter. Counts packets that were partially dropped and will be seen on RX side.";
    }
    leaf counters_slice4_ifg0_ifgb_rx_port_19_cgm_tc1_dropped_packets {
      type oc-yang:counter64;
      description
        "RX port cgm ostc1 drops counter. Counts packets that were totally dropped and will not be seen on RX side.";
    }
    leaf counters_slice4_ifg0_ifgb_rx_port_19_cgm_tc1_partially_dropped_packets {
      type oc-yang:counter64;
      description
        "RX port cgm ostc1 partial drops counter. Counts packets that were partially dropped and will be seen on RX side.";
    }
    leaf counters_slice4_ifg0_ifgb_rx_port_19_cgm_tc2_dropped_packets {
      type oc-yang:counter64;
      description
        "RX port cgm ostc2 drops counter. Counts packets that were totally dropped and will not be seen on RX side.";
    }
    leaf counters_slice4_ifg0_ifgb_rx_port_19_cgm_tc2_partially_dropped_packets {
      type oc-yang:counter64;
      description
        "RX port cgm ostc2 partial drops counter. Counts packets that were partially dropped and will be seen on RX side.";
    }
    leaf counters_slice4_ifg0_ifgb_rx_port_19_cgm_tc3_dropped_packets {
      type oc-yang:counter64;
      description
        "RX port cgm ostc3 drops counter. Counts packets that were totally dropped and will not be seen on RX side.";
    }
    leaf counters_slice4_ifg0_ifgb_rx_port_19_cgm_tc3_partially_dropped_packets {
      type oc-yang:counter64;
      description
        "RX port cgm ostc3 partial drops counter. Counts packets that were partially dropped and will be seen on RX side.";
    }
    leaf counters_slice4_ifg0_ifgb_rx_port_2_cgm_tc0_dropped_packets {
      type oc-yang:counter64;
      description
        "RX port cgm ostc0 drops counter. Counts packets that were totally dropped and will not be seen on RX side.";
    }
    leaf counters_slice4_ifg0_ifgb_rx_port_2_cgm_tc0_partially_dropped_packets {
      type oc-yang:counter64;
      description
        "RX port cgm ostc0 partial drops counter. Counts packets that were partially dropped and will be seen on RX side.";
    }
    leaf counters_slice4_ifg0_ifgb_rx_port_2_cgm_tc1_dropped_packets {
      type oc-yang:counter64;
      description
        "RX port cgm ostc1 drops counter. Counts packets that were totally dropped and will not be seen on RX side.";
    }
    leaf counters_slice4_ifg0_ifgb_rx_port_2_cgm_tc1_partially_dropped_packets {
      type oc-yang:counter64;
      description
        "RX port cgm ostc1 partial drops counter. Counts packets that were partially dropped and will be seen on RX side.";
    }
    leaf counters_slice4_ifg0_ifgb_rx_port_2_cgm_tc2_dropped_packets {
      type oc-yang:counter64;
      description
        "RX port cgm ostc2 drops counter. Counts packets that were totally dropped and will not be seen on RX side.";
    }
    leaf counters_slice4_ifg0_ifgb_rx_port_2_cgm_tc2_partially_dropped_packets {
      type oc-yang:counter64;
      description
        "RX port cgm ostc2 partial drops counter. Counts packets that were partially dropped and will be seen on RX side.";
    }
    leaf counters_slice4_ifg0_ifgb_rx_port_2_cgm_tc3_dropped_packets {
      type oc-yang:counter64;
      description
        "RX port cgm ostc3 drops counter. Counts packets that were totally dropped and will not be seen on RX side.";
    }
    leaf counters_slice4_ifg0_ifgb_rx_port_2_cgm_tc3_partially_dropped_packets {
      type oc-yang:counter64;
      description
        "RX port cgm ostc3 partial drops counter. Counts packets that were partially dropped and will be seen on RX side.";
    }
    leaf counters_slice4_ifg0_ifgb_rx_port_20_cgm_tc0_dropped_packets {
      type oc-yang:counter64;
      description
        "RX port cgm ostc0 drops counter. Counts packets that were totally dropped and will not be seen on RX side.";
    }
    leaf counters_slice4_ifg0_ifgb_rx_port_20_cgm_tc0_partially_dropped_packets {
      type oc-yang:counter64;
      description
        "RX port cgm ostc0 partial drops counter. Counts packets that were partially dropped and will be seen on RX side.";
    }
    leaf counters_slice4_ifg0_ifgb_rx_port_20_cgm_tc1_dropped_packets {
      type oc-yang:counter64;
      description
        "RX port cgm ostc1 drops counter. Counts packets that were totally dropped and will not be seen on RX side.";
    }
    leaf counters_slice4_ifg0_ifgb_rx_port_20_cgm_tc1_partially_dropped_packets {
      type oc-yang:counter64;
      description
        "RX port cgm ostc1 partial drops counter. Counts packets that were partially dropped and will be seen on RX side.";
    }
    leaf counters_slice4_ifg0_ifgb_rx_port_20_cgm_tc2_dropped_packets {
      type oc-yang:counter64;
      description
        "RX port cgm ostc2 drops counter. Counts packets that were totally dropped and will not be seen on RX side.";
    }
    leaf counters_slice4_ifg0_ifgb_rx_port_20_cgm_tc2_partially_dropped_packets {
      type oc-yang:counter64;
      description
        "RX port cgm ostc2 partial drops counter. Counts packets that were partially dropped and will be seen on RX side.";
    }
    leaf counters_slice4_ifg0_ifgb_rx_port_20_cgm_tc3_dropped_packets {
      type oc-yang:counter64;
      description
        "RX port cgm ostc3 drops counter. Counts packets that were totally dropped and will not be seen on RX side.";
    }
    leaf counters_slice4_ifg0_ifgb_rx_port_20_cgm_tc3_partially_dropped_packets {
      type oc-yang:counter64;
      description
        "RX port cgm ostc3 partial drops counter. Counts packets that were partially dropped and will be seen on RX side.";
    }
    leaf counters_slice4_ifg0_ifgb_rx_port_21_cgm_tc0_dropped_packets {
      type oc-yang:counter64;
      description
        "RX port cgm ostc0 drops counter. Counts packets that were totally dropped and will not be seen on RX side.";
    }
    leaf counters_slice4_ifg0_ifgb_rx_port_21_cgm_tc0_partially_dropped_packets {
      type oc-yang:counter64;
      description
        "RX port cgm ostc0 partial drops counter. Counts packets that were partially dropped and will be seen on RX side.";
    }
    leaf counters_slice4_ifg0_ifgb_rx_port_21_cgm_tc1_dropped_packets {
      type oc-yang:counter64;
      description
        "RX port cgm ostc1 drops counter. Counts packets that were totally dropped and will not be seen on RX side.";
    }
    leaf counters_slice4_ifg0_ifgb_rx_port_21_cgm_tc1_partially_dropped_packets {
      type oc-yang:counter64;
      description
        "RX port cgm ostc1 partial drops counter. Counts packets that were partially dropped and will be seen on RX side.";
    }
    leaf counters_slice4_ifg0_ifgb_rx_port_21_cgm_tc2_dropped_packets {
      type oc-yang:counter64;
      description
        "RX port cgm ostc2 drops counter. Counts packets that were totally dropped and will not be seen on RX side.";
    }
    leaf counters_slice4_ifg0_ifgb_rx_port_21_cgm_tc2_partially_dropped_packets {
      type oc-yang:counter64;
      description
        "RX port cgm ostc2 partial drops counter. Counts packets that were partially dropped and will be seen on RX side.";
    }
    leaf counters_slice4_ifg0_ifgb_rx_port_21_cgm_tc3_dropped_packets {
      type oc-yang:counter64;
      description
        "RX port cgm ostc3 drops counter. Counts packets that were totally dropped and will not be seen on RX side.";
    }
    leaf counters_slice4_ifg0_ifgb_rx_port_21_cgm_tc3_partially_dropped_packets {
      type oc-yang:counter64;
      description
        "RX port cgm ostc3 partial drops counter. Counts packets that were partially dropped and will be seen on RX side.";
    }
    leaf counters_slice4_ifg0_ifgb_rx_port_22_cgm_tc0_dropped_packets {
      type oc-yang:counter64;
      description
        "RX port cgm ostc0 drops counter. Counts packets that were totally dropped and will not be seen on RX side.";
    }
    leaf counters_slice4_ifg0_ifgb_rx_port_22_cgm_tc0_partially_dropped_packets {
      type oc-yang:counter64;
      description
        "RX port cgm ostc0 partial drops counter. Counts packets that were partially dropped and will be seen on RX side.";
    }
    leaf counters_slice4_ifg0_ifgb_rx_port_22_cgm_tc1_dropped_packets {
      type oc-yang:counter64;
      description
        "RX port cgm ostc1 drops counter. Counts packets that were totally dropped and will not be seen on RX side.";
    }
    leaf counters_slice4_ifg0_ifgb_rx_port_22_cgm_tc1_partially_dropped_packets {
      type oc-yang:counter64;
      description
        "RX port cgm ostc1 partial drops counter. Counts packets that were partially dropped and will be seen on RX side.";
    }
    leaf counters_slice4_ifg0_ifgb_rx_port_22_cgm_tc2_dropped_packets {
      type oc-yang:counter64;
      description
        "RX port cgm ostc2 drops counter. Counts packets that were totally dropped and will not be seen on RX side.";
    }
    leaf counters_slice4_ifg0_ifgb_rx_port_22_cgm_tc2_partially_dropped_packets {
      type oc-yang:counter64;
      description
        "RX port cgm ostc2 partial drops counter. Counts packets that were partially dropped and will be seen on RX side.";
    }
    leaf counters_slice4_ifg0_ifgb_rx_port_22_cgm_tc3_dropped_packets {
      type oc-yang:counter64;
      description
        "RX port cgm ostc3 drops counter. Counts packets that were totally dropped and will not be seen on RX side.";
    }
    leaf counters_slice4_ifg0_ifgb_rx_port_22_cgm_tc3_partially_dropped_packets {
      type oc-yang:counter64;
      description
        "RX port cgm ostc3 partial drops counter. Counts packets that were partially dropped and will be seen on RX side.";
    }
    leaf counters_slice4_ifg0_ifgb_rx_port_23_cgm_tc0_dropped_packets {
      type oc-yang:counter64;
      description
        "RX port cgm ostc0 drops counter. Counts packets that were totally dropped and will not be seen on RX side.";
    }
    leaf counters_slice4_ifg0_ifgb_rx_port_23_cgm_tc0_partially_dropped_packets {
      type oc-yang:counter64;
      description
        "RX port cgm ostc0 partial drops counter. Counts packets that were partially dropped and will be seen on RX side.";
    }
    leaf counters_slice4_ifg0_ifgb_rx_port_23_cgm_tc1_dropped_packets {
      type oc-yang:counter64;
      description
        "RX port cgm ostc1 drops counter. Counts packets that were totally dropped and will not be seen on RX side.";
    }
    leaf counters_slice4_ifg0_ifgb_rx_port_23_cgm_tc1_partially_dropped_packets {
      type oc-yang:counter64;
      description
        "RX port cgm ostc1 partial drops counter. Counts packets that were partially dropped and will be seen on RX side.";
    }
    leaf counters_slice4_ifg0_ifgb_rx_port_23_cgm_tc2_dropped_packets {
      type oc-yang:counter64;
      description
        "RX port cgm ostc2 drops counter. Counts packets that were totally dropped and will not be seen on RX side.";
    }
    leaf counters_slice4_ifg0_ifgb_rx_port_23_cgm_tc2_partially_dropped_packets {
      type oc-yang:counter64;
      description
        "RX port cgm ostc2 partial drops counter. Counts packets that were partially dropped and will be seen on RX side.";
    }
    leaf counters_slice4_ifg0_ifgb_rx_port_23_cgm_tc3_dropped_packets {
      type oc-yang:counter64;
      description
        "RX port cgm ostc3 drops counter. Counts packets that were totally dropped and will not be seen on RX side.";
    }
    leaf counters_slice4_ifg0_ifgb_rx_port_23_cgm_tc3_partially_dropped_packets {
      type oc-yang:counter64;
      description
        "RX port cgm ostc3 partial drops counter. Counts packets that were partially dropped and will be seen on RX side.";
    }
    leaf counters_slice4_ifg0_ifgb_rx_port_24_cgm_tc0_dropped_packets {
      type oc-yang:counter64;
      description
        "RX port cgm ostc0 drops counter. Counts packets that were totally dropped and will not be seen on RX side.";
    }
    leaf counters_slice4_ifg0_ifgb_rx_port_24_cgm_tc0_partially_dropped_packets {
      type oc-yang:counter64;
      description
        "RX port cgm ostc0 partial drops counter. Counts packets that were partially dropped and will be seen on RX side.";
    }
    leaf counters_slice4_ifg0_ifgb_rx_port_24_cgm_tc1_dropped_packets {
      type oc-yang:counter64;
      description
        "RX port cgm ostc1 drops counter. Counts packets that were totally dropped and will not be seen on RX side.";
    }
    leaf counters_slice4_ifg0_ifgb_rx_port_24_cgm_tc1_partially_dropped_packets {
      type oc-yang:counter64;
      description
        "RX port cgm ostc1 partial drops counter. Counts packets that were partially dropped and will be seen on RX side.";
    }
    leaf counters_slice4_ifg0_ifgb_rx_port_24_cgm_tc2_dropped_packets {
      type oc-yang:counter64;
      description
        "RX port cgm ostc2 drops counter. Counts packets that were totally dropped and will not be seen on RX side.";
    }
    leaf counters_slice4_ifg0_ifgb_rx_port_24_cgm_tc2_partially_dropped_packets {
      type oc-yang:counter64;
      description
        "RX port cgm ostc2 partial drops counter. Counts packets that were partially dropped and will be seen on RX side.";
    }
    leaf counters_slice4_ifg0_ifgb_rx_port_24_cgm_tc3_dropped_packets {
      type oc-yang:counter64;
      description
        "RX port cgm ostc3 drops counter. Counts packets that were totally dropped and will not be seen on RX side.";
    }
    leaf counters_slice4_ifg0_ifgb_rx_port_24_cgm_tc3_partially_dropped_packets {
      type oc-yang:counter64;
      description
        "RX port cgm ostc3 partial drops counter. Counts packets that were partially dropped and will be seen on RX side.";
    }
    leaf counters_slice4_ifg0_ifgb_rx_port_25_cgm_tc0_dropped_packets {
      type oc-yang:counter64;
      description
        "RX port cgm ostc0 drops counter. Counts packets that were totally dropped and will not be seen on RX side.";
    }
    leaf counters_slice4_ifg0_ifgb_rx_port_25_cgm_tc0_partially_dropped_packets {
      type oc-yang:counter64;
      description
        "RX port cgm ostc0 partial drops counter. Counts packets that were partially dropped and will be seen on RX side.";
    }
    leaf counters_slice4_ifg0_ifgb_rx_port_25_cgm_tc1_dropped_packets {
      type oc-yang:counter64;
      description
        "RX port cgm ostc1 drops counter. Counts packets that were totally dropped and will not be seen on RX side.";
    }
    leaf counters_slice4_ifg0_ifgb_rx_port_25_cgm_tc1_partially_dropped_packets {
      type oc-yang:counter64;
      description
        "RX port cgm ostc1 partial drops counter. Counts packets that were partially dropped and will be seen on RX side.";
    }
    leaf counters_slice4_ifg0_ifgb_rx_port_25_cgm_tc2_dropped_packets {
      type oc-yang:counter64;
      description
        "RX port cgm ostc2 drops counter. Counts packets that were totally dropped and will not be seen on RX side.";
    }
    leaf counters_slice4_ifg0_ifgb_rx_port_25_cgm_tc2_partially_dropped_packets {
      type oc-yang:counter64;
      description
        "RX port cgm ostc2 partial drops counter. Counts packets that were partially dropped and will be seen on RX side.";
    }
    leaf counters_slice4_ifg0_ifgb_rx_port_25_cgm_tc3_dropped_packets {
      type oc-yang:counter64;
      description
        "RX port cgm ostc3 drops counter. Counts packets that were totally dropped and will not be seen on RX side.";
    }
    leaf counters_slice4_ifg0_ifgb_rx_port_25_cgm_tc3_partially_dropped_packets {
      type oc-yang:counter64;
      description
        "RX port cgm ostc3 partial drops counter. Counts packets that were partially dropped and will be seen on RX side.";
    }
    leaf counters_slice4_ifg0_ifgb_rx_port_26_cgm_tc0_dropped_packets {
      type oc-yang:counter64;
      description
        "RX port cgm ostc0 drops counter. Counts packets that were totally dropped and will not be seen on RX side.";
    }
    leaf counters_slice4_ifg0_ifgb_rx_port_26_cgm_tc0_partially_dropped_packets {
      type oc-yang:counter64;
      description
        "RX port cgm ostc0 partial drops counter. Counts packets that were partially dropped and will be seen on RX side.";
    }
    leaf counters_slice4_ifg0_ifgb_rx_port_26_cgm_tc1_dropped_packets {
      type oc-yang:counter64;
      description
        "RX port cgm ostc1 drops counter. Counts packets that were totally dropped and will not be seen on RX side.";
    }
    leaf counters_slice4_ifg0_ifgb_rx_port_26_cgm_tc1_partially_dropped_packets {
      type oc-yang:counter64;
      description
        "RX port cgm ostc1 partial drops counter. Counts packets that were partially dropped and will be seen on RX side.";
    }
    leaf counters_slice4_ifg0_ifgb_rx_port_26_cgm_tc2_dropped_packets {
      type oc-yang:counter64;
      description
        "RX port cgm ostc2 drops counter. Counts packets that were totally dropped and will not be seen on RX side.";
    }
    leaf counters_slice4_ifg0_ifgb_rx_port_26_cgm_tc2_partially_dropped_packets {
      type oc-yang:counter64;
      description
        "RX port cgm ostc2 partial drops counter. Counts packets that were partially dropped and will be seen on RX side.";
    }
    leaf counters_slice4_ifg0_ifgb_rx_port_26_cgm_tc3_dropped_packets {
      type oc-yang:counter64;
      description
        "RX port cgm ostc3 drops counter. Counts packets that were totally dropped and will not be seen on RX side.";
    }
    leaf counters_slice4_ifg0_ifgb_rx_port_26_cgm_tc3_partially_dropped_packets {
      type oc-yang:counter64;
      description
        "RX port cgm ostc3 partial drops counter. Counts packets that were partially dropped and will be seen on RX side.";
    }
    leaf counters_slice4_ifg0_ifgb_rx_port_27_cgm_tc0_dropped_packets {
      type oc-yang:counter64;
      description
        "RX port cgm ostc0 drops counter. Counts packets that were totally dropped and will not be seen on RX side.";
    }
    leaf counters_slice4_ifg0_ifgb_rx_port_27_cgm_tc0_partially_dropped_packets {
      type oc-yang:counter64;
      description
        "RX port cgm ostc0 partial drops counter. Counts packets that were partially dropped and will be seen on RX side.";
    }
    leaf counters_slice4_ifg0_ifgb_rx_port_27_cgm_tc1_dropped_packets {
      type oc-yang:counter64;
      description
        "RX port cgm ostc1 drops counter. Counts packets that were totally dropped and will not be seen on RX side.";
    }
    leaf counters_slice4_ifg0_ifgb_rx_port_27_cgm_tc1_partially_dropped_packets {
      type oc-yang:counter64;
      description
        "RX port cgm ostc1 partial drops counter. Counts packets that were partially dropped and will be seen on RX side.";
    }
    leaf counters_slice4_ifg0_ifgb_rx_port_27_cgm_tc2_dropped_packets {
      type oc-yang:counter64;
      description
        "RX port cgm ostc2 drops counter. Counts packets that were totally dropped and will not be seen on RX side.";
    }
    leaf counters_slice4_ifg0_ifgb_rx_port_27_cgm_tc2_partially_dropped_packets {
      type oc-yang:counter64;
      description
        "RX port cgm ostc2 partial drops counter. Counts packets that were partially dropped and will be seen on RX side.";
    }
    leaf counters_slice4_ifg0_ifgb_rx_port_27_cgm_tc3_dropped_packets {
      type oc-yang:counter64;
      description
        "RX port cgm ostc3 drops counter. Counts packets that were totally dropped and will not be seen on RX side.";
    }
    leaf counters_slice4_ifg0_ifgb_rx_port_27_cgm_tc3_partially_dropped_packets {
      type oc-yang:counter64;
      description
        "RX port cgm ostc3 partial drops counter. Counts packets that were partially dropped and will be seen on RX side.";
    }
    leaf counters_slice4_ifg0_ifgb_rx_port_28_cgm_tc0_dropped_packets {
      type oc-yang:counter64;
      description
        "RX port cgm ostc0 drops counter. Counts packets that were totally dropped and will not be seen on RX side.";
    }
    leaf counters_slice4_ifg0_ifgb_rx_port_28_cgm_tc0_partially_dropped_packets {
      type oc-yang:counter64;
      description
        "RX port cgm ostc0 partial drops counter. Counts packets that were partially dropped and will be seen on RX side.";
    }
    leaf counters_slice4_ifg0_ifgb_rx_port_28_cgm_tc1_dropped_packets {
      type oc-yang:counter64;
      description
        "RX port cgm ostc1 drops counter. Counts packets that were totally dropped and will not be seen on RX side.";
    }
    leaf counters_slice4_ifg0_ifgb_rx_port_28_cgm_tc1_partially_dropped_packets {
      type oc-yang:counter64;
      description
        "RX port cgm ostc1 partial drops counter. Counts packets that were partially dropped and will be seen on RX side.";
    }
    leaf counters_slice4_ifg0_ifgb_rx_port_28_cgm_tc2_dropped_packets {
      type oc-yang:counter64;
      description
        "RX port cgm ostc2 drops counter. Counts packets that were totally dropped and will not be seen on RX side.";
    }
    leaf counters_slice4_ifg0_ifgb_rx_port_28_cgm_tc2_partially_dropped_packets {
      type oc-yang:counter64;
      description
        "RX port cgm ostc2 partial drops counter. Counts packets that were partially dropped and will be seen on RX side.";
    }
    leaf counters_slice4_ifg0_ifgb_rx_port_28_cgm_tc3_dropped_packets {
      type oc-yang:counter64;
      description
        "RX port cgm ostc3 drops counter. Counts packets that were totally dropped and will not be seen on RX side.";
    }
    leaf counters_slice4_ifg0_ifgb_rx_port_28_cgm_tc3_partially_dropped_packets {
      type oc-yang:counter64;
      description
        "RX port cgm ostc3 partial drops counter. Counts packets that were partially dropped and will be seen on RX side.";
    }
    leaf counters_slice4_ifg0_ifgb_rx_port_29_cgm_tc0_dropped_packets {
      type oc-yang:counter64;
      description
        "RX port cgm ostc0 drops counter. Counts packets that were totally dropped and will not be seen on RX side.";
    }
    leaf counters_slice4_ifg0_ifgb_rx_port_29_cgm_tc0_partially_dropped_packets {
      type oc-yang:counter64;
      description
        "RX port cgm ostc0 partial drops counter. Counts packets that were partially dropped and will be seen on RX side.";
    }
    leaf counters_slice4_ifg0_ifgb_rx_port_29_cgm_tc1_dropped_packets {
      type oc-yang:counter64;
      description
        "RX port cgm ostc1 drops counter. Counts packets that were totally dropped and will not be seen on RX side.";
    }
    leaf counters_slice4_ifg0_ifgb_rx_port_29_cgm_tc1_partially_dropped_packets {
      type oc-yang:counter64;
      description
        "RX port cgm ostc1 partial drops counter. Counts packets that were partially dropped and will be seen on RX side.";
    }
    leaf counters_slice4_ifg0_ifgb_rx_port_29_cgm_tc2_dropped_packets {
      type oc-yang:counter64;
      description
        "RX port cgm ostc2 drops counter. Counts packets that were totally dropped and will not be seen on RX side.";
    }
    leaf counters_slice4_ifg0_ifgb_rx_port_29_cgm_tc2_partially_dropped_packets {
      type oc-yang:counter64;
      description
        "RX port cgm ostc2 partial drops counter. Counts packets that were partially dropped and will be seen on RX side.";
    }
    leaf counters_slice4_ifg0_ifgb_rx_port_29_cgm_tc3_dropped_packets {
      type oc-yang:counter64;
      description
        "RX port cgm ostc3 drops counter. Counts packets that were totally dropped and will not be seen on RX side.";
    }
    leaf counters_slice4_ifg0_ifgb_rx_port_29_cgm_tc3_partially_dropped_packets {
      type oc-yang:counter64;
      description
        "RX port cgm ostc3 partial drops counter. Counts packets that were partially dropped and will be seen on RX side.";
    }
    leaf counters_slice4_ifg0_ifgb_rx_port_3_cgm_tc0_dropped_packets {
      type oc-yang:counter64;
      description
        "RX port cgm ostc0 drops counter. Counts packets that were totally dropped and will not be seen on RX side.";
    }
    leaf counters_slice4_ifg0_ifgb_rx_port_3_cgm_tc0_partially_dropped_packets {
      type oc-yang:counter64;
      description
        "RX port cgm ostc0 partial drops counter. Counts packets that were partially dropped and will be seen on RX side.";
    }
    leaf counters_slice4_ifg0_ifgb_rx_port_3_cgm_tc1_dropped_packets {
      type oc-yang:counter64;
      description
        "RX port cgm ostc1 drops counter. Counts packets that were totally dropped and will not be seen on RX side.";
    }
    leaf counters_slice4_ifg0_ifgb_rx_port_3_cgm_tc1_partially_dropped_packets {
      type oc-yang:counter64;
      description
        "RX port cgm ostc1 partial drops counter. Counts packets that were partially dropped and will be seen on RX side.";
    }
    leaf counters_slice4_ifg0_ifgb_rx_port_3_cgm_tc2_dropped_packets {
      type oc-yang:counter64;
      description
        "RX port cgm ostc2 drops counter. Counts packets that were totally dropped and will not be seen on RX side.";
    }
    leaf counters_slice4_ifg0_ifgb_rx_port_3_cgm_tc2_partially_dropped_packets {
      type oc-yang:counter64;
      description
        "RX port cgm ostc2 partial drops counter. Counts packets that were partially dropped and will be seen on RX side.";
    }
    leaf counters_slice4_ifg0_ifgb_rx_port_3_cgm_tc3_dropped_packets {
      type oc-yang:counter64;
      description
        "RX port cgm ostc3 drops counter. Counts packets that were totally dropped and will not be seen on RX side.";
    }
    leaf counters_slice4_ifg0_ifgb_rx_port_3_cgm_tc3_partially_dropped_packets {
      type oc-yang:counter64;
      description
        "RX port cgm ostc3 partial drops counter. Counts packets that were partially dropped and will be seen on RX side.";
    }
    leaf counters_slice4_ifg0_ifgb_rx_port_30_cgm_tc0_dropped_packets {
      type oc-yang:counter64;
      description
        "RX port cgm ostc0 drops counter. Counts packets that were totally dropped and will not be seen on RX side.";
    }
    leaf counters_slice4_ifg0_ifgb_rx_port_30_cgm_tc0_partially_dropped_packets {
      type oc-yang:counter64;
      description
        "RX port cgm ostc0 partial drops counter. Counts packets that were partially dropped and will be seen on RX side.";
    }
    leaf counters_slice4_ifg0_ifgb_rx_port_30_cgm_tc1_dropped_packets {
      type oc-yang:counter64;
      description
        "RX port cgm ostc1 drops counter. Counts packets that were totally dropped and will not be seen on RX side.";
    }
    leaf counters_slice4_ifg0_ifgb_rx_port_30_cgm_tc1_partially_dropped_packets {
      type oc-yang:counter64;
      description
        "RX port cgm ostc1 partial drops counter. Counts packets that were partially dropped and will be seen on RX side.";
    }
    leaf counters_slice4_ifg0_ifgb_rx_port_30_cgm_tc2_dropped_packets {
      type oc-yang:counter64;
      description
        "RX port cgm ostc2 drops counter. Counts packets that were totally dropped and will not be seen on RX side.";
    }
    leaf counters_slice4_ifg0_ifgb_rx_port_30_cgm_tc2_partially_dropped_packets {
      type oc-yang:counter64;
      description
        "RX port cgm ostc2 partial drops counter. Counts packets that were partially dropped and will be seen on RX side.";
    }
    leaf counters_slice4_ifg0_ifgb_rx_port_30_cgm_tc3_dropped_packets {
      type oc-yang:counter64;
      description
        "RX port cgm ostc3 drops counter. Counts packets that were totally dropped and will not be seen on RX side.";
    }
    leaf counters_slice4_ifg0_ifgb_rx_port_30_cgm_tc3_partially_dropped_packets {
      type oc-yang:counter64;
      description
        "RX port cgm ostc3 partial drops counter. Counts packets that were partially dropped and will be seen on RX side.";
    }
    leaf counters_slice4_ifg0_ifgb_rx_port_31_cgm_tc0_dropped_packets {
      type oc-yang:counter64;
      description
        "RX port cgm ostc0 drops counter. Counts packets that were totally dropped and will not be seen on RX side.";
    }
    leaf counters_slice4_ifg0_ifgb_rx_port_31_cgm_tc0_partially_dropped_packets {
      type oc-yang:counter64;
      description
        "RX port cgm ostc0 partial drops counter. Counts packets that were partially dropped and will be seen on RX side.";
    }
    leaf counters_slice4_ifg0_ifgb_rx_port_31_cgm_tc1_dropped_packets {
      type oc-yang:counter64;
      description
        "RX port cgm ostc1 drops counter. Counts packets that were totally dropped and will not be seen on RX side.";
    }
    leaf counters_slice4_ifg0_ifgb_rx_port_31_cgm_tc1_partially_dropped_packets {
      type oc-yang:counter64;
      description
        "RX port cgm ostc1 partial drops counter. Counts packets that were partially dropped and will be seen on RX side.";
    }
    leaf counters_slice4_ifg0_ifgb_rx_port_31_cgm_tc2_dropped_packets {
      type oc-yang:counter64;
      description
        "RX port cgm ostc2 drops counter. Counts packets that were totally dropped and will not be seen on RX side.";
    }
    leaf counters_slice4_ifg0_ifgb_rx_port_31_cgm_tc2_partially_dropped_packets {
      type oc-yang:counter64;
      description
        "RX port cgm ostc2 partial drops counter. Counts packets that were partially dropped and will be seen on RX side.";
    }
    leaf counters_slice4_ifg0_ifgb_rx_port_31_cgm_tc3_dropped_packets {
      type oc-yang:counter64;
      description
        "RX port cgm ostc3 drops counter. Counts packets that were totally dropped and will not be seen on RX side.";
    }
    leaf counters_slice4_ifg0_ifgb_rx_port_31_cgm_tc3_partially_dropped_packets {
      type oc-yang:counter64;
      description
        "RX port cgm ostc3 partial drops counter. Counts packets that were partially dropped and will be seen on RX side.";
    }
    leaf counters_slice4_ifg0_ifgb_rx_port_4_cgm_tc0_dropped_packets {
      type oc-yang:counter64;
      description
        "RX port cgm ostc0 drops counter. Counts packets that were totally dropped and will not be seen on RX side.";
    }
    leaf counters_slice4_ifg0_ifgb_rx_port_4_cgm_tc0_partially_dropped_packets {
      type oc-yang:counter64;
      description
        "RX port cgm ostc0 partial drops counter. Counts packets that were partially dropped and will be seen on RX side.";
    }
    leaf counters_slice4_ifg0_ifgb_rx_port_4_cgm_tc1_dropped_packets {
      type oc-yang:counter64;
      description
        "RX port cgm ostc1 drops counter. Counts packets that were totally dropped and will not be seen on RX side.";
    }
    leaf counters_slice4_ifg0_ifgb_rx_port_4_cgm_tc1_partially_dropped_packets {
      type oc-yang:counter64;
      description
        "RX port cgm ostc1 partial drops counter. Counts packets that were partially dropped and will be seen on RX side.";
    }
    leaf counters_slice4_ifg0_ifgb_rx_port_4_cgm_tc2_dropped_packets {
      type oc-yang:counter64;
      description
        "RX port cgm ostc2 drops counter. Counts packets that were totally dropped and will not be seen on RX side.";
    }
    leaf counters_slice4_ifg0_ifgb_rx_port_4_cgm_tc2_partially_dropped_packets {
      type oc-yang:counter64;
      description
        "RX port cgm ostc2 partial drops counter. Counts packets that were partially dropped and will be seen on RX side.";
    }
    leaf counters_slice4_ifg0_ifgb_rx_port_4_cgm_tc3_dropped_packets {
      type oc-yang:counter64;
      description
        "RX port cgm ostc3 drops counter. Counts packets that were totally dropped and will not be seen on RX side.";
    }
    leaf counters_slice4_ifg0_ifgb_rx_port_4_cgm_tc3_partially_dropped_packets {
      type oc-yang:counter64;
      description
        "RX port cgm ostc3 partial drops counter. Counts packets that were partially dropped and will be seen on RX side.";
    }
    leaf counters_slice4_ifg0_ifgb_rx_port_5_cgm_tc0_dropped_packets {
      type oc-yang:counter64;
      description
        "RX port cgm ostc0 drops counter. Counts packets that were totally dropped and will not be seen on RX side.";
    }
    leaf counters_slice4_ifg0_ifgb_rx_port_5_cgm_tc0_partially_dropped_packets {
      type oc-yang:counter64;
      description
        "RX port cgm ostc0 partial drops counter. Counts packets that were partially dropped and will be seen on RX side.";
    }
    leaf counters_slice4_ifg0_ifgb_rx_port_5_cgm_tc1_dropped_packets {
      type oc-yang:counter64;
      description
        "RX port cgm ostc1 drops counter. Counts packets that were totally dropped and will not be seen on RX side.";
    }
    leaf counters_slice4_ifg0_ifgb_rx_port_5_cgm_tc1_partially_dropped_packets {
      type oc-yang:counter64;
      description
        "RX port cgm ostc1 partial drops counter. Counts packets that were partially dropped and will be seen on RX side.";
    }
    leaf counters_slice4_ifg0_ifgb_rx_port_5_cgm_tc2_dropped_packets {
      type oc-yang:counter64;
      description
        "RX port cgm ostc2 drops counter. Counts packets that were totally dropped and will not be seen on RX side.";
    }
    leaf counters_slice4_ifg0_ifgb_rx_port_5_cgm_tc2_partially_dropped_packets {
      type oc-yang:counter64;
      description
        "RX port cgm ostc2 partial drops counter. Counts packets that were partially dropped and will be seen on RX side.";
    }
    leaf counters_slice4_ifg0_ifgb_rx_port_5_cgm_tc3_dropped_packets {
      type oc-yang:counter64;
      description
        "RX port cgm ostc3 drops counter. Counts packets that were totally dropped and will not be seen on RX side.";
    }
    leaf counters_slice4_ifg0_ifgb_rx_port_5_cgm_tc3_partially_dropped_packets {
      type oc-yang:counter64;
      description
        "RX port cgm ostc3 partial drops counter. Counts packets that were partially dropped and will be seen on RX side.";
    }
    leaf counters_slice4_ifg0_ifgb_rx_port_6_cgm_tc0_dropped_packets {
      type oc-yang:counter64;
      description
        "RX port cgm ostc0 drops counter. Counts packets that were totally dropped and will not be seen on RX side.";
    }
    leaf counters_slice4_ifg0_ifgb_rx_port_6_cgm_tc0_partially_dropped_packets {
      type oc-yang:counter64;
      description
        "RX port cgm ostc0 partial drops counter. Counts packets that were partially dropped and will be seen on RX side.";
    }
    leaf counters_slice4_ifg0_ifgb_rx_port_6_cgm_tc1_dropped_packets {
      type oc-yang:counter64;
      description
        "RX port cgm ostc1 drops counter. Counts packets that were totally dropped and will not be seen on RX side.";
    }
    leaf counters_slice4_ifg0_ifgb_rx_port_6_cgm_tc1_partially_dropped_packets {
      type oc-yang:counter64;
      description
        "RX port cgm ostc1 partial drops counter. Counts packets that were partially dropped and will be seen on RX side.";
    }
    leaf counters_slice4_ifg0_ifgb_rx_port_6_cgm_tc2_dropped_packets {
      type oc-yang:counter64;
      description
        "RX port cgm ostc2 drops counter. Counts packets that were totally dropped and will not be seen on RX side.";
    }
    leaf counters_slice4_ifg0_ifgb_rx_port_6_cgm_tc2_partially_dropped_packets {
      type oc-yang:counter64;
      description
        "RX port cgm ostc2 partial drops counter. Counts packets that were partially dropped and will be seen on RX side.";
    }
    leaf counters_slice4_ifg0_ifgb_rx_port_6_cgm_tc3_dropped_packets {
      type oc-yang:counter64;
      description
        "RX port cgm ostc3 drops counter. Counts packets that were totally dropped and will not be seen on RX side.";
    }
    leaf counters_slice4_ifg0_ifgb_rx_port_6_cgm_tc3_partially_dropped_packets {
      type oc-yang:counter64;
      description
        "RX port cgm ostc3 partial drops counter. Counts packets that were partially dropped and will be seen on RX side.";
    }
    leaf counters_slice4_ifg0_ifgb_rx_port_7_cgm_tc0_dropped_packets {
      type oc-yang:counter64;
      description
        "RX port cgm ostc0 drops counter. Counts packets that were totally dropped and will not be seen on RX side.";
    }
    leaf counters_slice4_ifg0_ifgb_rx_port_7_cgm_tc0_partially_dropped_packets {
      type oc-yang:counter64;
      description
        "RX port cgm ostc0 partial drops counter. Counts packets that were partially dropped and will be seen on RX side.";
    }
    leaf counters_slice4_ifg0_ifgb_rx_port_7_cgm_tc1_dropped_packets {
      type oc-yang:counter64;
      description
        "RX port cgm ostc1 drops counter. Counts packets that were totally dropped and will not be seen on RX side.";
    }
    leaf counters_slice4_ifg0_ifgb_rx_port_7_cgm_tc1_partially_dropped_packets {
      type oc-yang:counter64;
      description
        "RX port cgm ostc1 partial drops counter. Counts packets that were partially dropped and will be seen on RX side.";
    }
    leaf counters_slice4_ifg0_ifgb_rx_port_7_cgm_tc2_dropped_packets {
      type oc-yang:counter64;
      description
        "RX port cgm ostc2 drops counter. Counts packets that were totally dropped and will not be seen on RX side.";
    }
    leaf counters_slice4_ifg0_ifgb_rx_port_7_cgm_tc2_partially_dropped_packets {
      type oc-yang:counter64;
      description
        "RX port cgm ostc2 partial drops counter. Counts packets that were partially dropped and will be seen on RX side.";
    }
    leaf counters_slice4_ifg0_ifgb_rx_port_7_cgm_tc3_dropped_packets {
      type oc-yang:counter64;
      description
        "RX port cgm ostc3 drops counter. Counts packets that were totally dropped and will not be seen on RX side.";
    }
    leaf counters_slice4_ifg0_ifgb_rx_port_7_cgm_tc3_partially_dropped_packets {
      type oc-yang:counter64;
      description
        "RX port cgm ostc3 partial drops counter. Counts packets that were partially dropped and will be seen on RX side.";
    }
    leaf counters_slice4_ifg0_ifgb_rx_port_8_cgm_tc0_dropped_packets {
      type oc-yang:counter64;
      description
        "RX port cgm ostc0 drops counter. Counts packets that were totally dropped and will not be seen on RX side.";
    }
    leaf counters_slice4_ifg0_ifgb_rx_port_8_cgm_tc0_partially_dropped_packets {
      type oc-yang:counter64;
      description
        "RX port cgm ostc0 partial drops counter. Counts packets that were partially dropped and will be seen on RX side.";
    }
    leaf counters_slice4_ifg0_ifgb_rx_port_8_cgm_tc1_dropped_packets {
      type oc-yang:counter64;
      description
        "RX port cgm ostc1 drops counter. Counts packets that were totally dropped and will not be seen on RX side.";
    }
    leaf counters_slice4_ifg0_ifgb_rx_port_8_cgm_tc1_partially_dropped_packets {
      type oc-yang:counter64;
      description
        "RX port cgm ostc1 partial drops counter. Counts packets that were partially dropped and will be seen on RX side.";
    }
    leaf counters_slice4_ifg0_ifgb_rx_port_8_cgm_tc2_dropped_packets {
      type oc-yang:counter64;
      description
        "RX port cgm ostc2 drops counter. Counts packets that were totally dropped and will not be seen on RX side.";
    }
    leaf counters_slice4_ifg0_ifgb_rx_port_8_cgm_tc2_partially_dropped_packets {
      type oc-yang:counter64;
      description
        "RX port cgm ostc2 partial drops counter. Counts packets that were partially dropped and will be seen on RX side.";
    }
    leaf counters_slice4_ifg0_ifgb_rx_port_8_cgm_tc3_dropped_packets {
      type oc-yang:counter64;
      description
        "RX port cgm ostc3 drops counter. Counts packets that were totally dropped and will not be seen on RX side.";
    }
    leaf counters_slice4_ifg0_ifgb_rx_port_8_cgm_tc3_partially_dropped_packets {
      type oc-yang:counter64;
      description
        "RX port cgm ostc3 partial drops counter. Counts packets that were partially dropped and will be seen on RX side.";
    }
    leaf counters_slice4_ifg0_ifgb_rx_port_9_cgm_tc0_dropped_packets {
      type oc-yang:counter64;
      description
        "RX port cgm ostc0 drops counter. Counts packets that were totally dropped and will not be seen on RX side.";
    }
    leaf counters_slice4_ifg0_ifgb_rx_port_9_cgm_tc0_partially_dropped_packets {
      type oc-yang:counter64;
      description
        "RX port cgm ostc0 partial drops counter. Counts packets that were partially dropped and will be seen on RX side.";
    }
    leaf counters_slice4_ifg0_ifgb_rx_port_9_cgm_tc1_dropped_packets {
      type oc-yang:counter64;
      description
        "RX port cgm ostc1 drops counter. Counts packets that were totally dropped and will not be seen on RX side.";
    }
    leaf counters_slice4_ifg0_ifgb_rx_port_9_cgm_tc1_partially_dropped_packets {
      type oc-yang:counter64;
      description
        "RX port cgm ostc1 partial drops counter. Counts packets that were partially dropped and will be seen on RX side.";
    }
    leaf counters_slice4_ifg0_ifgb_rx_port_9_cgm_tc2_dropped_packets {
      type oc-yang:counter64;
      description
        "RX port cgm ostc2 drops counter. Counts packets that were totally dropped and will not be seen on RX side.";
    }
    leaf counters_slice4_ifg0_ifgb_rx_port_9_cgm_tc2_partially_dropped_packets {
      type oc-yang:counter64;
      description
        "RX port cgm ostc2 partial drops counter. Counts packets that were partially dropped and will be seen on RX side.";
    }
    leaf counters_slice4_ifg0_ifgb_rx_port_9_cgm_tc3_dropped_packets {
      type oc-yang:counter64;
      description
        "RX port cgm ostc3 drops counter. Counts packets that were totally dropped and will not be seen on RX side.";
    }
    leaf counters_slice4_ifg0_ifgb_rx_port_9_cgm_tc3_partially_dropped_packets {
      type oc-yang:counter64;
      description
        "RX port cgm ostc3 partial drops counter. Counts packets that were partially dropped and will be seen on RX side.";
    }
    leaf counters_slice4_ifg1_ifgb_rx_port_0_cgm_tc0_dropped_packets {
      type oc-yang:counter64;
      description
        "RX port cgm ostc0 drops counter. Counts packets that were totally dropped and will not be seen on RX side.";
    }
    leaf counters_slice4_ifg1_ifgb_rx_port_0_cgm_tc0_partially_dropped_packets {
      type oc-yang:counter64;
      description
        "RX port cgm ostc0 partial drops counter. Counts packets that were partially dropped and will be seen on RX side.";
    }
    leaf counters_slice4_ifg1_ifgb_rx_port_0_cgm_tc1_dropped_packets {
      type oc-yang:counter64;
      description
        "RX port cgm ostc1 drops counter. Counts packets that were totally dropped and will not be seen on RX side.";
    }
    leaf counters_slice4_ifg1_ifgb_rx_port_0_cgm_tc1_partially_dropped_packets {
      type oc-yang:counter64;
      description
        "RX port cgm ostc1 partial drops counter. Counts packets that were partially dropped and will be seen on RX side.";
    }
    leaf counters_slice4_ifg1_ifgb_rx_port_0_cgm_tc2_dropped_packets {
      type oc-yang:counter64;
      description
        "RX port cgm ostc2 drops counter. Counts packets that were totally dropped and will not be seen on RX side.";
    }
    leaf counters_slice4_ifg1_ifgb_rx_port_0_cgm_tc2_partially_dropped_packets {
      type oc-yang:counter64;
      description
        "RX port cgm ostc2 partial drops counter. Counts packets that were partially dropped and will be seen on RX side.";
    }
    leaf counters_slice4_ifg1_ifgb_rx_port_0_cgm_tc3_dropped_packets {
      type oc-yang:counter64;
      description
        "RX port cgm ostc3 drops counter. Counts packets that were totally dropped and will not be seen on RX side.";
    }
    leaf counters_slice4_ifg1_ifgb_rx_port_0_cgm_tc3_partially_dropped_packets {
      type oc-yang:counter64;
      description
        "RX port cgm ostc3 partial drops counter. Counts packets that were partially dropped and will be seen on RX side.";
    }
    leaf counters_slice4_ifg1_ifgb_rx_port_1_cgm_tc0_dropped_packets {
      type oc-yang:counter64;
      description
        "RX port cgm ostc0 drops counter. Counts packets that were totally dropped and will not be seen on RX side.";
    }
    leaf counters_slice4_ifg1_ifgb_rx_port_1_cgm_tc0_partially_dropped_packets {
      type oc-yang:counter64;
      description
        "RX port cgm ostc0 partial drops counter. Counts packets that were partially dropped and will be seen on RX side.";
    }
    leaf counters_slice4_ifg1_ifgb_rx_port_1_cgm_tc1_dropped_packets {
      type oc-yang:counter64;
      description
        "RX port cgm ostc1 drops counter. Counts packets that were totally dropped and will not be seen on RX side.";
    }
    leaf counters_slice4_ifg1_ifgb_rx_port_1_cgm_tc1_partially_dropped_packets {
      type oc-yang:counter64;
      description
        "RX port cgm ostc1 partial drops counter. Counts packets that were partially dropped and will be seen on RX side.";
    }
    leaf counters_slice4_ifg1_ifgb_rx_port_1_cgm_tc2_dropped_packets {
      type oc-yang:counter64;
      description
        "RX port cgm ostc2 drops counter. Counts packets that were totally dropped and will not be seen on RX side.";
    }
    leaf counters_slice4_ifg1_ifgb_rx_port_1_cgm_tc2_partially_dropped_packets {
      type oc-yang:counter64;
      description
        "RX port cgm ostc2 partial drops counter. Counts packets that were partially dropped and will be seen on RX side.";
    }
    leaf counters_slice4_ifg1_ifgb_rx_port_1_cgm_tc3_dropped_packets {
      type oc-yang:counter64;
      description
        "RX port cgm ostc3 drops counter. Counts packets that were totally dropped and will not be seen on RX side.";
    }
    leaf counters_slice4_ifg1_ifgb_rx_port_1_cgm_tc3_partially_dropped_packets {
      type oc-yang:counter64;
      description
        "RX port cgm ostc3 partial drops counter. Counts packets that were partially dropped and will be seen on RX side.";
    }
    leaf counters_slice4_ifg1_ifgb_rx_port_10_cgm_tc0_dropped_packets {
      type oc-yang:counter64;
      description
        "RX port cgm ostc0 drops counter. Counts packets that were totally dropped and will not be seen on RX side.";
    }
    leaf counters_slice4_ifg1_ifgb_rx_port_10_cgm_tc0_partially_dropped_packets {
      type oc-yang:counter64;
      description
        "RX port cgm ostc0 partial drops counter. Counts packets that were partially dropped and will be seen on RX side.";
    }
    leaf counters_slice4_ifg1_ifgb_rx_port_10_cgm_tc1_dropped_packets {
      type oc-yang:counter64;
      description
        "RX port cgm ostc1 drops counter. Counts packets that were totally dropped and will not be seen on RX side.";
    }
    leaf counters_slice4_ifg1_ifgb_rx_port_10_cgm_tc1_partially_dropped_packets {
      type oc-yang:counter64;
      description
        "RX port cgm ostc1 partial drops counter. Counts packets that were partially dropped and will be seen on RX side.";
    }
    leaf counters_slice4_ifg1_ifgb_rx_port_10_cgm_tc2_dropped_packets {
      type oc-yang:counter64;
      description
        "RX port cgm ostc2 drops counter. Counts packets that were totally dropped and will not be seen on RX side.";
    }
    leaf counters_slice4_ifg1_ifgb_rx_port_10_cgm_tc2_partially_dropped_packets {
      type oc-yang:counter64;
      description
        "RX port cgm ostc2 partial drops counter. Counts packets that were partially dropped and will be seen on RX side.";
    }
    leaf counters_slice4_ifg1_ifgb_rx_port_10_cgm_tc3_dropped_packets {
      type oc-yang:counter64;
      description
        "RX port cgm ostc3 drops counter. Counts packets that were totally dropped and will not be seen on RX side.";
    }
    leaf counters_slice4_ifg1_ifgb_rx_port_10_cgm_tc3_partially_dropped_packets {
      type oc-yang:counter64;
      description
        "RX port cgm ostc3 partial drops counter. Counts packets that were partially dropped and will be seen on RX side.";
    }
    leaf counters_slice4_ifg1_ifgb_rx_port_11_cgm_tc0_dropped_packets {
      type oc-yang:counter64;
      description
        "RX port cgm ostc0 drops counter. Counts packets that were totally dropped and will not be seen on RX side.";
    }
    leaf counters_slice4_ifg1_ifgb_rx_port_11_cgm_tc0_partially_dropped_packets {
      type oc-yang:counter64;
      description
        "RX port cgm ostc0 partial drops counter. Counts packets that were partially dropped and will be seen on RX side.";
    }
    leaf counters_slice4_ifg1_ifgb_rx_port_11_cgm_tc1_dropped_packets {
      type oc-yang:counter64;
      description
        "RX port cgm ostc1 drops counter. Counts packets that were totally dropped and will not be seen on RX side.";
    }
    leaf counters_slice4_ifg1_ifgb_rx_port_11_cgm_tc1_partially_dropped_packets {
      type oc-yang:counter64;
      description
        "RX port cgm ostc1 partial drops counter. Counts packets that were partially dropped and will be seen on RX side.";
    }
    leaf counters_slice4_ifg1_ifgb_rx_port_11_cgm_tc2_dropped_packets {
      type oc-yang:counter64;
      description
        "RX port cgm ostc2 drops counter. Counts packets that were totally dropped and will not be seen on RX side.";
    }
    leaf counters_slice4_ifg1_ifgb_rx_port_11_cgm_tc2_partially_dropped_packets {
      type oc-yang:counter64;
      description
        "RX port cgm ostc2 partial drops counter. Counts packets that were partially dropped and will be seen on RX side.";
    }
    leaf counters_slice4_ifg1_ifgb_rx_port_11_cgm_tc3_dropped_packets {
      type oc-yang:counter64;
      description
        "RX port cgm ostc3 drops counter. Counts packets that were totally dropped and will not be seen on RX side.";
    }
    leaf counters_slice4_ifg1_ifgb_rx_port_11_cgm_tc3_partially_dropped_packets {
      type oc-yang:counter64;
      description
        "RX port cgm ostc3 partial drops counter. Counts packets that were partially dropped and will be seen on RX side.";
    }
    leaf counters_slice4_ifg1_ifgb_rx_port_12_cgm_tc0_dropped_packets {
      type oc-yang:counter64;
      description
        "RX port cgm ostc0 drops counter. Counts packets that were totally dropped and will not be seen on RX side.";
    }
    leaf counters_slice4_ifg1_ifgb_rx_port_12_cgm_tc0_partially_dropped_packets {
      type oc-yang:counter64;
      description
        "RX port cgm ostc0 partial drops counter. Counts packets that were partially dropped and will be seen on RX side.";
    }
    leaf counters_slice4_ifg1_ifgb_rx_port_12_cgm_tc1_dropped_packets {
      type oc-yang:counter64;
      description
        "RX port cgm ostc1 drops counter. Counts packets that were totally dropped and will not be seen on RX side.";
    }
    leaf counters_slice4_ifg1_ifgb_rx_port_12_cgm_tc1_partially_dropped_packets {
      type oc-yang:counter64;
      description
        "RX port cgm ostc1 partial drops counter. Counts packets that were partially dropped and will be seen on RX side.";
    }
    leaf counters_slice4_ifg1_ifgb_rx_port_12_cgm_tc2_dropped_packets {
      type oc-yang:counter64;
      description
        "RX port cgm ostc2 drops counter. Counts packets that were totally dropped and will not be seen on RX side.";
    }
    leaf counters_slice4_ifg1_ifgb_rx_port_12_cgm_tc2_partially_dropped_packets {
      type oc-yang:counter64;
      description
        "RX port cgm ostc2 partial drops counter. Counts packets that were partially dropped and will be seen on RX side.";
    }
    leaf counters_slice4_ifg1_ifgb_rx_port_12_cgm_tc3_dropped_packets {
      type oc-yang:counter64;
      description
        "RX port cgm ostc3 drops counter. Counts packets that were totally dropped and will not be seen on RX side.";
    }
    leaf counters_slice4_ifg1_ifgb_rx_port_12_cgm_tc3_partially_dropped_packets {
      type oc-yang:counter64;
      description
        "RX port cgm ostc3 partial drops counter. Counts packets that were partially dropped and will be seen on RX side.";
    }
    leaf counters_slice4_ifg1_ifgb_rx_port_13_cgm_tc0_dropped_packets {
      type oc-yang:counter64;
      description
        "RX port cgm ostc0 drops counter. Counts packets that were totally dropped and will not be seen on RX side.";
    }
    leaf counters_slice4_ifg1_ifgb_rx_port_13_cgm_tc0_partially_dropped_packets {
      type oc-yang:counter64;
      description
        "RX port cgm ostc0 partial drops counter. Counts packets that were partially dropped and will be seen on RX side.";
    }
    leaf counters_slice4_ifg1_ifgb_rx_port_13_cgm_tc1_dropped_packets {
      type oc-yang:counter64;
      description
        "RX port cgm ostc1 drops counter. Counts packets that were totally dropped and will not be seen on RX side.";
    }
    leaf counters_slice4_ifg1_ifgb_rx_port_13_cgm_tc1_partially_dropped_packets {
      type oc-yang:counter64;
      description
        "RX port cgm ostc1 partial drops counter. Counts packets that were partially dropped and will be seen on RX side.";
    }
    leaf counters_slice4_ifg1_ifgb_rx_port_13_cgm_tc2_dropped_packets {
      type oc-yang:counter64;
      description
        "RX port cgm ostc2 drops counter. Counts packets that were totally dropped and will not be seen on RX side.";
    }
    leaf counters_slice4_ifg1_ifgb_rx_port_13_cgm_tc2_partially_dropped_packets {
      type oc-yang:counter64;
      description
        "RX port cgm ostc2 partial drops counter. Counts packets that were partially dropped and will be seen on RX side.";
    }
    leaf counters_slice4_ifg1_ifgb_rx_port_13_cgm_tc3_dropped_packets {
      type oc-yang:counter64;
      description
        "RX port cgm ostc3 drops counter. Counts packets that were totally dropped and will not be seen on RX side.";
    }
    leaf counters_slice4_ifg1_ifgb_rx_port_13_cgm_tc3_partially_dropped_packets {
      type oc-yang:counter64;
      description
        "RX port cgm ostc3 partial drops counter. Counts packets that were partially dropped and will be seen on RX side.";
    }
    leaf counters_slice4_ifg1_ifgb_rx_port_14_cgm_tc0_dropped_packets {
      type oc-yang:counter64;
      description
        "RX port cgm ostc0 drops counter. Counts packets that were totally dropped and will not be seen on RX side.";
    }
    leaf counters_slice4_ifg1_ifgb_rx_port_14_cgm_tc0_partially_dropped_packets {
      type oc-yang:counter64;
      description
        "RX port cgm ostc0 partial drops counter. Counts packets that were partially dropped and will be seen on RX side.";
    }
    leaf counters_slice4_ifg1_ifgb_rx_port_14_cgm_tc1_dropped_packets {
      type oc-yang:counter64;
      description
        "RX port cgm ostc1 drops counter. Counts packets that were totally dropped and will not be seen on RX side.";
    }
    leaf counters_slice4_ifg1_ifgb_rx_port_14_cgm_tc1_partially_dropped_packets {
      type oc-yang:counter64;
      description
        "RX port cgm ostc1 partial drops counter. Counts packets that were partially dropped and will be seen on RX side.";
    }
    leaf counters_slice4_ifg1_ifgb_rx_port_14_cgm_tc2_dropped_packets {
      type oc-yang:counter64;
      description
        "RX port cgm ostc2 drops counter. Counts packets that were totally dropped and will not be seen on RX side.";
    }
    leaf counters_slice4_ifg1_ifgb_rx_port_14_cgm_tc2_partially_dropped_packets {
      type oc-yang:counter64;
      description
        "RX port cgm ostc2 partial drops counter. Counts packets that were partially dropped and will be seen on RX side.";
    }
    leaf counters_slice4_ifg1_ifgb_rx_port_14_cgm_tc3_dropped_packets {
      type oc-yang:counter64;
      description
        "RX port cgm ostc3 drops counter. Counts packets that were totally dropped and will not be seen on RX side.";
    }
    leaf counters_slice4_ifg1_ifgb_rx_port_14_cgm_tc3_partially_dropped_packets {
      type oc-yang:counter64;
      description
        "RX port cgm ostc3 partial drops counter. Counts packets that were partially dropped and will be seen on RX side.";
    }
    leaf counters_slice4_ifg1_ifgb_rx_port_15_cgm_tc0_dropped_packets {
      type oc-yang:counter64;
      description
        "RX port cgm ostc0 drops counter. Counts packets that were totally dropped and will not be seen on RX side.";
    }
    leaf counters_slice4_ifg1_ifgb_rx_port_15_cgm_tc0_partially_dropped_packets {
      type oc-yang:counter64;
      description
        "RX port cgm ostc0 partial drops counter. Counts packets that were partially dropped and will be seen on RX side.";
    }
    leaf counters_slice4_ifg1_ifgb_rx_port_15_cgm_tc1_dropped_packets {
      type oc-yang:counter64;
      description
        "RX port cgm ostc1 drops counter. Counts packets that were totally dropped and will not be seen on RX side.";
    }
    leaf counters_slice4_ifg1_ifgb_rx_port_15_cgm_tc1_partially_dropped_packets {
      type oc-yang:counter64;
      description
        "RX port cgm ostc1 partial drops counter. Counts packets that were partially dropped and will be seen on RX side.";
    }
    leaf counters_slice4_ifg1_ifgb_rx_port_15_cgm_tc2_dropped_packets {
      type oc-yang:counter64;
      description
        "RX port cgm ostc2 drops counter. Counts packets that were totally dropped and will not be seen on RX side.";
    }
    leaf counters_slice4_ifg1_ifgb_rx_port_15_cgm_tc2_partially_dropped_packets {
      type oc-yang:counter64;
      description
        "RX port cgm ostc2 partial drops counter. Counts packets that were partially dropped and will be seen on RX side.";
    }
    leaf counters_slice4_ifg1_ifgb_rx_port_15_cgm_tc3_dropped_packets {
      type oc-yang:counter64;
      description
        "RX port cgm ostc3 drops counter. Counts packets that were totally dropped and will not be seen on RX side.";
    }
    leaf counters_slice4_ifg1_ifgb_rx_port_15_cgm_tc3_partially_dropped_packets {
      type oc-yang:counter64;
      description
        "RX port cgm ostc3 partial drops counter. Counts packets that were partially dropped and will be seen on RX side.";
    }
    leaf counters_slice4_ifg1_ifgb_rx_port_16_cgm_tc0_dropped_packets {
      type oc-yang:counter64;
      description
        "RX port cgm ostc0 drops counter. Counts packets that were totally dropped and will not be seen on RX side.";
    }
    leaf counters_slice4_ifg1_ifgb_rx_port_16_cgm_tc0_partially_dropped_packets {
      type oc-yang:counter64;
      description
        "RX port cgm ostc0 partial drops counter. Counts packets that were partially dropped and will be seen on RX side.";
    }
    leaf counters_slice4_ifg1_ifgb_rx_port_16_cgm_tc1_dropped_packets {
      type oc-yang:counter64;
      description
        "RX port cgm ostc1 drops counter. Counts packets that were totally dropped and will not be seen on RX side.";
    }
    leaf counters_slice4_ifg1_ifgb_rx_port_16_cgm_tc1_partially_dropped_packets {
      type oc-yang:counter64;
      description
        "RX port cgm ostc1 partial drops counter. Counts packets that were partially dropped and will be seen on RX side.";
    }
    leaf counters_slice4_ifg1_ifgb_rx_port_16_cgm_tc2_dropped_packets {
      type oc-yang:counter64;
      description
        "RX port cgm ostc2 drops counter. Counts packets that were totally dropped and will not be seen on RX side.";
    }
    leaf counters_slice4_ifg1_ifgb_rx_port_16_cgm_tc2_partially_dropped_packets {
      type oc-yang:counter64;
      description
        "RX port cgm ostc2 partial drops counter. Counts packets that were partially dropped and will be seen on RX side.";
    }
    leaf counters_slice4_ifg1_ifgb_rx_port_16_cgm_tc3_dropped_packets {
      type oc-yang:counter64;
      description
        "RX port cgm ostc3 drops counter. Counts packets that were totally dropped and will not be seen on RX side.";
    }
    leaf counters_slice4_ifg1_ifgb_rx_port_16_cgm_tc3_partially_dropped_packets {
      type oc-yang:counter64;
      description
        "RX port cgm ostc3 partial drops counter. Counts packets that were partially dropped and will be seen on RX side.";
    }
    leaf counters_slice4_ifg1_ifgb_rx_port_17_cgm_tc0_dropped_packets {
      type oc-yang:counter64;
      description
        "RX port cgm ostc0 drops counter. Counts packets that were totally dropped and will not be seen on RX side.";
    }
    leaf counters_slice4_ifg1_ifgb_rx_port_17_cgm_tc0_partially_dropped_packets {
      type oc-yang:counter64;
      description
        "RX port cgm ostc0 partial drops counter. Counts packets that were partially dropped and will be seen on RX side.";
    }
    leaf counters_slice4_ifg1_ifgb_rx_port_17_cgm_tc1_dropped_packets {
      type oc-yang:counter64;
      description
        "RX port cgm ostc1 drops counter. Counts packets that were totally dropped and will not be seen on RX side.";
    }
    leaf counters_slice4_ifg1_ifgb_rx_port_17_cgm_tc1_partially_dropped_packets {
      type oc-yang:counter64;
      description
        "RX port cgm ostc1 partial drops counter. Counts packets that were partially dropped and will be seen on RX side.";
    }
    leaf counters_slice4_ifg1_ifgb_rx_port_17_cgm_tc2_dropped_packets {
      type oc-yang:counter64;
      description
        "RX port cgm ostc2 drops counter. Counts packets that were totally dropped and will not be seen on RX side.";
    }
    leaf counters_slice4_ifg1_ifgb_rx_port_17_cgm_tc2_partially_dropped_packets {
      type oc-yang:counter64;
      description
        "RX port cgm ostc2 partial drops counter. Counts packets that were partially dropped and will be seen on RX side.";
    }
    leaf counters_slice4_ifg1_ifgb_rx_port_17_cgm_tc3_dropped_packets {
      type oc-yang:counter64;
      description
        "RX port cgm ostc3 drops counter. Counts packets that were totally dropped and will not be seen on RX side.";
    }
    leaf counters_slice4_ifg1_ifgb_rx_port_17_cgm_tc3_partially_dropped_packets {
      type oc-yang:counter64;
      description
        "RX port cgm ostc3 partial drops counter. Counts packets that were partially dropped and will be seen on RX side.";
    }
    leaf counters_slice4_ifg1_ifgb_rx_port_18_cgm_tc0_dropped_packets {
      type oc-yang:counter64;
      description
        "RX port cgm ostc0 drops counter. Counts packets that were totally dropped and will not be seen on RX side.";
    }
    leaf counters_slice4_ifg1_ifgb_rx_port_18_cgm_tc0_partially_dropped_packets {
      type oc-yang:counter64;
      description
        "RX port cgm ostc0 partial drops counter. Counts packets that were partially dropped and will be seen on RX side.";
    }
    leaf counters_slice4_ifg1_ifgb_rx_port_18_cgm_tc1_dropped_packets {
      type oc-yang:counter64;
      description
        "RX port cgm ostc1 drops counter. Counts packets that were totally dropped and will not be seen on RX side.";
    }
    leaf counters_slice4_ifg1_ifgb_rx_port_18_cgm_tc1_partially_dropped_packets {
      type oc-yang:counter64;
      description
        "RX port cgm ostc1 partial drops counter. Counts packets that were partially dropped and will be seen on RX side.";
    }
    leaf counters_slice4_ifg1_ifgb_rx_port_18_cgm_tc2_dropped_packets {
      type oc-yang:counter64;
      description
        "RX port cgm ostc2 drops counter. Counts packets that were totally dropped and will not be seen on RX side.";
    }
    leaf counters_slice4_ifg1_ifgb_rx_port_18_cgm_tc2_partially_dropped_packets {
      type oc-yang:counter64;
      description
        "RX port cgm ostc2 partial drops counter. Counts packets that were partially dropped and will be seen on RX side.";
    }
    leaf counters_slice4_ifg1_ifgb_rx_port_18_cgm_tc3_dropped_packets {
      type oc-yang:counter64;
      description
        "RX port cgm ostc3 drops counter. Counts packets that were totally dropped and will not be seen on RX side.";
    }
    leaf counters_slice4_ifg1_ifgb_rx_port_18_cgm_tc3_partially_dropped_packets {
      type oc-yang:counter64;
      description
        "RX port cgm ostc3 partial drops counter. Counts packets that were partially dropped and will be seen on RX side.";
    }
    leaf counters_slice4_ifg1_ifgb_rx_port_19_cgm_tc0_dropped_packets {
      type oc-yang:counter64;
      description
        "RX port cgm ostc0 drops counter. Counts packets that were totally dropped and will not be seen on RX side.";
    }
    leaf counters_slice4_ifg1_ifgb_rx_port_19_cgm_tc0_partially_dropped_packets {
      type oc-yang:counter64;
      description
        "RX port cgm ostc0 partial drops counter. Counts packets that were partially dropped and will be seen on RX side.";
    }
    leaf counters_slice4_ifg1_ifgb_rx_port_19_cgm_tc1_dropped_packets {
      type oc-yang:counter64;
      description
        "RX port cgm ostc1 drops counter. Counts packets that were totally dropped and will not be seen on RX side.";
    }
    leaf counters_slice4_ifg1_ifgb_rx_port_19_cgm_tc1_partially_dropped_packets {
      type oc-yang:counter64;
      description
        "RX port cgm ostc1 partial drops counter. Counts packets that were partially dropped and will be seen on RX side.";
    }
    leaf counters_slice4_ifg1_ifgb_rx_port_19_cgm_tc2_dropped_packets {
      type oc-yang:counter64;
      description
        "RX port cgm ostc2 drops counter. Counts packets that were totally dropped and will not be seen on RX side.";
    }
    leaf counters_slice4_ifg1_ifgb_rx_port_19_cgm_tc2_partially_dropped_packets {
      type oc-yang:counter64;
      description
        "RX port cgm ostc2 partial drops counter. Counts packets that were partially dropped and will be seen on RX side.";
    }
    leaf counters_slice4_ifg1_ifgb_rx_port_19_cgm_tc3_dropped_packets {
      type oc-yang:counter64;
      description
        "RX port cgm ostc3 drops counter. Counts packets that were totally dropped and will not be seen on RX side.";
    }
    leaf counters_slice4_ifg1_ifgb_rx_port_19_cgm_tc3_partially_dropped_packets {
      type oc-yang:counter64;
      description
        "RX port cgm ostc3 partial drops counter. Counts packets that were partially dropped and will be seen on RX side.";
    }
    leaf counters_slice4_ifg1_ifgb_rx_port_2_cgm_tc0_dropped_packets {
      type oc-yang:counter64;
      description
        "RX port cgm ostc0 drops counter. Counts packets that were totally dropped and will not be seen on RX side.";
    }
    leaf counters_slice4_ifg1_ifgb_rx_port_2_cgm_tc0_partially_dropped_packets {
      type oc-yang:counter64;
      description
        "RX port cgm ostc0 partial drops counter. Counts packets that were partially dropped and will be seen on RX side.";
    }
    leaf counters_slice4_ifg1_ifgb_rx_port_2_cgm_tc1_dropped_packets {
      type oc-yang:counter64;
      description
        "RX port cgm ostc1 drops counter. Counts packets that were totally dropped and will not be seen on RX side.";
    }
    leaf counters_slice4_ifg1_ifgb_rx_port_2_cgm_tc1_partially_dropped_packets {
      type oc-yang:counter64;
      description
        "RX port cgm ostc1 partial drops counter. Counts packets that were partially dropped and will be seen on RX side.";
    }
    leaf counters_slice4_ifg1_ifgb_rx_port_2_cgm_tc2_dropped_packets {
      type oc-yang:counter64;
      description
        "RX port cgm ostc2 drops counter. Counts packets that were totally dropped and will not be seen on RX side.";
    }
    leaf counters_slice4_ifg1_ifgb_rx_port_2_cgm_tc2_partially_dropped_packets {
      type oc-yang:counter64;
      description
        "RX port cgm ostc2 partial drops counter. Counts packets that were partially dropped and will be seen on RX side.";
    }
    leaf counters_slice4_ifg1_ifgb_rx_port_2_cgm_tc3_dropped_packets {
      type oc-yang:counter64;
      description
        "RX port cgm ostc3 drops counter. Counts packets that were totally dropped and will not be seen on RX side.";
    }
    leaf counters_slice4_ifg1_ifgb_rx_port_2_cgm_tc3_partially_dropped_packets {
      type oc-yang:counter64;
      description
        "RX port cgm ostc3 partial drops counter. Counts packets that were partially dropped and will be seen on RX side.";
    }
    leaf counters_slice4_ifg1_ifgb_rx_port_20_cgm_tc0_dropped_packets {
      type oc-yang:counter64;
      description
        "RX port cgm ostc0 drops counter. Counts packets that were totally dropped and will not be seen on RX side.";
    }
    leaf counters_slice4_ifg1_ifgb_rx_port_20_cgm_tc0_partially_dropped_packets {
      type oc-yang:counter64;
      description
        "RX port cgm ostc0 partial drops counter. Counts packets that were partially dropped and will be seen on RX side.";
    }
    leaf counters_slice4_ifg1_ifgb_rx_port_20_cgm_tc1_dropped_packets {
      type oc-yang:counter64;
      description
        "RX port cgm ostc1 drops counter. Counts packets that were totally dropped and will not be seen on RX side.";
    }
    leaf counters_slice4_ifg1_ifgb_rx_port_20_cgm_tc1_partially_dropped_packets {
      type oc-yang:counter64;
      description
        "RX port cgm ostc1 partial drops counter. Counts packets that were partially dropped and will be seen on RX side.";
    }
    leaf counters_slice4_ifg1_ifgb_rx_port_20_cgm_tc2_dropped_packets {
      type oc-yang:counter64;
      description
        "RX port cgm ostc2 drops counter. Counts packets that were totally dropped and will not be seen on RX side.";
    }
    leaf counters_slice4_ifg1_ifgb_rx_port_20_cgm_tc2_partially_dropped_packets {
      type oc-yang:counter64;
      description
        "RX port cgm ostc2 partial drops counter. Counts packets that were partially dropped and will be seen on RX side.";
    }
    leaf counters_slice4_ifg1_ifgb_rx_port_20_cgm_tc3_dropped_packets {
      type oc-yang:counter64;
      description
        "RX port cgm ostc3 drops counter. Counts packets that were totally dropped and will not be seen on RX side.";
    }
    leaf counters_slice4_ifg1_ifgb_rx_port_20_cgm_tc3_partially_dropped_packets {
      type oc-yang:counter64;
      description
        "RX port cgm ostc3 partial drops counter. Counts packets that were partially dropped and will be seen on RX side.";
    }
    leaf counters_slice4_ifg1_ifgb_rx_port_21_cgm_tc0_dropped_packets {
      type oc-yang:counter64;
      description
        "RX port cgm ostc0 drops counter. Counts packets that were totally dropped and will not be seen on RX side.";
    }
    leaf counters_slice4_ifg1_ifgb_rx_port_21_cgm_tc0_partially_dropped_packets {
      type oc-yang:counter64;
      description
        "RX port cgm ostc0 partial drops counter. Counts packets that were partially dropped and will be seen on RX side.";
    }
    leaf counters_slice4_ifg1_ifgb_rx_port_21_cgm_tc1_dropped_packets {
      type oc-yang:counter64;
      description
        "RX port cgm ostc1 drops counter. Counts packets that were totally dropped and will not be seen on RX side.";
    }
    leaf counters_slice4_ifg1_ifgb_rx_port_21_cgm_tc1_partially_dropped_packets {
      type oc-yang:counter64;
      description
        "RX port cgm ostc1 partial drops counter. Counts packets that were partially dropped and will be seen on RX side.";
    }
    leaf counters_slice4_ifg1_ifgb_rx_port_21_cgm_tc2_dropped_packets {
      type oc-yang:counter64;
      description
        "RX port cgm ostc2 drops counter. Counts packets that were totally dropped and will not be seen on RX side.";
    }
    leaf counters_slice4_ifg1_ifgb_rx_port_21_cgm_tc2_partially_dropped_packets {
      type oc-yang:counter64;
      description
        "RX port cgm ostc2 partial drops counter. Counts packets that were partially dropped and will be seen on RX side.";
    }
    leaf counters_slice4_ifg1_ifgb_rx_port_21_cgm_tc3_dropped_packets {
      type oc-yang:counter64;
      description
        "RX port cgm ostc3 drops counter. Counts packets that were totally dropped and will not be seen on RX side.";
    }
    leaf counters_slice4_ifg1_ifgb_rx_port_21_cgm_tc3_partially_dropped_packets {
      type oc-yang:counter64;
      description
        "RX port cgm ostc3 partial drops counter. Counts packets that were partially dropped and will be seen on RX side.";
    }
    leaf counters_slice4_ifg1_ifgb_rx_port_22_cgm_tc0_dropped_packets {
      type oc-yang:counter64;
      description
        "RX port cgm ostc0 drops counter. Counts packets that were totally dropped and will not be seen on RX side.";
    }
    leaf counters_slice4_ifg1_ifgb_rx_port_22_cgm_tc0_partially_dropped_packets {
      type oc-yang:counter64;
      description
        "RX port cgm ostc0 partial drops counter. Counts packets that were partially dropped and will be seen on RX side.";
    }
    leaf counters_slice4_ifg1_ifgb_rx_port_22_cgm_tc1_dropped_packets {
      type oc-yang:counter64;
      description
        "RX port cgm ostc1 drops counter. Counts packets that were totally dropped and will not be seen on RX side.";
    }
    leaf counters_slice4_ifg1_ifgb_rx_port_22_cgm_tc1_partially_dropped_packets {
      type oc-yang:counter64;
      description
        "RX port cgm ostc1 partial drops counter. Counts packets that were partially dropped and will be seen on RX side.";
    }
    leaf counters_slice4_ifg1_ifgb_rx_port_22_cgm_tc2_dropped_packets {
      type oc-yang:counter64;
      description
        "RX port cgm ostc2 drops counter. Counts packets that were totally dropped and will not be seen on RX side.";
    }
    leaf counters_slice4_ifg1_ifgb_rx_port_22_cgm_tc2_partially_dropped_packets {
      type oc-yang:counter64;
      description
        "RX port cgm ostc2 partial drops counter. Counts packets that were partially dropped and will be seen on RX side.";
    }
    leaf counters_slice4_ifg1_ifgb_rx_port_22_cgm_tc3_dropped_packets {
      type oc-yang:counter64;
      description
        "RX port cgm ostc3 drops counter. Counts packets that were totally dropped and will not be seen on RX side.";
    }
    leaf counters_slice4_ifg1_ifgb_rx_port_22_cgm_tc3_partially_dropped_packets {
      type oc-yang:counter64;
      description
        "RX port cgm ostc3 partial drops counter. Counts packets that were partially dropped and will be seen on RX side.";
    }
    leaf counters_slice4_ifg1_ifgb_rx_port_23_cgm_tc0_dropped_packets {
      type oc-yang:counter64;
      description
        "RX port cgm ostc0 drops counter. Counts packets that were totally dropped and will not be seen on RX side.";
    }
    leaf counters_slice4_ifg1_ifgb_rx_port_23_cgm_tc0_partially_dropped_packets {
      type oc-yang:counter64;
      description
        "RX port cgm ostc0 partial drops counter. Counts packets that were partially dropped and will be seen on RX side.";
    }
    leaf counters_slice4_ifg1_ifgb_rx_port_23_cgm_tc1_dropped_packets {
      type oc-yang:counter64;
      description
        "RX port cgm ostc1 drops counter. Counts packets that were totally dropped and will not be seen on RX side.";
    }
    leaf counters_slice4_ifg1_ifgb_rx_port_23_cgm_tc1_partially_dropped_packets {
      type oc-yang:counter64;
      description
        "RX port cgm ostc1 partial drops counter. Counts packets that were partially dropped and will be seen on RX side.";
    }
    leaf counters_slice4_ifg1_ifgb_rx_port_23_cgm_tc2_dropped_packets {
      type oc-yang:counter64;
      description
        "RX port cgm ostc2 drops counter. Counts packets that were totally dropped and will not be seen on RX side.";
    }
    leaf counters_slice4_ifg1_ifgb_rx_port_23_cgm_tc2_partially_dropped_packets {
      type oc-yang:counter64;
      description
        "RX port cgm ostc2 partial drops counter. Counts packets that were partially dropped and will be seen on RX side.";
    }
    leaf counters_slice4_ifg1_ifgb_rx_port_23_cgm_tc3_dropped_packets {
      type oc-yang:counter64;
      description
        "RX port cgm ostc3 drops counter. Counts packets that were totally dropped and will not be seen on RX side.";
    }
    leaf counters_slice4_ifg1_ifgb_rx_port_23_cgm_tc3_partially_dropped_packets {
      type oc-yang:counter64;
      description
        "RX port cgm ostc3 partial drops counter. Counts packets that were partially dropped and will be seen on RX side.";
    }
    leaf counters_slice4_ifg1_ifgb_rx_port_24_cgm_tc0_dropped_packets {
      type oc-yang:counter64;
      description
        "RX port cgm ostc0 drops counter. Counts packets that were totally dropped and will not be seen on RX side.";
    }
    leaf counters_slice4_ifg1_ifgb_rx_port_24_cgm_tc0_partially_dropped_packets {
      type oc-yang:counter64;
      description
        "RX port cgm ostc0 partial drops counter. Counts packets that were partially dropped and will be seen on RX side.";
    }
    leaf counters_slice4_ifg1_ifgb_rx_port_24_cgm_tc1_dropped_packets {
      type oc-yang:counter64;
      description
        "RX port cgm ostc1 drops counter. Counts packets that were totally dropped and will not be seen on RX side.";
    }
    leaf counters_slice4_ifg1_ifgb_rx_port_24_cgm_tc1_partially_dropped_packets {
      type oc-yang:counter64;
      description
        "RX port cgm ostc1 partial drops counter. Counts packets that were partially dropped and will be seen on RX side.";
    }
    leaf counters_slice4_ifg1_ifgb_rx_port_24_cgm_tc2_dropped_packets {
      type oc-yang:counter64;
      description
        "RX port cgm ostc2 drops counter. Counts packets that were totally dropped and will not be seen on RX side.";
    }
    leaf counters_slice4_ifg1_ifgb_rx_port_24_cgm_tc2_partially_dropped_packets {
      type oc-yang:counter64;
      description
        "RX port cgm ostc2 partial drops counter. Counts packets that were partially dropped and will be seen on RX side.";
    }
    leaf counters_slice4_ifg1_ifgb_rx_port_24_cgm_tc3_dropped_packets {
      type oc-yang:counter64;
      description
        "RX port cgm ostc3 drops counter. Counts packets that were totally dropped and will not be seen on RX side.";
    }
    leaf counters_slice4_ifg1_ifgb_rx_port_24_cgm_tc3_partially_dropped_packets {
      type oc-yang:counter64;
      description
        "RX port cgm ostc3 partial drops counter. Counts packets that were partially dropped and will be seen on RX side.";
    }
    leaf counters_slice4_ifg1_ifgb_rx_port_25_cgm_tc0_dropped_packets {
      type oc-yang:counter64;
      description
        "RX port cgm ostc0 drops counter. Counts packets that were totally dropped and will not be seen on RX side.";
    }
    leaf counters_slice4_ifg1_ifgb_rx_port_25_cgm_tc0_partially_dropped_packets {
      type oc-yang:counter64;
      description
        "RX port cgm ostc0 partial drops counter. Counts packets that were partially dropped and will be seen on RX side.";
    }
    leaf counters_slice4_ifg1_ifgb_rx_port_25_cgm_tc1_dropped_packets {
      type oc-yang:counter64;
      description
        "RX port cgm ostc1 drops counter. Counts packets that were totally dropped and will not be seen on RX side.";
    }
    leaf counters_slice4_ifg1_ifgb_rx_port_25_cgm_tc1_partially_dropped_packets {
      type oc-yang:counter64;
      description
        "RX port cgm ostc1 partial drops counter. Counts packets that were partially dropped and will be seen on RX side.";
    }
    leaf counters_slice4_ifg1_ifgb_rx_port_25_cgm_tc2_dropped_packets {
      type oc-yang:counter64;
      description
        "RX port cgm ostc2 drops counter. Counts packets that were totally dropped and will not be seen on RX side.";
    }
    leaf counters_slice4_ifg1_ifgb_rx_port_25_cgm_tc2_partially_dropped_packets {
      type oc-yang:counter64;
      description
        "RX port cgm ostc2 partial drops counter. Counts packets that were partially dropped and will be seen on RX side.";
    }
    leaf counters_slice4_ifg1_ifgb_rx_port_25_cgm_tc3_dropped_packets {
      type oc-yang:counter64;
      description
        "RX port cgm ostc3 drops counter. Counts packets that were totally dropped and will not be seen on RX side.";
    }
    leaf counters_slice4_ifg1_ifgb_rx_port_25_cgm_tc3_partially_dropped_packets {
      type oc-yang:counter64;
      description
        "RX port cgm ostc3 partial drops counter. Counts packets that were partially dropped and will be seen on RX side.";
    }
    leaf counters_slice4_ifg1_ifgb_rx_port_26_cgm_tc0_dropped_packets {
      type oc-yang:counter64;
      description
        "RX port cgm ostc0 drops counter. Counts packets that were totally dropped and will not be seen on RX side.";
    }
    leaf counters_slice4_ifg1_ifgb_rx_port_26_cgm_tc0_partially_dropped_packets {
      type oc-yang:counter64;
      description
        "RX port cgm ostc0 partial drops counter. Counts packets that were partially dropped and will be seen on RX side.";
    }
    leaf counters_slice4_ifg1_ifgb_rx_port_26_cgm_tc1_dropped_packets {
      type oc-yang:counter64;
      description
        "RX port cgm ostc1 drops counter. Counts packets that were totally dropped and will not be seen on RX side.";
    }
    leaf counters_slice4_ifg1_ifgb_rx_port_26_cgm_tc1_partially_dropped_packets {
      type oc-yang:counter64;
      description
        "RX port cgm ostc1 partial drops counter. Counts packets that were partially dropped and will be seen on RX side.";
    }
    leaf counters_slice4_ifg1_ifgb_rx_port_26_cgm_tc2_dropped_packets {
      type oc-yang:counter64;
      description
        "RX port cgm ostc2 drops counter. Counts packets that were totally dropped and will not be seen on RX side.";
    }
    leaf counters_slice4_ifg1_ifgb_rx_port_26_cgm_tc2_partially_dropped_packets {
      type oc-yang:counter64;
      description
        "RX port cgm ostc2 partial drops counter. Counts packets that were partially dropped and will be seen on RX side.";
    }
    leaf counters_slice4_ifg1_ifgb_rx_port_26_cgm_tc3_dropped_packets {
      type oc-yang:counter64;
      description
        "RX port cgm ostc3 drops counter. Counts packets that were totally dropped and will not be seen on RX side.";
    }
    leaf counters_slice4_ifg1_ifgb_rx_port_26_cgm_tc3_partially_dropped_packets {
      type oc-yang:counter64;
      description
        "RX port cgm ostc3 partial drops counter. Counts packets that were partially dropped and will be seen on RX side.";
    }
    leaf counters_slice4_ifg1_ifgb_rx_port_27_cgm_tc0_dropped_packets {
      type oc-yang:counter64;
      description
        "RX port cgm ostc0 drops counter. Counts packets that were totally dropped and will not be seen on RX side.";
    }
    leaf counters_slice4_ifg1_ifgb_rx_port_27_cgm_tc0_partially_dropped_packets {
      type oc-yang:counter64;
      description
        "RX port cgm ostc0 partial drops counter. Counts packets that were partially dropped and will be seen on RX side.";
    }
    leaf counters_slice4_ifg1_ifgb_rx_port_27_cgm_tc1_dropped_packets {
      type oc-yang:counter64;
      description
        "RX port cgm ostc1 drops counter. Counts packets that were totally dropped and will not be seen on RX side.";
    }
    leaf counters_slice4_ifg1_ifgb_rx_port_27_cgm_tc1_partially_dropped_packets {
      type oc-yang:counter64;
      description
        "RX port cgm ostc1 partial drops counter. Counts packets that were partially dropped and will be seen on RX side.";
    }
    leaf counters_slice4_ifg1_ifgb_rx_port_27_cgm_tc2_dropped_packets {
      type oc-yang:counter64;
      description
        "RX port cgm ostc2 drops counter. Counts packets that were totally dropped and will not be seen on RX side.";
    }
    leaf counters_slice4_ifg1_ifgb_rx_port_27_cgm_tc2_partially_dropped_packets {
      type oc-yang:counter64;
      description
        "RX port cgm ostc2 partial drops counter. Counts packets that were partially dropped and will be seen on RX side.";
    }
    leaf counters_slice4_ifg1_ifgb_rx_port_27_cgm_tc3_dropped_packets {
      type oc-yang:counter64;
      description
        "RX port cgm ostc3 drops counter. Counts packets that were totally dropped and will not be seen on RX side.";
    }
    leaf counters_slice4_ifg1_ifgb_rx_port_27_cgm_tc3_partially_dropped_packets {
      type oc-yang:counter64;
      description
        "RX port cgm ostc3 partial drops counter. Counts packets that were partially dropped and will be seen on RX side.";
    }
    leaf counters_slice4_ifg1_ifgb_rx_port_28_cgm_tc0_dropped_packets {
      type oc-yang:counter64;
      description
        "RX port cgm ostc0 drops counter. Counts packets that were totally dropped and will not be seen on RX side.";
    }
    leaf counters_slice4_ifg1_ifgb_rx_port_28_cgm_tc0_partially_dropped_packets {
      type oc-yang:counter64;
      description
        "RX port cgm ostc0 partial drops counter. Counts packets that were partially dropped and will be seen on RX side.";
    }
    leaf counters_slice4_ifg1_ifgb_rx_port_28_cgm_tc1_dropped_packets {
      type oc-yang:counter64;
      description
        "RX port cgm ostc1 drops counter. Counts packets that were totally dropped and will not be seen on RX side.";
    }
    leaf counters_slice4_ifg1_ifgb_rx_port_28_cgm_tc1_partially_dropped_packets {
      type oc-yang:counter64;
      description
        "RX port cgm ostc1 partial drops counter. Counts packets that were partially dropped and will be seen on RX side.";
    }
    leaf counters_slice4_ifg1_ifgb_rx_port_28_cgm_tc2_dropped_packets {
      type oc-yang:counter64;
      description
        "RX port cgm ostc2 drops counter. Counts packets that were totally dropped and will not be seen on RX side.";
    }
    leaf counters_slice4_ifg1_ifgb_rx_port_28_cgm_tc2_partially_dropped_packets {
      type oc-yang:counter64;
      description
        "RX port cgm ostc2 partial drops counter. Counts packets that were partially dropped and will be seen on RX side.";
    }
    leaf counters_slice4_ifg1_ifgb_rx_port_28_cgm_tc3_dropped_packets {
      type oc-yang:counter64;
      description
        "RX port cgm ostc3 drops counter. Counts packets that were totally dropped and will not be seen on RX side.";
    }
    leaf counters_slice4_ifg1_ifgb_rx_port_28_cgm_tc3_partially_dropped_packets {
      type oc-yang:counter64;
      description
        "RX port cgm ostc3 partial drops counter. Counts packets that were partially dropped and will be seen on RX side.";
    }
    leaf counters_slice4_ifg1_ifgb_rx_port_29_cgm_tc0_dropped_packets {
      type oc-yang:counter64;
      description
        "RX port cgm ostc0 drops counter. Counts packets that were totally dropped and will not be seen on RX side.";
    }
    leaf counters_slice4_ifg1_ifgb_rx_port_29_cgm_tc0_partially_dropped_packets {
      type oc-yang:counter64;
      description
        "RX port cgm ostc0 partial drops counter. Counts packets that were partially dropped and will be seen on RX side.";
    }
    leaf counters_slice4_ifg1_ifgb_rx_port_29_cgm_tc1_dropped_packets {
      type oc-yang:counter64;
      description
        "RX port cgm ostc1 drops counter. Counts packets that were totally dropped and will not be seen on RX side.";
    }
    leaf counters_slice4_ifg1_ifgb_rx_port_29_cgm_tc1_partially_dropped_packets {
      type oc-yang:counter64;
      description
        "RX port cgm ostc1 partial drops counter. Counts packets that were partially dropped and will be seen on RX side.";
    }
    leaf counters_slice4_ifg1_ifgb_rx_port_29_cgm_tc2_dropped_packets {
      type oc-yang:counter64;
      description
        "RX port cgm ostc2 drops counter. Counts packets that were totally dropped and will not be seen on RX side.";
    }
    leaf counters_slice4_ifg1_ifgb_rx_port_29_cgm_tc2_partially_dropped_packets {
      type oc-yang:counter64;
      description
        "RX port cgm ostc2 partial drops counter. Counts packets that were partially dropped and will be seen on RX side.";
    }
    leaf counters_slice4_ifg1_ifgb_rx_port_29_cgm_tc3_dropped_packets {
      type oc-yang:counter64;
      description
        "RX port cgm ostc3 drops counter. Counts packets that were totally dropped and will not be seen on RX side.";
    }
    leaf counters_slice4_ifg1_ifgb_rx_port_29_cgm_tc3_partially_dropped_packets {
      type oc-yang:counter64;
      description
        "RX port cgm ostc3 partial drops counter. Counts packets that were partially dropped and will be seen on RX side.";
    }
    leaf counters_slice4_ifg1_ifgb_rx_port_3_cgm_tc0_dropped_packets {
      type oc-yang:counter64;
      description
        "RX port cgm ostc0 drops counter. Counts packets that were totally dropped and will not be seen on RX side.";
    }
    leaf counters_slice4_ifg1_ifgb_rx_port_3_cgm_tc0_partially_dropped_packets {
      type oc-yang:counter64;
      description
        "RX port cgm ostc0 partial drops counter. Counts packets that were partially dropped and will be seen on RX side.";
    }
    leaf counters_slice4_ifg1_ifgb_rx_port_3_cgm_tc1_dropped_packets {
      type oc-yang:counter64;
      description
        "RX port cgm ostc1 drops counter. Counts packets that were totally dropped and will not be seen on RX side.";
    }
    leaf counters_slice4_ifg1_ifgb_rx_port_3_cgm_tc1_partially_dropped_packets {
      type oc-yang:counter64;
      description
        "RX port cgm ostc1 partial drops counter. Counts packets that were partially dropped and will be seen on RX side.";
    }
    leaf counters_slice4_ifg1_ifgb_rx_port_3_cgm_tc2_dropped_packets {
      type oc-yang:counter64;
      description
        "RX port cgm ostc2 drops counter. Counts packets that were totally dropped and will not be seen on RX side.";
    }
    leaf counters_slice4_ifg1_ifgb_rx_port_3_cgm_tc2_partially_dropped_packets {
      type oc-yang:counter64;
      description
        "RX port cgm ostc2 partial drops counter. Counts packets that were partially dropped and will be seen on RX side.";
    }
    leaf counters_slice4_ifg1_ifgb_rx_port_3_cgm_tc3_dropped_packets {
      type oc-yang:counter64;
      description
        "RX port cgm ostc3 drops counter. Counts packets that were totally dropped and will not be seen on RX side.";
    }
    leaf counters_slice4_ifg1_ifgb_rx_port_3_cgm_tc3_partially_dropped_packets {
      type oc-yang:counter64;
      description
        "RX port cgm ostc3 partial drops counter. Counts packets that were partially dropped and will be seen on RX side.";
    }
    leaf counters_slice4_ifg1_ifgb_rx_port_30_cgm_tc0_dropped_packets {
      type oc-yang:counter64;
      description
        "RX port cgm ostc0 drops counter. Counts packets that were totally dropped and will not be seen on RX side.";
    }
    leaf counters_slice4_ifg1_ifgb_rx_port_30_cgm_tc0_partially_dropped_packets {
      type oc-yang:counter64;
      description
        "RX port cgm ostc0 partial drops counter. Counts packets that were partially dropped and will be seen on RX side.";
    }
    leaf counters_slice4_ifg1_ifgb_rx_port_30_cgm_tc1_dropped_packets {
      type oc-yang:counter64;
      description
        "RX port cgm ostc1 drops counter. Counts packets that were totally dropped and will not be seen on RX side.";
    }
    leaf counters_slice4_ifg1_ifgb_rx_port_30_cgm_tc1_partially_dropped_packets {
      type oc-yang:counter64;
      description
        "RX port cgm ostc1 partial drops counter. Counts packets that were partially dropped and will be seen on RX side.";
    }
    leaf counters_slice4_ifg1_ifgb_rx_port_30_cgm_tc2_dropped_packets {
      type oc-yang:counter64;
      description
        "RX port cgm ostc2 drops counter. Counts packets that were totally dropped and will not be seen on RX side.";
    }
    leaf counters_slice4_ifg1_ifgb_rx_port_30_cgm_tc2_partially_dropped_packets {
      type oc-yang:counter64;
      description
        "RX port cgm ostc2 partial drops counter. Counts packets that were partially dropped and will be seen on RX side.";
    }
    leaf counters_slice4_ifg1_ifgb_rx_port_30_cgm_tc3_dropped_packets {
      type oc-yang:counter64;
      description
        "RX port cgm ostc3 drops counter. Counts packets that were totally dropped and will not be seen on RX side.";
    }
    leaf counters_slice4_ifg1_ifgb_rx_port_30_cgm_tc3_partially_dropped_packets {
      type oc-yang:counter64;
      description
        "RX port cgm ostc3 partial drops counter. Counts packets that were partially dropped and will be seen on RX side.";
    }
    leaf counters_slice4_ifg1_ifgb_rx_port_31_cgm_tc0_dropped_packets {
      type oc-yang:counter64;
      description
        "RX port cgm ostc0 drops counter. Counts packets that were totally dropped and will not be seen on RX side.";
    }
    leaf counters_slice4_ifg1_ifgb_rx_port_31_cgm_tc0_partially_dropped_packets {
      type oc-yang:counter64;
      description
        "RX port cgm ostc0 partial drops counter. Counts packets that were partially dropped and will be seen on RX side.";
    }
    leaf counters_slice4_ifg1_ifgb_rx_port_31_cgm_tc1_dropped_packets {
      type oc-yang:counter64;
      description
        "RX port cgm ostc1 drops counter. Counts packets that were totally dropped and will not be seen on RX side.";
    }
    leaf counters_slice4_ifg1_ifgb_rx_port_31_cgm_tc1_partially_dropped_packets {
      type oc-yang:counter64;
      description
        "RX port cgm ostc1 partial drops counter. Counts packets that were partially dropped and will be seen on RX side.";
    }
    leaf counters_slice4_ifg1_ifgb_rx_port_31_cgm_tc2_dropped_packets {
      type oc-yang:counter64;
      description
        "RX port cgm ostc2 drops counter. Counts packets that were totally dropped and will not be seen on RX side.";
    }
    leaf counters_slice4_ifg1_ifgb_rx_port_31_cgm_tc2_partially_dropped_packets {
      type oc-yang:counter64;
      description
        "RX port cgm ostc2 partial drops counter. Counts packets that were partially dropped and will be seen on RX side.";
    }
    leaf counters_slice4_ifg1_ifgb_rx_port_31_cgm_tc3_dropped_packets {
      type oc-yang:counter64;
      description
        "RX port cgm ostc3 drops counter. Counts packets that were totally dropped and will not be seen on RX side.";
    }
    leaf counters_slice4_ifg1_ifgb_rx_port_31_cgm_tc3_partially_dropped_packets {
      type oc-yang:counter64;
      description
        "RX port cgm ostc3 partial drops counter. Counts packets that were partially dropped and will be seen on RX side.";
    }
    leaf counters_slice4_ifg1_ifgb_rx_port_4_cgm_tc0_dropped_packets {
      type oc-yang:counter64;
      description
        "RX port cgm ostc0 drops counter. Counts packets that were totally dropped and will not be seen on RX side.";
    }
    leaf counters_slice4_ifg1_ifgb_rx_port_4_cgm_tc0_partially_dropped_packets {
      type oc-yang:counter64;
      description
        "RX port cgm ostc0 partial drops counter. Counts packets that were partially dropped and will be seen on RX side.";
    }
    leaf counters_slice4_ifg1_ifgb_rx_port_4_cgm_tc1_dropped_packets {
      type oc-yang:counter64;
      description
        "RX port cgm ostc1 drops counter. Counts packets that were totally dropped and will not be seen on RX side.";
    }
    leaf counters_slice4_ifg1_ifgb_rx_port_4_cgm_tc1_partially_dropped_packets {
      type oc-yang:counter64;
      description
        "RX port cgm ostc1 partial drops counter. Counts packets that were partially dropped and will be seen on RX side.";
    }
    leaf counters_slice4_ifg1_ifgb_rx_port_4_cgm_tc2_dropped_packets {
      type oc-yang:counter64;
      description
        "RX port cgm ostc2 drops counter. Counts packets that were totally dropped and will not be seen on RX side.";
    }
    leaf counters_slice4_ifg1_ifgb_rx_port_4_cgm_tc2_partially_dropped_packets {
      type oc-yang:counter64;
      description
        "RX port cgm ostc2 partial drops counter. Counts packets that were partially dropped and will be seen on RX side.";
    }
    leaf counters_slice4_ifg1_ifgb_rx_port_4_cgm_tc3_dropped_packets {
      type oc-yang:counter64;
      description
        "RX port cgm ostc3 drops counter. Counts packets that were totally dropped and will not be seen on RX side.";
    }
    leaf counters_slice4_ifg1_ifgb_rx_port_4_cgm_tc3_partially_dropped_packets {
      type oc-yang:counter64;
      description
        "RX port cgm ostc3 partial drops counter. Counts packets that were partially dropped and will be seen on RX side.";
    }
    leaf counters_slice4_ifg1_ifgb_rx_port_5_cgm_tc0_dropped_packets {
      type oc-yang:counter64;
      description
        "RX port cgm ostc0 drops counter. Counts packets that were totally dropped and will not be seen on RX side.";
    }
    leaf counters_slice4_ifg1_ifgb_rx_port_5_cgm_tc0_partially_dropped_packets {
      type oc-yang:counter64;
      description
        "RX port cgm ostc0 partial drops counter. Counts packets that were partially dropped and will be seen on RX side.";
    }
    leaf counters_slice4_ifg1_ifgb_rx_port_5_cgm_tc1_dropped_packets {
      type oc-yang:counter64;
      description
        "RX port cgm ostc1 drops counter. Counts packets that were totally dropped and will not be seen on RX side.";
    }
    leaf counters_slice4_ifg1_ifgb_rx_port_5_cgm_tc1_partially_dropped_packets {
      type oc-yang:counter64;
      description
        "RX port cgm ostc1 partial drops counter. Counts packets that were partially dropped and will be seen on RX side.";
    }
    leaf counters_slice4_ifg1_ifgb_rx_port_5_cgm_tc2_dropped_packets {
      type oc-yang:counter64;
      description
        "RX port cgm ostc2 drops counter. Counts packets that were totally dropped and will not be seen on RX side.";
    }
    leaf counters_slice4_ifg1_ifgb_rx_port_5_cgm_tc2_partially_dropped_packets {
      type oc-yang:counter64;
      description
        "RX port cgm ostc2 partial drops counter. Counts packets that were partially dropped and will be seen on RX side.";
    }
    leaf counters_slice4_ifg1_ifgb_rx_port_5_cgm_tc3_dropped_packets {
      type oc-yang:counter64;
      description
        "RX port cgm ostc3 drops counter. Counts packets that were totally dropped and will not be seen on RX side.";
    }
    leaf counters_slice4_ifg1_ifgb_rx_port_5_cgm_tc3_partially_dropped_packets {
      type oc-yang:counter64;
      description
        "RX port cgm ostc3 partial drops counter. Counts packets that were partially dropped and will be seen on RX side.";
    }
    leaf counters_slice4_ifg1_ifgb_rx_port_6_cgm_tc0_dropped_packets {
      type oc-yang:counter64;
      description
        "RX port cgm ostc0 drops counter. Counts packets that were totally dropped and will not be seen on RX side.";
    }
    leaf counters_slice4_ifg1_ifgb_rx_port_6_cgm_tc0_partially_dropped_packets {
      type oc-yang:counter64;
      description
        "RX port cgm ostc0 partial drops counter. Counts packets that were partially dropped and will be seen on RX side.";
    }
    leaf counters_slice4_ifg1_ifgb_rx_port_6_cgm_tc1_dropped_packets {
      type oc-yang:counter64;
      description
        "RX port cgm ostc1 drops counter. Counts packets that were totally dropped and will not be seen on RX side.";
    }
    leaf counters_slice4_ifg1_ifgb_rx_port_6_cgm_tc1_partially_dropped_packets {
      type oc-yang:counter64;
      description
        "RX port cgm ostc1 partial drops counter. Counts packets that were partially dropped and will be seen on RX side.";
    }
    leaf counters_slice4_ifg1_ifgb_rx_port_6_cgm_tc2_dropped_packets {
      type oc-yang:counter64;
      description
        "RX port cgm ostc2 drops counter. Counts packets that were totally dropped and will not be seen on RX side.";
    }
    leaf counters_slice4_ifg1_ifgb_rx_port_6_cgm_tc2_partially_dropped_packets {
      type oc-yang:counter64;
      description
        "RX port cgm ostc2 partial drops counter. Counts packets that were partially dropped and will be seen on RX side.";
    }
    leaf counters_slice4_ifg1_ifgb_rx_port_6_cgm_tc3_dropped_packets {
      type oc-yang:counter64;
      description
        "RX port cgm ostc3 drops counter. Counts packets that were totally dropped and will not be seen on RX side.";
    }
    leaf counters_slice4_ifg1_ifgb_rx_port_6_cgm_tc3_partially_dropped_packets {
      type oc-yang:counter64;
      description
        "RX port cgm ostc3 partial drops counter. Counts packets that were partially dropped and will be seen on RX side.";
    }
    leaf counters_slice4_ifg1_ifgb_rx_port_7_cgm_tc0_dropped_packets {
      type oc-yang:counter64;
      description
        "RX port cgm ostc0 drops counter. Counts packets that were totally dropped and will not be seen on RX side.";
    }
    leaf counters_slice4_ifg1_ifgb_rx_port_7_cgm_tc0_partially_dropped_packets {
      type oc-yang:counter64;
      description
        "RX port cgm ostc0 partial drops counter. Counts packets that were partially dropped and will be seen on RX side.";
    }
    leaf counters_slice4_ifg1_ifgb_rx_port_7_cgm_tc1_dropped_packets {
      type oc-yang:counter64;
      description
        "RX port cgm ostc1 drops counter. Counts packets that were totally dropped and will not be seen on RX side.";
    }
    leaf counters_slice4_ifg1_ifgb_rx_port_7_cgm_tc1_partially_dropped_packets {
      type oc-yang:counter64;
      description
        "RX port cgm ostc1 partial drops counter. Counts packets that were partially dropped and will be seen on RX side.";
    }
    leaf counters_slice4_ifg1_ifgb_rx_port_7_cgm_tc2_dropped_packets {
      type oc-yang:counter64;
      description
        "RX port cgm ostc2 drops counter. Counts packets that were totally dropped and will not be seen on RX side.";
    }
    leaf counters_slice4_ifg1_ifgb_rx_port_7_cgm_tc2_partially_dropped_packets {
      type oc-yang:counter64;
      description
        "RX port cgm ostc2 partial drops counter. Counts packets that were partially dropped and will be seen on RX side.";
    }
    leaf counters_slice4_ifg1_ifgb_rx_port_7_cgm_tc3_dropped_packets {
      type oc-yang:counter64;
      description
        "RX port cgm ostc3 drops counter. Counts packets that were totally dropped and will not be seen on RX side.";
    }
    leaf counters_slice4_ifg1_ifgb_rx_port_7_cgm_tc3_partially_dropped_packets {
      type oc-yang:counter64;
      description
        "RX port cgm ostc3 partial drops counter. Counts packets that were partially dropped and will be seen on RX side.";
    }
    leaf counters_slice4_ifg1_ifgb_rx_port_8_cgm_tc0_dropped_packets {
      type oc-yang:counter64;
      description
        "RX port cgm ostc0 drops counter. Counts packets that were totally dropped and will not be seen on RX side.";
    }
    leaf counters_slice4_ifg1_ifgb_rx_port_8_cgm_tc0_partially_dropped_packets {
      type oc-yang:counter64;
      description
        "RX port cgm ostc0 partial drops counter. Counts packets that were partially dropped and will be seen on RX side.";
    }
    leaf counters_slice4_ifg1_ifgb_rx_port_8_cgm_tc1_dropped_packets {
      type oc-yang:counter64;
      description
        "RX port cgm ostc1 drops counter. Counts packets that were totally dropped and will not be seen on RX side.";
    }
    leaf counters_slice4_ifg1_ifgb_rx_port_8_cgm_tc1_partially_dropped_packets {
      type oc-yang:counter64;
      description
        "RX port cgm ostc1 partial drops counter. Counts packets that were partially dropped and will be seen on RX side.";
    }
    leaf counters_slice4_ifg1_ifgb_rx_port_8_cgm_tc2_dropped_packets {
      type oc-yang:counter64;
      description
        "RX port cgm ostc2 drops counter. Counts packets that were totally dropped and will not be seen on RX side.";
    }
    leaf counters_slice4_ifg1_ifgb_rx_port_8_cgm_tc2_partially_dropped_packets {
      type oc-yang:counter64;
      description
        "RX port cgm ostc2 partial drops counter. Counts packets that were partially dropped and will be seen on RX side.";
    }
    leaf counters_slice4_ifg1_ifgb_rx_port_8_cgm_tc3_dropped_packets {
      type oc-yang:counter64;
      description
        "RX port cgm ostc3 drops counter. Counts packets that were totally dropped and will not be seen on RX side.";
    }
    leaf counters_slice4_ifg1_ifgb_rx_port_8_cgm_tc3_partially_dropped_packets {
      type oc-yang:counter64;
      description
        "RX port cgm ostc3 partial drops counter. Counts packets that were partially dropped and will be seen on RX side.";
    }
    leaf counters_slice4_ifg1_ifgb_rx_port_9_cgm_tc0_dropped_packets {
      type oc-yang:counter64;
      description
        "RX port cgm ostc0 drops counter. Counts packets that were totally dropped and will not be seen on RX side.";
    }
    leaf counters_slice4_ifg1_ifgb_rx_port_9_cgm_tc0_partially_dropped_packets {
      type oc-yang:counter64;
      description
        "RX port cgm ostc0 partial drops counter. Counts packets that were partially dropped and will be seen on RX side.";
    }
    leaf counters_slice4_ifg1_ifgb_rx_port_9_cgm_tc1_dropped_packets {
      type oc-yang:counter64;
      description
        "RX port cgm ostc1 drops counter. Counts packets that were totally dropped and will not be seen on RX side.";
    }
    leaf counters_slice4_ifg1_ifgb_rx_port_9_cgm_tc1_partially_dropped_packets {
      type oc-yang:counter64;
      description
        "RX port cgm ostc1 partial drops counter. Counts packets that were partially dropped and will be seen on RX side.";
    }
    leaf counters_slice4_ifg1_ifgb_rx_port_9_cgm_tc2_dropped_packets {
      type oc-yang:counter64;
      description
        "RX port cgm ostc2 drops counter. Counts packets that were totally dropped and will not be seen on RX side.";
    }
    leaf counters_slice4_ifg1_ifgb_rx_port_9_cgm_tc2_partially_dropped_packets {
      type oc-yang:counter64;
      description
        "RX port cgm ostc2 partial drops counter. Counts packets that were partially dropped and will be seen on RX side.";
    }
    leaf counters_slice4_ifg1_ifgb_rx_port_9_cgm_tc3_dropped_packets {
      type oc-yang:counter64;
      description
        "RX port cgm ostc3 drops counter. Counts packets that were totally dropped and will not be seen on RX side.";
    }
    leaf counters_slice4_ifg1_ifgb_rx_port_9_cgm_tc3_partially_dropped_packets {
      type oc-yang:counter64;
      description
        "RX port cgm ostc3 partial drops counter. Counts packets that were partially dropped and will be seen on RX side.";
    }
    leaf counters_slice4_tx_cgm_dropped_packets_due_to_max_allowed_qsize {
      type oc-yang:counter64;
      description
        "Counts number of dropped packets by max allowed threshold";
    }
    leaf counters_slice4_tx_cgm_local_sch_uc_buffer_c_dropped_packets {
      type oc-yang:counter64;
      description
        "Counts number of dropped packets by counter C";
    }
    leaf counters_slice4_tx_cgm_mc_silently_dropped_packets {
      type oc-yang:counter64;
      description
        "Counter of dropped MC packets that were silently dropped";
    }
    leaf counters_slice4_tx_cgm_sch_uc_buffers_cd_dropped_packets {
      type oc-yang:counter64;
      description
        "Counts number of dropped packets by counter C+D";
    }
    leaf counters_slice4_tx_cgm_sch_uc_counter_z_dropped_packets {
      type oc-yang:counter64;
      description
        "Counts number of dropped packets by counter Z";
    }
    leaf counters_slice4_tx_cgm_total_dropped_packets {
      type oc-yang:counter64;
      description
        "Counts number of dropped in TxCGM only packets";
    }
    leaf counters_slice4_tx_cgm_uc_oq_test_dropped_packets {
      type oc-yang:counter64;
      description
        "Counts number of dropped by UC OQ test";
    }
    leaf counters_slice4_tx_cgm_uc_oqg_dropped_packets {
      type oc-yang:counter64;
      description
        "Counts number of dropped by UC OQG test";
    }
    leaf counters_slice4_tx_cgm_unsch_counter_w_dropped_packets {
      type oc-yang:counter64;
      description
        "Counts number of dropped packets by counter W";
    }
    leaf counters_slice4_tx_cgm_green_mc_oq_bytes_test_dropped_packets {
      type oc-yang:counter64;
      description
        "Counts number of dropped packets by OQ MC green bytes test";
    }
    leaf counters_slice4_tx_cgm_green_mc_oq_pds_test_dropped_packets {
      type oc-yang:counter64;
      description
        "Counts number of dropped packets by OQ MC green PDs test";
    }
    leaf counters_slice4_tx_cgm_mc_color_test0_dropped_packets {
      type oc-yang:counter64;
      description
        "Counts number of dropped packet by MC color test for:0 - Green1 - Yellow2 - Red3 - Other";
    }
    leaf counters_slice4_tx_cgm_mc_color_test1_dropped_packets {
      type oc-yang:counter64;
      description
        "Counts number of dropped packet by MC color test for:0 - Green1 - Yellow2 - Red3 - Other";
    }
    leaf counters_slice4_tx_cgm_mc_color_test2_dropped_packets {
      type oc-yang:counter64;
      description
        "Counts number of dropped packet by MC color test for:0 - Green1 - Yellow2 - Red3 - Other";
    }
    leaf counters_slice4_tx_cgm_mc_color_test3_dropped_packets {
      type oc-yang:counter64;
      description
        "Counts number of dropped packet by MC color test for:0 - Green1 - Yellow2 - Red3 - Other";
    }
    leaf counters_slice4_tx_cgm_mc_set0_dropped_bytes {
      type oc-yang:counter64;
      description
        "Counts MC dropped bytes";
    }
    leaf counters_slice4_tx_cgm_mc_set0_dropped_packets {
      type oc-yang:counter64;
      description
        "Counts MC dropped packets";
    }
    leaf counters_slice4_tx_cgm_mc_set1_dropped_bytes {
      type oc-yang:counter64;
      description
        "Counts MC dropped bytes";
    }
    leaf counters_slice4_tx_cgm_mc_set1_dropped_packets {
      type oc-yang:counter64;
      description
        "Counts MC dropped packets";
    }
    leaf counters_slice4_tx_cgm_mc_set2_dropped_bytes {
      type oc-yang:counter64;
      description
        "Counts MC dropped bytes";
    }
    leaf counters_slice4_tx_cgm_mc_set2_dropped_packets {
      type oc-yang:counter64;
      description
        "Counts MC dropped packets";
    }
    leaf counters_slice4_tx_cgm_mc_set3_dropped_bytes {
      type oc-yang:counter64;
      description
        "Counts MC dropped bytes";
    }
    leaf counters_slice4_tx_cgm_mc_set3_dropped_packets {
      type oc-yang:counter64;
      description
        "Counts MC dropped packets";
    }
    leaf counters_slice4_tx_cgm_uc_color_test0_dropped_packets {
      type oc-yang:counter64;
      description
        "Counts number of dropped packet by UC color test for:0 - Green1 - Yellow2 - Red3 - Other";
    }
    leaf counters_slice4_tx_cgm_uc_color_test1_dropped_packets {
      type oc-yang:counter64;
      description
        "Counts number of dropped packet by UC color test for:0 - Green1 - Yellow2 - Red3 - Other";
    }
    leaf counters_slice4_tx_cgm_uc_color_test2_dropped_packets {
      type oc-yang:counter64;
      description
        "Counts number of dropped packet by UC color test for:0 - Green1 - Yellow2 - Red3 - Other";
    }
    leaf counters_slice4_tx_cgm_uc_color_test3_dropped_packets {
      type oc-yang:counter64;
      description
        "Counts number of dropped packet by UC color test for:0 - Green1 - Yellow2 - Red3 - Other";
    }
    leaf counters_slice4_tx_cgm_uc_set0_dropped_bytes {
      type oc-yang:counter64;
      description
        "Counts UC dropped bytes";
    }
    leaf counters_slice4_tx_cgm_uc_set0_dropped_packets {
      type oc-yang:counter64;
      description
        "Counts UC dropped packets";
    }
    leaf counters_slice4_tx_cgm_uc_set1_dropped_bytes {
      type oc-yang:counter64;
      description
        "Counts UC dropped bytes";
    }
    leaf counters_slice4_tx_cgm_uc_set1_dropped_packets {
      type oc-yang:counter64;
      description
        "Counts UC dropped packets";
    }
    leaf counters_slice4_tx_cgm_uc_set2_dropped_bytes {
      type oc-yang:counter64;
      description
        "Counts UC dropped bytes";
    }
    leaf counters_slice4_tx_cgm_uc_set2_dropped_packets {
      type oc-yang:counter64;
      description
        "Counts UC dropped packets";
    }
    leaf counters_slice4_tx_cgm_uc_set3_dropped_bytes {
      type oc-yang:counter64;
      description
        "Counts UC dropped bytes";
    }
    leaf counters_slice4_tx_cgm_uc_set3_dropped_packets {
      type oc-yang:counter64;
      description
        "Counts UC dropped packets";
    }
    leaf counters_slice4_tx_cgm_yellow_mc_oq_bytes_test_dropped_packets {
      type oc-yang:counter64;
      description
        "Counts number of dropped packets by OQ MC yellow bytes test";
    }
    leaf counters_slice4_tx_cgm_yellow_mc_oq_pds_test_dropped_packets {
      type oc-yang:counter64;
      description
        "Counts number of dropped packets by OQ MC yellow PDs test";
    }
    leaf counters_slice4_tx_pdr_txrq_full_egress_rep_dropped_packets {
      type oc-yang:counter64;
      description
        "Number of dropped packets";
    }
    leaf counters_slice4_tx_pdr_txrq_overload_egress_rep_dropped_packets {
      type oc-yang:counter64;
      description
        "Number of dropped packets";
    }
    leaf counters_slice4_tx_pdr_txrq0_full_egress_rep_dropped_packets {
      type oc-yang:counter64;
      description
        "Number of dropped packets";
    }
    leaf counters_slice4_tx_pdr_txrq0_threshold0_deq_dropped_packets {
      type oc-yang:counter64;
      description
        "Number of dropped packets in TXRQ deq";
    }
    leaf counters_slice4_tx_pdr_txrq0_threshold0_enq_dropped_packets {
      type oc-yang:counter64;
      description
        "Number of dropped packets in TXRQ enq";
    }
    leaf counters_slice4_tx_pdr_txrq0_threshold0_unscheduled_cgm_drops {
      type oc-yang:counter64;
      description
        "nan";
    }
    leaf counters_slice4_tx_pdr_txrq0_threshold1_deq_dropped_packets {
      type oc-yang:counter64;
      description
        "Number of dropped packets in TXRQ deq";
    }
    leaf counters_slice4_tx_pdr_txrq0_threshold1_enq_dropped_packets {
      type oc-yang:counter64;
      description
        "Number of dropped packets in TXRQ enq";
    }
    leaf counters_slice4_tx_pdr_txrq0_threshold1_unscheduled_cgm_drops {
      type oc-yang:counter64;
      description
        "nan";
    }
    leaf counters_slice4_tx_pdr_txrq1_full_egress_rep_dropped_packets {
      type oc-yang:counter64;
      description
        "Number of dropped packets";
    }
    leaf counters_slice4_tx_pdr_txrq1_threshold0_deq_dropped_packets {
      type oc-yang:counter64;
      description
        "Number of dropped packets in TXRQ deq";
    }
    leaf counters_slice4_tx_pdr_txrq1_threshold0_enq_dropped_packets {
      type oc-yang:counter64;
      description
        "Number of dropped packets in TXRQ enq";
    }
    leaf counters_slice4_tx_pdr_txrq1_threshold0_unscheduled_cgm_drops {
      type oc-yang:counter64;
      description
        "nan";
    }
    leaf counters_slice4_tx_pdr_txrq1_threshold1_deq_dropped_packets {
      type oc-yang:counter64;
      description
        "Number of dropped packets in TXRQ deq";
    }
    leaf counters_slice4_tx_pdr_txrq1_threshold1_enq_dropped_packets {
      type oc-yang:counter64;
      description
        "Number of dropped packets in TXRQ enq";
    }
    leaf counters_slice4_tx_pdr_txrq1_threshold1_unscheduled_cgm_drops {
      type oc-yang:counter64;
      description
        "nan";
    }
    leaf counters_slice4_tx_pdr_txrq2_full_egress_rep_dropped_packets {
      type oc-yang:counter64;
      description
        "Number of dropped packets";
    }
    leaf counters_slice4_tx_pdr_txrq2_threshold0_deq_dropped_packets {
      type oc-yang:counter64;
      description
        "Number of dropped packets in TXRQ deq";
    }
    leaf counters_slice4_tx_pdr_txrq2_threshold0_enq_dropped_packets {
      type oc-yang:counter64;
      description
        "Number of dropped packets in TXRQ enq";
    }
    leaf counters_slice4_tx_pdr_txrq2_threshold1_deq_dropped_packets {
      type oc-yang:counter64;
      description
        "Number of dropped packets in TXRQ deq";
    }
    leaf counters_slice4_tx_pdr_txrq2_threshold1_enq_dropped_packets {
      type oc-yang:counter64;
      description
        "Number of dropped packets in TXRQ enq";
    }
    leaf counters_slice4_tx_pdr_txrq3_full_egress_rep_dropped_packets {
      type oc-yang:counter64;
      description
        "Number of dropped packets";
    }
    leaf counters_slice4_tx_pdr_txrq3_threshold0_deq_dropped_packets {
      type oc-yang:counter64;
      description
        "Number of dropped packets in TXRQ deq";
    }
    leaf counters_slice4_tx_pdr_txrq3_threshold0_enq_dropped_packets {
      type oc-yang:counter64;
      description
        "Number of dropped packets in TXRQ enq";
    }
    leaf counters_slice4_tx_pdr_txrq3_threshold1_deq_dropped_packets {
      type oc-yang:counter64;
      description
        "Number of dropped packets in TXRQ deq";
    }
    leaf counters_slice4_tx_pdr_txrq3_threshold1_enq_dropped_packets {
      type oc-yang:counter64;
      description
        "Number of dropped packets in TXRQ enq";
    }
    leaf counters_slice5_ifg0_ifgb_rx_port_0_cgm_tc0_dropped_packets {
      type oc-yang:counter64;
      description
        "RX port cgm ostc0 drops counter. Counts packets that were totally dropped and will not be seen on RX side.";
    }
    leaf counters_slice5_ifg0_ifgb_rx_port_0_cgm_tc0_partially_dropped_packets {
      type oc-yang:counter64;
      description
        "RX port cgm ostc0 partial drops counter. Counts packets that were partially dropped and will be seen on RX side.";
    }
    leaf counters_slice5_ifg0_ifgb_rx_port_0_cgm_tc1_dropped_packets {
      type oc-yang:counter64;
      description
        "RX port cgm ostc1 drops counter. Counts packets that were totally dropped and will not be seen on RX side.";
    }
    leaf counters_slice5_ifg0_ifgb_rx_port_0_cgm_tc1_partially_dropped_packets {
      type oc-yang:counter64;
      description
        "RX port cgm ostc1 partial drops counter. Counts packets that were partially dropped and will be seen on RX side.";
    }
    leaf counters_slice5_ifg0_ifgb_rx_port_0_cgm_tc2_dropped_packets {
      type oc-yang:counter64;
      description
        "RX port cgm ostc2 drops counter. Counts packets that were totally dropped and will not be seen on RX side.";
    }
    leaf counters_slice5_ifg0_ifgb_rx_port_0_cgm_tc2_partially_dropped_packets {
      type oc-yang:counter64;
      description
        "RX port cgm ostc2 partial drops counter. Counts packets that were partially dropped and will be seen on RX side.";
    }
    leaf counters_slice5_ifg0_ifgb_rx_port_0_cgm_tc3_dropped_packets {
      type oc-yang:counter64;
      description
        "RX port cgm ostc3 drops counter. Counts packets that were totally dropped and will not be seen on RX side.";
    }
    leaf counters_slice5_ifg0_ifgb_rx_port_0_cgm_tc3_partially_dropped_packets {
      type oc-yang:counter64;
      description
        "RX port cgm ostc3 partial drops counter. Counts packets that were partially dropped and will be seen on RX side.";
    }
    leaf counters_slice5_ifg0_ifgb_rx_port_1_cgm_tc0_dropped_packets {
      type oc-yang:counter64;
      description
        "RX port cgm ostc0 drops counter. Counts packets that were totally dropped and will not be seen on RX side.";
    }
    leaf counters_slice5_ifg0_ifgb_rx_port_1_cgm_tc0_partially_dropped_packets {
      type oc-yang:counter64;
      description
        "RX port cgm ostc0 partial drops counter. Counts packets that were partially dropped and will be seen on RX side.";
    }
    leaf counters_slice5_ifg0_ifgb_rx_port_1_cgm_tc1_dropped_packets {
      type oc-yang:counter64;
      description
        "RX port cgm ostc1 drops counter. Counts packets that were totally dropped and will not be seen on RX side.";
    }
    leaf counters_slice5_ifg0_ifgb_rx_port_1_cgm_tc1_partially_dropped_packets {
      type oc-yang:counter64;
      description
        "RX port cgm ostc1 partial drops counter. Counts packets that were partially dropped and will be seen on RX side.";
    }
    leaf counters_slice5_ifg0_ifgb_rx_port_1_cgm_tc2_dropped_packets {
      type oc-yang:counter64;
      description
        "RX port cgm ostc2 drops counter. Counts packets that were totally dropped and will not be seen on RX side.";
    }
    leaf counters_slice5_ifg0_ifgb_rx_port_1_cgm_tc2_partially_dropped_packets {
      type oc-yang:counter64;
      description
        "RX port cgm ostc2 partial drops counter. Counts packets that were partially dropped and will be seen on RX side.";
    }
    leaf counters_slice5_ifg0_ifgb_rx_port_1_cgm_tc3_dropped_packets {
      type oc-yang:counter64;
      description
        "RX port cgm ostc3 drops counter. Counts packets that were totally dropped and will not be seen on RX side.";
    }
    leaf counters_slice5_ifg0_ifgb_rx_port_1_cgm_tc3_partially_dropped_packets {
      type oc-yang:counter64;
      description
        "RX port cgm ostc3 partial drops counter. Counts packets that were partially dropped and will be seen on RX side.";
    }
    leaf counters_slice5_ifg0_ifgb_rx_port_10_cgm_tc0_dropped_packets {
      type oc-yang:counter64;
      description
        "RX port cgm ostc0 drops counter. Counts packets that were totally dropped and will not be seen on RX side.";
    }
    leaf counters_slice5_ifg0_ifgb_rx_port_10_cgm_tc0_partially_dropped_packets {
      type oc-yang:counter64;
      description
        "RX port cgm ostc0 partial drops counter. Counts packets that were partially dropped and will be seen on RX side.";
    }
    leaf counters_slice5_ifg0_ifgb_rx_port_10_cgm_tc1_dropped_packets {
      type oc-yang:counter64;
      description
        "RX port cgm ostc1 drops counter. Counts packets that were totally dropped and will not be seen on RX side.";
    }
    leaf counters_slice5_ifg0_ifgb_rx_port_10_cgm_tc1_partially_dropped_packets {
      type oc-yang:counter64;
      description
        "RX port cgm ostc1 partial drops counter. Counts packets that were partially dropped and will be seen on RX side.";
    }
    leaf counters_slice5_ifg0_ifgb_rx_port_10_cgm_tc2_dropped_packets {
      type oc-yang:counter64;
      description
        "RX port cgm ostc2 drops counter. Counts packets that were totally dropped and will not be seen on RX side.";
    }
    leaf counters_slice5_ifg0_ifgb_rx_port_10_cgm_tc2_partially_dropped_packets {
      type oc-yang:counter64;
      description
        "RX port cgm ostc2 partial drops counter. Counts packets that were partially dropped and will be seen on RX side.";
    }
    leaf counters_slice5_ifg0_ifgb_rx_port_10_cgm_tc3_dropped_packets {
      type oc-yang:counter64;
      description
        "RX port cgm ostc3 drops counter. Counts packets that were totally dropped and will not be seen on RX side.";
    }
    leaf counters_slice5_ifg0_ifgb_rx_port_10_cgm_tc3_partially_dropped_packets {
      type oc-yang:counter64;
      description
        "RX port cgm ostc3 partial drops counter. Counts packets that were partially dropped and will be seen on RX side.";
    }
    leaf counters_slice5_ifg0_ifgb_rx_port_11_cgm_tc0_dropped_packets {
      type oc-yang:counter64;
      description
        "RX port cgm ostc0 drops counter. Counts packets that were totally dropped and will not be seen on RX side.";
    }
    leaf counters_slice5_ifg0_ifgb_rx_port_11_cgm_tc0_partially_dropped_packets {
      type oc-yang:counter64;
      description
        "RX port cgm ostc0 partial drops counter. Counts packets that were partially dropped and will be seen on RX side.";
    }
    leaf counters_slice5_ifg0_ifgb_rx_port_11_cgm_tc1_dropped_packets {
      type oc-yang:counter64;
      description
        "RX port cgm ostc1 drops counter. Counts packets that were totally dropped and will not be seen on RX side.";
    }
    leaf counters_slice5_ifg0_ifgb_rx_port_11_cgm_tc1_partially_dropped_packets {
      type oc-yang:counter64;
      description
        "RX port cgm ostc1 partial drops counter. Counts packets that were partially dropped and will be seen on RX side.";
    }
    leaf counters_slice5_ifg0_ifgb_rx_port_11_cgm_tc2_dropped_packets {
      type oc-yang:counter64;
      description
        "RX port cgm ostc2 drops counter. Counts packets that were totally dropped and will not be seen on RX side.";
    }
    leaf counters_slice5_ifg0_ifgb_rx_port_11_cgm_tc2_partially_dropped_packets {
      type oc-yang:counter64;
      description
        "RX port cgm ostc2 partial drops counter. Counts packets that were partially dropped and will be seen on RX side.";
    }
    leaf counters_slice5_ifg0_ifgb_rx_port_11_cgm_tc3_dropped_packets {
      type oc-yang:counter64;
      description
        "RX port cgm ostc3 drops counter. Counts packets that were totally dropped and will not be seen on RX side.";
    }
    leaf counters_slice5_ifg0_ifgb_rx_port_11_cgm_tc3_partially_dropped_packets {
      type oc-yang:counter64;
      description
        "RX port cgm ostc3 partial drops counter. Counts packets that were partially dropped and will be seen on RX side.";
    }
    leaf counters_slice5_ifg0_ifgb_rx_port_12_cgm_tc0_dropped_packets {
      type oc-yang:counter64;
      description
        "RX port cgm ostc0 drops counter. Counts packets that were totally dropped and will not be seen on RX side.";
    }
    leaf counters_slice5_ifg0_ifgb_rx_port_12_cgm_tc0_partially_dropped_packets {
      type oc-yang:counter64;
      description
        "RX port cgm ostc0 partial drops counter. Counts packets that were partially dropped and will be seen on RX side.";
    }
    leaf counters_slice5_ifg0_ifgb_rx_port_12_cgm_tc1_dropped_packets {
      type oc-yang:counter64;
      description
        "RX port cgm ostc1 drops counter. Counts packets that were totally dropped and will not be seen on RX side.";
    }
    leaf counters_slice5_ifg0_ifgb_rx_port_12_cgm_tc1_partially_dropped_packets {
      type oc-yang:counter64;
      description
        "RX port cgm ostc1 partial drops counter. Counts packets that were partially dropped and will be seen on RX side.";
    }
    leaf counters_slice5_ifg0_ifgb_rx_port_12_cgm_tc2_dropped_packets {
      type oc-yang:counter64;
      description
        "RX port cgm ostc2 drops counter. Counts packets that were totally dropped and will not be seen on RX side.";
    }
    leaf counters_slice5_ifg0_ifgb_rx_port_12_cgm_tc2_partially_dropped_packets {
      type oc-yang:counter64;
      description
        "RX port cgm ostc2 partial drops counter. Counts packets that were partially dropped and will be seen on RX side.";
    }
    leaf counters_slice5_ifg0_ifgb_rx_port_12_cgm_tc3_dropped_packets {
      type oc-yang:counter64;
      description
        "RX port cgm ostc3 drops counter. Counts packets that were totally dropped and will not be seen on RX side.";
    }
    leaf counters_slice5_ifg0_ifgb_rx_port_12_cgm_tc3_partially_dropped_packets {
      type oc-yang:counter64;
      description
        "RX port cgm ostc3 partial drops counter. Counts packets that were partially dropped and will be seen on RX side.";
    }
    leaf counters_slice5_ifg0_ifgb_rx_port_13_cgm_tc0_dropped_packets {
      type oc-yang:counter64;
      description
        "RX port cgm ostc0 drops counter. Counts packets that were totally dropped and will not be seen on RX side.";
    }
    leaf counters_slice5_ifg0_ifgb_rx_port_13_cgm_tc0_partially_dropped_packets {
      type oc-yang:counter64;
      description
        "RX port cgm ostc0 partial drops counter. Counts packets that were partially dropped and will be seen on RX side.";
    }
    leaf counters_slice5_ifg0_ifgb_rx_port_13_cgm_tc1_dropped_packets {
      type oc-yang:counter64;
      description
        "RX port cgm ostc1 drops counter. Counts packets that were totally dropped and will not be seen on RX side.";
    }
    leaf counters_slice5_ifg0_ifgb_rx_port_13_cgm_tc1_partially_dropped_packets {
      type oc-yang:counter64;
      description
        "RX port cgm ostc1 partial drops counter. Counts packets that were partially dropped and will be seen on RX side.";
    }
    leaf counters_slice5_ifg0_ifgb_rx_port_13_cgm_tc2_dropped_packets {
      type oc-yang:counter64;
      description
        "RX port cgm ostc2 drops counter. Counts packets that were totally dropped and will not be seen on RX side.";
    }
    leaf counters_slice5_ifg0_ifgb_rx_port_13_cgm_tc2_partially_dropped_packets {
      type oc-yang:counter64;
      description
        "RX port cgm ostc2 partial drops counter. Counts packets that were partially dropped and will be seen on RX side.";
    }
    leaf counters_slice5_ifg0_ifgb_rx_port_13_cgm_tc3_dropped_packets {
      type oc-yang:counter64;
      description
        "RX port cgm ostc3 drops counter. Counts packets that were totally dropped and will not be seen on RX side.";
    }
    leaf counters_slice5_ifg0_ifgb_rx_port_13_cgm_tc3_partially_dropped_packets {
      type oc-yang:counter64;
      description
        "RX port cgm ostc3 partial drops counter. Counts packets that were partially dropped and will be seen on RX side.";
    }
    leaf counters_slice5_ifg0_ifgb_rx_port_14_cgm_tc0_dropped_packets {
      type oc-yang:counter64;
      description
        "RX port cgm ostc0 drops counter. Counts packets that were totally dropped and will not be seen on RX side.";
    }
    leaf counters_slice5_ifg0_ifgb_rx_port_14_cgm_tc0_partially_dropped_packets {
      type oc-yang:counter64;
      description
        "RX port cgm ostc0 partial drops counter. Counts packets that were partially dropped and will be seen on RX side.";
    }
    leaf counters_slice5_ifg0_ifgb_rx_port_14_cgm_tc1_dropped_packets {
      type oc-yang:counter64;
      description
        "RX port cgm ostc1 drops counter. Counts packets that were totally dropped and will not be seen on RX side.";
    }
    leaf counters_slice5_ifg0_ifgb_rx_port_14_cgm_tc1_partially_dropped_packets {
      type oc-yang:counter64;
      description
        "RX port cgm ostc1 partial drops counter. Counts packets that were partially dropped and will be seen on RX side.";
    }
    leaf counters_slice5_ifg0_ifgb_rx_port_14_cgm_tc2_dropped_packets {
      type oc-yang:counter64;
      description
        "RX port cgm ostc2 drops counter. Counts packets that were totally dropped and will not be seen on RX side.";
    }
    leaf counters_slice5_ifg0_ifgb_rx_port_14_cgm_tc2_partially_dropped_packets {
      type oc-yang:counter64;
      description
        "RX port cgm ostc2 partial drops counter. Counts packets that were partially dropped and will be seen on RX side.";
    }
    leaf counters_slice5_ifg0_ifgb_rx_port_14_cgm_tc3_dropped_packets {
      type oc-yang:counter64;
      description
        "RX port cgm ostc3 drops counter. Counts packets that were totally dropped and will not be seen on RX side.";
    }
    leaf counters_slice5_ifg0_ifgb_rx_port_14_cgm_tc3_partially_dropped_packets {
      type oc-yang:counter64;
      description
        "RX port cgm ostc3 partial drops counter. Counts packets that were partially dropped and will be seen on RX side.";
    }
    leaf counters_slice5_ifg0_ifgb_rx_port_15_cgm_tc0_dropped_packets {
      type oc-yang:counter64;
      description
        "RX port cgm ostc0 drops counter. Counts packets that were totally dropped and will not be seen on RX side.";
    }
    leaf counters_slice5_ifg0_ifgb_rx_port_15_cgm_tc0_partially_dropped_packets {
      type oc-yang:counter64;
      description
        "RX port cgm ostc0 partial drops counter. Counts packets that were partially dropped and will be seen on RX side.";
    }
    leaf counters_slice5_ifg0_ifgb_rx_port_15_cgm_tc1_dropped_packets {
      type oc-yang:counter64;
      description
        "RX port cgm ostc1 drops counter. Counts packets that were totally dropped and will not be seen on RX side.";
    }
    leaf counters_slice5_ifg0_ifgb_rx_port_15_cgm_tc1_partially_dropped_packets {
      type oc-yang:counter64;
      description
        "RX port cgm ostc1 partial drops counter. Counts packets that were partially dropped and will be seen on RX side.";
    }
    leaf counters_slice5_ifg0_ifgb_rx_port_15_cgm_tc2_dropped_packets {
      type oc-yang:counter64;
      description
        "RX port cgm ostc2 drops counter. Counts packets that were totally dropped and will not be seen on RX side.";
    }
    leaf counters_slice5_ifg0_ifgb_rx_port_15_cgm_tc2_partially_dropped_packets {
      type oc-yang:counter64;
      description
        "RX port cgm ostc2 partial drops counter. Counts packets that were partially dropped and will be seen on RX side.";
    }
    leaf counters_slice5_ifg0_ifgb_rx_port_15_cgm_tc3_dropped_packets {
      type oc-yang:counter64;
      description
        "RX port cgm ostc3 drops counter. Counts packets that were totally dropped and will not be seen on RX side.";
    }
    leaf counters_slice5_ifg0_ifgb_rx_port_15_cgm_tc3_partially_dropped_packets {
      type oc-yang:counter64;
      description
        "RX port cgm ostc3 partial drops counter. Counts packets that were partially dropped and will be seen on RX side.";
    }
    leaf counters_slice5_ifg0_ifgb_rx_port_16_cgm_tc0_dropped_packets {
      type oc-yang:counter64;
      description
        "RX port cgm ostc0 drops counter. Counts packets that were totally dropped and will not be seen on RX side.";
    }
    leaf counters_slice5_ifg0_ifgb_rx_port_16_cgm_tc0_partially_dropped_packets {
      type oc-yang:counter64;
      description
        "RX port cgm ostc0 partial drops counter. Counts packets that were partially dropped and will be seen on RX side.";
    }
    leaf counters_slice5_ifg0_ifgb_rx_port_16_cgm_tc1_dropped_packets {
      type oc-yang:counter64;
      description
        "RX port cgm ostc1 drops counter. Counts packets that were totally dropped and will not be seen on RX side.";
    }
    leaf counters_slice5_ifg0_ifgb_rx_port_16_cgm_tc1_partially_dropped_packets {
      type oc-yang:counter64;
      description
        "RX port cgm ostc1 partial drops counter. Counts packets that were partially dropped and will be seen on RX side.";
    }
    leaf counters_slice5_ifg0_ifgb_rx_port_16_cgm_tc2_dropped_packets {
      type oc-yang:counter64;
      description
        "RX port cgm ostc2 drops counter. Counts packets that were totally dropped and will not be seen on RX side.";
    }
    leaf counters_slice5_ifg0_ifgb_rx_port_16_cgm_tc2_partially_dropped_packets {
      type oc-yang:counter64;
      description
        "RX port cgm ostc2 partial drops counter. Counts packets that were partially dropped and will be seen on RX side.";
    }
    leaf counters_slice5_ifg0_ifgb_rx_port_16_cgm_tc3_dropped_packets {
      type oc-yang:counter64;
      description
        "RX port cgm ostc3 drops counter. Counts packets that were totally dropped and will not be seen on RX side.";
    }
    leaf counters_slice5_ifg0_ifgb_rx_port_16_cgm_tc3_partially_dropped_packets {
      type oc-yang:counter64;
      description
        "RX port cgm ostc3 partial drops counter. Counts packets that were partially dropped and will be seen on RX side.";
    }
    leaf counters_slice5_ifg0_ifgb_rx_port_17_cgm_tc0_dropped_packets {
      type oc-yang:counter64;
      description
        "RX port cgm ostc0 drops counter. Counts packets that were totally dropped and will not be seen on RX side.";
    }
    leaf counters_slice5_ifg0_ifgb_rx_port_17_cgm_tc0_partially_dropped_packets {
      type oc-yang:counter64;
      description
        "RX port cgm ostc0 partial drops counter. Counts packets that were partially dropped and will be seen on RX side.";
    }
    leaf counters_slice5_ifg0_ifgb_rx_port_17_cgm_tc1_dropped_packets {
      type oc-yang:counter64;
      description
        "RX port cgm ostc1 drops counter. Counts packets that were totally dropped and will not be seen on RX side.";
    }
    leaf counters_slice5_ifg0_ifgb_rx_port_17_cgm_tc1_partially_dropped_packets {
      type oc-yang:counter64;
      description
        "RX port cgm ostc1 partial drops counter. Counts packets that were partially dropped and will be seen on RX side.";
    }
    leaf counters_slice5_ifg0_ifgb_rx_port_17_cgm_tc2_dropped_packets {
      type oc-yang:counter64;
      description
        "RX port cgm ostc2 drops counter. Counts packets that were totally dropped and will not be seen on RX side.";
    }
    leaf counters_slice5_ifg0_ifgb_rx_port_17_cgm_tc2_partially_dropped_packets {
      type oc-yang:counter64;
      description
        "RX port cgm ostc2 partial drops counter. Counts packets that were partially dropped and will be seen on RX side.";
    }
    leaf counters_slice5_ifg0_ifgb_rx_port_17_cgm_tc3_dropped_packets {
      type oc-yang:counter64;
      description
        "RX port cgm ostc3 drops counter. Counts packets that were totally dropped and will not be seen on RX side.";
    }
    leaf counters_slice5_ifg0_ifgb_rx_port_17_cgm_tc3_partially_dropped_packets {
      type oc-yang:counter64;
      description
        "RX port cgm ostc3 partial drops counter. Counts packets that were partially dropped and will be seen on RX side.";
    }
    leaf counters_slice5_ifg0_ifgb_rx_port_18_cgm_tc0_dropped_packets {
      type oc-yang:counter64;
      description
        "RX port cgm ostc0 drops counter. Counts packets that were totally dropped and will not be seen on RX side.";
    }
    leaf counters_slice5_ifg0_ifgb_rx_port_18_cgm_tc0_partially_dropped_packets {
      type oc-yang:counter64;
      description
        "RX port cgm ostc0 partial drops counter. Counts packets that were partially dropped and will be seen on RX side.";
    }
    leaf counters_slice5_ifg0_ifgb_rx_port_18_cgm_tc1_dropped_packets {
      type oc-yang:counter64;
      description
        "RX port cgm ostc1 drops counter. Counts packets that were totally dropped and will not be seen on RX side.";
    }
    leaf counters_slice5_ifg0_ifgb_rx_port_18_cgm_tc1_partially_dropped_packets {
      type oc-yang:counter64;
      description
        "RX port cgm ostc1 partial drops counter. Counts packets that were partially dropped and will be seen on RX side.";
    }
    leaf counters_slice5_ifg0_ifgb_rx_port_18_cgm_tc2_dropped_packets {
      type oc-yang:counter64;
      description
        "RX port cgm ostc2 drops counter. Counts packets that were totally dropped and will not be seen on RX side.";
    }
    leaf counters_slice5_ifg0_ifgb_rx_port_18_cgm_tc2_partially_dropped_packets {
      type oc-yang:counter64;
      description
        "RX port cgm ostc2 partial drops counter. Counts packets that were partially dropped and will be seen on RX side.";
    }
    leaf counters_slice5_ifg0_ifgb_rx_port_18_cgm_tc3_dropped_packets {
      type oc-yang:counter64;
      description
        "RX port cgm ostc3 drops counter. Counts packets that were totally dropped and will not be seen on RX side.";
    }
    leaf counters_slice5_ifg0_ifgb_rx_port_18_cgm_tc3_partially_dropped_packets {
      type oc-yang:counter64;
      description
        "RX port cgm ostc3 partial drops counter. Counts packets that were partially dropped and will be seen on RX side.";
    }
    leaf counters_slice5_ifg0_ifgb_rx_port_19_cgm_tc0_dropped_packets {
      type oc-yang:counter64;
      description
        "RX port cgm ostc0 drops counter. Counts packets that were totally dropped and will not be seen on RX side.";
    }
    leaf counters_slice5_ifg0_ifgb_rx_port_19_cgm_tc0_partially_dropped_packets {
      type oc-yang:counter64;
      description
        "RX port cgm ostc0 partial drops counter. Counts packets that were partially dropped and will be seen on RX side.";
    }
    leaf counters_slice5_ifg0_ifgb_rx_port_19_cgm_tc1_dropped_packets {
      type oc-yang:counter64;
      description
        "RX port cgm ostc1 drops counter. Counts packets that were totally dropped and will not be seen on RX side.";
    }
    leaf counters_slice5_ifg0_ifgb_rx_port_19_cgm_tc1_partially_dropped_packets {
      type oc-yang:counter64;
      description
        "RX port cgm ostc1 partial drops counter. Counts packets that were partially dropped and will be seen on RX side.";
    }
    leaf counters_slice5_ifg0_ifgb_rx_port_19_cgm_tc2_dropped_packets {
      type oc-yang:counter64;
      description
        "RX port cgm ostc2 drops counter. Counts packets that were totally dropped and will not be seen on RX side.";
    }
    leaf counters_slice5_ifg0_ifgb_rx_port_19_cgm_tc2_partially_dropped_packets {
      type oc-yang:counter64;
      description
        "RX port cgm ostc2 partial drops counter. Counts packets that were partially dropped and will be seen on RX side.";
    }
    leaf counters_slice5_ifg0_ifgb_rx_port_19_cgm_tc3_dropped_packets {
      type oc-yang:counter64;
      description
        "RX port cgm ostc3 drops counter. Counts packets that were totally dropped and will not be seen on RX side.";
    }
    leaf counters_slice5_ifg0_ifgb_rx_port_19_cgm_tc3_partially_dropped_packets {
      type oc-yang:counter64;
      description
        "RX port cgm ostc3 partial drops counter. Counts packets that were partially dropped and will be seen on RX side.";
    }
    leaf counters_slice5_ifg0_ifgb_rx_port_2_cgm_tc0_dropped_packets {
      type oc-yang:counter64;
      description
        "RX port cgm ostc0 drops counter. Counts packets that were totally dropped and will not be seen on RX side.";
    }
    leaf counters_slice5_ifg0_ifgb_rx_port_2_cgm_tc0_partially_dropped_packets {
      type oc-yang:counter64;
      description
        "RX port cgm ostc0 partial drops counter. Counts packets that were partially dropped and will be seen on RX side.";
    }
    leaf counters_slice5_ifg0_ifgb_rx_port_2_cgm_tc1_dropped_packets {
      type oc-yang:counter64;
      description
        "RX port cgm ostc1 drops counter. Counts packets that were totally dropped and will not be seen on RX side.";
    }
    leaf counters_slice5_ifg0_ifgb_rx_port_2_cgm_tc1_partially_dropped_packets {
      type oc-yang:counter64;
      description
        "RX port cgm ostc1 partial drops counter. Counts packets that were partially dropped and will be seen on RX side.";
    }
    leaf counters_slice5_ifg0_ifgb_rx_port_2_cgm_tc2_dropped_packets {
      type oc-yang:counter64;
      description
        "RX port cgm ostc2 drops counter. Counts packets that were totally dropped and will not be seen on RX side.";
    }
    leaf counters_slice5_ifg0_ifgb_rx_port_2_cgm_tc2_partially_dropped_packets {
      type oc-yang:counter64;
      description
        "RX port cgm ostc2 partial drops counter. Counts packets that were partially dropped and will be seen on RX side.";
    }
    leaf counters_slice5_ifg0_ifgb_rx_port_2_cgm_tc3_dropped_packets {
      type oc-yang:counter64;
      description
        "RX port cgm ostc3 drops counter. Counts packets that were totally dropped and will not be seen on RX side.";
    }
    leaf counters_slice5_ifg0_ifgb_rx_port_2_cgm_tc3_partially_dropped_packets {
      type oc-yang:counter64;
      description
        "RX port cgm ostc3 partial drops counter. Counts packets that were partially dropped and will be seen on RX side.";
    }
    leaf counters_slice5_ifg0_ifgb_rx_port_20_cgm_tc0_dropped_packets {
      type oc-yang:counter64;
      description
        "RX port cgm ostc0 drops counter. Counts packets that were totally dropped and will not be seen on RX side.";
    }
    leaf counters_slice5_ifg0_ifgb_rx_port_20_cgm_tc0_partially_dropped_packets {
      type oc-yang:counter64;
      description
        "RX port cgm ostc0 partial drops counter. Counts packets that were partially dropped and will be seen on RX side.";
    }
    leaf counters_slice5_ifg0_ifgb_rx_port_20_cgm_tc1_dropped_packets {
      type oc-yang:counter64;
      description
        "RX port cgm ostc1 drops counter. Counts packets that were totally dropped and will not be seen on RX side.";
    }
    leaf counters_slice5_ifg0_ifgb_rx_port_20_cgm_tc1_partially_dropped_packets {
      type oc-yang:counter64;
      description
        "RX port cgm ostc1 partial drops counter. Counts packets that were partially dropped and will be seen on RX side.";
    }
    leaf counters_slice5_ifg0_ifgb_rx_port_20_cgm_tc2_dropped_packets {
      type oc-yang:counter64;
      description
        "RX port cgm ostc2 drops counter. Counts packets that were totally dropped and will not be seen on RX side.";
    }
    leaf counters_slice5_ifg0_ifgb_rx_port_20_cgm_tc2_partially_dropped_packets {
      type oc-yang:counter64;
      description
        "RX port cgm ostc2 partial drops counter. Counts packets that were partially dropped and will be seen on RX side.";
    }
    leaf counters_slice5_ifg0_ifgb_rx_port_20_cgm_tc3_dropped_packets {
      type oc-yang:counter64;
      description
        "RX port cgm ostc3 drops counter. Counts packets that were totally dropped and will not be seen on RX side.";
    }
    leaf counters_slice5_ifg0_ifgb_rx_port_20_cgm_tc3_partially_dropped_packets {
      type oc-yang:counter64;
      description
        "RX port cgm ostc3 partial drops counter. Counts packets that were partially dropped and will be seen on RX side.";
    }
    leaf counters_slice5_ifg0_ifgb_rx_port_21_cgm_tc0_dropped_packets {
      type oc-yang:counter64;
      description
        "RX port cgm ostc0 drops counter. Counts packets that were totally dropped and will not be seen on RX side.";
    }
    leaf counters_slice5_ifg0_ifgb_rx_port_21_cgm_tc0_partially_dropped_packets {
      type oc-yang:counter64;
      description
        "RX port cgm ostc0 partial drops counter. Counts packets that were partially dropped and will be seen on RX side.";
    }
    leaf counters_slice5_ifg0_ifgb_rx_port_21_cgm_tc1_dropped_packets {
      type oc-yang:counter64;
      description
        "RX port cgm ostc1 drops counter. Counts packets that were totally dropped and will not be seen on RX side.";
    }
    leaf counters_slice5_ifg0_ifgb_rx_port_21_cgm_tc1_partially_dropped_packets {
      type oc-yang:counter64;
      description
        "RX port cgm ostc1 partial drops counter. Counts packets that were partially dropped and will be seen on RX side.";
    }
    leaf counters_slice5_ifg0_ifgb_rx_port_21_cgm_tc2_dropped_packets {
      type oc-yang:counter64;
      description
        "RX port cgm ostc2 drops counter. Counts packets that were totally dropped and will not be seen on RX side.";
    }
    leaf counters_slice5_ifg0_ifgb_rx_port_21_cgm_tc2_partially_dropped_packets {
      type oc-yang:counter64;
      description
        "RX port cgm ostc2 partial drops counter. Counts packets that were partially dropped and will be seen on RX side.";
    }
    leaf counters_slice5_ifg0_ifgb_rx_port_21_cgm_tc3_dropped_packets {
      type oc-yang:counter64;
      description
        "RX port cgm ostc3 drops counter. Counts packets that were totally dropped and will not be seen on RX side.";
    }
    leaf counters_slice5_ifg0_ifgb_rx_port_21_cgm_tc3_partially_dropped_packets {
      type oc-yang:counter64;
      description
        "RX port cgm ostc3 partial drops counter. Counts packets that were partially dropped and will be seen on RX side.";
    }
    leaf counters_slice5_ifg0_ifgb_rx_port_22_cgm_tc0_dropped_packets {
      type oc-yang:counter64;
      description
        "RX port cgm ostc0 drops counter. Counts packets that were totally dropped and will not be seen on RX side.";
    }
    leaf counters_slice5_ifg0_ifgb_rx_port_22_cgm_tc0_partially_dropped_packets {
      type oc-yang:counter64;
      description
        "RX port cgm ostc0 partial drops counter. Counts packets that were partially dropped and will be seen on RX side.";
    }
    leaf counters_slice5_ifg0_ifgb_rx_port_22_cgm_tc1_dropped_packets {
      type oc-yang:counter64;
      description
        "RX port cgm ostc1 drops counter. Counts packets that were totally dropped and will not be seen on RX side.";
    }
    leaf counters_slice5_ifg0_ifgb_rx_port_22_cgm_tc1_partially_dropped_packets {
      type oc-yang:counter64;
      description
        "RX port cgm ostc1 partial drops counter. Counts packets that were partially dropped and will be seen on RX side.";
    }
    leaf counters_slice5_ifg0_ifgb_rx_port_22_cgm_tc2_dropped_packets {
      type oc-yang:counter64;
      description
        "RX port cgm ostc2 drops counter. Counts packets that were totally dropped and will not be seen on RX side.";
    }
    leaf counters_slice5_ifg0_ifgb_rx_port_22_cgm_tc2_partially_dropped_packets {
      type oc-yang:counter64;
      description
        "RX port cgm ostc2 partial drops counter. Counts packets that were partially dropped and will be seen on RX side.";
    }
    leaf counters_slice5_ifg0_ifgb_rx_port_22_cgm_tc3_dropped_packets {
      type oc-yang:counter64;
      description
        "RX port cgm ostc3 drops counter. Counts packets that were totally dropped and will not be seen on RX side.";
    }
    leaf counters_slice5_ifg0_ifgb_rx_port_22_cgm_tc3_partially_dropped_packets {
      type oc-yang:counter64;
      description
        "RX port cgm ostc3 partial drops counter. Counts packets that were partially dropped and will be seen on RX side.";
    }
    leaf counters_slice5_ifg0_ifgb_rx_port_23_cgm_tc0_dropped_packets {
      type oc-yang:counter64;
      description
        "RX port cgm ostc0 drops counter. Counts packets that were totally dropped and will not be seen on RX side.";
    }
    leaf counters_slice5_ifg0_ifgb_rx_port_23_cgm_tc0_partially_dropped_packets {
      type oc-yang:counter64;
      description
        "RX port cgm ostc0 partial drops counter. Counts packets that were partially dropped and will be seen on RX side.";
    }
    leaf counters_slice5_ifg0_ifgb_rx_port_23_cgm_tc1_dropped_packets {
      type oc-yang:counter64;
      description
        "RX port cgm ostc1 drops counter. Counts packets that were totally dropped and will not be seen on RX side.";
    }
    leaf counters_slice5_ifg0_ifgb_rx_port_23_cgm_tc1_partially_dropped_packets {
      type oc-yang:counter64;
      description
        "RX port cgm ostc1 partial drops counter. Counts packets that were partially dropped and will be seen on RX side.";
    }
    leaf counters_slice5_ifg0_ifgb_rx_port_23_cgm_tc2_dropped_packets {
      type oc-yang:counter64;
      description
        "RX port cgm ostc2 drops counter. Counts packets that were totally dropped and will not be seen on RX side.";
    }
    leaf counters_slice5_ifg0_ifgb_rx_port_23_cgm_tc2_partially_dropped_packets {
      type oc-yang:counter64;
      description
        "RX port cgm ostc2 partial drops counter. Counts packets that were partially dropped and will be seen on RX side.";
    }
    leaf counters_slice5_ifg0_ifgb_rx_port_23_cgm_tc3_dropped_packets {
      type oc-yang:counter64;
      description
        "RX port cgm ostc3 drops counter. Counts packets that were totally dropped and will not be seen on RX side.";
    }
    leaf counters_slice5_ifg0_ifgb_rx_port_23_cgm_tc3_partially_dropped_packets {
      type oc-yang:counter64;
      description
        "RX port cgm ostc3 partial drops counter. Counts packets that were partially dropped and will be seen on RX side.";
    }
    leaf counters_slice5_ifg0_ifgb_rx_port_24_cgm_tc0_dropped_packets {
      type oc-yang:counter64;
      description
        "RX port cgm ostc0 drops counter. Counts packets that were totally dropped and will not be seen on RX side.";
    }
    leaf counters_slice5_ifg0_ifgb_rx_port_24_cgm_tc0_partially_dropped_packets {
      type oc-yang:counter64;
      description
        "RX port cgm ostc0 partial drops counter. Counts packets that were partially dropped and will be seen on RX side.";
    }
    leaf counters_slice5_ifg0_ifgb_rx_port_24_cgm_tc1_dropped_packets {
      type oc-yang:counter64;
      description
        "RX port cgm ostc1 drops counter. Counts packets that were totally dropped and will not be seen on RX side.";
    }
    leaf counters_slice5_ifg0_ifgb_rx_port_24_cgm_tc1_partially_dropped_packets {
      type oc-yang:counter64;
      description
        "RX port cgm ostc1 partial drops counter. Counts packets that were partially dropped and will be seen on RX side.";
    }
    leaf counters_slice5_ifg0_ifgb_rx_port_24_cgm_tc2_dropped_packets {
      type oc-yang:counter64;
      description
        "RX port cgm ostc2 drops counter. Counts packets that were totally dropped and will not be seen on RX side.";
    }
    leaf counters_slice5_ifg0_ifgb_rx_port_24_cgm_tc2_partially_dropped_packets {
      type oc-yang:counter64;
      description
        "RX port cgm ostc2 partial drops counter. Counts packets that were partially dropped and will be seen on RX side.";
    }
    leaf counters_slice5_ifg0_ifgb_rx_port_24_cgm_tc3_dropped_packets {
      type oc-yang:counter64;
      description
        "RX port cgm ostc3 drops counter. Counts packets that were totally dropped and will not be seen on RX side.";
    }
    leaf counters_slice5_ifg0_ifgb_rx_port_24_cgm_tc3_partially_dropped_packets {
      type oc-yang:counter64;
      description
        "RX port cgm ostc3 partial drops counter. Counts packets that were partially dropped and will be seen on RX side.";
    }
    leaf counters_slice5_ifg0_ifgb_rx_port_25_cgm_tc0_dropped_packets {
      type oc-yang:counter64;
      description
        "RX port cgm ostc0 drops counter. Counts packets that were totally dropped and will not be seen on RX side.";
    }
    leaf counters_slice5_ifg0_ifgb_rx_port_25_cgm_tc0_partially_dropped_packets {
      type oc-yang:counter64;
      description
        "RX port cgm ostc0 partial drops counter. Counts packets that were partially dropped and will be seen on RX side.";
    }
    leaf counters_slice5_ifg0_ifgb_rx_port_25_cgm_tc1_dropped_packets {
      type oc-yang:counter64;
      description
        "RX port cgm ostc1 drops counter. Counts packets that were totally dropped and will not be seen on RX side.";
    }
    leaf counters_slice5_ifg0_ifgb_rx_port_25_cgm_tc1_partially_dropped_packets {
      type oc-yang:counter64;
      description
        "RX port cgm ostc1 partial drops counter. Counts packets that were partially dropped and will be seen on RX side.";
    }
    leaf counters_slice5_ifg0_ifgb_rx_port_25_cgm_tc2_dropped_packets {
      type oc-yang:counter64;
      description
        "RX port cgm ostc2 drops counter. Counts packets that were totally dropped and will not be seen on RX side.";
    }
    leaf counters_slice5_ifg0_ifgb_rx_port_25_cgm_tc2_partially_dropped_packets {
      type oc-yang:counter64;
      description
        "RX port cgm ostc2 partial drops counter. Counts packets that were partially dropped and will be seen on RX side.";
    }
    leaf counters_slice5_ifg0_ifgb_rx_port_25_cgm_tc3_dropped_packets {
      type oc-yang:counter64;
      description
        "RX port cgm ostc3 drops counter. Counts packets that were totally dropped and will not be seen on RX side.";
    }
    leaf counters_slice5_ifg0_ifgb_rx_port_25_cgm_tc3_partially_dropped_packets {
      type oc-yang:counter64;
      description
        "RX port cgm ostc3 partial drops counter. Counts packets that were partially dropped and will be seen on RX side.";
    }
    leaf counters_slice5_ifg0_ifgb_rx_port_26_cgm_tc0_dropped_packets {
      type oc-yang:counter64;
      description
        "RX port cgm ostc0 drops counter. Counts packets that were totally dropped and will not be seen on RX side.";
    }
    leaf counters_slice5_ifg0_ifgb_rx_port_26_cgm_tc0_partially_dropped_packets {
      type oc-yang:counter64;
      description
        "RX port cgm ostc0 partial drops counter. Counts packets that were partially dropped and will be seen on RX side.";
    }
    leaf counters_slice5_ifg0_ifgb_rx_port_26_cgm_tc1_dropped_packets {
      type oc-yang:counter64;
      description
        "RX port cgm ostc1 drops counter. Counts packets that were totally dropped and will not be seen on RX side.";
    }
    leaf counters_slice5_ifg0_ifgb_rx_port_26_cgm_tc1_partially_dropped_packets {
      type oc-yang:counter64;
      description
        "RX port cgm ostc1 partial drops counter. Counts packets that were partially dropped and will be seen on RX side.";
    }
    leaf counters_slice5_ifg0_ifgb_rx_port_26_cgm_tc2_dropped_packets {
      type oc-yang:counter64;
      description
        "RX port cgm ostc2 drops counter. Counts packets that were totally dropped and will not be seen on RX side.";
    }
    leaf counters_slice5_ifg0_ifgb_rx_port_26_cgm_tc2_partially_dropped_packets {
      type oc-yang:counter64;
      description
        "RX port cgm ostc2 partial drops counter. Counts packets that were partially dropped and will be seen on RX side.";
    }
    leaf counters_slice5_ifg0_ifgb_rx_port_26_cgm_tc3_dropped_packets {
      type oc-yang:counter64;
      description
        "RX port cgm ostc3 drops counter. Counts packets that were totally dropped and will not be seen on RX side.";
    }
    leaf counters_slice5_ifg0_ifgb_rx_port_26_cgm_tc3_partially_dropped_packets {
      type oc-yang:counter64;
      description
        "RX port cgm ostc3 partial drops counter. Counts packets that were partially dropped and will be seen on RX side.";
    }
    leaf counters_slice5_ifg0_ifgb_rx_port_27_cgm_tc0_dropped_packets {
      type oc-yang:counter64;
      description
        "RX port cgm ostc0 drops counter. Counts packets that were totally dropped and will not be seen on RX side.";
    }
    leaf counters_slice5_ifg0_ifgb_rx_port_27_cgm_tc0_partially_dropped_packets {
      type oc-yang:counter64;
      description
        "RX port cgm ostc0 partial drops counter. Counts packets that were partially dropped and will be seen on RX side.";
    }
    leaf counters_slice5_ifg0_ifgb_rx_port_27_cgm_tc1_dropped_packets {
      type oc-yang:counter64;
      description
        "RX port cgm ostc1 drops counter. Counts packets that were totally dropped and will not be seen on RX side.";
    }
    leaf counters_slice5_ifg0_ifgb_rx_port_27_cgm_tc1_partially_dropped_packets {
      type oc-yang:counter64;
      description
        "RX port cgm ostc1 partial drops counter. Counts packets that were partially dropped and will be seen on RX side.";
    }
    leaf counters_slice5_ifg0_ifgb_rx_port_27_cgm_tc2_dropped_packets {
      type oc-yang:counter64;
      description
        "RX port cgm ostc2 drops counter. Counts packets that were totally dropped and will not be seen on RX side.";
    }
    leaf counters_slice5_ifg0_ifgb_rx_port_27_cgm_tc2_partially_dropped_packets {
      type oc-yang:counter64;
      description
        "RX port cgm ostc2 partial drops counter. Counts packets that were partially dropped and will be seen on RX side.";
    }
    leaf counters_slice5_ifg0_ifgb_rx_port_27_cgm_tc3_dropped_packets {
      type oc-yang:counter64;
      description
        "RX port cgm ostc3 drops counter. Counts packets that were totally dropped and will not be seen on RX side.";
    }
    leaf counters_slice5_ifg0_ifgb_rx_port_27_cgm_tc3_partially_dropped_packets {
      type oc-yang:counter64;
      description
        "RX port cgm ostc3 partial drops counter. Counts packets that were partially dropped and will be seen on RX side.";
    }
    leaf counters_slice5_ifg0_ifgb_rx_port_28_cgm_tc0_dropped_packets {
      type oc-yang:counter64;
      description
        "RX port cgm ostc0 drops counter. Counts packets that were totally dropped and will not be seen on RX side.";
    }
    leaf counters_slice5_ifg0_ifgb_rx_port_28_cgm_tc0_partially_dropped_packets {
      type oc-yang:counter64;
      description
        "RX port cgm ostc0 partial drops counter. Counts packets that were partially dropped and will be seen on RX side.";
    }
    leaf counters_slice5_ifg0_ifgb_rx_port_28_cgm_tc1_dropped_packets {
      type oc-yang:counter64;
      description
        "RX port cgm ostc1 drops counter. Counts packets that were totally dropped and will not be seen on RX side.";
    }
    leaf counters_slice5_ifg0_ifgb_rx_port_28_cgm_tc1_partially_dropped_packets {
      type oc-yang:counter64;
      description
        "RX port cgm ostc1 partial drops counter. Counts packets that were partially dropped and will be seen on RX side.";
    }
    leaf counters_slice5_ifg0_ifgb_rx_port_28_cgm_tc2_dropped_packets {
      type oc-yang:counter64;
      description
        "RX port cgm ostc2 drops counter. Counts packets that were totally dropped and will not be seen on RX side.";
    }
    leaf counters_slice5_ifg0_ifgb_rx_port_28_cgm_tc2_partially_dropped_packets {
      type oc-yang:counter64;
      description
        "RX port cgm ostc2 partial drops counter. Counts packets that were partially dropped and will be seen on RX side.";
    }
    leaf counters_slice5_ifg0_ifgb_rx_port_28_cgm_tc3_dropped_packets {
      type oc-yang:counter64;
      description
        "RX port cgm ostc3 drops counter. Counts packets that were totally dropped and will not be seen on RX side.";
    }
    leaf counters_slice5_ifg0_ifgb_rx_port_28_cgm_tc3_partially_dropped_packets {
      type oc-yang:counter64;
      description
        "RX port cgm ostc3 partial drops counter. Counts packets that were partially dropped and will be seen on RX side.";
    }
    leaf counters_slice5_ifg0_ifgb_rx_port_29_cgm_tc0_dropped_packets {
      type oc-yang:counter64;
      description
        "RX port cgm ostc0 drops counter. Counts packets that were totally dropped and will not be seen on RX side.";
    }
    leaf counters_slice5_ifg0_ifgb_rx_port_29_cgm_tc0_partially_dropped_packets {
      type oc-yang:counter64;
      description
        "RX port cgm ostc0 partial drops counter. Counts packets that were partially dropped and will be seen on RX side.";
    }
    leaf counters_slice5_ifg0_ifgb_rx_port_29_cgm_tc1_dropped_packets {
      type oc-yang:counter64;
      description
        "RX port cgm ostc1 drops counter. Counts packets that were totally dropped and will not be seen on RX side.";
    }
    leaf counters_slice5_ifg0_ifgb_rx_port_29_cgm_tc1_partially_dropped_packets {
      type oc-yang:counter64;
      description
        "RX port cgm ostc1 partial drops counter. Counts packets that were partially dropped and will be seen on RX side.";
    }
    leaf counters_slice5_ifg0_ifgb_rx_port_29_cgm_tc2_dropped_packets {
      type oc-yang:counter64;
      description
        "RX port cgm ostc2 drops counter. Counts packets that were totally dropped and will not be seen on RX side.";
    }
    leaf counters_slice5_ifg0_ifgb_rx_port_29_cgm_tc2_partially_dropped_packets {
      type oc-yang:counter64;
      description
        "RX port cgm ostc2 partial drops counter. Counts packets that were partially dropped and will be seen on RX side.";
    }
    leaf counters_slice5_ifg0_ifgb_rx_port_29_cgm_tc3_dropped_packets {
      type oc-yang:counter64;
      description
        "RX port cgm ostc3 drops counter. Counts packets that were totally dropped and will not be seen on RX side.";
    }
    leaf counters_slice5_ifg0_ifgb_rx_port_29_cgm_tc3_partially_dropped_packets {
      type oc-yang:counter64;
      description
        "RX port cgm ostc3 partial drops counter. Counts packets that were partially dropped and will be seen on RX side.";
    }
    leaf counters_slice5_ifg0_ifgb_rx_port_3_cgm_tc0_dropped_packets {
      type oc-yang:counter64;
      description
        "RX port cgm ostc0 drops counter. Counts packets that were totally dropped and will not be seen on RX side.";
    }
    leaf counters_slice5_ifg0_ifgb_rx_port_3_cgm_tc0_partially_dropped_packets {
      type oc-yang:counter64;
      description
        "RX port cgm ostc0 partial drops counter. Counts packets that were partially dropped and will be seen on RX side.";
    }
    leaf counters_slice5_ifg0_ifgb_rx_port_3_cgm_tc1_dropped_packets {
      type oc-yang:counter64;
      description
        "RX port cgm ostc1 drops counter. Counts packets that were totally dropped and will not be seen on RX side.";
    }
    leaf counters_slice5_ifg0_ifgb_rx_port_3_cgm_tc1_partially_dropped_packets {
      type oc-yang:counter64;
      description
        "RX port cgm ostc1 partial drops counter. Counts packets that were partially dropped and will be seen on RX side.";
    }
    leaf counters_slice5_ifg0_ifgb_rx_port_3_cgm_tc2_dropped_packets {
      type oc-yang:counter64;
      description
        "RX port cgm ostc2 drops counter. Counts packets that were totally dropped and will not be seen on RX side.";
    }
    leaf counters_slice5_ifg0_ifgb_rx_port_3_cgm_tc2_partially_dropped_packets {
      type oc-yang:counter64;
      description
        "RX port cgm ostc2 partial drops counter. Counts packets that were partially dropped and will be seen on RX side.";
    }
    leaf counters_slice5_ifg0_ifgb_rx_port_3_cgm_tc3_dropped_packets {
      type oc-yang:counter64;
      description
        "RX port cgm ostc3 drops counter. Counts packets that were totally dropped and will not be seen on RX side.";
    }
    leaf counters_slice5_ifg0_ifgb_rx_port_3_cgm_tc3_partially_dropped_packets {
      type oc-yang:counter64;
      description
        "RX port cgm ostc3 partial drops counter. Counts packets that were partially dropped and will be seen on RX side.";
    }
    leaf counters_slice5_ifg0_ifgb_rx_port_30_cgm_tc0_dropped_packets {
      type oc-yang:counter64;
      description
        "RX port cgm ostc0 drops counter. Counts packets that were totally dropped and will not be seen on RX side.";
    }
    leaf counters_slice5_ifg0_ifgb_rx_port_30_cgm_tc0_partially_dropped_packets {
      type oc-yang:counter64;
      description
        "RX port cgm ostc0 partial drops counter. Counts packets that were partially dropped and will be seen on RX side.";
    }
    leaf counters_slice5_ifg0_ifgb_rx_port_30_cgm_tc1_dropped_packets {
      type oc-yang:counter64;
      description
        "RX port cgm ostc1 drops counter. Counts packets that were totally dropped and will not be seen on RX side.";
    }
    leaf counters_slice5_ifg0_ifgb_rx_port_30_cgm_tc1_partially_dropped_packets {
      type oc-yang:counter64;
      description
        "RX port cgm ostc1 partial drops counter. Counts packets that were partially dropped and will be seen on RX side.";
    }
    leaf counters_slice5_ifg0_ifgb_rx_port_30_cgm_tc2_dropped_packets {
      type oc-yang:counter64;
      description
        "RX port cgm ostc2 drops counter. Counts packets that were totally dropped and will not be seen on RX side.";
    }
    leaf counters_slice5_ifg0_ifgb_rx_port_30_cgm_tc2_partially_dropped_packets {
      type oc-yang:counter64;
      description
        "RX port cgm ostc2 partial drops counter. Counts packets that were partially dropped and will be seen on RX side.";
    }
    leaf counters_slice5_ifg0_ifgb_rx_port_30_cgm_tc3_dropped_packets {
      type oc-yang:counter64;
      description
        "RX port cgm ostc3 drops counter. Counts packets that were totally dropped and will not be seen on RX side.";
    }
    leaf counters_slice5_ifg0_ifgb_rx_port_30_cgm_tc3_partially_dropped_packets {
      type oc-yang:counter64;
      description
        "RX port cgm ostc3 partial drops counter. Counts packets that were partially dropped and will be seen on RX side.";
    }
    leaf counters_slice5_ifg0_ifgb_rx_port_31_cgm_tc0_dropped_packets {
      type oc-yang:counter64;
      description
        "RX port cgm ostc0 drops counter. Counts packets that were totally dropped and will not be seen on RX side.";
    }
    leaf counters_slice5_ifg0_ifgb_rx_port_31_cgm_tc0_partially_dropped_packets {
      type oc-yang:counter64;
      description
        "RX port cgm ostc0 partial drops counter. Counts packets that were partially dropped and will be seen on RX side.";
    }
    leaf counters_slice5_ifg0_ifgb_rx_port_31_cgm_tc1_dropped_packets {
      type oc-yang:counter64;
      description
        "RX port cgm ostc1 drops counter. Counts packets that were totally dropped and will not be seen on RX side.";
    }
    leaf counters_slice5_ifg0_ifgb_rx_port_31_cgm_tc1_partially_dropped_packets {
      type oc-yang:counter64;
      description
        "RX port cgm ostc1 partial drops counter. Counts packets that were partially dropped and will be seen on RX side.";
    }
    leaf counters_slice5_ifg0_ifgb_rx_port_31_cgm_tc2_dropped_packets {
      type oc-yang:counter64;
      description
        "RX port cgm ostc2 drops counter. Counts packets that were totally dropped and will not be seen on RX side.";
    }
    leaf counters_slice5_ifg0_ifgb_rx_port_31_cgm_tc2_partially_dropped_packets {
      type oc-yang:counter64;
      description
        "RX port cgm ostc2 partial drops counter. Counts packets that were partially dropped and will be seen on RX side.";
    }
    leaf counters_slice5_ifg0_ifgb_rx_port_31_cgm_tc3_dropped_packets {
      type oc-yang:counter64;
      description
        "RX port cgm ostc3 drops counter. Counts packets that were totally dropped and will not be seen on RX side.";
    }
    leaf counters_slice5_ifg0_ifgb_rx_port_31_cgm_tc3_partially_dropped_packets {
      type oc-yang:counter64;
      description
        "RX port cgm ostc3 partial drops counter. Counts packets that were partially dropped and will be seen on RX side.";
    }
    leaf counters_slice5_ifg0_ifgb_rx_port_4_cgm_tc0_dropped_packets {
      type oc-yang:counter64;
      description
        "RX port cgm ostc0 drops counter. Counts packets that were totally dropped and will not be seen on RX side.";
    }
    leaf counters_slice5_ifg0_ifgb_rx_port_4_cgm_tc0_partially_dropped_packets {
      type oc-yang:counter64;
      description
        "RX port cgm ostc0 partial drops counter. Counts packets that were partially dropped and will be seen on RX side.";
    }
    leaf counters_slice5_ifg0_ifgb_rx_port_4_cgm_tc1_dropped_packets {
      type oc-yang:counter64;
      description
        "RX port cgm ostc1 drops counter. Counts packets that were totally dropped and will not be seen on RX side.";
    }
    leaf counters_slice5_ifg0_ifgb_rx_port_4_cgm_tc1_partially_dropped_packets {
      type oc-yang:counter64;
      description
        "RX port cgm ostc1 partial drops counter. Counts packets that were partially dropped and will be seen on RX side.";
    }
    leaf counters_slice5_ifg0_ifgb_rx_port_4_cgm_tc2_dropped_packets {
      type oc-yang:counter64;
      description
        "RX port cgm ostc2 drops counter. Counts packets that were totally dropped and will not be seen on RX side.";
    }
    leaf counters_slice5_ifg0_ifgb_rx_port_4_cgm_tc2_partially_dropped_packets {
      type oc-yang:counter64;
      description
        "RX port cgm ostc2 partial drops counter. Counts packets that were partially dropped and will be seen on RX side.";
    }
    leaf counters_slice5_ifg0_ifgb_rx_port_4_cgm_tc3_dropped_packets {
      type oc-yang:counter64;
      description
        "RX port cgm ostc3 drops counter. Counts packets that were totally dropped and will not be seen on RX side.";
    }
    leaf counters_slice5_ifg0_ifgb_rx_port_4_cgm_tc3_partially_dropped_packets {
      type oc-yang:counter64;
      description
        "RX port cgm ostc3 partial drops counter. Counts packets that were partially dropped and will be seen on RX side.";
    }
    leaf counters_slice5_ifg0_ifgb_rx_port_5_cgm_tc0_dropped_packets {
      type oc-yang:counter64;
      description
        "RX port cgm ostc0 drops counter. Counts packets that were totally dropped and will not be seen on RX side.";
    }
    leaf counters_slice5_ifg0_ifgb_rx_port_5_cgm_tc0_partially_dropped_packets {
      type oc-yang:counter64;
      description
        "RX port cgm ostc0 partial drops counter. Counts packets that were partially dropped and will be seen on RX side.";
    }
    leaf counters_slice5_ifg0_ifgb_rx_port_5_cgm_tc1_dropped_packets {
      type oc-yang:counter64;
      description
        "RX port cgm ostc1 drops counter. Counts packets that were totally dropped and will not be seen on RX side.";
    }
    leaf counters_slice5_ifg0_ifgb_rx_port_5_cgm_tc1_partially_dropped_packets {
      type oc-yang:counter64;
      description
        "RX port cgm ostc1 partial drops counter. Counts packets that were partially dropped and will be seen on RX side.";
    }
    leaf counters_slice5_ifg0_ifgb_rx_port_5_cgm_tc2_dropped_packets {
      type oc-yang:counter64;
      description
        "RX port cgm ostc2 drops counter. Counts packets that were totally dropped and will not be seen on RX side.";
    }
    leaf counters_slice5_ifg0_ifgb_rx_port_5_cgm_tc2_partially_dropped_packets {
      type oc-yang:counter64;
      description
        "RX port cgm ostc2 partial drops counter. Counts packets that were partially dropped and will be seen on RX side.";
    }
    leaf counters_slice5_ifg0_ifgb_rx_port_5_cgm_tc3_dropped_packets {
      type oc-yang:counter64;
      description
        "RX port cgm ostc3 drops counter. Counts packets that were totally dropped and will not be seen on RX side.";
    }
    leaf counters_slice5_ifg0_ifgb_rx_port_5_cgm_tc3_partially_dropped_packets {
      type oc-yang:counter64;
      description
        "RX port cgm ostc3 partial drops counter. Counts packets that were partially dropped and will be seen on RX side.";
    }
    leaf counters_slice5_ifg0_ifgb_rx_port_6_cgm_tc0_dropped_packets {
      type oc-yang:counter64;
      description
        "RX port cgm ostc0 drops counter. Counts packets that were totally dropped and will not be seen on RX side.";
    }
    leaf counters_slice5_ifg0_ifgb_rx_port_6_cgm_tc0_partially_dropped_packets {
      type oc-yang:counter64;
      description
        "RX port cgm ostc0 partial drops counter. Counts packets that were partially dropped and will be seen on RX side.";
    }
    leaf counters_slice5_ifg0_ifgb_rx_port_6_cgm_tc1_dropped_packets {
      type oc-yang:counter64;
      description
        "RX port cgm ostc1 drops counter. Counts packets that were totally dropped and will not be seen on RX side.";
    }
    leaf counters_slice5_ifg0_ifgb_rx_port_6_cgm_tc1_partially_dropped_packets {
      type oc-yang:counter64;
      description
        "RX port cgm ostc1 partial drops counter. Counts packets that were partially dropped and will be seen on RX side.";
    }
    leaf counters_slice5_ifg0_ifgb_rx_port_6_cgm_tc2_dropped_packets {
      type oc-yang:counter64;
      description
        "RX port cgm ostc2 drops counter. Counts packets that were totally dropped and will not be seen on RX side.";
    }
    leaf counters_slice5_ifg0_ifgb_rx_port_6_cgm_tc2_partially_dropped_packets {
      type oc-yang:counter64;
      description
        "RX port cgm ostc2 partial drops counter. Counts packets that were partially dropped and will be seen on RX side.";
    }
    leaf counters_slice5_ifg0_ifgb_rx_port_6_cgm_tc3_dropped_packets {
      type oc-yang:counter64;
      description
        "RX port cgm ostc3 drops counter. Counts packets that were totally dropped and will not be seen on RX side.";
    }
    leaf counters_slice5_ifg0_ifgb_rx_port_6_cgm_tc3_partially_dropped_packets {
      type oc-yang:counter64;
      description
        "RX port cgm ostc3 partial drops counter. Counts packets that were partially dropped and will be seen on RX side.";
    }
    leaf counters_slice5_ifg0_ifgb_rx_port_7_cgm_tc0_dropped_packets {
      type oc-yang:counter64;
      description
        "RX port cgm ostc0 drops counter. Counts packets that were totally dropped and will not be seen on RX side.";
    }
    leaf counters_slice5_ifg0_ifgb_rx_port_7_cgm_tc0_partially_dropped_packets {
      type oc-yang:counter64;
      description
        "RX port cgm ostc0 partial drops counter. Counts packets that were partially dropped and will be seen on RX side.";
    }
    leaf counters_slice5_ifg0_ifgb_rx_port_7_cgm_tc1_dropped_packets {
      type oc-yang:counter64;
      description
        "RX port cgm ostc1 drops counter. Counts packets that were totally dropped and will not be seen on RX side.";
    }
    leaf counters_slice5_ifg0_ifgb_rx_port_7_cgm_tc1_partially_dropped_packets {
      type oc-yang:counter64;
      description
        "RX port cgm ostc1 partial drops counter. Counts packets that were partially dropped and will be seen on RX side.";
    }
    leaf counters_slice5_ifg0_ifgb_rx_port_7_cgm_tc2_dropped_packets {
      type oc-yang:counter64;
      description
        "RX port cgm ostc2 drops counter. Counts packets that were totally dropped and will not be seen on RX side.";
    }
    leaf counters_slice5_ifg0_ifgb_rx_port_7_cgm_tc2_partially_dropped_packets {
      type oc-yang:counter64;
      description
        "RX port cgm ostc2 partial drops counter. Counts packets that were partially dropped and will be seen on RX side.";
    }
    leaf counters_slice5_ifg0_ifgb_rx_port_7_cgm_tc3_dropped_packets {
      type oc-yang:counter64;
      description
        "RX port cgm ostc3 drops counter. Counts packets that were totally dropped and will not be seen on RX side.";
    }
    leaf counters_slice5_ifg0_ifgb_rx_port_7_cgm_tc3_partially_dropped_packets {
      type oc-yang:counter64;
      description
        "RX port cgm ostc3 partial drops counter. Counts packets that were partially dropped and will be seen on RX side.";
    }
    leaf counters_slice5_ifg0_ifgb_rx_port_8_cgm_tc0_dropped_packets {
      type oc-yang:counter64;
      description
        "RX port cgm ostc0 drops counter. Counts packets that were totally dropped and will not be seen on RX side.";
    }
    leaf counters_slice5_ifg0_ifgb_rx_port_8_cgm_tc0_partially_dropped_packets {
      type oc-yang:counter64;
      description
        "RX port cgm ostc0 partial drops counter. Counts packets that were partially dropped and will be seen on RX side.";
    }
    leaf counters_slice5_ifg0_ifgb_rx_port_8_cgm_tc1_dropped_packets {
      type oc-yang:counter64;
      description
        "RX port cgm ostc1 drops counter. Counts packets that were totally dropped and will not be seen on RX side.";
    }
    leaf counters_slice5_ifg0_ifgb_rx_port_8_cgm_tc1_partially_dropped_packets {
      type oc-yang:counter64;
      description
        "RX port cgm ostc1 partial drops counter. Counts packets that were partially dropped and will be seen on RX side.";
    }
    leaf counters_slice5_ifg0_ifgb_rx_port_8_cgm_tc2_dropped_packets {
      type oc-yang:counter64;
      description
        "RX port cgm ostc2 drops counter. Counts packets that were totally dropped and will not be seen on RX side.";
    }
    leaf counters_slice5_ifg0_ifgb_rx_port_8_cgm_tc2_partially_dropped_packets {
      type oc-yang:counter64;
      description
        "RX port cgm ostc2 partial drops counter. Counts packets that were partially dropped and will be seen on RX side.";
    }
    leaf counters_slice5_ifg0_ifgb_rx_port_8_cgm_tc3_dropped_packets {
      type oc-yang:counter64;
      description
        "RX port cgm ostc3 drops counter. Counts packets that were totally dropped and will not be seen on RX side.";
    }
    leaf counters_slice5_ifg0_ifgb_rx_port_8_cgm_tc3_partially_dropped_packets {
      type oc-yang:counter64;
      description
        "RX port cgm ostc3 partial drops counter. Counts packets that were partially dropped and will be seen on RX side.";
    }
    leaf counters_slice5_ifg0_ifgb_rx_port_9_cgm_tc0_dropped_packets {
      type oc-yang:counter64;
      description
        "RX port cgm ostc0 drops counter. Counts packets that were totally dropped and will not be seen on RX side.";
    }
    leaf counters_slice5_ifg0_ifgb_rx_port_9_cgm_tc0_partially_dropped_packets {
      type oc-yang:counter64;
      description
        "RX port cgm ostc0 partial drops counter. Counts packets that were partially dropped and will be seen on RX side.";
    }
    leaf counters_slice5_ifg0_ifgb_rx_port_9_cgm_tc1_dropped_packets {
      type oc-yang:counter64;
      description
        "RX port cgm ostc1 drops counter. Counts packets that were totally dropped and will not be seen on RX side.";
    }
    leaf counters_slice5_ifg0_ifgb_rx_port_9_cgm_tc1_partially_dropped_packets {
      type oc-yang:counter64;
      description
        "RX port cgm ostc1 partial drops counter. Counts packets that were partially dropped and will be seen on RX side.";
    }
    leaf counters_slice5_ifg0_ifgb_rx_port_9_cgm_tc2_dropped_packets {
      type oc-yang:counter64;
      description
        "RX port cgm ostc2 drops counter. Counts packets that were totally dropped and will not be seen on RX side.";
    }
    leaf counters_slice5_ifg0_ifgb_rx_port_9_cgm_tc2_partially_dropped_packets {
      type oc-yang:counter64;
      description
        "RX port cgm ostc2 partial drops counter. Counts packets that were partially dropped and will be seen on RX side.";
    }
    leaf counters_slice5_ifg0_ifgb_rx_port_9_cgm_tc3_dropped_packets {
      type oc-yang:counter64;
      description
        "RX port cgm ostc3 drops counter. Counts packets that were totally dropped and will not be seen on RX side.";
    }
    leaf counters_slice5_ifg0_ifgb_rx_port_9_cgm_tc3_partially_dropped_packets {
      type oc-yang:counter64;
      description
        "RX port cgm ostc3 partial drops counter. Counts packets that were partially dropped and will be seen on RX side.";
    }
    leaf counters_slice5_ifg1_ifgb_rx_port_0_cgm_tc0_dropped_packets {
      type oc-yang:counter64;
      description
        "RX port cgm ostc0 drops counter. Counts packets that were totally dropped and will not be seen on RX side.";
    }
    leaf counters_slice5_ifg1_ifgb_rx_port_0_cgm_tc0_partially_dropped_packets {
      type oc-yang:counter64;
      description
        "RX port cgm ostc0 partial drops counter. Counts packets that were partially dropped and will be seen on RX side.";
    }
    leaf counters_slice5_ifg1_ifgb_rx_port_0_cgm_tc1_dropped_packets {
      type oc-yang:counter64;
      description
        "RX port cgm ostc1 drops counter. Counts packets that were totally dropped and will not be seen on RX side.";
    }
    leaf counters_slice5_ifg1_ifgb_rx_port_0_cgm_tc1_partially_dropped_packets {
      type oc-yang:counter64;
      description
        "RX port cgm ostc1 partial drops counter. Counts packets that were partially dropped and will be seen on RX side.";
    }
    leaf counters_slice5_ifg1_ifgb_rx_port_0_cgm_tc2_dropped_packets {
      type oc-yang:counter64;
      description
        "RX port cgm ostc2 drops counter. Counts packets that were totally dropped and will not be seen on RX side.";
    }
    leaf counters_slice5_ifg1_ifgb_rx_port_0_cgm_tc2_partially_dropped_packets {
      type oc-yang:counter64;
      description
        "RX port cgm ostc2 partial drops counter. Counts packets that were partially dropped and will be seen on RX side.";
    }
    leaf counters_slice5_ifg1_ifgb_rx_port_0_cgm_tc3_dropped_packets {
      type oc-yang:counter64;
      description
        "RX port cgm ostc3 drops counter. Counts packets that were totally dropped and will not be seen on RX side.";
    }
    leaf counters_slice5_ifg1_ifgb_rx_port_0_cgm_tc3_partially_dropped_packets {
      type oc-yang:counter64;
      description
        "RX port cgm ostc3 partial drops counter. Counts packets that were partially dropped and will be seen on RX side.";
    }
    leaf counters_slice5_ifg1_ifgb_rx_port_1_cgm_tc0_dropped_packets {
      type oc-yang:counter64;
      description
        "RX port cgm ostc0 drops counter. Counts packets that were totally dropped and will not be seen on RX side.";
    }
    leaf counters_slice5_ifg1_ifgb_rx_port_1_cgm_tc0_partially_dropped_packets {
      type oc-yang:counter64;
      description
        "RX port cgm ostc0 partial drops counter. Counts packets that were partially dropped and will be seen on RX side.";
    }
    leaf counters_slice5_ifg1_ifgb_rx_port_1_cgm_tc1_dropped_packets {
      type oc-yang:counter64;
      description
        "RX port cgm ostc1 drops counter. Counts packets that were totally dropped and will not be seen on RX side.";
    }
    leaf counters_slice5_ifg1_ifgb_rx_port_1_cgm_tc1_partially_dropped_packets {
      type oc-yang:counter64;
      description
        "RX port cgm ostc1 partial drops counter. Counts packets that were partially dropped and will be seen on RX side.";
    }
    leaf counters_slice5_ifg1_ifgb_rx_port_1_cgm_tc2_dropped_packets {
      type oc-yang:counter64;
      description
        "RX port cgm ostc2 drops counter. Counts packets that were totally dropped and will not be seen on RX side.";
    }
    leaf counters_slice5_ifg1_ifgb_rx_port_1_cgm_tc2_partially_dropped_packets {
      type oc-yang:counter64;
      description
        "RX port cgm ostc2 partial drops counter. Counts packets that were partially dropped and will be seen on RX side.";
    }
    leaf counters_slice5_ifg1_ifgb_rx_port_1_cgm_tc3_dropped_packets {
      type oc-yang:counter64;
      description
        "RX port cgm ostc3 drops counter. Counts packets that were totally dropped and will not be seen on RX side.";
    }
    leaf counters_slice5_ifg1_ifgb_rx_port_1_cgm_tc3_partially_dropped_packets {
      type oc-yang:counter64;
      description
        "RX port cgm ostc3 partial drops counter. Counts packets that were partially dropped and will be seen on RX side.";
    }
    leaf counters_slice5_ifg1_ifgb_rx_port_10_cgm_tc0_dropped_packets {
      type oc-yang:counter64;
      description
        "RX port cgm ostc0 drops counter. Counts packets that were totally dropped and will not be seen on RX side.";
    }
    leaf counters_slice5_ifg1_ifgb_rx_port_10_cgm_tc0_partially_dropped_packets {
      type oc-yang:counter64;
      description
        "RX port cgm ostc0 partial drops counter. Counts packets that were partially dropped and will be seen on RX side.";
    }
    leaf counters_slice5_ifg1_ifgb_rx_port_10_cgm_tc1_dropped_packets {
      type oc-yang:counter64;
      description
        "RX port cgm ostc1 drops counter. Counts packets that were totally dropped and will not be seen on RX side.";
    }
    leaf counters_slice5_ifg1_ifgb_rx_port_10_cgm_tc1_partially_dropped_packets {
      type oc-yang:counter64;
      description
        "RX port cgm ostc1 partial drops counter. Counts packets that were partially dropped and will be seen on RX side.";
    }
    leaf counters_slice5_ifg1_ifgb_rx_port_10_cgm_tc2_dropped_packets {
      type oc-yang:counter64;
      description
        "RX port cgm ostc2 drops counter. Counts packets that were totally dropped and will not be seen on RX side.";
    }
    leaf counters_slice5_ifg1_ifgb_rx_port_10_cgm_tc2_partially_dropped_packets {
      type oc-yang:counter64;
      description
        "RX port cgm ostc2 partial drops counter. Counts packets that were partially dropped and will be seen on RX side.";
    }
    leaf counters_slice5_ifg1_ifgb_rx_port_10_cgm_tc3_dropped_packets {
      type oc-yang:counter64;
      description
        "RX port cgm ostc3 drops counter. Counts packets that were totally dropped and will not be seen on RX side.";
    }
    leaf counters_slice5_ifg1_ifgb_rx_port_10_cgm_tc3_partially_dropped_packets {
      type oc-yang:counter64;
      description
        "RX port cgm ostc3 partial drops counter. Counts packets that were partially dropped and will be seen on RX side.";
    }
    leaf counters_slice5_ifg1_ifgb_rx_port_11_cgm_tc0_dropped_packets {
      type oc-yang:counter64;
      description
        "RX port cgm ostc0 drops counter. Counts packets that were totally dropped and will not be seen on RX side.";
    }
    leaf counters_slice5_ifg1_ifgb_rx_port_11_cgm_tc0_partially_dropped_packets {
      type oc-yang:counter64;
      description
        "RX port cgm ostc0 partial drops counter. Counts packets that were partially dropped and will be seen on RX side.";
    }
    leaf counters_slice5_ifg1_ifgb_rx_port_11_cgm_tc1_dropped_packets {
      type oc-yang:counter64;
      description
        "RX port cgm ostc1 drops counter. Counts packets that were totally dropped and will not be seen on RX side.";
    }
    leaf counters_slice5_ifg1_ifgb_rx_port_11_cgm_tc1_partially_dropped_packets {
      type oc-yang:counter64;
      description
        "RX port cgm ostc1 partial drops counter. Counts packets that were partially dropped and will be seen on RX side.";
    }
    leaf counters_slice5_ifg1_ifgb_rx_port_11_cgm_tc2_dropped_packets {
      type oc-yang:counter64;
      description
        "RX port cgm ostc2 drops counter. Counts packets that were totally dropped and will not be seen on RX side.";
    }
    leaf counters_slice5_ifg1_ifgb_rx_port_11_cgm_tc2_partially_dropped_packets {
      type oc-yang:counter64;
      description
        "RX port cgm ostc2 partial drops counter. Counts packets that were partially dropped and will be seen on RX side.";
    }
    leaf counters_slice5_ifg1_ifgb_rx_port_11_cgm_tc3_dropped_packets {
      type oc-yang:counter64;
      description
        "RX port cgm ostc3 drops counter. Counts packets that were totally dropped and will not be seen on RX side.";
    }
    leaf counters_slice5_ifg1_ifgb_rx_port_11_cgm_tc3_partially_dropped_packets {
      type oc-yang:counter64;
      description
        "RX port cgm ostc3 partial drops counter. Counts packets that were partially dropped and will be seen on RX side.";
    }
    leaf counters_slice5_ifg1_ifgb_rx_port_12_cgm_tc0_dropped_packets {
      type oc-yang:counter64;
      description
        "RX port cgm ostc0 drops counter. Counts packets that were totally dropped and will not be seen on RX side.";
    }
    leaf counters_slice5_ifg1_ifgb_rx_port_12_cgm_tc0_partially_dropped_packets {
      type oc-yang:counter64;
      description
        "RX port cgm ostc0 partial drops counter. Counts packets that were partially dropped and will be seen on RX side.";
    }
    leaf counters_slice5_ifg1_ifgb_rx_port_12_cgm_tc1_dropped_packets {
      type oc-yang:counter64;
      description
        "RX port cgm ostc1 drops counter. Counts packets that were totally dropped and will not be seen on RX side.";
    }
    leaf counters_slice5_ifg1_ifgb_rx_port_12_cgm_tc1_partially_dropped_packets {
      type oc-yang:counter64;
      description
        "RX port cgm ostc1 partial drops counter. Counts packets that were partially dropped and will be seen on RX side.";
    }
    leaf counters_slice5_ifg1_ifgb_rx_port_12_cgm_tc2_dropped_packets {
      type oc-yang:counter64;
      description
        "RX port cgm ostc2 drops counter. Counts packets that were totally dropped and will not be seen on RX side.";
    }
    leaf counters_slice5_ifg1_ifgb_rx_port_12_cgm_tc2_partially_dropped_packets {
      type oc-yang:counter64;
      description
        "RX port cgm ostc2 partial drops counter. Counts packets that were partially dropped and will be seen on RX side.";
    }
    leaf counters_slice5_ifg1_ifgb_rx_port_12_cgm_tc3_dropped_packets {
      type oc-yang:counter64;
      description
        "RX port cgm ostc3 drops counter. Counts packets that were totally dropped and will not be seen on RX side.";
    }
    leaf counters_slice5_ifg1_ifgb_rx_port_12_cgm_tc3_partially_dropped_packets {
      type oc-yang:counter64;
      description
        "RX port cgm ostc3 partial drops counter. Counts packets that were partially dropped and will be seen on RX side.";
    }
    leaf counters_slice5_ifg1_ifgb_rx_port_13_cgm_tc0_dropped_packets {
      type oc-yang:counter64;
      description
        "RX port cgm ostc0 drops counter. Counts packets that were totally dropped and will not be seen on RX side.";
    }
    leaf counters_slice5_ifg1_ifgb_rx_port_13_cgm_tc0_partially_dropped_packets {
      type oc-yang:counter64;
      description
        "RX port cgm ostc0 partial drops counter. Counts packets that were partially dropped and will be seen on RX side.";
    }
    leaf counters_slice5_ifg1_ifgb_rx_port_13_cgm_tc1_dropped_packets {
      type oc-yang:counter64;
      description
        "RX port cgm ostc1 drops counter. Counts packets that were totally dropped and will not be seen on RX side.";
    }
    leaf counters_slice5_ifg1_ifgb_rx_port_13_cgm_tc1_partially_dropped_packets {
      type oc-yang:counter64;
      description
        "RX port cgm ostc1 partial drops counter. Counts packets that were partially dropped and will be seen on RX side.";
    }
    leaf counters_slice5_ifg1_ifgb_rx_port_13_cgm_tc2_dropped_packets {
      type oc-yang:counter64;
      description
        "RX port cgm ostc2 drops counter. Counts packets that were totally dropped and will not be seen on RX side.";
    }
    leaf counters_slice5_ifg1_ifgb_rx_port_13_cgm_tc2_partially_dropped_packets {
      type oc-yang:counter64;
      description
        "RX port cgm ostc2 partial drops counter. Counts packets that were partially dropped and will be seen on RX side.";
    }
    leaf counters_slice5_ifg1_ifgb_rx_port_13_cgm_tc3_dropped_packets {
      type oc-yang:counter64;
      description
        "RX port cgm ostc3 drops counter. Counts packets that were totally dropped and will not be seen on RX side.";
    }
    leaf counters_slice5_ifg1_ifgb_rx_port_13_cgm_tc3_partially_dropped_packets {
      type oc-yang:counter64;
      description
        "RX port cgm ostc3 partial drops counter. Counts packets that were partially dropped and will be seen on RX side.";
    }
    leaf counters_slice5_ifg1_ifgb_rx_port_14_cgm_tc0_dropped_packets {
      type oc-yang:counter64;
      description
        "RX port cgm ostc0 drops counter. Counts packets that were totally dropped and will not be seen on RX side.";
    }
    leaf counters_slice5_ifg1_ifgb_rx_port_14_cgm_tc0_partially_dropped_packets {
      type oc-yang:counter64;
      description
        "RX port cgm ostc0 partial drops counter. Counts packets that were partially dropped and will be seen on RX side.";
    }
    leaf counters_slice5_ifg1_ifgb_rx_port_14_cgm_tc1_dropped_packets {
      type oc-yang:counter64;
      description
        "RX port cgm ostc1 drops counter. Counts packets that were totally dropped and will not be seen on RX side.";
    }
    leaf counters_slice5_ifg1_ifgb_rx_port_14_cgm_tc1_partially_dropped_packets {
      type oc-yang:counter64;
      description
        "RX port cgm ostc1 partial drops counter. Counts packets that were partially dropped and will be seen on RX side.";
    }
    leaf counters_slice5_ifg1_ifgb_rx_port_14_cgm_tc2_dropped_packets {
      type oc-yang:counter64;
      description
        "RX port cgm ostc2 drops counter. Counts packets that were totally dropped and will not be seen on RX side.";
    }
    leaf counters_slice5_ifg1_ifgb_rx_port_14_cgm_tc2_partially_dropped_packets {
      type oc-yang:counter64;
      description
        "RX port cgm ostc2 partial drops counter. Counts packets that were partially dropped and will be seen on RX side.";
    }
    leaf counters_slice5_ifg1_ifgb_rx_port_14_cgm_tc3_dropped_packets {
      type oc-yang:counter64;
      description
        "RX port cgm ostc3 drops counter. Counts packets that were totally dropped and will not be seen on RX side.";
    }
    leaf counters_slice5_ifg1_ifgb_rx_port_14_cgm_tc3_partially_dropped_packets {
      type oc-yang:counter64;
      description
        "RX port cgm ostc3 partial drops counter. Counts packets that were partially dropped and will be seen on RX side.";
    }
    leaf counters_slice5_ifg1_ifgb_rx_port_15_cgm_tc0_dropped_packets {
      type oc-yang:counter64;
      description
        "RX port cgm ostc0 drops counter. Counts packets that were totally dropped and will not be seen on RX side.";
    }
    leaf counters_slice5_ifg1_ifgb_rx_port_15_cgm_tc0_partially_dropped_packets {
      type oc-yang:counter64;
      description
        "RX port cgm ostc0 partial drops counter. Counts packets that were partially dropped and will be seen on RX side.";
    }
    leaf counters_slice5_ifg1_ifgb_rx_port_15_cgm_tc1_dropped_packets {
      type oc-yang:counter64;
      description
        "RX port cgm ostc1 drops counter. Counts packets that were totally dropped and will not be seen on RX side.";
    }
    leaf counters_slice5_ifg1_ifgb_rx_port_15_cgm_tc1_partially_dropped_packets {
      type oc-yang:counter64;
      description
        "RX port cgm ostc1 partial drops counter. Counts packets that were partially dropped and will be seen on RX side.";
    }
    leaf counters_slice5_ifg1_ifgb_rx_port_15_cgm_tc2_dropped_packets {
      type oc-yang:counter64;
      description
        "RX port cgm ostc2 drops counter. Counts packets that were totally dropped and will not be seen on RX side.";
    }
    leaf counters_slice5_ifg1_ifgb_rx_port_15_cgm_tc2_partially_dropped_packets {
      type oc-yang:counter64;
      description
        "RX port cgm ostc2 partial drops counter. Counts packets that were partially dropped and will be seen on RX side.";
    }
    leaf counters_slice5_ifg1_ifgb_rx_port_15_cgm_tc3_dropped_packets {
      type oc-yang:counter64;
      description
        "RX port cgm ostc3 drops counter. Counts packets that were totally dropped and will not be seen on RX side.";
    }
    leaf counters_slice5_ifg1_ifgb_rx_port_15_cgm_tc3_partially_dropped_packets {
      type oc-yang:counter64;
      description
        "RX port cgm ostc3 partial drops counter. Counts packets that were partially dropped and will be seen on RX side.";
    }
    leaf counters_slice5_ifg1_ifgb_rx_port_16_cgm_tc0_dropped_packets {
      type oc-yang:counter64;
      description
        "RX port cgm ostc0 drops counter. Counts packets that were totally dropped and will not be seen on RX side.";
    }
    leaf counters_slice5_ifg1_ifgb_rx_port_16_cgm_tc0_partially_dropped_packets {
      type oc-yang:counter64;
      description
        "RX port cgm ostc0 partial drops counter. Counts packets that were partially dropped and will be seen on RX side.";
    }
    leaf counters_slice5_ifg1_ifgb_rx_port_16_cgm_tc1_dropped_packets {
      type oc-yang:counter64;
      description
        "RX port cgm ostc1 drops counter. Counts packets that were totally dropped and will not be seen on RX side.";
    }
    leaf counters_slice5_ifg1_ifgb_rx_port_16_cgm_tc1_partially_dropped_packets {
      type oc-yang:counter64;
      description
        "RX port cgm ostc1 partial drops counter. Counts packets that were partially dropped and will be seen on RX side.";
    }
    leaf counters_slice5_ifg1_ifgb_rx_port_16_cgm_tc2_dropped_packets {
      type oc-yang:counter64;
      description
        "RX port cgm ostc2 drops counter. Counts packets that were totally dropped and will not be seen on RX side.";
    }
    leaf counters_slice5_ifg1_ifgb_rx_port_16_cgm_tc2_partially_dropped_packets {
      type oc-yang:counter64;
      description
        "RX port cgm ostc2 partial drops counter. Counts packets that were partially dropped and will be seen on RX side.";
    }
    leaf counters_slice5_ifg1_ifgb_rx_port_16_cgm_tc3_dropped_packets {
      type oc-yang:counter64;
      description
        "RX port cgm ostc3 drops counter. Counts packets that were totally dropped and will not be seen on RX side.";
    }
    leaf counters_slice5_ifg1_ifgb_rx_port_16_cgm_tc3_partially_dropped_packets {
      type oc-yang:counter64;
      description
        "RX port cgm ostc3 partial drops counter. Counts packets that were partially dropped and will be seen on RX side.";
    }
    leaf counters_slice5_ifg1_ifgb_rx_port_17_cgm_tc0_dropped_packets {
      type oc-yang:counter64;
      description
        "RX port cgm ostc0 drops counter. Counts packets that were totally dropped and will not be seen on RX side.";
    }
    leaf counters_slice5_ifg1_ifgb_rx_port_17_cgm_tc0_partially_dropped_packets {
      type oc-yang:counter64;
      description
        "RX port cgm ostc0 partial drops counter. Counts packets that were partially dropped and will be seen on RX side.";
    }
    leaf counters_slice5_ifg1_ifgb_rx_port_17_cgm_tc1_dropped_packets {
      type oc-yang:counter64;
      description
        "RX port cgm ostc1 drops counter. Counts packets that were totally dropped and will not be seen on RX side.";
    }
    leaf counters_slice5_ifg1_ifgb_rx_port_17_cgm_tc1_partially_dropped_packets {
      type oc-yang:counter64;
      description
        "RX port cgm ostc1 partial drops counter. Counts packets that were partially dropped and will be seen on RX side.";
    }
    leaf counters_slice5_ifg1_ifgb_rx_port_17_cgm_tc2_dropped_packets {
      type oc-yang:counter64;
      description
        "RX port cgm ostc2 drops counter. Counts packets that were totally dropped and will not be seen on RX side.";
    }
    leaf counters_slice5_ifg1_ifgb_rx_port_17_cgm_tc2_partially_dropped_packets {
      type oc-yang:counter64;
      description
        "RX port cgm ostc2 partial drops counter. Counts packets that were partially dropped and will be seen on RX side.";
    }
    leaf counters_slice5_ifg1_ifgb_rx_port_17_cgm_tc3_dropped_packets {
      type oc-yang:counter64;
      description
        "RX port cgm ostc3 drops counter. Counts packets that were totally dropped and will not be seen on RX side.";
    }
    leaf counters_slice5_ifg1_ifgb_rx_port_17_cgm_tc3_partially_dropped_packets {
      type oc-yang:counter64;
      description
        "RX port cgm ostc3 partial drops counter. Counts packets that were partially dropped and will be seen on RX side.";
    }
    leaf counters_slice5_ifg1_ifgb_rx_port_18_cgm_tc0_dropped_packets {
      type oc-yang:counter64;
      description
        "RX port cgm ostc0 drops counter. Counts packets that were totally dropped and will not be seen on RX side.";
    }
    leaf counters_slice5_ifg1_ifgb_rx_port_18_cgm_tc0_partially_dropped_packets {
      type oc-yang:counter64;
      description
        "RX port cgm ostc0 partial drops counter. Counts packets that were partially dropped and will be seen on RX side.";
    }
    leaf counters_slice5_ifg1_ifgb_rx_port_18_cgm_tc1_dropped_packets {
      type oc-yang:counter64;
      description
        "RX port cgm ostc1 drops counter. Counts packets that were totally dropped and will not be seen on RX side.";
    }
    leaf counters_slice5_ifg1_ifgb_rx_port_18_cgm_tc1_partially_dropped_packets {
      type oc-yang:counter64;
      description
        "RX port cgm ostc1 partial drops counter. Counts packets that were partially dropped and will be seen on RX side.";
    }
    leaf counters_slice5_ifg1_ifgb_rx_port_18_cgm_tc2_dropped_packets {
      type oc-yang:counter64;
      description
        "RX port cgm ostc2 drops counter. Counts packets that were totally dropped and will not be seen on RX side.";
    }
    leaf counters_slice5_ifg1_ifgb_rx_port_18_cgm_tc2_partially_dropped_packets {
      type oc-yang:counter64;
      description
        "RX port cgm ostc2 partial drops counter. Counts packets that were partially dropped and will be seen on RX side.";
    }
    leaf counters_slice5_ifg1_ifgb_rx_port_18_cgm_tc3_dropped_packets {
      type oc-yang:counter64;
      description
        "RX port cgm ostc3 drops counter. Counts packets that were totally dropped and will not be seen on RX side.";
    }
    leaf counters_slice5_ifg1_ifgb_rx_port_18_cgm_tc3_partially_dropped_packets {
      type oc-yang:counter64;
      description
        "RX port cgm ostc3 partial drops counter. Counts packets that were partially dropped and will be seen on RX side.";
    }
    leaf counters_slice5_ifg1_ifgb_rx_port_19_cgm_tc0_dropped_packets {
      type oc-yang:counter64;
      description
        "RX port cgm ostc0 drops counter. Counts packets that were totally dropped and will not be seen on RX side.";
    }
    leaf counters_slice5_ifg1_ifgb_rx_port_19_cgm_tc0_partially_dropped_packets {
      type oc-yang:counter64;
      description
        "RX port cgm ostc0 partial drops counter. Counts packets that were partially dropped and will be seen on RX side.";
    }
    leaf counters_slice5_ifg1_ifgb_rx_port_19_cgm_tc1_dropped_packets {
      type oc-yang:counter64;
      description
        "RX port cgm ostc1 drops counter. Counts packets that were totally dropped and will not be seen on RX side.";
    }
    leaf counters_slice5_ifg1_ifgb_rx_port_19_cgm_tc1_partially_dropped_packets {
      type oc-yang:counter64;
      description
        "RX port cgm ostc1 partial drops counter. Counts packets that were partially dropped and will be seen on RX side.";
    }
    leaf counters_slice5_ifg1_ifgb_rx_port_19_cgm_tc2_dropped_packets {
      type oc-yang:counter64;
      description
        "RX port cgm ostc2 drops counter. Counts packets that were totally dropped and will not be seen on RX side.";
    }
    leaf counters_slice5_ifg1_ifgb_rx_port_19_cgm_tc2_partially_dropped_packets {
      type oc-yang:counter64;
      description
        "RX port cgm ostc2 partial drops counter. Counts packets that were partially dropped and will be seen on RX side.";
    }
    leaf counters_slice5_ifg1_ifgb_rx_port_19_cgm_tc3_dropped_packets {
      type oc-yang:counter64;
      description
        "RX port cgm ostc3 drops counter. Counts packets that were totally dropped and will not be seen on RX side.";
    }
    leaf counters_slice5_ifg1_ifgb_rx_port_19_cgm_tc3_partially_dropped_packets {
      type oc-yang:counter64;
      description
        "RX port cgm ostc3 partial drops counter. Counts packets that were partially dropped and will be seen on RX side.";
    }
    leaf counters_slice5_ifg1_ifgb_rx_port_2_cgm_tc0_dropped_packets {
      type oc-yang:counter64;
      description
        "RX port cgm ostc0 drops counter. Counts packets that were totally dropped and will not be seen on RX side.";
    }
    leaf counters_slice5_ifg1_ifgb_rx_port_2_cgm_tc0_partially_dropped_packets {
      type oc-yang:counter64;
      description
        "RX port cgm ostc0 partial drops counter. Counts packets that were partially dropped and will be seen on RX side.";
    }
    leaf counters_slice5_ifg1_ifgb_rx_port_2_cgm_tc1_dropped_packets {
      type oc-yang:counter64;
      description
        "RX port cgm ostc1 drops counter. Counts packets that were totally dropped and will not be seen on RX side.";
    }
    leaf counters_slice5_ifg1_ifgb_rx_port_2_cgm_tc1_partially_dropped_packets {
      type oc-yang:counter64;
      description
        "RX port cgm ostc1 partial drops counter. Counts packets that were partially dropped and will be seen on RX side.";
    }
    leaf counters_slice5_ifg1_ifgb_rx_port_2_cgm_tc2_dropped_packets {
      type oc-yang:counter64;
      description
        "RX port cgm ostc2 drops counter. Counts packets that were totally dropped and will not be seen on RX side.";
    }
    leaf counters_slice5_ifg1_ifgb_rx_port_2_cgm_tc2_partially_dropped_packets {
      type oc-yang:counter64;
      description
        "RX port cgm ostc2 partial drops counter. Counts packets that were partially dropped and will be seen on RX side.";
    }
    leaf counters_slice5_ifg1_ifgb_rx_port_2_cgm_tc3_dropped_packets {
      type oc-yang:counter64;
      description
        "RX port cgm ostc3 drops counter. Counts packets that were totally dropped and will not be seen on RX side.";
    }
    leaf counters_slice5_ifg1_ifgb_rx_port_2_cgm_tc3_partially_dropped_packets {
      type oc-yang:counter64;
      description
        "RX port cgm ostc3 partial drops counter. Counts packets that were partially dropped and will be seen on RX side.";
    }
    leaf counters_slice5_ifg1_ifgb_rx_port_20_cgm_tc0_dropped_packets {
      type oc-yang:counter64;
      description
        "RX port cgm ostc0 drops counter. Counts packets that were totally dropped and will not be seen on RX side.";
    }
    leaf counters_slice5_ifg1_ifgb_rx_port_20_cgm_tc0_partially_dropped_packets {
      type oc-yang:counter64;
      description
        "RX port cgm ostc0 partial drops counter. Counts packets that were partially dropped and will be seen on RX side.";
    }
    leaf counters_slice5_ifg1_ifgb_rx_port_20_cgm_tc1_dropped_packets {
      type oc-yang:counter64;
      description
        "RX port cgm ostc1 drops counter. Counts packets that were totally dropped and will not be seen on RX side.";
    }
    leaf counters_slice5_ifg1_ifgb_rx_port_20_cgm_tc1_partially_dropped_packets {
      type oc-yang:counter64;
      description
        "RX port cgm ostc1 partial drops counter. Counts packets that were partially dropped and will be seen on RX side.";
    }
    leaf counters_slice5_ifg1_ifgb_rx_port_20_cgm_tc2_dropped_packets {
      type oc-yang:counter64;
      description
        "RX port cgm ostc2 drops counter. Counts packets that were totally dropped and will not be seen on RX side.";
    }
    leaf counters_slice5_ifg1_ifgb_rx_port_20_cgm_tc2_partially_dropped_packets {
      type oc-yang:counter64;
      description
        "RX port cgm ostc2 partial drops counter. Counts packets that were partially dropped and will be seen on RX side.";
    }
    leaf counters_slice5_ifg1_ifgb_rx_port_20_cgm_tc3_dropped_packets {
      type oc-yang:counter64;
      description
        "RX port cgm ostc3 drops counter. Counts packets that were totally dropped and will not be seen on RX side.";
    }
    leaf counters_slice5_ifg1_ifgb_rx_port_20_cgm_tc3_partially_dropped_packets {
      type oc-yang:counter64;
      description
        "RX port cgm ostc3 partial drops counter. Counts packets that were partially dropped and will be seen on RX side.";
    }
    leaf counters_slice5_ifg1_ifgb_rx_port_21_cgm_tc0_dropped_packets {
      type oc-yang:counter64;
      description
        "RX port cgm ostc0 drops counter. Counts packets that were totally dropped and will not be seen on RX side.";
    }
    leaf counters_slice5_ifg1_ifgb_rx_port_21_cgm_tc0_partially_dropped_packets {
      type oc-yang:counter64;
      description
        "RX port cgm ostc0 partial drops counter. Counts packets that were partially dropped and will be seen on RX side.";
    }
    leaf counters_slice5_ifg1_ifgb_rx_port_21_cgm_tc1_dropped_packets {
      type oc-yang:counter64;
      description
        "RX port cgm ostc1 drops counter. Counts packets that were totally dropped and will not be seen on RX side.";
    }
    leaf counters_slice5_ifg1_ifgb_rx_port_21_cgm_tc1_partially_dropped_packets {
      type oc-yang:counter64;
      description
        "RX port cgm ostc1 partial drops counter. Counts packets that were partially dropped and will be seen on RX side.";
    }
    leaf counters_slice5_ifg1_ifgb_rx_port_21_cgm_tc2_dropped_packets {
      type oc-yang:counter64;
      description
        "RX port cgm ostc2 drops counter. Counts packets that were totally dropped and will not be seen on RX side.";
    }
    leaf counters_slice5_ifg1_ifgb_rx_port_21_cgm_tc2_partially_dropped_packets {
      type oc-yang:counter64;
      description
        "RX port cgm ostc2 partial drops counter. Counts packets that were partially dropped and will be seen on RX side.";
    }
    leaf counters_slice5_ifg1_ifgb_rx_port_21_cgm_tc3_dropped_packets {
      type oc-yang:counter64;
      description
        "RX port cgm ostc3 drops counter. Counts packets that were totally dropped and will not be seen on RX side.";
    }
    leaf counters_slice5_ifg1_ifgb_rx_port_21_cgm_tc3_partially_dropped_packets {
      type oc-yang:counter64;
      description
        "RX port cgm ostc3 partial drops counter. Counts packets that were partially dropped and will be seen on RX side.";
    }
    leaf counters_slice5_ifg1_ifgb_rx_port_22_cgm_tc0_dropped_packets {
      type oc-yang:counter64;
      description
        "RX port cgm ostc0 drops counter. Counts packets that were totally dropped and will not be seen on RX side.";
    }
    leaf counters_slice5_ifg1_ifgb_rx_port_22_cgm_tc0_partially_dropped_packets {
      type oc-yang:counter64;
      description
        "RX port cgm ostc0 partial drops counter. Counts packets that were partially dropped and will be seen on RX side.";
    }
    leaf counters_slice5_ifg1_ifgb_rx_port_22_cgm_tc1_dropped_packets {
      type oc-yang:counter64;
      description
        "RX port cgm ostc1 drops counter. Counts packets that were totally dropped and will not be seen on RX side.";
    }
    leaf counters_slice5_ifg1_ifgb_rx_port_22_cgm_tc1_partially_dropped_packets {
      type oc-yang:counter64;
      description
        "RX port cgm ostc1 partial drops counter. Counts packets that were partially dropped and will be seen on RX side.";
    }
    leaf counters_slice5_ifg1_ifgb_rx_port_22_cgm_tc2_dropped_packets {
      type oc-yang:counter64;
      description
        "RX port cgm ostc2 drops counter. Counts packets that were totally dropped and will not be seen on RX side.";
    }
    leaf counters_slice5_ifg1_ifgb_rx_port_22_cgm_tc2_partially_dropped_packets {
      type oc-yang:counter64;
      description
        "RX port cgm ostc2 partial drops counter. Counts packets that were partially dropped and will be seen on RX side.";
    }
    leaf counters_slice5_ifg1_ifgb_rx_port_22_cgm_tc3_dropped_packets {
      type oc-yang:counter64;
      description
        "RX port cgm ostc3 drops counter. Counts packets that were totally dropped and will not be seen on RX side.";
    }
    leaf counters_slice5_ifg1_ifgb_rx_port_22_cgm_tc3_partially_dropped_packets {
      type oc-yang:counter64;
      description
        "RX port cgm ostc3 partial drops counter. Counts packets that were partially dropped and will be seen on RX side.";
    }
    leaf counters_slice5_ifg1_ifgb_rx_port_23_cgm_tc0_dropped_packets {
      type oc-yang:counter64;
      description
        "RX port cgm ostc0 drops counter. Counts packets that were totally dropped and will not be seen on RX side.";
    }
    leaf counters_slice5_ifg1_ifgb_rx_port_23_cgm_tc0_partially_dropped_packets {
      type oc-yang:counter64;
      description
        "RX port cgm ostc0 partial drops counter. Counts packets that were partially dropped and will be seen on RX side.";
    }
    leaf counters_slice5_ifg1_ifgb_rx_port_23_cgm_tc1_dropped_packets {
      type oc-yang:counter64;
      description
        "RX port cgm ostc1 drops counter. Counts packets that were totally dropped and will not be seen on RX side.";
    }
    leaf counters_slice5_ifg1_ifgb_rx_port_23_cgm_tc1_partially_dropped_packets {
      type oc-yang:counter64;
      description
        "RX port cgm ostc1 partial drops counter. Counts packets that were partially dropped and will be seen on RX side.";
    }
    leaf counters_slice5_ifg1_ifgb_rx_port_23_cgm_tc2_dropped_packets {
      type oc-yang:counter64;
      description
        "RX port cgm ostc2 drops counter. Counts packets that were totally dropped and will not be seen on RX side.";
    }
    leaf counters_slice5_ifg1_ifgb_rx_port_23_cgm_tc2_partially_dropped_packets {
      type oc-yang:counter64;
      description
        "RX port cgm ostc2 partial drops counter. Counts packets that were partially dropped and will be seen on RX side.";
    }
    leaf counters_slice5_ifg1_ifgb_rx_port_23_cgm_tc3_dropped_packets {
      type oc-yang:counter64;
      description
        "RX port cgm ostc3 drops counter. Counts packets that were totally dropped and will not be seen on RX side.";
    }
    leaf counters_slice5_ifg1_ifgb_rx_port_23_cgm_tc3_partially_dropped_packets {
      type oc-yang:counter64;
      description
        "RX port cgm ostc3 partial drops counter. Counts packets that were partially dropped and will be seen on RX side.";
    }
    leaf counters_slice5_ifg1_ifgb_rx_port_24_cgm_tc0_dropped_packets {
      type oc-yang:counter64;
      description
        "RX port cgm ostc0 drops counter. Counts packets that were totally dropped and will not be seen on RX side.";
    }
    leaf counters_slice5_ifg1_ifgb_rx_port_24_cgm_tc0_partially_dropped_packets {
      type oc-yang:counter64;
      description
        "RX port cgm ostc0 partial drops counter. Counts packets that were partially dropped and will be seen on RX side.";
    }
    leaf counters_slice5_ifg1_ifgb_rx_port_24_cgm_tc1_dropped_packets {
      type oc-yang:counter64;
      description
        "RX port cgm ostc1 drops counter. Counts packets that were totally dropped and will not be seen on RX side.";
    }
    leaf counters_slice5_ifg1_ifgb_rx_port_24_cgm_tc1_partially_dropped_packets {
      type oc-yang:counter64;
      description
        "RX port cgm ostc1 partial drops counter. Counts packets that were partially dropped and will be seen on RX side.";
    }
    leaf counters_slice5_ifg1_ifgb_rx_port_24_cgm_tc2_dropped_packets {
      type oc-yang:counter64;
      description
        "RX port cgm ostc2 drops counter. Counts packets that were totally dropped and will not be seen on RX side.";
    }
    leaf counters_slice5_ifg1_ifgb_rx_port_24_cgm_tc2_partially_dropped_packets {
      type oc-yang:counter64;
      description
        "RX port cgm ostc2 partial drops counter. Counts packets that were partially dropped and will be seen on RX side.";
    }
    leaf counters_slice5_ifg1_ifgb_rx_port_24_cgm_tc3_dropped_packets {
      type oc-yang:counter64;
      description
        "RX port cgm ostc3 drops counter. Counts packets that were totally dropped and will not be seen on RX side.";
    }
    leaf counters_slice5_ifg1_ifgb_rx_port_24_cgm_tc3_partially_dropped_packets {
      type oc-yang:counter64;
      description
        "RX port cgm ostc3 partial drops counter. Counts packets that were partially dropped and will be seen on RX side.";
    }
    leaf counters_slice5_ifg1_ifgb_rx_port_25_cgm_tc0_dropped_packets {
      type oc-yang:counter64;
      description
        "RX port cgm ostc0 drops counter. Counts packets that were totally dropped and will not be seen on RX side.";
    }
    leaf counters_slice5_ifg1_ifgb_rx_port_25_cgm_tc0_partially_dropped_packets {
      type oc-yang:counter64;
      description
        "RX port cgm ostc0 partial drops counter. Counts packets that were partially dropped and will be seen on RX side.";
    }
    leaf counters_slice5_ifg1_ifgb_rx_port_25_cgm_tc1_dropped_packets {
      type oc-yang:counter64;
      description
        "RX port cgm ostc1 drops counter. Counts packets that were totally dropped and will not be seen on RX side.";
    }
    leaf counters_slice5_ifg1_ifgb_rx_port_25_cgm_tc1_partially_dropped_packets {
      type oc-yang:counter64;
      description
        "RX port cgm ostc1 partial drops counter. Counts packets that were partially dropped and will be seen on RX side.";
    }
    leaf counters_slice5_ifg1_ifgb_rx_port_25_cgm_tc2_dropped_packets {
      type oc-yang:counter64;
      description
        "RX port cgm ostc2 drops counter. Counts packets that were totally dropped and will not be seen on RX side.";
    }
    leaf counters_slice5_ifg1_ifgb_rx_port_25_cgm_tc2_partially_dropped_packets {
      type oc-yang:counter64;
      description
        "RX port cgm ostc2 partial drops counter. Counts packets that were partially dropped and will be seen on RX side.";
    }
    leaf counters_slice5_ifg1_ifgb_rx_port_25_cgm_tc3_dropped_packets {
      type oc-yang:counter64;
      description
        "RX port cgm ostc3 drops counter. Counts packets that were totally dropped and will not be seen on RX side.";
    }
    leaf counters_slice5_ifg1_ifgb_rx_port_25_cgm_tc3_partially_dropped_packets {
      type oc-yang:counter64;
      description
        "RX port cgm ostc3 partial drops counter. Counts packets that were partially dropped and will be seen on RX side.";
    }
    leaf counters_slice5_ifg1_ifgb_rx_port_26_cgm_tc0_dropped_packets {
      type oc-yang:counter64;
      description
        "RX port cgm ostc0 drops counter. Counts packets that were totally dropped and will not be seen on RX side.";
    }
    leaf counters_slice5_ifg1_ifgb_rx_port_26_cgm_tc0_partially_dropped_packets {
      type oc-yang:counter64;
      description
        "RX port cgm ostc0 partial drops counter. Counts packets that were partially dropped and will be seen on RX side.";
    }
    leaf counters_slice5_ifg1_ifgb_rx_port_26_cgm_tc1_dropped_packets {
      type oc-yang:counter64;
      description
        "RX port cgm ostc1 drops counter. Counts packets that were totally dropped and will not be seen on RX side.";
    }
    leaf counters_slice5_ifg1_ifgb_rx_port_26_cgm_tc1_partially_dropped_packets {
      type oc-yang:counter64;
      description
        "RX port cgm ostc1 partial drops counter. Counts packets that were partially dropped and will be seen on RX side.";
    }
    leaf counters_slice5_ifg1_ifgb_rx_port_26_cgm_tc2_dropped_packets {
      type oc-yang:counter64;
      description
        "RX port cgm ostc2 drops counter. Counts packets that were totally dropped and will not be seen on RX side.";
    }
    leaf counters_slice5_ifg1_ifgb_rx_port_26_cgm_tc2_partially_dropped_packets {
      type oc-yang:counter64;
      description
        "RX port cgm ostc2 partial drops counter. Counts packets that were partially dropped and will be seen on RX side.";
    }
    leaf counters_slice5_ifg1_ifgb_rx_port_26_cgm_tc3_dropped_packets {
      type oc-yang:counter64;
      description
        "RX port cgm ostc3 drops counter. Counts packets that were totally dropped and will not be seen on RX side.";
    }
    leaf counters_slice5_ifg1_ifgb_rx_port_26_cgm_tc3_partially_dropped_packets {
      type oc-yang:counter64;
      description
        "RX port cgm ostc3 partial drops counter. Counts packets that were partially dropped and will be seen on RX side.";
    }
    leaf counters_slice5_ifg1_ifgb_rx_port_27_cgm_tc0_dropped_packets {
      type oc-yang:counter64;
      description
        "RX port cgm ostc0 drops counter. Counts packets that were totally dropped and will not be seen on RX side.";
    }
    leaf counters_slice5_ifg1_ifgb_rx_port_27_cgm_tc0_partially_dropped_packets {
      type oc-yang:counter64;
      description
        "RX port cgm ostc0 partial drops counter. Counts packets that were partially dropped and will be seen on RX side.";
    }
    leaf counters_slice5_ifg1_ifgb_rx_port_27_cgm_tc1_dropped_packets {
      type oc-yang:counter64;
      description
        "RX port cgm ostc1 drops counter. Counts packets that were totally dropped and will not be seen on RX side.";
    }
    leaf counters_slice5_ifg1_ifgb_rx_port_27_cgm_tc1_partially_dropped_packets {
      type oc-yang:counter64;
      description
        "RX port cgm ostc1 partial drops counter. Counts packets that were partially dropped and will be seen on RX side.";
    }
    leaf counters_slice5_ifg1_ifgb_rx_port_27_cgm_tc2_dropped_packets {
      type oc-yang:counter64;
      description
        "RX port cgm ostc2 drops counter. Counts packets that were totally dropped and will not be seen on RX side.";
    }
    leaf counters_slice5_ifg1_ifgb_rx_port_27_cgm_tc2_partially_dropped_packets {
      type oc-yang:counter64;
      description
        "RX port cgm ostc2 partial drops counter. Counts packets that were partially dropped and will be seen on RX side.";
    }
    leaf counters_slice5_ifg1_ifgb_rx_port_27_cgm_tc3_dropped_packets {
      type oc-yang:counter64;
      description
        "RX port cgm ostc3 drops counter. Counts packets that were totally dropped and will not be seen on RX side.";
    }
    leaf counters_slice5_ifg1_ifgb_rx_port_27_cgm_tc3_partially_dropped_packets {
      type oc-yang:counter64;
      description
        "RX port cgm ostc3 partial drops counter. Counts packets that were partially dropped and will be seen on RX side.";
    }
    leaf counters_slice5_ifg1_ifgb_rx_port_28_cgm_tc0_dropped_packets {
      type oc-yang:counter64;
      description
        "RX port cgm ostc0 drops counter. Counts packets that were totally dropped and will not be seen on RX side.";
    }
    leaf counters_slice5_ifg1_ifgb_rx_port_28_cgm_tc0_partially_dropped_packets {
      type oc-yang:counter64;
      description
        "RX port cgm ostc0 partial drops counter. Counts packets that were partially dropped and will be seen on RX side.";
    }
    leaf counters_slice5_ifg1_ifgb_rx_port_28_cgm_tc1_dropped_packets {
      type oc-yang:counter64;
      description
        "RX port cgm ostc1 drops counter. Counts packets that were totally dropped and will not be seen on RX side.";
    }
    leaf counters_slice5_ifg1_ifgb_rx_port_28_cgm_tc1_partially_dropped_packets {
      type oc-yang:counter64;
      description
        "RX port cgm ostc1 partial drops counter. Counts packets that were partially dropped and will be seen on RX side.";
    }
    leaf counters_slice5_ifg1_ifgb_rx_port_28_cgm_tc2_dropped_packets {
      type oc-yang:counter64;
      description
        "RX port cgm ostc2 drops counter. Counts packets that were totally dropped and will not be seen on RX side.";
    }
    leaf counters_slice5_ifg1_ifgb_rx_port_28_cgm_tc2_partially_dropped_packets {
      type oc-yang:counter64;
      description
        "RX port cgm ostc2 partial drops counter. Counts packets that were partially dropped and will be seen on RX side.";
    }
    leaf counters_slice5_ifg1_ifgb_rx_port_28_cgm_tc3_dropped_packets {
      type oc-yang:counter64;
      description
        "RX port cgm ostc3 drops counter. Counts packets that were totally dropped and will not be seen on RX side.";
    }
    leaf counters_slice5_ifg1_ifgb_rx_port_28_cgm_tc3_partially_dropped_packets {
      type oc-yang:counter64;
      description
        "RX port cgm ostc3 partial drops counter. Counts packets that were partially dropped and will be seen on RX side.";
    }
    leaf counters_slice5_ifg1_ifgb_rx_port_29_cgm_tc0_dropped_packets {
      type oc-yang:counter64;
      description
        "RX port cgm ostc0 drops counter. Counts packets that were totally dropped and will not be seen on RX side.";
    }
    leaf counters_slice5_ifg1_ifgb_rx_port_29_cgm_tc0_partially_dropped_packets {
      type oc-yang:counter64;
      description
        "RX port cgm ostc0 partial drops counter. Counts packets that were partially dropped and will be seen on RX side.";
    }
    leaf counters_slice5_ifg1_ifgb_rx_port_29_cgm_tc1_dropped_packets {
      type oc-yang:counter64;
      description
        "RX port cgm ostc1 drops counter. Counts packets that were totally dropped and will not be seen on RX side.";
    }
    leaf counters_slice5_ifg1_ifgb_rx_port_29_cgm_tc1_partially_dropped_packets {
      type oc-yang:counter64;
      description
        "RX port cgm ostc1 partial drops counter. Counts packets that were partially dropped and will be seen on RX side.";
    }
    leaf counters_slice5_ifg1_ifgb_rx_port_29_cgm_tc2_dropped_packets {
      type oc-yang:counter64;
      description
        "RX port cgm ostc2 drops counter. Counts packets that were totally dropped and will not be seen on RX side.";
    }
    leaf counters_slice5_ifg1_ifgb_rx_port_29_cgm_tc2_partially_dropped_packets {
      type oc-yang:counter64;
      description
        "RX port cgm ostc2 partial drops counter. Counts packets that were partially dropped and will be seen on RX side.";
    }
    leaf counters_slice5_ifg1_ifgb_rx_port_29_cgm_tc3_dropped_packets {
      type oc-yang:counter64;
      description
        "RX port cgm ostc3 drops counter. Counts packets that were totally dropped and will not be seen on RX side.";
    }
    leaf counters_slice5_ifg1_ifgb_rx_port_29_cgm_tc3_partially_dropped_packets {
      type oc-yang:counter64;
      description
        "RX port cgm ostc3 partial drops counter. Counts packets that were partially dropped and will be seen on RX side.";
    }
    leaf counters_slice5_ifg1_ifgb_rx_port_3_cgm_tc0_dropped_packets {
      type oc-yang:counter64;
      description
        "RX port cgm ostc0 drops counter. Counts packets that were totally dropped and will not be seen on RX side.";
    }
    leaf counters_slice5_ifg1_ifgb_rx_port_3_cgm_tc0_partially_dropped_packets {
      type oc-yang:counter64;
      description
        "RX port cgm ostc0 partial drops counter. Counts packets that were partially dropped and will be seen on RX side.";
    }
    leaf counters_slice5_ifg1_ifgb_rx_port_3_cgm_tc1_dropped_packets {
      type oc-yang:counter64;
      description
        "RX port cgm ostc1 drops counter. Counts packets that were totally dropped and will not be seen on RX side.";
    }
    leaf counters_slice5_ifg1_ifgb_rx_port_3_cgm_tc1_partially_dropped_packets {
      type oc-yang:counter64;
      description
        "RX port cgm ostc1 partial drops counter. Counts packets that were partially dropped and will be seen on RX side.";
    }
    leaf counters_slice5_ifg1_ifgb_rx_port_3_cgm_tc2_dropped_packets {
      type oc-yang:counter64;
      description
        "RX port cgm ostc2 drops counter. Counts packets that were totally dropped and will not be seen on RX side.";
    }
    leaf counters_slice5_ifg1_ifgb_rx_port_3_cgm_tc2_partially_dropped_packets {
      type oc-yang:counter64;
      description
        "RX port cgm ostc2 partial drops counter. Counts packets that were partially dropped and will be seen on RX side.";
    }
    leaf counters_slice5_ifg1_ifgb_rx_port_3_cgm_tc3_dropped_packets {
      type oc-yang:counter64;
      description
        "RX port cgm ostc3 drops counter. Counts packets that were totally dropped and will not be seen on RX side.";
    }
    leaf counters_slice5_ifg1_ifgb_rx_port_3_cgm_tc3_partially_dropped_packets {
      type oc-yang:counter64;
      description
        "RX port cgm ostc3 partial drops counter. Counts packets that were partially dropped and will be seen on RX side.";
    }
    leaf counters_slice5_ifg1_ifgb_rx_port_30_cgm_tc0_dropped_packets {
      type oc-yang:counter64;
      description
        "RX port cgm ostc0 drops counter. Counts packets that were totally dropped and will not be seen on RX side.";
    }
    leaf counters_slice5_ifg1_ifgb_rx_port_30_cgm_tc0_partially_dropped_packets {
      type oc-yang:counter64;
      description
        "RX port cgm ostc0 partial drops counter. Counts packets that were partially dropped and will be seen on RX side.";
    }
    leaf counters_slice5_ifg1_ifgb_rx_port_30_cgm_tc1_dropped_packets {
      type oc-yang:counter64;
      description
        "RX port cgm ostc1 drops counter. Counts packets that were totally dropped and will not be seen on RX side.";
    }
    leaf counters_slice5_ifg1_ifgb_rx_port_30_cgm_tc1_partially_dropped_packets {
      type oc-yang:counter64;
      description
        "RX port cgm ostc1 partial drops counter. Counts packets that were partially dropped and will be seen on RX side.";
    }
    leaf counters_slice5_ifg1_ifgb_rx_port_30_cgm_tc2_dropped_packets {
      type oc-yang:counter64;
      description
        "RX port cgm ostc2 drops counter. Counts packets that were totally dropped and will not be seen on RX side.";
    }
    leaf counters_slice5_ifg1_ifgb_rx_port_30_cgm_tc2_partially_dropped_packets {
      type oc-yang:counter64;
      description
        "RX port cgm ostc2 partial drops counter. Counts packets that were partially dropped and will be seen on RX side.";
    }
    leaf counters_slice5_ifg1_ifgb_rx_port_30_cgm_tc3_dropped_packets {
      type oc-yang:counter64;
      description
        "RX port cgm ostc3 drops counter. Counts packets that were totally dropped and will not be seen on RX side.";
    }
    leaf counters_slice5_ifg1_ifgb_rx_port_30_cgm_tc3_partially_dropped_packets {
      type oc-yang:counter64;
      description
        "RX port cgm ostc3 partial drops counter. Counts packets that were partially dropped and will be seen on RX side.";
    }
    leaf counters_slice5_ifg1_ifgb_rx_port_31_cgm_tc0_dropped_packets {
      type oc-yang:counter64;
      description
        "RX port cgm ostc0 drops counter. Counts packets that were totally dropped and will not be seen on RX side.";
    }
    leaf counters_slice5_ifg1_ifgb_rx_port_31_cgm_tc0_partially_dropped_packets {
      type oc-yang:counter64;
      description
        "RX port cgm ostc0 partial drops counter. Counts packets that were partially dropped and will be seen on RX side.";
    }
    leaf counters_slice5_ifg1_ifgb_rx_port_31_cgm_tc1_dropped_packets {
      type oc-yang:counter64;
      description
        "RX port cgm ostc1 drops counter. Counts packets that were totally dropped and will not be seen on RX side.";
    }
    leaf counters_slice5_ifg1_ifgb_rx_port_31_cgm_tc1_partially_dropped_packets {
      type oc-yang:counter64;
      description
        "RX port cgm ostc1 partial drops counter. Counts packets that were partially dropped and will be seen on RX side.";
    }
    leaf counters_slice5_ifg1_ifgb_rx_port_31_cgm_tc2_dropped_packets {
      type oc-yang:counter64;
      description
        "RX port cgm ostc2 drops counter. Counts packets that were totally dropped and will not be seen on RX side.";
    }
    leaf counters_slice5_ifg1_ifgb_rx_port_31_cgm_tc2_partially_dropped_packets {
      type oc-yang:counter64;
      description
        "RX port cgm ostc2 partial drops counter. Counts packets that were partially dropped and will be seen on RX side.";
    }
    leaf counters_slice5_ifg1_ifgb_rx_port_31_cgm_tc3_dropped_packets {
      type oc-yang:counter64;
      description
        "RX port cgm ostc3 drops counter. Counts packets that were totally dropped and will not be seen on RX side.";
    }
    leaf counters_slice5_ifg1_ifgb_rx_port_31_cgm_tc3_partially_dropped_packets {
      type oc-yang:counter64;
      description
        "RX port cgm ostc3 partial drops counter. Counts packets that were partially dropped and will be seen on RX side.";
    }
    leaf counters_slice5_ifg1_ifgb_rx_port_4_cgm_tc0_dropped_packets {
      type oc-yang:counter64;
      description
        "RX port cgm ostc0 drops counter. Counts packets that were totally dropped and will not be seen on RX side.";
    }
    leaf counters_slice5_ifg1_ifgb_rx_port_4_cgm_tc0_partially_dropped_packets {
      type oc-yang:counter64;
      description
        "RX port cgm ostc0 partial drops counter. Counts packets that were partially dropped and will be seen on RX side.";
    }
    leaf counters_slice5_ifg1_ifgb_rx_port_4_cgm_tc1_dropped_packets {
      type oc-yang:counter64;
      description
        "RX port cgm ostc1 drops counter. Counts packets that were totally dropped and will not be seen on RX side.";
    }
    leaf counters_slice5_ifg1_ifgb_rx_port_4_cgm_tc1_partially_dropped_packets {
      type oc-yang:counter64;
      description
        "RX port cgm ostc1 partial drops counter. Counts packets that were partially dropped and will be seen on RX side.";
    }
    leaf counters_slice5_ifg1_ifgb_rx_port_4_cgm_tc2_dropped_packets {
      type oc-yang:counter64;
      description
        "RX port cgm ostc2 drops counter. Counts packets that were totally dropped and will not be seen on RX side.";
    }
    leaf counters_slice5_ifg1_ifgb_rx_port_4_cgm_tc2_partially_dropped_packets {
      type oc-yang:counter64;
      description
        "RX port cgm ostc2 partial drops counter. Counts packets that were partially dropped and will be seen on RX side.";
    }
    leaf counters_slice5_ifg1_ifgb_rx_port_4_cgm_tc3_dropped_packets {
      type oc-yang:counter64;
      description
        "RX port cgm ostc3 drops counter. Counts packets that were totally dropped and will not be seen on RX side.";
    }
    leaf counters_slice5_ifg1_ifgb_rx_port_4_cgm_tc3_partially_dropped_packets {
      type oc-yang:counter64;
      description
        "RX port cgm ostc3 partial drops counter. Counts packets that were partially dropped and will be seen on RX side.";
    }
    leaf counters_slice5_ifg1_ifgb_rx_port_5_cgm_tc0_dropped_packets {
      type oc-yang:counter64;
      description
        "RX port cgm ostc0 drops counter. Counts packets that were totally dropped and will not be seen on RX side.";
    }
    leaf counters_slice5_ifg1_ifgb_rx_port_5_cgm_tc0_partially_dropped_packets {
      type oc-yang:counter64;
      description
        "RX port cgm ostc0 partial drops counter. Counts packets that were partially dropped and will be seen on RX side.";
    }
    leaf counters_slice5_ifg1_ifgb_rx_port_5_cgm_tc1_dropped_packets {
      type oc-yang:counter64;
      description
        "RX port cgm ostc1 drops counter. Counts packets that were totally dropped and will not be seen on RX side.";
    }
    leaf counters_slice5_ifg1_ifgb_rx_port_5_cgm_tc1_partially_dropped_packets {
      type oc-yang:counter64;
      description
        "RX port cgm ostc1 partial drops counter. Counts packets that were partially dropped and will be seen on RX side.";
    }
    leaf counters_slice5_ifg1_ifgb_rx_port_5_cgm_tc2_dropped_packets {
      type oc-yang:counter64;
      description
        "RX port cgm ostc2 drops counter. Counts packets that were totally dropped and will not be seen on RX side.";
    }
    leaf counters_slice5_ifg1_ifgb_rx_port_5_cgm_tc2_partially_dropped_packets {
      type oc-yang:counter64;
      description
        "RX port cgm ostc2 partial drops counter. Counts packets that were partially dropped and will be seen on RX side.";
    }
    leaf counters_slice5_ifg1_ifgb_rx_port_5_cgm_tc3_dropped_packets {
      type oc-yang:counter64;
      description
        "RX port cgm ostc3 drops counter. Counts packets that were totally dropped and will not be seen on RX side.";
    }
    leaf counters_slice5_ifg1_ifgb_rx_port_5_cgm_tc3_partially_dropped_packets {
      type oc-yang:counter64;
      description
        "RX port cgm ostc3 partial drops counter. Counts packets that were partially dropped and will be seen on RX side.";
    }
    leaf counters_slice5_ifg1_ifgb_rx_port_6_cgm_tc0_dropped_packets {
      type oc-yang:counter64;
      description
        "RX port cgm ostc0 drops counter. Counts packets that were totally dropped and will not be seen on RX side.";
    }
    leaf counters_slice5_ifg1_ifgb_rx_port_6_cgm_tc0_partially_dropped_packets {
      type oc-yang:counter64;
      description
        "RX port cgm ostc0 partial drops counter. Counts packets that were partially dropped and will be seen on RX side.";
    }
    leaf counters_slice5_ifg1_ifgb_rx_port_6_cgm_tc1_dropped_packets {
      type oc-yang:counter64;
      description
        "RX port cgm ostc1 drops counter. Counts packets that were totally dropped and will not be seen on RX side.";
    }
    leaf counters_slice5_ifg1_ifgb_rx_port_6_cgm_tc1_partially_dropped_packets {
      type oc-yang:counter64;
      description
        "RX port cgm ostc1 partial drops counter. Counts packets that were partially dropped and will be seen on RX side.";
    }
    leaf counters_slice5_ifg1_ifgb_rx_port_6_cgm_tc2_dropped_packets {
      type oc-yang:counter64;
      description
        "RX port cgm ostc2 drops counter. Counts packets that were totally dropped and will not be seen on RX side.";
    }
    leaf counters_slice5_ifg1_ifgb_rx_port_6_cgm_tc2_partially_dropped_packets {
      type oc-yang:counter64;
      description
        "RX port cgm ostc2 partial drops counter. Counts packets that were partially dropped and will be seen on RX side.";
    }
    leaf counters_slice5_ifg1_ifgb_rx_port_6_cgm_tc3_dropped_packets {
      type oc-yang:counter64;
      description
        "RX port cgm ostc3 drops counter. Counts packets that were totally dropped and will not be seen on RX side.";
    }
    leaf counters_slice5_ifg1_ifgb_rx_port_6_cgm_tc3_partially_dropped_packets {
      type oc-yang:counter64;
      description
        "RX port cgm ostc3 partial drops counter. Counts packets that were partially dropped and will be seen on RX side.";
    }
    leaf counters_slice5_ifg1_ifgb_rx_port_7_cgm_tc0_dropped_packets {
      type oc-yang:counter64;
      description
        "RX port cgm ostc0 drops counter. Counts packets that were totally dropped and will not be seen on RX side.";
    }
    leaf counters_slice5_ifg1_ifgb_rx_port_7_cgm_tc0_partially_dropped_packets {
      type oc-yang:counter64;
      description
        "RX port cgm ostc0 partial drops counter. Counts packets that were partially dropped and will be seen on RX side.";
    }
    leaf counters_slice5_ifg1_ifgb_rx_port_7_cgm_tc1_dropped_packets {
      type oc-yang:counter64;
      description
        "RX port cgm ostc1 drops counter. Counts packets that were totally dropped and will not be seen on RX side.";
    }
    leaf counters_slice5_ifg1_ifgb_rx_port_7_cgm_tc1_partially_dropped_packets {
      type oc-yang:counter64;
      description
        "RX port cgm ostc1 partial drops counter. Counts packets that were partially dropped and will be seen on RX side.";
    }
    leaf counters_slice5_ifg1_ifgb_rx_port_7_cgm_tc2_dropped_packets {
      type oc-yang:counter64;
      description
        "RX port cgm ostc2 drops counter. Counts packets that were totally dropped and will not be seen on RX side.";
    }
    leaf counters_slice5_ifg1_ifgb_rx_port_7_cgm_tc2_partially_dropped_packets {
      type oc-yang:counter64;
      description
        "RX port cgm ostc2 partial drops counter. Counts packets that were partially dropped and will be seen on RX side.";
    }
    leaf counters_slice5_ifg1_ifgb_rx_port_7_cgm_tc3_dropped_packets {
      type oc-yang:counter64;
      description
        "RX port cgm ostc3 drops counter. Counts packets that were totally dropped and will not be seen on RX side.";
    }
    leaf counters_slice5_ifg1_ifgb_rx_port_7_cgm_tc3_partially_dropped_packets {
      type oc-yang:counter64;
      description
        "RX port cgm ostc3 partial drops counter. Counts packets that were partially dropped and will be seen on RX side.";
    }
    leaf counters_slice5_ifg1_ifgb_rx_port_8_cgm_tc0_dropped_packets {
      type oc-yang:counter64;
      description
        "RX port cgm ostc0 drops counter. Counts packets that were totally dropped and will not be seen on RX side.";
    }
    leaf counters_slice5_ifg1_ifgb_rx_port_8_cgm_tc0_partially_dropped_packets {
      type oc-yang:counter64;
      description
        "RX port cgm ostc0 partial drops counter. Counts packets that were partially dropped and will be seen on RX side.";
    }
    leaf counters_slice5_ifg1_ifgb_rx_port_8_cgm_tc1_dropped_packets {
      type oc-yang:counter64;
      description
        "RX port cgm ostc1 drops counter. Counts packets that were totally dropped and will not be seen on RX side.";
    }
    leaf counters_slice5_ifg1_ifgb_rx_port_8_cgm_tc1_partially_dropped_packets {
      type oc-yang:counter64;
      description
        "RX port cgm ostc1 partial drops counter. Counts packets that were partially dropped and will be seen on RX side.";
    }
    leaf counters_slice5_ifg1_ifgb_rx_port_8_cgm_tc2_dropped_packets {
      type oc-yang:counter64;
      description
        "RX port cgm ostc2 drops counter. Counts packets that were totally dropped and will not be seen on RX side.";
    }
    leaf counters_slice5_ifg1_ifgb_rx_port_8_cgm_tc2_partially_dropped_packets {
      type oc-yang:counter64;
      description
        "RX port cgm ostc2 partial drops counter. Counts packets that were partially dropped and will be seen on RX side.";
    }
    leaf counters_slice5_ifg1_ifgb_rx_port_8_cgm_tc3_dropped_packets {
      type oc-yang:counter64;
      description
        "RX port cgm ostc3 drops counter. Counts packets that were totally dropped and will not be seen on RX side.";
    }
    leaf counters_slice5_ifg1_ifgb_rx_port_8_cgm_tc3_partially_dropped_packets {
      type oc-yang:counter64;
      description
        "RX port cgm ostc3 partial drops counter. Counts packets that were partially dropped and will be seen on RX side.";
    }
    leaf counters_slice5_ifg1_ifgb_rx_port_9_cgm_tc0_dropped_packets {
      type oc-yang:counter64;
      description
        "RX port cgm ostc0 drops counter. Counts packets that were totally dropped and will not be seen on RX side.";
    }
    leaf counters_slice5_ifg1_ifgb_rx_port_9_cgm_tc0_partially_dropped_packets {
      type oc-yang:counter64;
      description
        "RX port cgm ostc0 partial drops counter. Counts packets that were partially dropped and will be seen on RX side.";
    }
    leaf counters_slice5_ifg1_ifgb_rx_port_9_cgm_tc1_dropped_packets {
      type oc-yang:counter64;
      description
        "RX port cgm ostc1 drops counter. Counts packets that were totally dropped and will not be seen on RX side.";
    }
    leaf counters_slice5_ifg1_ifgb_rx_port_9_cgm_tc1_partially_dropped_packets {
      type oc-yang:counter64;
      description
        "RX port cgm ostc1 partial drops counter. Counts packets that were partially dropped and will be seen on RX side.";
    }
    leaf counters_slice5_ifg1_ifgb_rx_port_9_cgm_tc2_dropped_packets {
      type oc-yang:counter64;
      description
        "RX port cgm ostc2 drops counter. Counts packets that were totally dropped and will not be seen on RX side.";
    }
    leaf counters_slice5_ifg1_ifgb_rx_port_9_cgm_tc2_partially_dropped_packets {
      type oc-yang:counter64;
      description
        "RX port cgm ostc2 partial drops counter. Counts packets that were partially dropped and will be seen on RX side.";
    }
    leaf counters_slice5_ifg1_ifgb_rx_port_9_cgm_tc3_dropped_packets {
      type oc-yang:counter64;
      description
        "RX port cgm ostc3 drops counter. Counts packets that were totally dropped and will not be seen on RX side.";
    }
    leaf counters_slice5_ifg1_ifgb_rx_port_9_cgm_tc3_partially_dropped_packets {
      type oc-yang:counter64;
      description
        "RX port cgm ostc3 partial drops counter. Counts packets that were partially dropped and will be seen on RX side.";
    }
    leaf counters_slice5_tx_cgm_dropped_packets_due_to_max_allowed_qsize {
      type oc-yang:counter64;
      description
        "Counts number of dropped packets by max allowed threshold";
    }
    leaf counters_slice5_tx_cgm_local_sch_uc_buffer_c_dropped_packets {
      type oc-yang:counter64;
      description
        "Counts number of dropped packets by counter C";
    }
    leaf counters_slice5_tx_cgm_mc_silently_dropped_packets {
      type oc-yang:counter64;
      description
        "Counter of dropped MC packets that were silently dropped";
    }
    leaf counters_slice5_tx_cgm_sch_uc_buffers_cd_dropped_packets {
      type oc-yang:counter64;
      description
        "Counts number of dropped packets by counter C+D";
    }
    leaf counters_slice5_tx_cgm_sch_uc_counter_z_dropped_packets {
      type oc-yang:counter64;
      description
        "Counts number of dropped packets by counter Z";
    }
    leaf counters_slice5_tx_cgm_total_dropped_packets {
      type oc-yang:counter64;
      description
        "Counts number of dropped in TxCGM only packets";
    }
    leaf counters_slice5_tx_cgm_uc_oq_test_dropped_packets {
      type oc-yang:counter64;
      description
        "Counts number of dropped by UC OQ test";
    }
    leaf counters_slice5_tx_cgm_uc_oqg_dropped_packets {
      type oc-yang:counter64;
      description
        "Counts number of dropped by UC OQG test";
    }
    leaf counters_slice5_tx_cgm_unsch_counter_w_dropped_packets {
      type oc-yang:counter64;
      description
        "Counts number of dropped packets by counter W";
    }
    leaf counters_slice5_tx_cgm_green_mc_oq_bytes_test_dropped_packets {
      type oc-yang:counter64;
      description
        "Counts number of dropped packets by OQ MC green bytes test";
    }
    leaf counters_slice5_tx_cgm_green_mc_oq_pds_test_dropped_packets {
      type oc-yang:counter64;
      description
        "Counts number of dropped packets by OQ MC green PDs test";
    }
    leaf counters_slice5_tx_cgm_mc_color_test0_dropped_packets {
      type oc-yang:counter64;
      description
        "Counts number of dropped packet by MC color test for:0 - Green1 - Yellow2 - Red3 - Other";
    }
    leaf counters_slice5_tx_cgm_mc_color_test1_dropped_packets {
      type oc-yang:counter64;
      description
        "Counts number of dropped packet by MC color test for:0 - Green1 - Yellow2 - Red3 - Other";
    }
    leaf counters_slice5_tx_cgm_mc_color_test2_dropped_packets {
      type oc-yang:counter64;
      description
        "Counts number of dropped packet by MC color test for:0 - Green1 - Yellow2 - Red3 - Other";
    }
    leaf counters_slice5_tx_cgm_mc_color_test3_dropped_packets {
      type oc-yang:counter64;
      description
        "Counts number of dropped packet by MC color test for:0 - Green1 - Yellow2 - Red3 - Other";
    }
    leaf counters_slice5_tx_cgm_mc_set0_dropped_bytes {
      type oc-yang:counter64;
      description
        "Counts MC dropped bytes";
    }
    leaf counters_slice5_tx_cgm_mc_set0_dropped_packets {
      type oc-yang:counter64;
      description
        "Counts MC dropped packets";
    }
    leaf counters_slice5_tx_cgm_mc_set1_dropped_bytes {
      type oc-yang:counter64;
      description
        "Counts MC dropped bytes";
    }
    leaf counters_slice5_tx_cgm_mc_set1_dropped_packets {
      type oc-yang:counter64;
      description
        "Counts MC dropped packets";
    }
    leaf counters_slice5_tx_cgm_mc_set2_dropped_bytes {
      type oc-yang:counter64;
      description
        "Counts MC dropped bytes";
    }
    leaf counters_slice5_tx_cgm_mc_set2_dropped_packets {
      type oc-yang:counter64;
      description
        "Counts MC dropped packets";
    }
    leaf counters_slice5_tx_cgm_mc_set3_dropped_bytes {
      type oc-yang:counter64;
      description
        "Counts MC dropped bytes";
    }
    leaf counters_slice5_tx_cgm_mc_set3_dropped_packets {
      type oc-yang:counter64;
      description
        "Counts MC dropped packets";
    }
    leaf counters_slice5_tx_cgm_uc_color_test0_dropped_packets {
      type oc-yang:counter64;
      description
        "Counts number of dropped packet by UC color test for:0 - Green1 - Yellow2 - Red3 - Other";
    }
    leaf counters_slice5_tx_cgm_uc_color_test1_dropped_packets {
      type oc-yang:counter64;
      description
        "Counts number of dropped packet by UC color test for:0 - Green1 - Yellow2 - Red3 - Other";
    }
    leaf counters_slice5_tx_cgm_uc_color_test2_dropped_packets {
      type oc-yang:counter64;
      description
        "Counts number of dropped packet by UC color test for:0 - Green1 - Yellow2 - Red3 - Other";
    }
    leaf counters_slice5_tx_cgm_uc_color_test3_dropped_packets {
      type oc-yang:counter64;
      description
        "Counts number of dropped packet by UC color test for:0 - Green1 - Yellow2 - Red3 - Other";
    }
    leaf counters_slice5_tx_cgm_uc_set0_dropped_bytes {
      type oc-yang:counter64;
      description
        "Counts UC dropped bytes";
    }
    leaf counters_slice5_tx_cgm_uc_set0_dropped_packets {
      type oc-yang:counter64;
      description
        "Counts UC dropped packets";
    }
    leaf counters_slice5_tx_cgm_uc_set1_dropped_bytes {
      type oc-yang:counter64;
      description
        "Counts UC dropped bytes";
    }
    leaf counters_slice5_tx_cgm_uc_set1_dropped_packets {
      type oc-yang:counter64;
      description
        "Counts UC dropped packets";
    }
    leaf counters_slice5_tx_cgm_uc_set2_dropped_bytes {
      type oc-yang:counter64;
      description
        "Counts UC dropped bytes";
    }
    leaf counters_slice5_tx_cgm_uc_set2_dropped_packets {
      type oc-yang:counter64;
      description
        "Counts UC dropped packets";
    }
    leaf counters_slice5_tx_cgm_uc_set3_dropped_bytes {
      type oc-yang:counter64;
      description
        "Counts UC dropped bytes";
    }
    leaf counters_slice5_tx_cgm_uc_set3_dropped_packets {
      type oc-yang:counter64;
      description
        "Counts UC dropped packets";
    }
    leaf counters_slice5_tx_cgm_yellow_mc_oq_bytes_test_dropped_packets {
      type oc-yang:counter64;
      description
        "Counts number of dropped packets by OQ MC yellow bytes test";
    }
    leaf counters_slice5_tx_cgm_yellow_mc_oq_pds_test_dropped_packets {
      type oc-yang:counter64;
      description
        "Counts number of dropped packets by OQ MC yellow PDs test";
    }
    leaf counters_slice5_tx_pdr_txrq_full_egress_rep_dropped_packets {
      type oc-yang:counter64;
      description
        "Number of dropped packets";
    }
    leaf counters_slice5_tx_pdr_txrq_overload_egress_rep_dropped_packets {
      type oc-yang:counter64;
      description
        "Number of dropped packets";
    }
    leaf counters_slice5_tx_pdr_txrq0_full_egress_rep_dropped_packets {
      type oc-yang:counter64;
      description
        "Number of dropped packets";
    }
    leaf counters_slice5_tx_pdr_txrq0_threshold0_deq_dropped_packets {
      type oc-yang:counter64;
      description
        "Number of dropped packets in TXRQ deq";
    }
    leaf counters_slice5_tx_pdr_txrq0_threshold0_enq_dropped_packets {
      type oc-yang:counter64;
      description
        "Number of dropped packets in TXRQ enq";
    }
    leaf counters_slice5_tx_pdr_txrq0_threshold0_unscheduled_cgm_drops {
      type oc-yang:counter64;
      description
        "nan";
    }
    leaf counters_slice5_tx_pdr_txrq0_threshold1_deq_dropped_packets {
      type oc-yang:counter64;
      description
        "Number of dropped packets in TXRQ deq";
    }
    leaf counters_slice5_tx_pdr_txrq0_threshold1_enq_dropped_packets {
      type oc-yang:counter64;
      description
        "Number of dropped packets in TXRQ enq";
    }
    leaf counters_slice5_tx_pdr_txrq0_threshold1_unscheduled_cgm_drops {
      type oc-yang:counter64;
      description
        "nan";
    }
    leaf counters_slice5_tx_pdr_txrq1_full_egress_rep_dropped_packets {
      type oc-yang:counter64;
      description
        "Number of dropped packets";
    }
    leaf counters_slice5_tx_pdr_txrq1_threshold0_deq_dropped_packets {
      type oc-yang:counter64;
      description
        "Number of dropped packets in TXRQ deq";
    }
    leaf counters_slice5_tx_pdr_txrq1_threshold0_enq_dropped_packets {
      type oc-yang:counter64;
      description
        "Number of dropped packets in TXRQ enq";
    }
    leaf counters_slice5_tx_pdr_txrq1_threshold0_unscheduled_cgm_drops {
      type oc-yang:counter64;
      description
        "nan";
    }
    leaf counters_slice5_tx_pdr_txrq1_threshold1_deq_dropped_packets {
      type oc-yang:counter64;
      description
        "Number of dropped packets in TXRQ deq";
    }
    leaf counters_slice5_tx_pdr_txrq1_threshold1_enq_dropped_packets {
      type oc-yang:counter64;
      description
        "Number of dropped packets in TXRQ enq";
    }
    leaf counters_slice5_tx_pdr_txrq1_threshold1_unscheduled_cgm_drops {
      type oc-yang:counter64;
      description
        "nan";
    }
    leaf counters_slice5_tx_pdr_txrq2_full_egress_rep_dropped_packets {
      type oc-yang:counter64;
      description
        "Number of dropped packets";
    }
    leaf counters_slice5_tx_pdr_txrq2_threshold0_deq_dropped_packets {
      type oc-yang:counter64;
      description
        "Number of dropped packets in TXRQ deq";
    }
    leaf counters_slice5_tx_pdr_txrq2_threshold0_enq_dropped_packets {
      type oc-yang:counter64;
      description
        "Number of dropped packets in TXRQ enq";
    }
    leaf counters_slice5_tx_pdr_txrq2_threshold1_deq_dropped_packets {
      type oc-yang:counter64;
      description
        "Number of dropped packets in TXRQ deq";
    }
    leaf counters_slice5_tx_pdr_txrq2_threshold1_enq_dropped_packets {
      type oc-yang:counter64;
      description
        "Number of dropped packets in TXRQ enq";
    }
    leaf counters_slice5_tx_pdr_txrq3_full_egress_rep_dropped_packets {
      type oc-yang:counter64;
      description
        "Number of dropped packets";
    }
    leaf counters_slice5_tx_pdr_txrq3_threshold0_deq_dropped_packets {
      type oc-yang:counter64;
      description
        "Number of dropped packets in TXRQ deq";
    }
    leaf counters_slice5_tx_pdr_txrq3_threshold0_enq_dropped_packets {
      type oc-yang:counter64;
      description
        "Number of dropped packets in TXRQ enq";
    }
    leaf counters_slice5_tx_pdr_txrq3_threshold1_deq_dropped_packets {
      type oc-yang:counter64;
      description
        "Number of dropped packets in TXRQ deq";
    }
    leaf counters_slice5_tx_pdr_txrq3_threshold1_enq_dropped_packets {
      type oc-yang:counter64;
      description
        "Number of dropped packets in TXRQ enq";
    }
    leaf counters_slice_pair0_rx_pdr_cgm0_dropped_packets_a {
      type oc-yang:counter64;
      description
        "Number of packets dropped due to CGM counter A";
    }
    leaf counters_slice_pair0_rx_pdr_cgm0_dropped_packets_b {
      type oc-yang:counter64;
      description
        "Number of packets dropped due to CGM counter B";
    }
    leaf counters_slice_pair0_rx_pdr_cgm0_dropped_packets_e {
      type oc-yang:counter64;
      description
        "Number of packets dropped due to CGM counter E";
    }
    leaf counters_slice_pair0_rx_pdr_cgm0_dropped_packets_g {
      type oc-yang:counter64;
      description
        "Number of packets whose mirror copies were dropped due to CGM counter G";
    }
    leaf counters_slice_pair0_rx_pdr_cgm1_dropped_packets_a {
      type oc-yang:counter64;
      description
        "Number of packets dropped due to CGM counter A";
    }
    leaf counters_slice_pair0_rx_pdr_cgm1_dropped_packets_b {
      type oc-yang:counter64;
      description
        "Number of packets dropped due to CGM counter B";
    }
    leaf counters_slice_pair0_rx_pdr_cgm1_dropped_packets_e {
      type oc-yang:counter64;
      description
        "Number of packets dropped due to CGM counter E";
    }
    leaf counters_slice_pair0_rx_pdr_cgm1_dropped_packets_g {
      type oc-yang:counter64;
      description
        "Number of packets whose mirror copies were dropped due to CGM counter G";
    }
    leaf counters_slice_pair0_rx_pdr_cgm0_deq_drop {
      type oc-yang:counter64;
      description
        "nan";
    }
    leaf counters_slice_pair0_rx_pdr_cgm0_deq_ibm_counter_g_drop {
      type oc-yang:counter64;
      description
        "nan";
    }
    leaf counters_slice_pair0_rx_pdr_cgm0_deq_ibm_drop {
      type oc-yang:counter64;
      description
        "nan";
    }
    leaf counters_slice_pair0_rx_pdr_cgm0_enq_drop {
      type oc-yang:counter64;
      description
        "nan";
    }
    leaf counters_slice_pair0_rx_pdr_cgm1_deq_drop {
      type oc-yang:counter64;
      description
        "nan";
    }
    leaf counters_slice_pair0_rx_pdr_cgm1_deq_ibm_counter_g_drop {
      type oc-yang:counter64;
      description
        "nan";
    }
    leaf counters_slice_pair0_rx_pdr_cgm1_deq_ibm_drop {
      type oc-yang:counter64;
      description
        "nan";
    }
    leaf counters_slice_pair0_rx_pdr_cgm1_enq_drop {
      type oc-yang:counter64;
      description
        "nan";
    }
    leaf counters_slice_pair0_rx_pdr_rxrqs_debug_reg0_rxrq_drop {
      type oc-yang:counter64;
      description
        "A counter per RXRQ that counts the number of PDs that were dropped due to congestion i.e. RXRQ was full.";
    }
    leaf counters_slice_pair0_rx_pdr_rxrqs_debug_reg1_rxrq_drop {
      type oc-yang:counter64;
      description
        "A counter per RXRQ that counts the number of PDs that were dropped due to congestion i.e. RXRQ was full.";
    }
    leaf counters_slice_pair0_rx_pdr_rxrqs_debug_reg2_rxrq_drop {
      type oc-yang:counter64;
      description
        "A counter per RXRQ that counts the number of PDs that were dropped due to congestion i.e. RXRQ was full.";
    }
    leaf counters_slice_pair0_rx_pdr_rxrqs_debug_reg3_rxrq_drop {
      type oc-yang:counter64;
      description
        "A counter per RXRQ that counts the number of PDs that were dropped due to congestion i.e. RXRQ was full.";
    }
    leaf counters_slice_pair0_rx_pdr_rxrqs_debug_reg4_rxrq_drop {
      type oc-yang:counter64;
      description
        "A counter per RXRQ that counts the number of PDs that were dropped due to congestion i.e. RXRQ was full.";
    }
    leaf counters_slice_pair0_rx_pdr_rxrqs_debug_reg5_rxrq_drop {
      type oc-yang:counter64;
      description
        "A counter per RXRQ that counts the number of PDs that were dropped due to congestion i.e. RXRQ was full.";
    }
    leaf counters_slice_pair0_rx_pdr_rxrqs_debug_reg6_rxrq_drop {
      type oc-yang:counter64;
      description
        "A counter per RXRQ that counts the number of PDs that were dropped due to congestion i.e. RXRQ was full.";
    }
    leaf counters_slice_pair0_rx_pdr_rxrqs_debug_reg7_rxrq_drop {
      type oc-yang:counter64;
      description
        "A counter per RXRQ that counts the number of PDs that were dropped due to congestion i.e. RXRQ was full.";
    }
    leaf counters_slice_pair0_rx_pdr_rxrqs_debug_reg8_rxrq_drop {
      type oc-yang:counter64;
      description
        "A counter per RXRQ that counts the number of PDs that were dropped due to congestion i.e. RXRQ was full.";
    }
    leaf counters_slice_pair0_rx_pdr_rxrqs_debug_reg9_rxrq_drop {
      type oc-yang:counter64;
      description
        "A counter per RXRQ that counts the number of PDs that were dropped due to congestion i.e. RXRQ was full.";
    }
    leaf counters_slice_pair1_rx_pdr_cgm0_dropped_packets_a {
      type oc-yang:counter64;
      description
        "Number of packets dropped due to CGM counter A";
    }
    leaf counters_slice_pair1_rx_pdr_cgm0_dropped_packets_b {
      type oc-yang:counter64;
      description
        "Number of packets dropped due to CGM counter B";
    }
    leaf counters_slice_pair1_rx_pdr_cgm0_dropped_packets_e {
      type oc-yang:counter64;
      description
        "Number of packets dropped due to CGM counter E";
    }
    leaf counters_slice_pair1_rx_pdr_cgm0_dropped_packets_g {
      type oc-yang:counter64;
      description
        "Number of packets whose mirror copies were dropped due to CGM counter G";
    }
    leaf counters_slice_pair1_rx_pdr_cgm1_dropped_packets_a {
      type oc-yang:counter64;
      description
        "Number of packets dropped due to CGM counter A";
    }
    leaf counters_slice_pair1_rx_pdr_cgm1_dropped_packets_b {
      type oc-yang:counter64;
      description
        "Number of packets dropped due to CGM counter B";
    }
    leaf counters_slice_pair1_rx_pdr_cgm1_dropped_packets_e {
      type oc-yang:counter64;
      description
        "Number of packets dropped due to CGM counter E";
    }
    leaf counters_slice_pair1_rx_pdr_cgm1_dropped_packets_g {
      type oc-yang:counter64;
      description
        "Number of packets whose mirror copies were dropped due to CGM counter G";
    }
    leaf counters_slice_pair1_rx_pdr_cgm0_deq_drop {
      type oc-yang:counter64;
      description
        "nan";
    }
    leaf counters_slice_pair1_rx_pdr_cgm0_deq_ibm_counter_g_drop {
      type oc-yang:counter64;
      description
        "nan";
    }
    leaf counters_slice_pair1_rx_pdr_cgm0_deq_ibm_drop {
      type oc-yang:counter64;
      description
        "nan";
    }
    leaf counters_slice_pair1_rx_pdr_cgm0_enq_drop {
      type oc-yang:counter64;
      description
        "nan";
    }
    leaf counters_slice_pair1_rx_pdr_cgm1_deq_drop {
      type oc-yang:counter64;
      description
        "nan";
    }
    leaf counters_slice_pair1_rx_pdr_cgm1_deq_ibm_counter_g_drop {
      type oc-yang:counter64;
      description
        "nan";
    }
    leaf counters_slice_pair1_rx_pdr_cgm1_deq_ibm_drop {
      type oc-yang:counter64;
      description
        "nan";
    }
    leaf counters_slice_pair1_rx_pdr_cgm1_enq_drop {
      type oc-yang:counter64;
      description
        "nan";
    }
    leaf counters_slice_pair1_rx_pdr_rxrqs_debug_reg0_rxrq_drop {
      type oc-yang:counter64;
      description
        "A counter per RXRQ that counts the number of PDs that were dropped due to congestion i.e. RXRQ was full.";
    }
    leaf counters_slice_pair1_rx_pdr_rxrqs_debug_reg1_rxrq_drop {
      type oc-yang:counter64;
      description
        "A counter per RXRQ that counts the number of PDs that were dropped due to congestion i.e. RXRQ was full.";
    }
    leaf counters_slice_pair1_rx_pdr_rxrqs_debug_reg2_rxrq_drop {
      type oc-yang:counter64;
      description
        "A counter per RXRQ that counts the number of PDs that were dropped due to congestion i.e. RXRQ was full.";
    }
    leaf counters_slice_pair1_rx_pdr_rxrqs_debug_reg3_rxrq_drop {
      type oc-yang:counter64;
      description
        "A counter per RXRQ that counts the number of PDs that were dropped due to congestion i.e. RXRQ was full.";
    }
    leaf counters_slice_pair1_rx_pdr_rxrqs_debug_reg4_rxrq_drop {
      type oc-yang:counter64;
      description
        "A counter per RXRQ that counts the number of PDs that were dropped due to congestion i.e. RXRQ was full.";
    }
    leaf counters_slice_pair1_rx_pdr_rxrqs_debug_reg5_rxrq_drop {
      type oc-yang:counter64;
      description
        "A counter per RXRQ that counts the number of PDs that were dropped due to congestion i.e. RXRQ was full.";
    }
    leaf counters_slice_pair1_rx_pdr_rxrqs_debug_reg6_rxrq_drop {
      type oc-yang:counter64;
      description
        "A counter per RXRQ that counts the number of PDs that were dropped due to congestion i.e. RXRQ was full.";
    }
    leaf counters_slice_pair1_rx_pdr_rxrqs_debug_reg7_rxrq_drop {
      type oc-yang:counter64;
      description
        "A counter per RXRQ that counts the number of PDs that were dropped due to congestion i.e. RXRQ was full.";
    }
    leaf counters_slice_pair1_rx_pdr_rxrqs_debug_reg8_rxrq_drop {
      type oc-yang:counter64;
      description
        "A counter per RXRQ that counts the number of PDs that were dropped due to congestion i.e. RXRQ was full.";
    }
    leaf counters_slice_pair1_rx_pdr_rxrqs_debug_reg9_rxrq_drop {
      type oc-yang:counter64;
      description
        "A counter per RXRQ that counts the number of PDs that were dropped due to congestion i.e. RXRQ was full.";
    }
    leaf counters_slice_pair2_rx_pdr_cgm0_dropped_packets_a {
      type oc-yang:counter64;
      description
        "Number of packets dropped due to CGM counter A";
    }
    leaf counters_slice_pair2_rx_pdr_cgm0_dropped_packets_b {
      type oc-yang:counter64;
      description
        "Number of packets dropped due to CGM counter B";
    }
    leaf counters_slice_pair2_rx_pdr_cgm0_dropped_packets_e {
      type oc-yang:counter64;
      description
        "Number of packets dropped due to CGM counter E";
    }
    leaf counters_slice_pair2_rx_pdr_cgm0_dropped_packets_g {
      type oc-yang:counter64;
      description
        "Number of packets whose mirror copies were dropped due to CGM counter G";
    }
    leaf counters_slice_pair2_rx_pdr_cgm1_dropped_packets_a {
      type oc-yang:counter64;
      description
        "Number of packets dropped due to CGM counter A";
    }
    leaf counters_slice_pair2_rx_pdr_cgm1_dropped_packets_b {
      type oc-yang:counter64;
      description
        "Number of packets dropped due to CGM counter B";
    }
    leaf counters_slice_pair2_rx_pdr_cgm1_dropped_packets_e {
      type oc-yang:counter64;
      description
        "Number of packets dropped due to CGM counter E";
    }
    leaf counters_slice_pair2_rx_pdr_cgm1_dropped_packets_g {
      type oc-yang:counter64;
      description
        "Number of packets whose mirror copies were dropped due to CGM counter G";
    }
    leaf counters_slice_pair2_rx_pdr_cgm0_deq_drop {
      type oc-yang:counter64;
      description
        "nan";
    }
    leaf counters_slice_pair2_rx_pdr_cgm0_deq_ibm_counter_g_drop {
      type oc-yang:counter64;
      description
        "nan";
    }
    leaf counters_slice_pair2_rx_pdr_cgm0_deq_ibm_drop {
      type oc-yang:counter64;
      description
        "nan";
    }
    leaf counters_slice_pair2_rx_pdr_cgm0_enq_drop {
      type oc-yang:counter64;
      description
        "nan";
    }
    leaf counters_slice_pair2_rx_pdr_cgm1_deq_drop {
      type oc-yang:counter64;
      description
        "nan";
    }
    leaf counters_slice_pair2_rx_pdr_cgm1_deq_ibm_counter_g_drop {
      type oc-yang:counter64;
      description
        "nan";
    }
    leaf counters_slice_pair2_rx_pdr_cgm1_deq_ibm_drop {
      type oc-yang:counter64;
      description
        "nan";
    }
    leaf counters_slice_pair2_rx_pdr_cgm1_enq_drop {
      type oc-yang:counter64;
      description
        "nan";
    }
    leaf counters_slice_pair2_rx_pdr_rxrqs_debug_reg0_rxrq_drop {
      type oc-yang:counter64;
      description
        "A counter per RXRQ that counts the number of PDs that were dropped due to congestion i.e. RXRQ was full.";
    }
    leaf counters_slice_pair2_rx_pdr_rxrqs_debug_reg1_rxrq_drop {
      type oc-yang:counter64;
      description
        "A counter per RXRQ that counts the number of PDs that were dropped due to congestion i.e. RXRQ was full.";
    }
    leaf counters_slice_pair2_rx_pdr_rxrqs_debug_reg2_rxrq_drop {
      type oc-yang:counter64;
      description
        "A counter per RXRQ that counts the number of PDs that were dropped due to congestion i.e. RXRQ was full.";
    }
    leaf counters_slice_pair2_rx_pdr_rxrqs_debug_reg3_rxrq_drop {
      type oc-yang:counter64;
      description
        "A counter per RXRQ that counts the number of PDs that were dropped due to congestion i.e. RXRQ was full.";
    }
    leaf counters_slice_pair2_rx_pdr_rxrqs_debug_reg4_rxrq_drop {
      type oc-yang:counter64;
      description
        "A counter per RXRQ that counts the number of PDs that were dropped due to congestion i.e. RXRQ was full.";
    }
    leaf counters_slice_pair2_rx_pdr_rxrqs_debug_reg5_rxrq_drop {
      type oc-yang:counter64;
      description
        "A counter per RXRQ that counts the number of PDs that were dropped due to congestion i.e. RXRQ was full.";
    }
    leaf counters_slice_pair2_rx_pdr_rxrqs_debug_reg6_rxrq_drop {
      type oc-yang:counter64;
      description
        "A counter per RXRQ that counts the number of PDs that were dropped due to congestion i.e. RXRQ was full.";
    }
    leaf counters_slice_pair2_rx_pdr_rxrqs_debug_reg7_rxrq_drop {
      type oc-yang:counter64;
      description
        "A counter per RXRQ that counts the number of PDs that were dropped due to congestion i.e. RXRQ was full.";
    }
    leaf counters_slice_pair2_rx_pdr_rxrqs_debug_reg8_rxrq_drop {
      type oc-yang:counter64;
      description
        "A counter per RXRQ that counts the number of PDs that were dropped due to congestion i.e. RXRQ was full.";
    }
    leaf counters_slice_pair2_rx_pdr_rxrqs_debug_reg9_rxrq_drop {
      type oc-yang:counter64;
      description
        "A counter per RXRQ that counts the number of PDs that were dropped due to congestion i.e. RXRQ was full.";
    }
  }

  grouping cisco-p100-packet-processing-drop-counters {
    description
      "Packet processing Drop leafs grouping for the p100 asic";
    leaf l3_drop_adj_non_inject {
      type oc-yang:counter64;
      description
        "L3 route information is not available for prefix in the VRF";
    }
    leaf l3_ip_unicast_rpf {
      type oc-yang:counter64;
      description
        " Ip unicast RPF check failed Loose or strict mode";
    }
    leaf ipv4_uc_forwarding_disabled {
      type oc-yang:counter64;
      description
        "Incoming packet or inner IP after tunnel termination is IPv4 unicast however IPv4 UC forwarding is disabled on the ingress L3 Logical Port";
    }
    leaf ipv6_uc_forwarding_disabled {
      type oc-yang:counter64;
      description
        "Incoming packet or inner IP after tunnel termination is IPv6 unicast however IPv4 UC forwarding is disabled on the ingress L3 Logical Por";
    }
    leaf ethernet_acceptable_format {
      type oc-yang:counter64;
      description
        "The packet header VLAN format is illegal to the incoming Logical Port";
    }
    leaf ethernet_acl_drop {
      type oc-yang:counter64;
      description
        "The packet matched an ingress security ACL rule with a drop action";
    }
    leaf ethernet_acl_force_punt {
      type oc-yang:counter64;
      description
        "The packet matched an ingress security ACL rule with a punt to host action";
    }
    leaf ethernet_disabled {
      type oc-yang:counter64;
      description
        "Filter packet if L2 or VxLAN port is disabled to allow 1 plus1 protection";
    }
    leaf ethernet_distr_down_mep {
      type oc-yang:counter64;
      description
        "Trap Ingress OAM CFM MEP Packets";
    }
    leaf ethernet_distr_up_mep {
      type oc-yang:counter64;
      description
        " Trap Egress OAM CFM MEP Packets";
    }
    leaf ethernet_dot1_x_learn {
      type oc-yang:counter64;
      description
        "Punt incoming packet for Dot1x learning";
    }
    leaf ethernet_dot1_x_drop {
      type oc-yang:counter64;
      description
        "User or Dot1x device authenticated Drop subsequent packets";
    }
    leaf ethernet_dspa_mc_trim {
      type oc-yang:counter64;
      description
        "ulticast pruning of flood copies to LAG port";
    }
    leaf ethernet_dsp_disabled {
      type oc-yang:counter64;
      description
        "L3 DLP is disabled.Trap to drop transmitted packets on L3 DLP";
    }
    leaf ethernet_egress_stp_block {
      type oc-yang:counter64;
      description
        "Packet transmitted to l2 logical port with STP in blocked state";
    }
    leaf ethernet_incompatible_eve_cmd {
      type oc-yang:counter64;
      description
        "EVE command is incompatible with packet VLAN structure";
    }
    leaf ethernet_ingress_stp_block {
      type oc-yang:counter64;
      description
        "Trap incoming packet if packet is received on Ingress Logical port";
    }
    leaf ethernet_l2_dlp_not_found {
      type oc-yang:counter64;
      description
        "Failed to get attributes for destination L2 logical port in transmit database";
    }
    leaf ethernet_macsec_processing_err {
      type oc-yang:counter64;
      description
        "Macsec internal error occured while decrypting MACSec packets";
    }
    leaf ethernet_mc_snoop_lookup_miss {
      type oc-yang:counter64;
      description
        "IGMP snooping database lookup miss";
    }
    leaf ethernet_no_pwe_l3_dest {
      type oc-yang:counter64;
      description
        "Failed to find PWE to L3 Destination mapping for PWE imposition path";
    }
    leaf ethernet_no_sip_mapping {
      type oc-yang:counter64;
      description
        "Could not terminate tunnel Source IP. trigger snoop to host to add SIP to Source Logical Port mapping in termination database";
    }
    leaf ethernet_no_vni_mapping {
      type oc-yang:counter64;
      description
        "Could not resolve VXLAN VNI to L2  or could not map MAC relay to VNI for L2-VXLAN encapsulation";
    }
    leaf ethernet_padding_residue_in_second_line {
      type oc-yang:counter64;
      description
        "Failed to handle padding in special cases";
    }
    leaf ethernet_sa_error {
      type oc-yang:counter64;
      description
        "Incoming packet MAC SA equals zero";
    }
    leaf ethernet_sa_multicast {
      type oc-yang:counter64;
      description
        "Incoming packet MAC SA is a multicast address";
    }
    leaf ethernet_same_interface {
      type oc-yang:counter64;
      description
        "The packet is being transmitted back to the same port that it was received from";
    }
    leaf ethernet_smac_miss {
      type oc-yang:counter64;
      description
        "Bridged packet MAC SA not found in MAC forwarding table";
    }
    leaf ethernet_split_horizon {
      type oc-yang:counter64;
      description
        "Trap if source and destination Logical Port are not allowed to communicate";
    }
    leaf ethernet_svi_egress_dhcp {
      type oc-yang:counter64;
      description
        "Trap egress L2 packet routed through Switched Virtual Interface that are DHCP over IP";
    }
    leaf ethernet_system_mymac {
      type oc-yang:counter64;
      description
        "Global My-MAC termination of ethernet header";
    }
    leaf ethernet_unknown_bc {
      type oc-yang:counter64;
      description
        "Destination for broadcast packet is unknown.  Logical port attribute is set to drop it";
    }
    leaf ethernet_unknown_mc {
      type oc-yang:counter64;
      description
        "Destination for multicast packet is unknown.  Logical port attribute is set to drop it";
    }
    leaf ethernet_unknown_uc {
      type oc-yang:counter64;
      description
        "Destination for unicast packet is unknown.  Logical port attribute is set to drop it";
    }
    leaf ethernet_unprotected_data_pkt_on_macsec_en_port {
      type oc-yang:counter64;
      description
        "Unencrypted packet received on MACSec enable port expecting encrypted secure packets";
    }
    leaf ethernet_spa_port_member_rx_disabled {
      type oc-yang:counter64;
      description
        "Aggregate Member cannot receive traffic";
    }
    leaf ethernet_unknown_l3 {
      type oc-yang:counter64;
      description
        "Unknown overlay packet protocol following MAC termination of ethernet header";
    }
    leaf ethernet_no_termination_on_l3_port {
      type oc-yang:counter64;
      description
        "Failed to terminate L3-AC ports ";
    }
    leaf l3_glean_adj {
      type oc-yang:counter64;
      description
        "L3 forwarding FIB lookup could not resolve next hop";
    }
    leaf l3_local_subnet {
      type oc-yang:counter64;
      description
        "L3 forwarding FIB lookup is unresolved path It has hit local subnet route. ";
    }
    leaf l3_drop_adj {
      type oc-yang:counter64;
      description
        "L3 forwarding FIB lookup to adjacent node";
    }
    leaf ethernet_no_service_mapping {
      type oc-yang:counter64;
      description
        "Failed to map L2-Logical Port and VLAN-ID to source LP or MAC relay attributes";
    }
    leaf l3_ttl_or_hop_limit_is_one {
      type oc-yang:counter64;
      description
        " OFA_LA_EVENT_L3_TTL_IS_ONE_RX";
    }
    leaf l3_ttl_is_one_rx {
      type oc-yang:counter64;
      description
        "Incoming packet TTL is 1.Set a RX trap";
    }
    leaf ipv6_hop_limit_is_one_rx {
      type oc-yang:counter64;
      description
        " Ipv6 packet hop Limit is 1";
    }
    leaf mpls_ilm_miss {
      type oc-yang:counter64;
      description
        "MPLS packet forwarding lookup failed in MPLS forwarding database";
    }
    leaf l3_bfd_micro_ip_disabled {
      type oc-yang:counter64;
      description
        "Set a trap if IP protocol is disabled and incoming packet is IP UDP BFD micro hop packet required to bring up member link";
    }
    leaf ipv4_unknown_protocol {
      type oc-yang:counter64;
      description
        "Incoming packet IPv4 header protocol field is unknown";
    }
    leaf ipv6_illegal_dip {
      type oc-yang:counter64;
      description
        "Incoming IPv6 packet identified with illegal Destination IP";
    }
    leaf ipv6_zero_payload {
      type oc-yang:counter64;
      description
        "Incoming IPv6 packet identified with illegal payload-length is 0 and not hop-by-hop packet";
    }
    leaf l3_acl_drop {
      type oc-yang:counter64;
      description
        "L3 egress security ACL or User-Defined-Fields ACLs policy action deny packet";
    }
    leaf l3_acl_force_punt {
      type oc-yang:counter64;
      description
        "L3 egress security ACL or User-Defined-Fields ACLs policy action to punt packet to host";
    }
    leaf l3_no_l3_dlp_mapping {
      type oc-yang:counter64;
      description
        " The L3 DLP mapping is not available for the packet";
    }
    leaf l3_l3_dlp_disabled {
      type oc-yang:counter64;
      description
        "set a trap if egress L3 Destination Logical Port is disabled for 1 plus 1 linear protection";
    }
    leaf l3_asbr_table_miss {
      type oc-yang:counter64;
      description
        "No match found in per DPE and ASBR table during BGPLU label lookup ";
    }
    leaf l3_egress_monitor {
      type oc-yang:counter64;
      description
        "L3 egress interface is enabled for Netflow ";
    }
    leaf l3_encap_table_miss {
      type oc-yang:counter64;
      description
        "Trap if enacapsulation header or data for MPLS ASBR label or SRv6 SID cannot be determined";
    }
    leaf l3_glean_aci_proxy {
      type oc-yang:counter64;
      description
        "Forwarding destination resolved to glean adjacency Cisco ACI";
    }
    leaf l3_null_adj {
      type oc-yang:counter64;
      description
        "L3 forwarding FIB lookup indicates packets destined to a NULL interface";
    }
    leaf l3_no_hbm_access_dip {
      type oc-yang:counter64;
      description
        "IP packet destination IP LPM lookup failed";
    }
    leaf l3_no_hbm_access_sip {
      type oc-yang:counter64;
      description
        "IP packet source IP LPM lookup failed";
    }
    leaf l3_invalid_spi {
      type oc-yang:counter64;
      description
        "Incoming packet is processed only if packet intended for Security Engine.Trap if security profile cannot be determined or unencrypted clear packet destined to receive SEC";
    }
    leaf l3_int_hop_limit {
      type oc-yang:counter64;
      description
        "L3 egress packets header hop limit is less than or equal to 1";
    }
    leaf l3_ip_mc_drop {
      type oc-yang:counter64;
      description
        "IP MC packet simple MC RPF check failed";
    }
    leaf l3_ip_mc_punt_dc_pass {
      type oc-yang:counter64;
      description
        "Directly connected route IP multicast and IP MC RPF check passed";
    }
    leaf l3_ip_multicast_not_found {
      type oc-yang:counter64;
      description
        " IP multicast packet forwarding lookup failed in Multicast Group database";
    }
    leaf l3_l3_same_tunnel_intf {
      type oc-yang:counter64;
      description
        " Trap if source tunnel port is equal to destination tunnel port";
    }
    leaf l3_lpm_default_drop {
      type oc-yang:counter64;
      description
        " packet LPM forwarding lookup resulted in default deny destination";
    }
    leaf l3_lpm_drop {
      type oc-yang:counter64;
      description
        "IP unicast packet LPM destination resolved to a drop destination or VRF redirect exceeded iterations";
    }
    leaf l3_lpm_error {
      type oc-yang:counter64;
      description
        "trap if IP prefix database lookup failed";
    }
    leaf l3_mc_same_interface {
      type oc-yang:counter64;
      description
        "Filter IP multicast packets copies destined to the same L3 interface packet received from excluding collapsed multicast bridge copies";
    }
    leaf l3_no_hbm_access_og {
      type oc-yang:counter64;
      description
        "Database lookup to retrieve IP object group compression failed";
    }
    leaf l3_packet_from_tunnel {
      type oc-yang:counter64;
      description
        "Trap if packet was decapsulated on an IP tunnel and destined to another IP tunnel";
    }
    leaf l3_split_horizon {
      type oc-yang:counter64;
      description
        "Checks if egress L3-DLP is allowed to receive packets from ingress L3-DLP";
    }
    leaf l3_tx_drop {
      type oc-yang:counter64;
      description
        "L3 Packet dropped in the transmit side";
    }
    leaf l3_user_trap1 {
      type oc-yang:counter64;
      description
        "General purpose trap";
    }
    leaf l3_user_trap2 {
      type oc-yang:counter64;
      description
        " Generalpurpose trap";
    }
    leaf l3_rx_mru_failure {
      type oc-yang:counter64;
      description
        "L3 RX MRU exceeded";
    }
    leaf l3_no_lp_over_lag_mapping {
      type oc-yang:counter64;
      description
        "trap if failed to resolve Virtual Output Queue over LAG";
    }
    leaf l3_no_vni_mapping {
      type oc-yang:counter64;
      description
        " trap if could not resolve VNI from packet VRF in encapsulation";
    }
    leaf l3_no_vpn_label_found {
      type oc-yang:counter64;
      description
        "trap if expecting L3 IPv4 or IPv6 VPN label or L2 MPLS VPN label";
    }
    leaf l3_tunnel_sip_invalid {
      type oc-yang:counter64;
      description
        "Tunnel SIP ACL qualification failed";
    }
    leaf l3_tx_frr_drop {
      type oc-yang:counter64;
      description
        "Packet failed egress MLDP Transmit FRR checks";
    }
    leaf l3_tx_mtu_failure {
      type oc-yang:counter64;
      description
        "Transmit Packet exceeds egress port MTU";
    }
    leaf mpls_te_midpoint_ldp_labels_miss {
      type oc-yang:counter64;
      description
        "On egress failed to resolve the Midpoint Traffic-Engineering or LDP labels in encap database";
    }
    leaf mpls_unknown_protocol_after_bos {
      type oc-yang:counter64;
      description
        "MPLS packet reached BOS. Next layer protocol is unknown";
    }
    leaf mpls_ttl_is_zero {
      type oc-yang:counter64;
      description
        "Incoming MPLS packets header TTL value equal to 1";
    }
    leaf mpls_forwarding_disabled {
      type oc-yang:counter64;
      description
        "Received MPLS packet however MPLS forwarding is disabled";
    }
    leaf mpls_invalid_ttl {
      type oc-yang:counter64;
      description
        "Outgoing MPLS packet to be transmitted has MPLS header TTL field equal set 1";
    }
    leaf mpls_ilm_vrf_label_miss {
      type oc-yang:counter64;
      description
        "Label lookup in VRF fails on a CsC lookup miss in VRF MPLS forwarding database";
    }
    leaf mpls_ipv4_over_ipv6_explicit_null {
      type oc-yang:counter64;
      description
        "Error identified in packet format";
    }
    leaf mpls_extension_label {
      type oc-yang:counter64;
      description
        "Incoming MPLS packets label is reserved extension label";
    }
    leaf mpls_term_forwarding_disabled {
      type oc-yang:counter64;
      description
        " MPLS Termination Forwarding is Disabled";
    }
    leaf mpls_mpls_tp_over_lsp {
      type oc-yang:counter64;
      description
        "Incoming MPLS packets label is reserved GAL label";
    }
    leaf mpls_vpn_ttl_one {
      type oc-yang:counter64;
      description
        "VPN terminated";
    }
    leaf mpls_pwhe_fwd_unconfigured_slice {
      type oc-yang:counter64;
      description
        "MPLS PWE packet is forwarded on the slice where the configuration is not present";
    }
    leaf mpls_unexpected_reserved_label {
      type oc-yang:counter64;
      description
        "Incoming MPLS packets label is unknow reserved label";
    }
    leaf ipv4_iic_check_fail {
      type oc-yang:counter64;
      description
        "Ingress L3 Logical port is not in FTAG Tree";
    }
    leaf ipv4_non_comp_mc {
      type oc-yang:counter64;
      description
        "Incompatible IPV4 MC Addresses";
    }
    leaf ipv6_non_comp_mc {
      type oc-yang:counter64;
      description
        "Incompatible IPv6 MC Addresses";
    }
    leaf oamp_pfc_lookup_failed {
      type oc-yang:counter64;
      description
        "PFC SSP Lookup Failed";
    }
    leaf oamp_eth_mep_mapping_failed {
      type oc-yang:counter64;
      description
        "No Match in MEP Mapping lookup";
    }
    leaf oamp_eth_bad_md_name_format {
      type oc-yang:counter64;
      description
        "MD Name format is not equal to 01 Y1731";
    }
    leaf oamp_eth_multicast_da_no_match {
      type oc-yang:counter64;
      description
        "wRONG mULTICAST DA in OAM packet";
    }
    leaf oamp_eth_wrong_meg_id_format {
      type oc-yang:counter64;
      description
        " MEG Id format or length does not match MEP DB entry";
    }
    leaf oamp_eth_ccm_tlv_no_match {
      type oc-yang:counter64;
      description
        " TLV Offset packet is not equal to 70";
    }
    leaf oamp_transport_not_supported {
      type oc-yang:counter64;
      description
        " BFD or SR-PM processing session with incorrect transport";
    }
    leaf oamp_session_lookup_failed {
      type oc-yang:counter64;
      description
        " BFD or SR-PM session lookup failed";
    }
    leaf oamp_bfd_incorrect_ttl {
      type oc-yang:counter64;
      description
        "BFD failing TTL check";
    }
    leaf oamp_invalid_protocol {
      type oc-yang:counter64;
      description
        "BFD or SR-PM processing failing protocol check";
    }
    leaf oamp_bfd_incorrect_version {
      type oc-yang:counter64;
      description
        " BFD incorrect version";
    }
    leaf oamp_incorrect_address {
      type oc-yang:counter64;
      description
        "BFD or SR-PM processing incorrect address";
    }
    leaf oamp_session_received {
      type oc-yang:counter64;
      description
        "BFD or SR-PM session received";
    }
    leaf oamp_eth_unicast_da_no_match {
      type oc-yang:counter64;
      description
        "Unicast DA in OAM Packet doesnt match the MEP Mac address ";
    }
    leaf oamp_pfc_drop_invalid_rx {
      type oc-yang:counter64;
      description
        " PFC invalid Receive packet";
    }
    leaf oamp_icmp_incorrect_session_type_or_ssp {
      type oc-yang:counter64;
      description
        " Received incorrect ession type or on a wrong ssp";
    }
    leaf oamp_icmp_incorrect_ttl {
      type oc-yang:counter64;
      description
        " TTL value is 0 or 1";
    }
    leaf ipv4_options_exist_rx {
      type oc-yang:counter64;
      description
        " Received packet has IPV4 OPTIONS";
    }
    leaf ipv4_options_exist_tx {
      type oc-yang:counter64;
      description
        " Packet that needs to be transmitted needs IPV4 OPTIONS addition";
    }
    leaf ipv4_checksum {
      type oc-yang:counter64;
      description
        " Error in IPV4 CHECKSUM";
    }
    leaf ipv4_header_error {
      type oc-yang:counter64;
      description
        " Error in IPv4 header fields";
    }
    leaf ipv6_hop_by_hop {
      type oc-yang:counter64;
      description
        "Hop by hop header is set as the next header for the IPV6 packet";
    }
    leaf ipv6_header_error {
      type oc-yang:counter64;
      description
        " Error in IPV6 HEADER fields";
    }
    leaf ipv4_mc_forwarding_disabled {
      type oc-yang:counter64;
      description
        "IPV4 Multicast forwarding is disabled on the received port";
    }
    leaf ipv6_mc_forwarding_disabled {
      type oc-yang:counter64;
      description
        " IPV6 Multicast forwarding is disabled on the received port";
    }
    leaf counters_dmc_pier_oobe_dropped_packets {
      type oc-yang:counter64;
      description
        "This field counts the number of OOBE drop packets";
    }
    leaf counters_mmu_errors_lpm_errors {
      type oc-yang:counter64;
      description
        "Counter of LPM lookups returned with errors shared counter for both LPM interfaces";
    }
    leaf counters_mmu_errors_dram_drop_dbd_packets_read {
      type oc-yang:counter64;
      description
        "DRAM packets that are read from HBM for which drop bit was set in dics2mmu command.";
    }
    leaf counters_mmu_errors_sms0_dropped_packets {
      type oc-yang:counter64;
      description
        "Counter of invert_crc packets SOPs received by MMU from SMS if 0";
    }
    leaf counters_mmu_errors_sms1_dropped_packets {
      type oc-yang:counter64;
      description
        "Counter of invert_crc packets SOPs received by MMU from SMS if 1";
    }
    leaf counters_npu_host_out_packets_with_drop_ind_from_npe {
      type oc-yang:counter64;
      description
        "The amount of packets that were sent from the npu-host NPE with drop indication and were thus dropped.";
    }
    leaf counters_npu_host_scan_mps_drop {
      type oc-yang:counter64;
      description
        "nan";
    }
    leaf counters_npu_host_scan_sat_drop {
      type oc-yang:counter64;
      description
        "nan";
    }
    leaf counters_rx_lm_drop0_dropped_p_ds {
      type oc-yang:counter64;
      description
        "Number of LM-Read PDs that were dropped due to no available context";
    }
    leaf counters_rx_lm_drop1_dropped_p_ds {
      type oc-yang:counter64;
      description
        "Number of LM-Read PDs that were dropped due to no available context";
    }
    leaf counters_rx_lm_drop2_dropped_p_ds {
      type oc-yang:counter64;
      description
        "Number of LM-Read PDs that were dropped due to no available context";
    }
    leaf counters_rx_lm_drop3_dropped_p_ds {
      type oc-yang:counter64;
      description
        "Number of LM-Read PDs that were dropped due to no available context";
    }
    leaf counters_rx_lm_drop4_dropped_p_ds {
      type oc-yang:counter64;
      description
        "Number of LM-Read PDs that were dropped due to no available context";
    }
    leaf counters_rx_lm_drop5_dropped_p_ds {
      type oc-yang:counter64;
      description
        "Number of LM-Read PDs that were dropped due to no available context";
    }
    leaf counters_slice0_cluster0_ene_outgoing_headers_with_errors {
      type oc-yang:counter64;
      description
        "Number of headers Exiting the ENE with Error bit on";
    }
    leaf counters_slice0_cluster1_ene_outgoing_headers_with_errors {
      type oc-yang:counter64;
      description
        "Number of headers Exiting the ENE with Error bit on";
    }
    leaf counters_slice0_fllb_debug_register_dropped_p_ds {
      type oc-yang:counter64;
      description
        "Number of PDs dropped due to no eligible links";
    }
    leaf counters_slice0_ifg0_ifgb_rx_cgm_0_csms_dropped_packets {
      type oc-yang:counter64;
      description
        "RX CSMS packets drop counter.";
    }
    leaf counters_slice0_ifg0_ifgb_rx_cgm_0_frm_dropped_packets {
      type oc-yang:counter64;
      description
        "RX FRM packets drop counter.";
    }
    leaf counters_slice0_ifg0_ifgb_rx_cgm_0_fte_dropped_packets {
      type oc-yang:counter64;
      description
        "RX FTE packets drop counter.";
    }
    leaf counters_slice0_ifg0_ifgb_rx_cgm_1_csms_dropped_packets {
      type oc-yang:counter64;
      description
        "RX CSMS packets drop counter.";
    }
    leaf counters_slice0_ifg0_ifgb_rx_cgm_1_frm_dropped_packets {
      type oc-yang:counter64;
      description
        "RX FRM packets drop counter.";
    }
    leaf counters_slice0_ifg0_ifgb_rx_cgm_1_fte_dropped_packets {
      type oc-yang:counter64;
      description
        "RX FTE packets drop counter.";
    }
    leaf counters_slice0_ifg0_ifgb_rx_cgm_2_csms_dropped_packets {
      type oc-yang:counter64;
      description
        "RX CSMS packets drop counter.";
    }
    leaf counters_slice0_ifg0_ifgb_rx_cgm_2_frm_dropped_packets {
      type oc-yang:counter64;
      description
        "RX FRM packets drop counter.";
    }
    leaf counters_slice0_ifg0_ifgb_rx_cgm_2_fte_dropped_packets {
      type oc-yang:counter64;
      description
        "RX FTE packets drop counter.";
    }
    leaf counters_slice0_ifg0_ifgb_rx_cgm_3_csms_dropped_packets {
      type oc-yang:counter64;
      description
        "RX CSMS packets drop counter.";
    }
    leaf counters_slice0_ifg0_ifgb_rx_cgm_3_frm_dropped_packets {
      type oc-yang:counter64;
      description
        "RX FRM packets drop counter.";
    }
    leaf counters_slice0_ifg0_ifgb_rx_cgm_3_fte_dropped_packets {
      type oc-yang:counter64;
      description
        "RX FTE packets drop counter.";
    }
    leaf counters_slice0_ifg0_ifgb_rx_port_0_oobe_crc_errors {
      type oc-yang:counter64;
      description
        "OOB Extract CRC error counter per port";
    }
    leaf counters_slice0_ifg0_ifgb_rx_port_0_undersized_dropped_packets {
      type oc-yang:counter64;
      description
        "Counter for packets that were dropped because they were smaller than 64B.";
    }
    leaf counters_slice0_ifg0_ifgb_rx_port_1_oobe_crc_errors {
      type oc-yang:counter64;
      description
        "OOB Extract CRC error counter per port";
    }
    leaf counters_slice0_ifg0_ifgb_rx_port_1_undersized_dropped_packets {
      type oc-yang:counter64;
      description
        "Counter for packets that were dropped because they were smaller than 64B.";
    }
    leaf counters_slice0_ifg0_ifgb_rx_port_10_oobe_crc_errors {
      type oc-yang:counter64;
      description
        "OOB Extract CRC error counter per port";
    }
    leaf counters_slice0_ifg0_ifgb_rx_port_10_undersized_dropped_packets {
      type oc-yang:counter64;
      description
        "Counter for packets that were dropped because they were smaller than 64B.";
    }
    leaf counters_slice0_ifg0_ifgb_rx_port_11_oobe_crc_errors {
      type oc-yang:counter64;
      description
        "OOB Extract CRC error counter per port";
    }
    leaf counters_slice0_ifg0_ifgb_rx_port_11_undersized_dropped_packets {
      type oc-yang:counter64;
      description
        "Counter for packets that were dropped because they were smaller than 64B.";
    }
    leaf counters_slice0_ifg0_ifgb_rx_port_12_oobe_crc_errors {
      type oc-yang:counter64;
      description
        "OOB Extract CRC error counter per port";
    }
    leaf counters_slice0_ifg0_ifgb_rx_port_12_undersized_dropped_packets {
      type oc-yang:counter64;
      description
        "Counter for packets that were dropped because they were smaller than 64B.";
    }
    leaf counters_slice0_ifg0_ifgb_rx_port_13_oobe_crc_errors {
      type oc-yang:counter64;
      description
        "OOB Extract CRC error counter per port";
    }
    leaf counters_slice0_ifg0_ifgb_rx_port_13_undersized_dropped_packets {
      type oc-yang:counter64;
      description
        "Counter for packets that were dropped because they were smaller than 64B.";
    }
    leaf counters_slice0_ifg0_ifgb_rx_port_14_oobe_crc_errors {
      type oc-yang:counter64;
      description
        "OOB Extract CRC error counter per port";
    }
    leaf counters_slice0_ifg0_ifgb_rx_port_14_undersized_dropped_packets {
      type oc-yang:counter64;
      description
        "Counter for packets that were dropped because they were smaller than 64B.";
    }
    leaf counters_slice0_ifg0_ifgb_rx_port_15_oobe_crc_errors {
      type oc-yang:counter64;
      description
        "OOB Extract CRC error counter per port";
    }
    leaf counters_slice0_ifg0_ifgb_rx_port_15_undersized_dropped_packets {
      type oc-yang:counter64;
      description
        "Counter for packets that were dropped because they were smaller than 64B.";
    }
    leaf counters_slice0_ifg0_ifgb_rx_port_16_undersized_dropped_packets {
      type oc-yang:counter64;
      description
        "Counter for packets that were dropped because they were smaller than 64B.";
    }
    leaf counters_slice0_ifg0_ifgb_rx_port_17_undersized_dropped_packets {
      type oc-yang:counter64;
      description
        "Counter for packets that were dropped because they were smaller than 64B.";
    }
    leaf counters_slice0_ifg0_ifgb_rx_port_18_undersized_dropped_packets {
      type oc-yang:counter64;
      description
        "Counter for packets that were dropped because they were smaller than 64B.";
    }
    leaf counters_slice0_ifg0_ifgb_rx_port_19_undersized_dropped_packets {
      type oc-yang:counter64;
      description
        "Counter for packets that were dropped because they were smaller than 64B.";
    }
    leaf counters_slice0_ifg0_ifgb_rx_port_2_oobe_crc_errors {
      type oc-yang:counter64;
      description
        "OOB Extract CRC error counter per port";
    }
    leaf counters_slice0_ifg0_ifgb_rx_port_2_undersized_dropped_packets {
      type oc-yang:counter64;
      description
        "Counter for packets that were dropped because they were smaller than 64B.";
    }
    leaf counters_slice0_ifg0_ifgb_rx_port_20_undersized_dropped_packets {
      type oc-yang:counter64;
      description
        "Counter for packets that were dropped because they were smaller than 64B.";
    }
    leaf counters_slice0_ifg0_ifgb_rx_port_21_undersized_dropped_packets {
      type oc-yang:counter64;
      description
        "Counter for packets that were dropped because they were smaller than 64B.";
    }
    leaf counters_slice0_ifg0_ifgb_rx_port_22_undersized_dropped_packets {
      type oc-yang:counter64;
      description
        "Counter for packets that were dropped because they were smaller than 64B.";
    }
    leaf counters_slice0_ifg0_ifgb_rx_port_23_undersized_dropped_packets {
      type oc-yang:counter64;
      description
        "Counter for packets that were dropped because they were smaller than 64B.";
    }
    leaf counters_slice0_ifg0_ifgb_rx_port_24_undersized_dropped_packets {
      type oc-yang:counter64;
      description
        "Counter for packets that were dropped because they were smaller than 64B.";
    }
    leaf counters_slice0_ifg0_ifgb_rx_port_25_undersized_dropped_packets {
      type oc-yang:counter64;
      description
        "Counter for packets that were dropped because they were smaller than 64B.";
    }
    leaf counters_slice0_ifg0_ifgb_rx_port_26_undersized_dropped_packets {
      type oc-yang:counter64;
      description
        "Counter for packets that were dropped because they were smaller than 64B.";
    }
    leaf counters_slice0_ifg0_ifgb_rx_port_27_undersized_dropped_packets {
      type oc-yang:counter64;
      description
        "Counter for packets that were dropped because they were smaller than 64B.";
    }
    leaf counters_slice0_ifg0_ifgb_rx_port_28_undersized_dropped_packets {
      type oc-yang:counter64;
      description
        "Counter for packets that were dropped because they were smaller than 64B.";
    }
    leaf counters_slice0_ifg0_ifgb_rx_port_29_undersized_dropped_packets {
      type oc-yang:counter64;
      description
        "Counter for packets that were dropped because they were smaller than 64B.";
    }
    leaf counters_slice0_ifg0_ifgb_rx_port_3_oobe_crc_errors {
      type oc-yang:counter64;
      description
        "OOB Extract CRC error counter per port";
    }
    leaf counters_slice0_ifg0_ifgb_rx_port_3_undersized_dropped_packets {
      type oc-yang:counter64;
      description
        "Counter for packets that were dropped because they were smaller than 64B.";
    }
    leaf counters_slice0_ifg0_ifgb_rx_port_30_undersized_dropped_packets {
      type oc-yang:counter64;
      description
        "Counter for packets that were dropped because they were smaller than 64B.";
    }
    leaf counters_slice0_ifg0_ifgb_rx_port_31_undersized_dropped_packets {
      type oc-yang:counter64;
      description
        "Counter for packets that were dropped because they were smaller than 64B.";
    }
    leaf counters_slice0_ifg0_ifgb_rx_port_4_oobe_crc_errors {
      type oc-yang:counter64;
      description
        "OOB Extract CRC error counter per port";
    }
    leaf counters_slice0_ifg0_ifgb_rx_port_4_undersized_dropped_packets {
      type oc-yang:counter64;
      description
        "Counter for packets that were dropped because they were smaller than 64B.";
    }
    leaf counters_slice0_ifg0_ifgb_rx_port_5_oobe_crc_errors {
      type oc-yang:counter64;
      description
        "OOB Extract CRC error counter per port";
    }
    leaf counters_slice0_ifg0_ifgb_rx_port_5_undersized_dropped_packets {
      type oc-yang:counter64;
      description
        "Counter for packets that were dropped because they were smaller than 64B.";
    }
    leaf counters_slice0_ifg0_ifgb_rx_port_6_oobe_crc_errors {
      type oc-yang:counter64;
      description
        "OOB Extract CRC error counter per port";
    }
    leaf counters_slice0_ifg0_ifgb_rx_port_6_undersized_dropped_packets {
      type oc-yang:counter64;
      description
        "Counter for packets that were dropped because they were smaller than 64B.";
    }
    leaf counters_slice0_ifg0_ifgb_rx_port_7_oobe_crc_errors {
      type oc-yang:counter64;
      description
        "OOB Extract CRC error counter per port";
    }
    leaf counters_slice0_ifg0_ifgb_rx_port_7_undersized_dropped_packets {
      type oc-yang:counter64;
      description
        "Counter for packets that were dropped because they were smaller than 64B.";
    }
    leaf counters_slice0_ifg0_ifgb_rx_port_8_oobe_crc_errors {
      type oc-yang:counter64;
      description
        "OOB Extract CRC error counter per port";
    }
    leaf counters_slice0_ifg0_ifgb_rx_port_8_undersized_dropped_packets {
      type oc-yang:counter64;
      description
        "Counter for packets that were dropped because they were smaller than 64B.";
    }
    leaf counters_slice0_ifg0_ifgb_rx_port_9_oobe_crc_errors {
      type oc-yang:counter64;
      description
        "OOB Extract CRC error counter per port";
    }
    leaf counters_slice0_ifg0_ifgb_rx_port_9_undersized_dropped_packets {
      type oc-yang:counter64;
      description
        "Counter for packets that were dropped because they were smaller than 64B.";
    }
    leaf counters_slice0_ifg0_ifgb_rx_protection_dropped_fragments {
      type oc-yang:counter64;
      description
        "RXPP interface protection fragments drop counter.";
    }
    leaf counters_slice0_ifg0_ifgb_rx_protection_dropped_packets {
      type oc-yang:counter64;
      description
        "RXPP interface protection packet drop counter.";
    }
    leaf counters_slice0_ifg0_ifgbi_recycle_in_band_extract_npu_host_re_direct_drop {
      type oc-yang:counter64;
      description
        "InBand Extract NPU Host ReDirect drop counter. Increments based on the RcyDropCntrsCfg.";
    }
    leaf counters_slice0_ifg0_ifgbi_recycle_in_band_extract_packet_dma_re_direct_drop {
      type oc-yang:counter64;
      description
        "InBand Extract Pkt DMA ReDirect drop counter. Increments based on the RcyDropCntrsCfg.";
    }
    leaf counters_slice0_ifg0_npu_rxpp_fwd_post_npe_dropped_packets {
      type oc-yang:counter64;
      description
        "Counts packets dropped by the rxpp";
    }
    leaf counters_slice0_ifg0_npu_rxpp_fwd_post_npe_dropped_packets_due_destination {
      type oc-yang:counter64;
      description
        "nan";
    }
    leaf counters_slice0_ifg0_npu_rxpp_fwd_post_npe_dropped_packets_due_dummy {
      type oc-yang:counter64;
      description
        "nan";
    }
    leaf counters_slice0_ifg0_npu_rxpp_fwd_post_npe_dropped_packets_due_ecc {
      type oc-yang:counter64;
      description
        "nan";
    }
    leaf counters_slice0_ifg0_npu_rxpp_fwd_post_npe_dropped_packets_due_err_flag {
      type oc-yang:counter64;
      description
        "nan";
    }
    leaf counters_slice0_ifg0_npu_rxpp_fwd_post_npe_dropped_packets_due_frag_parity_error {
      type oc-yang:counter64;
      description
        "nan";
    }
    leaf counters_slice0_ifg0_npu_txpp_hw_editor_1_packets_with_error_bit {
      type oc-yang:counter64;
      description
        "Counts number of packet leaving HW Editor 1 inst 0 have error bit assered";
    }
    leaf counters_slice0_ifg0_npu_txpp_hw_editor_2_packets_with_error_bit {
      type oc-yang:counter64;
      description
        "Counts number of packet leaving HW Editor 2 towards ifg0 have error bit assered";
    }
    leaf counters_slice0_ifg0_npu_txpp_npe_packets_with_error_bit {
      type oc-yang:counter64;
      description
        "Counts number of packet leaving NPE 0 have error bit assered";
    }
    leaf counters_slice0_ifg0_npu_txpp_preprocess_packets_with_error_bit {
      type oc-yang:counter64;
      description
        "Counts number of packet leaving preprocessing 0 have error bit assered";
    }
    leaf counters_slice0_ifg1_ifgb_rx_cgm_0_csms_dropped_packets {
      type oc-yang:counter64;
      description
        "RX CSMS packets drop counter.";
    }
    leaf counters_slice0_ifg1_ifgb_rx_cgm_0_frm_dropped_packets {
      type oc-yang:counter64;
      description
        "RX FRM packets drop counter.";
    }
    leaf counters_slice0_ifg1_ifgb_rx_cgm_0_fte_dropped_packets {
      type oc-yang:counter64;
      description
        "RX FTE packets drop counter.";
    }
    leaf counters_slice0_ifg1_ifgb_rx_cgm_1_csms_dropped_packets {
      type oc-yang:counter64;
      description
        "RX CSMS packets drop counter.";
    }
    leaf counters_slice0_ifg1_ifgb_rx_cgm_1_frm_dropped_packets {
      type oc-yang:counter64;
      description
        "RX FRM packets drop counter.";
    }
    leaf counters_slice0_ifg1_ifgb_rx_cgm_1_fte_dropped_packets {
      type oc-yang:counter64;
      description
        "RX FTE packets drop counter.";
    }
    leaf counters_slice0_ifg1_ifgb_rx_cgm_2_csms_dropped_packets {
      type oc-yang:counter64;
      description
        "RX CSMS packets drop counter.";
    }
    leaf counters_slice0_ifg1_ifgb_rx_cgm_2_frm_dropped_packets {
      type oc-yang:counter64;
      description
        "RX FRM packets drop counter.";
    }
    leaf counters_slice0_ifg1_ifgb_rx_cgm_2_fte_dropped_packets {
      type oc-yang:counter64;
      description
        "RX FTE packets drop counter.";
    }
    leaf counters_slice0_ifg1_ifgb_rx_cgm_3_csms_dropped_packets {
      type oc-yang:counter64;
      description
        "RX CSMS packets drop counter.";
    }
    leaf counters_slice0_ifg1_ifgb_rx_cgm_3_frm_dropped_packets {
      type oc-yang:counter64;
      description
        "RX FRM packets drop counter.";
    }
    leaf counters_slice0_ifg1_ifgb_rx_cgm_3_fte_dropped_packets {
      type oc-yang:counter64;
      description
        "RX FTE packets drop counter.";
    }
    leaf counters_slice0_ifg1_ifgb_rx_port_0_oobe_crc_errors {
      type oc-yang:counter64;
      description
        "OOB Extract CRC error counter per port";
    }
    leaf counters_slice0_ifg1_ifgb_rx_port_0_undersized_dropped_packets {
      type oc-yang:counter64;
      description
        "Counter for packets that were dropped because they were smaller than 64B.";
    }
    leaf counters_slice0_ifg1_ifgb_rx_port_1_oobe_crc_errors {
      type oc-yang:counter64;
      description
        "OOB Extract CRC error counter per port";
    }
    leaf counters_slice0_ifg1_ifgb_rx_port_1_undersized_dropped_packets {
      type oc-yang:counter64;
      description
        "Counter for packets that were dropped because they were smaller than 64B.";
    }
    leaf counters_slice0_ifg1_ifgb_rx_port_10_oobe_crc_errors {
      type oc-yang:counter64;
      description
        "OOB Extract CRC error counter per port";
    }
    leaf counters_slice0_ifg1_ifgb_rx_port_10_undersized_dropped_packets {
      type oc-yang:counter64;
      description
        "Counter for packets that were dropped because they were smaller than 64B.";
    }
    leaf counters_slice0_ifg1_ifgb_rx_port_11_oobe_crc_errors {
      type oc-yang:counter64;
      description
        "OOB Extract CRC error counter per port";
    }
    leaf counters_slice0_ifg1_ifgb_rx_port_11_undersized_dropped_packets {
      type oc-yang:counter64;
      description
        "Counter for packets that were dropped because they were smaller than 64B.";
    }
    leaf counters_slice0_ifg1_ifgb_rx_port_12_oobe_crc_errors {
      type oc-yang:counter64;
      description
        "OOB Extract CRC error counter per port";
    }
    leaf counters_slice0_ifg1_ifgb_rx_port_12_undersized_dropped_packets {
      type oc-yang:counter64;
      description
        "Counter for packets that were dropped because they were smaller than 64B.";
    }
    leaf counters_slice0_ifg1_ifgb_rx_port_13_oobe_crc_errors {
      type oc-yang:counter64;
      description
        "OOB Extract CRC error counter per port";
    }
    leaf counters_slice0_ifg1_ifgb_rx_port_13_undersized_dropped_packets {
      type oc-yang:counter64;
      description
        "Counter for packets that were dropped because they were smaller than 64B.";
    }
    leaf counters_slice0_ifg1_ifgb_rx_port_14_oobe_crc_errors {
      type oc-yang:counter64;
      description
        "OOB Extract CRC error counter per port";
    }
    leaf counters_slice0_ifg1_ifgb_rx_port_14_undersized_dropped_packets {
      type oc-yang:counter64;
      description
        "Counter for packets that were dropped because they were smaller than 64B.";
    }
    leaf counters_slice0_ifg1_ifgb_rx_port_15_oobe_crc_errors {
      type oc-yang:counter64;
      description
        "OOB Extract CRC error counter per port";
    }
    leaf counters_slice0_ifg1_ifgb_rx_port_15_undersized_dropped_packets {
      type oc-yang:counter64;
      description
        "Counter for packets that were dropped because they were smaller than 64B.";
    }
    leaf counters_slice0_ifg1_ifgb_rx_port_16_undersized_dropped_packets {
      type oc-yang:counter64;
      description
        "Counter for packets that were dropped because they were smaller than 64B.";
    }
    leaf counters_slice0_ifg1_ifgb_rx_port_17_undersized_dropped_packets {
      type oc-yang:counter64;
      description
        "Counter for packets that were dropped because they were smaller than 64B.";
    }
    leaf counters_slice0_ifg1_ifgb_rx_port_18_undersized_dropped_packets {
      type oc-yang:counter64;
      description
        "Counter for packets that were dropped because they were smaller than 64B.";
    }
    leaf counters_slice0_ifg1_ifgb_rx_port_19_undersized_dropped_packets {
      type oc-yang:counter64;
      description
        "Counter for packets that were dropped because they were smaller than 64B.";
    }
    leaf counters_slice0_ifg1_ifgb_rx_port_2_oobe_crc_errors {
      type oc-yang:counter64;
      description
        "OOB Extract CRC error counter per port";
    }
    leaf counters_slice0_ifg1_ifgb_rx_port_2_undersized_dropped_packets {
      type oc-yang:counter64;
      description
        "Counter for packets that were dropped because they were smaller than 64B.";
    }
    leaf counters_slice0_ifg1_ifgb_rx_port_20_undersized_dropped_packets {
      type oc-yang:counter64;
      description
        "Counter for packets that were dropped because they were smaller than 64B.";
    }
    leaf counters_slice0_ifg1_ifgb_rx_port_21_undersized_dropped_packets {
      type oc-yang:counter64;
      description
        "Counter for packets that were dropped because they were smaller than 64B.";
    }
    leaf counters_slice0_ifg1_ifgb_rx_port_22_undersized_dropped_packets {
      type oc-yang:counter64;
      description
        "Counter for packets that were dropped because they were smaller than 64B.";
    }
    leaf counters_slice0_ifg1_ifgb_rx_port_23_undersized_dropped_packets {
      type oc-yang:counter64;
      description
        "Counter for packets that were dropped because they were smaller than 64B.";
    }
    leaf counters_slice0_ifg1_ifgb_rx_port_24_undersized_dropped_packets {
      type oc-yang:counter64;
      description
        "Counter for packets that were dropped because they were smaller than 64B.";
    }
    leaf counters_slice0_ifg1_ifgb_rx_port_25_undersized_dropped_packets {
      type oc-yang:counter64;
      description
        "Counter for packets that were dropped because they were smaller than 64B.";
    }
    leaf counters_slice0_ifg1_ifgb_rx_port_26_undersized_dropped_packets {
      type oc-yang:counter64;
      description
        "Counter for packets that were dropped because they were smaller than 64B.";
    }
    leaf counters_slice0_ifg1_ifgb_rx_port_27_undersized_dropped_packets {
      type oc-yang:counter64;
      description
        "Counter for packets that were dropped because they were smaller than 64B.";
    }
    leaf counters_slice0_ifg1_ifgb_rx_port_28_undersized_dropped_packets {
      type oc-yang:counter64;
      description
        "Counter for packets that were dropped because they were smaller than 64B.";
    }
    leaf counters_slice0_ifg1_ifgb_rx_port_29_undersized_dropped_packets {
      type oc-yang:counter64;
      description
        "Counter for packets that were dropped because they were smaller than 64B.";
    }
    leaf counters_slice0_ifg1_ifgb_rx_port_3_oobe_crc_errors {
      type oc-yang:counter64;
      description
        "OOB Extract CRC error counter per port";
    }
    leaf counters_slice0_ifg1_ifgb_rx_port_3_undersized_dropped_packets {
      type oc-yang:counter64;
      description
        "Counter for packets that were dropped because they were smaller than 64B.";
    }
    leaf counters_slice0_ifg1_ifgb_rx_port_30_undersized_dropped_packets {
      type oc-yang:counter64;
      description
        "Counter for packets that were dropped because they were smaller than 64B.";
    }
    leaf counters_slice0_ifg1_ifgb_rx_port_31_undersized_dropped_packets {
      type oc-yang:counter64;
      description
        "Counter for packets that were dropped because they were smaller than 64B.";
    }
    leaf counters_slice0_ifg1_ifgb_rx_port_4_oobe_crc_errors {
      type oc-yang:counter64;
      description
        "OOB Extract CRC error counter per port";
    }
    leaf counters_slice0_ifg1_ifgb_rx_port_4_undersized_dropped_packets {
      type oc-yang:counter64;
      description
        "Counter for packets that were dropped because they were smaller than 64B.";
    }
    leaf counters_slice0_ifg1_ifgb_rx_port_5_oobe_crc_errors {
      type oc-yang:counter64;
      description
        "OOB Extract CRC error counter per port";
    }
    leaf counters_slice0_ifg1_ifgb_rx_port_5_undersized_dropped_packets {
      type oc-yang:counter64;
      description
        "Counter for packets that were dropped because they were smaller than 64B.";
    }
    leaf counters_slice0_ifg1_ifgb_rx_port_6_oobe_crc_errors {
      type oc-yang:counter64;
      description
        "OOB Extract CRC error counter per port";
    }
    leaf counters_slice0_ifg1_ifgb_rx_port_6_undersized_dropped_packets {
      type oc-yang:counter64;
      description
        "Counter for packets that were dropped because they were smaller than 64B.";
    }
    leaf counters_slice0_ifg1_ifgb_rx_port_7_oobe_crc_errors {
      type oc-yang:counter64;
      description
        "OOB Extract CRC error counter per port";
    }
    leaf counters_slice0_ifg1_ifgb_rx_port_7_undersized_dropped_packets {
      type oc-yang:counter64;
      description
        "Counter for packets that were dropped because they were smaller than 64B.";
    }
    leaf counters_slice0_ifg1_ifgb_rx_port_8_oobe_crc_errors {
      type oc-yang:counter64;
      description
        "OOB Extract CRC error counter per port";
    }
    leaf counters_slice0_ifg1_ifgb_rx_port_8_undersized_dropped_packets {
      type oc-yang:counter64;
      description
        "Counter for packets that were dropped because they were smaller than 64B.";
    }
    leaf counters_slice0_ifg1_ifgb_rx_port_9_oobe_crc_errors {
      type oc-yang:counter64;
      description
        "OOB Extract CRC error counter per port";
    }
    leaf counters_slice0_ifg1_ifgb_rx_port_9_undersized_dropped_packets {
      type oc-yang:counter64;
      description
        "Counter for packets that were dropped because they were smaller than 64B.";
    }
    leaf counters_slice0_ifg1_ifgb_rx_protection_dropped_fragments {
      type oc-yang:counter64;
      description
        "RXPP interface protection fragments drop counter.";
    }
    leaf counters_slice0_ifg1_ifgb_rx_protection_dropped_packets {
      type oc-yang:counter64;
      description
        "RXPP interface protection packet drop counter.";
    }
    leaf counters_slice0_ifg1_ifgbi_recycle_in_band_extract_npu_host_re_direct_drop {
      type oc-yang:counter64;
      description
        "InBand Extract NPU Host ReDirect drop counter. Increments based on the RcyDropCntrsCfg.";
    }
    leaf counters_slice0_ifg1_ifgbi_recycle_in_band_extract_packet_dma_re_direct_drop {
      type oc-yang:counter64;
      description
        "InBand Extract Pkt DMA ReDirect drop counter. Increments based on the RcyDropCntrsCfg.";
    }
    leaf counters_slice0_ifg1_npu_rxpp_fwd_post_npe_dropped_packets {
      type oc-yang:counter64;
      description
        "Counts packets dropped by the rxpp";
    }
    leaf counters_slice0_ifg1_npu_rxpp_fwd_post_npe_dropped_packets_due_destination {
      type oc-yang:counter64;
      description
        "nan";
    }
    leaf counters_slice0_ifg1_npu_rxpp_fwd_post_npe_dropped_packets_due_dummy {
      type oc-yang:counter64;
      description
        "nan";
    }
    leaf counters_slice0_ifg1_npu_rxpp_fwd_post_npe_dropped_packets_due_ecc {
      type oc-yang:counter64;
      description
        "nan";
    }
    leaf counters_slice0_ifg1_npu_rxpp_fwd_post_npe_dropped_packets_due_err_flag {
      type oc-yang:counter64;
      description
        "nan";
    }
    leaf counters_slice0_ifg1_npu_rxpp_fwd_post_npe_dropped_packets_due_frag_parity_error {
      type oc-yang:counter64;
      description
        "nan";
    }
    leaf counters_slice0_ifg1_npu_txpp_hw_editor_1_packets_with_error_bit {
      type oc-yang:counter64;
      description
        "Counts number of packet leaving HW Editor 1 inst 1 have error bit assered";
    }
    leaf counters_slice0_ifg1_npu_txpp_hw_editor_2_packets_with_error_bit {
      type oc-yang:counter64;
      description
        "Counts number of packet leaving HW Editor 2 towards ifg1 have error bit assered";
    }
    leaf counters_slice0_ifg1_npu_txpp_npe_packets_with_error_bit {
      type oc-yang:counter64;
      description
        "Counts number of packet leaving NPE 1 have error bit assered";
    }
    leaf counters_slice0_ifg1_npu_txpp_preprocess_packets_with_error_bit {
      type oc-yang:counter64;
      description
        "Counts number of packet leaving preprocessing 1 have error bit assered";
    }
    leaf counters_slice1_cluster0_ene_outgoing_headers_with_errors {
      type oc-yang:counter64;
      description
        "Number of headers Exiting the ENE with Error bit on";
    }
    leaf counters_slice1_cluster1_ene_outgoing_headers_with_errors {
      type oc-yang:counter64;
      description
        "Number of headers Exiting the ENE with Error bit on";
    }
    leaf counters_slice1_fllb_debug_register_dropped_p_ds {
      type oc-yang:counter64;
      description
        "Number of PDs dropped due to no eligible links";
    }
    leaf counters_slice1_ifg0_ifgb_rx_cgm_0_csms_dropped_packets {
      type oc-yang:counter64;
      description
        "RX CSMS packets drop counter.";
    }
    leaf counters_slice1_ifg0_ifgb_rx_cgm_0_frm_dropped_packets {
      type oc-yang:counter64;
      description
        "RX FRM packets drop counter.";
    }
    leaf counters_slice1_ifg0_ifgb_rx_cgm_0_fte_dropped_packets {
      type oc-yang:counter64;
      description
        "RX FTE packets drop counter.";
    }
    leaf counters_slice1_ifg0_ifgb_rx_cgm_1_csms_dropped_packets {
      type oc-yang:counter64;
      description
        "RX CSMS packets drop counter.";
    }
    leaf counters_slice1_ifg0_ifgb_rx_cgm_1_frm_dropped_packets {
      type oc-yang:counter64;
      description
        "RX FRM packets drop counter.";
    }
    leaf counters_slice1_ifg0_ifgb_rx_cgm_1_fte_dropped_packets {
      type oc-yang:counter64;
      description
        "RX FTE packets drop counter.";
    }
    leaf counters_slice1_ifg0_ifgb_rx_cgm_2_csms_dropped_packets {
      type oc-yang:counter64;
      description
        "RX CSMS packets drop counter.";
    }
    leaf counters_slice1_ifg0_ifgb_rx_cgm_2_frm_dropped_packets {
      type oc-yang:counter64;
      description
        "RX FRM packets drop counter.";
    }
    leaf counters_slice1_ifg0_ifgb_rx_cgm_2_fte_dropped_packets {
      type oc-yang:counter64;
      description
        "RX FTE packets drop counter.";
    }
    leaf counters_slice1_ifg0_ifgb_rx_cgm_3_csms_dropped_packets {
      type oc-yang:counter64;
      description
        "RX CSMS packets drop counter.";
    }
    leaf counters_slice1_ifg0_ifgb_rx_cgm_3_frm_dropped_packets {
      type oc-yang:counter64;
      description
        "RX FRM packets drop counter.";
    }
    leaf counters_slice1_ifg0_ifgb_rx_cgm_3_fte_dropped_packets {
      type oc-yang:counter64;
      description
        "RX FTE packets drop counter.";
    }
    leaf counters_slice1_ifg0_ifgb_rx_port_0_oobe_crc_errors {
      type oc-yang:counter64;
      description
        "OOB Extract CRC error counter per port";
    }
    leaf counters_slice1_ifg0_ifgb_rx_port_0_undersized_dropped_packets {
      type oc-yang:counter64;
      description
        "Counter for packets that were dropped because they were smaller than 64B.";
    }
    leaf counters_slice1_ifg0_ifgb_rx_port_1_oobe_crc_errors {
      type oc-yang:counter64;
      description
        "OOB Extract CRC error counter per port";
    }
    leaf counters_slice1_ifg0_ifgb_rx_port_1_undersized_dropped_packets {
      type oc-yang:counter64;
      description
        "Counter for packets that were dropped because they were smaller than 64B.";
    }
    leaf counters_slice1_ifg0_ifgb_rx_port_10_oobe_crc_errors {
      type oc-yang:counter64;
      description
        "OOB Extract CRC error counter per port";
    }
    leaf counters_slice1_ifg0_ifgb_rx_port_10_undersized_dropped_packets {
      type oc-yang:counter64;
      description
        "Counter for packets that were dropped because they were smaller than 64B.";
    }
    leaf counters_slice1_ifg0_ifgb_rx_port_11_oobe_crc_errors {
      type oc-yang:counter64;
      description
        "OOB Extract CRC error counter per port";
    }
    leaf counters_slice1_ifg0_ifgb_rx_port_11_undersized_dropped_packets {
      type oc-yang:counter64;
      description
        "Counter for packets that were dropped because they were smaller than 64B.";
    }
    leaf counters_slice1_ifg0_ifgb_rx_port_12_oobe_crc_errors {
      type oc-yang:counter64;
      description
        "OOB Extract CRC error counter per port";
    }
    leaf counters_slice1_ifg0_ifgb_rx_port_12_undersized_dropped_packets {
      type oc-yang:counter64;
      description
        "Counter for packets that were dropped because they were smaller than 64B.";
    }
    leaf counters_slice1_ifg0_ifgb_rx_port_13_oobe_crc_errors {
      type oc-yang:counter64;
      description
        "OOB Extract CRC error counter per port";
    }
    leaf counters_slice1_ifg0_ifgb_rx_port_13_undersized_dropped_packets {
      type oc-yang:counter64;
      description
        "Counter for packets that were dropped because they were smaller than 64B.";
    }
    leaf counters_slice1_ifg0_ifgb_rx_port_14_oobe_crc_errors {
      type oc-yang:counter64;
      description
        "OOB Extract CRC error counter per port";
    }
    leaf counters_slice1_ifg0_ifgb_rx_port_14_undersized_dropped_packets {
      type oc-yang:counter64;
      description
        "Counter for packets that were dropped because they were smaller than 64B.";
    }
    leaf counters_slice1_ifg0_ifgb_rx_port_15_oobe_crc_errors {
      type oc-yang:counter64;
      description
        "OOB Extract CRC error counter per port";
    }
    leaf counters_slice1_ifg0_ifgb_rx_port_15_undersized_dropped_packets {
      type oc-yang:counter64;
      description
        "Counter for packets that were dropped because they were smaller than 64B.";
    }
    leaf counters_slice1_ifg0_ifgb_rx_port_16_undersized_dropped_packets {
      type oc-yang:counter64;
      description
        "Counter for packets that were dropped because they were smaller than 64B.";
    }
    leaf counters_slice1_ifg0_ifgb_rx_port_17_undersized_dropped_packets {
      type oc-yang:counter64;
      description
        "Counter for packets that were dropped because they were smaller than 64B.";
    }
    leaf counters_slice1_ifg0_ifgb_rx_port_18_undersized_dropped_packets {
      type oc-yang:counter64;
      description
        "Counter for packets that were dropped because they were smaller than 64B.";
    }
    leaf counters_slice1_ifg0_ifgb_rx_port_19_undersized_dropped_packets {
      type oc-yang:counter64;
      description
        "Counter for packets that were dropped because they were smaller than 64B.";
    }
    leaf counters_slice1_ifg0_ifgb_rx_port_2_oobe_crc_errors {
      type oc-yang:counter64;
      description
        "OOB Extract CRC error counter per port";
    }
    leaf counters_slice1_ifg0_ifgb_rx_port_2_undersized_dropped_packets {
      type oc-yang:counter64;
      description
        "Counter for packets that were dropped because they were smaller than 64B.";
    }
    leaf counters_slice1_ifg0_ifgb_rx_port_20_undersized_dropped_packets {
      type oc-yang:counter64;
      description
        "Counter for packets that were dropped because they were smaller than 64B.";
    }
    leaf counters_slice1_ifg0_ifgb_rx_port_21_undersized_dropped_packets {
      type oc-yang:counter64;
      description
        "Counter for packets that were dropped because they were smaller than 64B.";
    }
    leaf counters_slice1_ifg0_ifgb_rx_port_22_undersized_dropped_packets {
      type oc-yang:counter64;
      description
        "Counter for packets that were dropped because they were smaller than 64B.";
    }
    leaf counters_slice1_ifg0_ifgb_rx_port_23_undersized_dropped_packets {
      type oc-yang:counter64;
      description
        "Counter for packets that were dropped because they were smaller than 64B.";
    }
    leaf counters_slice1_ifg0_ifgb_rx_port_24_undersized_dropped_packets {
      type oc-yang:counter64;
      description
        "Counter for packets that were dropped because they were smaller than 64B.";
    }
    leaf counters_slice1_ifg0_ifgb_rx_port_25_undersized_dropped_packets {
      type oc-yang:counter64;
      description
        "Counter for packets that were dropped because they were smaller than 64B.";
    }
    leaf counters_slice1_ifg0_ifgb_rx_port_26_undersized_dropped_packets {
      type oc-yang:counter64;
      description
        "Counter for packets that were dropped because they were smaller than 64B.";
    }
    leaf counters_slice1_ifg0_ifgb_rx_port_27_undersized_dropped_packets {
      type oc-yang:counter64;
      description
        "Counter for packets that were dropped because they were smaller than 64B.";
    }
    leaf counters_slice1_ifg0_ifgb_rx_port_28_undersized_dropped_packets {
      type oc-yang:counter64;
      description
        "Counter for packets that were dropped because they were smaller than 64B.";
    }
    leaf counters_slice1_ifg0_ifgb_rx_port_29_undersized_dropped_packets {
      type oc-yang:counter64;
      description
        "Counter for packets that were dropped because they were smaller than 64B.";
    }
    leaf counters_slice1_ifg0_ifgb_rx_port_3_oobe_crc_errors {
      type oc-yang:counter64;
      description
        "OOB Extract CRC error counter per port";
    }
    leaf counters_slice1_ifg0_ifgb_rx_port_3_undersized_dropped_packets {
      type oc-yang:counter64;
      description
        "Counter for packets that were dropped because they were smaller than 64B.";
    }
    leaf counters_slice1_ifg0_ifgb_rx_port_30_undersized_dropped_packets {
      type oc-yang:counter64;
      description
        "Counter for packets that were dropped because they were smaller than 64B.";
    }
    leaf counters_slice1_ifg0_ifgb_rx_port_31_undersized_dropped_packets {
      type oc-yang:counter64;
      description
        "Counter for packets that were dropped because they were smaller than 64B.";
    }
    leaf counters_slice1_ifg0_ifgb_rx_port_4_oobe_crc_errors {
      type oc-yang:counter64;
      description
        "OOB Extract CRC error counter per port";
    }
    leaf counters_slice1_ifg0_ifgb_rx_port_4_undersized_dropped_packets {
      type oc-yang:counter64;
      description
        "Counter for packets that were dropped because they were smaller than 64B.";
    }
    leaf counters_slice1_ifg0_ifgb_rx_port_5_oobe_crc_errors {
      type oc-yang:counter64;
      description
        "OOB Extract CRC error counter per port";
    }
    leaf counters_slice1_ifg0_ifgb_rx_port_5_undersized_dropped_packets {
      type oc-yang:counter64;
      description
        "Counter for packets that were dropped because they were smaller than 64B.";
    }
    leaf counters_slice1_ifg0_ifgb_rx_port_6_oobe_crc_errors {
      type oc-yang:counter64;
      description
        "OOB Extract CRC error counter per port";
    }
    leaf counters_slice1_ifg0_ifgb_rx_port_6_undersized_dropped_packets {
      type oc-yang:counter64;
      description
        "Counter for packets that were dropped because they were smaller than 64B.";
    }
    leaf counters_slice1_ifg0_ifgb_rx_port_7_oobe_crc_errors {
      type oc-yang:counter64;
      description
        "OOB Extract CRC error counter per port";
    }
    leaf counters_slice1_ifg0_ifgb_rx_port_7_undersized_dropped_packets {
      type oc-yang:counter64;
      description
        "Counter for packets that were dropped because they were smaller than 64B.";
    }
    leaf counters_slice1_ifg0_ifgb_rx_port_8_oobe_crc_errors {
      type oc-yang:counter64;
      description
        "OOB Extract CRC error counter per port";
    }
    leaf counters_slice1_ifg0_ifgb_rx_port_8_undersized_dropped_packets {
      type oc-yang:counter64;
      description
        "Counter for packets that were dropped because they were smaller than 64B.";
    }
    leaf counters_slice1_ifg0_ifgb_rx_port_9_oobe_crc_errors {
      type oc-yang:counter64;
      description
        "OOB Extract CRC error counter per port";
    }
    leaf counters_slice1_ifg0_ifgb_rx_port_9_undersized_dropped_packets {
      type oc-yang:counter64;
      description
        "Counter for packets that were dropped because they were smaller than 64B.";
    }
    leaf counters_slice1_ifg0_ifgb_rx_protection_dropped_fragments {
      type oc-yang:counter64;
      description
        "RXPP interface protection fragments drop counter.";
    }
    leaf counters_slice1_ifg0_ifgb_rx_protection_dropped_packets {
      type oc-yang:counter64;
      description
        "RXPP interface protection packet drop counter.";
    }
    leaf counters_slice1_ifg0_ifgbi_recycle_in_band_extract_npu_host_re_direct_drop {
      type oc-yang:counter64;
      description
        "InBand Extract NPU Host ReDirect drop counter. Increments based on the RcyDropCntrsCfg.";
    }
    leaf counters_slice1_ifg0_ifgbi_recycle_in_band_extract_packet_dma_re_direct_drop {
      type oc-yang:counter64;
      description
        "InBand Extract Pkt DMA ReDirect drop counter. Increments based on the RcyDropCntrsCfg.";
    }
    leaf counters_slice1_ifg0_npu_rxpp_fwd_post_npe_dropped_packets {
      type oc-yang:counter64;
      description
        "Counts packets dropped by the rxpp";
    }
    leaf counters_slice1_ifg0_npu_rxpp_fwd_post_npe_dropped_packets_due_destination {
      type oc-yang:counter64;
      description
        "nan";
    }
    leaf counters_slice1_ifg0_npu_rxpp_fwd_post_npe_dropped_packets_due_dummy {
      type oc-yang:counter64;
      description
        "nan";
    }
    leaf counters_slice1_ifg0_npu_rxpp_fwd_post_npe_dropped_packets_due_ecc {
      type oc-yang:counter64;
      description
        "nan";
    }
    leaf counters_slice1_ifg0_npu_rxpp_fwd_post_npe_dropped_packets_due_err_flag {
      type oc-yang:counter64;
      description
        "nan";
    }
    leaf counters_slice1_ifg0_npu_rxpp_fwd_post_npe_dropped_packets_due_frag_parity_error {
      type oc-yang:counter64;
      description
        "nan";
    }
    leaf counters_slice1_ifg0_npu_txpp_hw_editor_1_packets_with_error_bit {
      type oc-yang:counter64;
      description
        "Counts number of packet leaving HW Editor 1 inst 0 have error bit assered";
    }
    leaf counters_slice1_ifg0_npu_txpp_hw_editor_2_packets_with_error_bit {
      type oc-yang:counter64;
      description
        "Counts number of packet leaving HW Editor 2 towards ifg0 have error bit assered";
    }
    leaf counters_slice1_ifg0_npu_txpp_npe_packets_with_error_bit {
      type oc-yang:counter64;
      description
        "Counts number of packet leaving NPE 0 have error bit assered";
    }
    leaf counters_slice1_ifg0_npu_txpp_preprocess_packets_with_error_bit {
      type oc-yang:counter64;
      description
        "Counts number of packet leaving preprocessing 0 have error bit assered";
    }
    leaf counters_slice1_ifg1_ifgb_rx_cgm_0_csms_dropped_packets {
      type oc-yang:counter64;
      description
        "RX CSMS packets drop counter.";
    }
    leaf counters_slice1_ifg1_ifgb_rx_cgm_0_frm_dropped_packets {
      type oc-yang:counter64;
      description
        "RX FRM packets drop counter.";
    }
    leaf counters_slice1_ifg1_ifgb_rx_cgm_0_fte_dropped_packets {
      type oc-yang:counter64;
      description
        "RX FTE packets drop counter.";
    }
    leaf counters_slice1_ifg1_ifgb_rx_cgm_1_csms_dropped_packets {
      type oc-yang:counter64;
      description
        "RX CSMS packets drop counter.";
    }
    leaf counters_slice1_ifg1_ifgb_rx_cgm_1_frm_dropped_packets {
      type oc-yang:counter64;
      description
        "RX FRM packets drop counter.";
    }
    leaf counters_slice1_ifg1_ifgb_rx_cgm_1_fte_dropped_packets {
      type oc-yang:counter64;
      description
        "RX FTE packets drop counter.";
    }
    leaf counters_slice1_ifg1_ifgb_rx_cgm_2_csms_dropped_packets {
      type oc-yang:counter64;
      description
        "RX CSMS packets drop counter.";
    }
    leaf counters_slice1_ifg1_ifgb_rx_cgm_2_frm_dropped_packets {
      type oc-yang:counter64;
      description
        "RX FRM packets drop counter.";
    }
    leaf counters_slice1_ifg1_ifgb_rx_cgm_2_fte_dropped_packets {
      type oc-yang:counter64;
      description
        "RX FTE packets drop counter.";
    }
    leaf counters_slice1_ifg1_ifgb_rx_cgm_3_csms_dropped_packets {
      type oc-yang:counter64;
      description
        "RX CSMS packets drop counter.";
    }
    leaf counters_slice1_ifg1_ifgb_rx_cgm_3_frm_dropped_packets {
      type oc-yang:counter64;
      description
        "RX FRM packets drop counter.";
    }
    leaf counters_slice1_ifg1_ifgb_rx_cgm_3_fte_dropped_packets {
      type oc-yang:counter64;
      description
        "RX FTE packets drop counter.";
    }
    leaf counters_slice1_ifg1_ifgb_rx_port_0_oobe_crc_errors {
      type oc-yang:counter64;
      description
        "OOB Extract CRC error counter per port";
    }
    leaf counters_slice1_ifg1_ifgb_rx_port_0_undersized_dropped_packets {
      type oc-yang:counter64;
      description
        "Counter for packets that were dropped because they were smaller than 64B.";
    }
    leaf counters_slice1_ifg1_ifgb_rx_port_1_oobe_crc_errors {
      type oc-yang:counter64;
      description
        "OOB Extract CRC error counter per port";
    }
    leaf counters_slice1_ifg1_ifgb_rx_port_1_undersized_dropped_packets {
      type oc-yang:counter64;
      description
        "Counter for packets that were dropped because they were smaller than 64B.";
    }
    leaf counters_slice1_ifg1_ifgb_rx_port_10_oobe_crc_errors {
      type oc-yang:counter64;
      description
        "OOB Extract CRC error counter per port";
    }
    leaf counters_slice1_ifg1_ifgb_rx_port_10_undersized_dropped_packets {
      type oc-yang:counter64;
      description
        "Counter for packets that were dropped because they were smaller than 64B.";
    }
    leaf counters_slice1_ifg1_ifgb_rx_port_11_oobe_crc_errors {
      type oc-yang:counter64;
      description
        "OOB Extract CRC error counter per port";
    }
    leaf counters_slice1_ifg1_ifgb_rx_port_11_undersized_dropped_packets {
      type oc-yang:counter64;
      description
        "Counter for packets that were dropped because they were smaller than 64B.";
    }
    leaf counters_slice1_ifg1_ifgb_rx_port_12_oobe_crc_errors {
      type oc-yang:counter64;
      description
        "OOB Extract CRC error counter per port";
    }
    leaf counters_slice1_ifg1_ifgb_rx_port_12_undersized_dropped_packets {
      type oc-yang:counter64;
      description
        "Counter for packets that were dropped because they were smaller than 64B.";
    }
    leaf counters_slice1_ifg1_ifgb_rx_port_13_oobe_crc_errors {
      type oc-yang:counter64;
      description
        "OOB Extract CRC error counter per port";
    }
    leaf counters_slice1_ifg1_ifgb_rx_port_13_undersized_dropped_packets {
      type oc-yang:counter64;
      description
        "Counter for packets that were dropped because they were smaller than 64B.";
    }
    leaf counters_slice1_ifg1_ifgb_rx_port_14_oobe_crc_errors {
      type oc-yang:counter64;
      description
        "OOB Extract CRC error counter per port";
    }
    leaf counters_slice1_ifg1_ifgb_rx_port_14_undersized_dropped_packets {
      type oc-yang:counter64;
      description
        "Counter for packets that were dropped because they were smaller than 64B.";
    }
    leaf counters_slice1_ifg1_ifgb_rx_port_15_oobe_crc_errors {
      type oc-yang:counter64;
      description
        "OOB Extract CRC error counter per port";
    }
    leaf counters_slice1_ifg1_ifgb_rx_port_15_undersized_dropped_packets {
      type oc-yang:counter64;
      description
        "Counter for packets that were dropped because they were smaller than 64B.";
    }
    leaf counters_slice1_ifg1_ifgb_rx_port_16_undersized_dropped_packets {
      type oc-yang:counter64;
      description
        "Counter for packets that were dropped because they were smaller than 64B.";
    }
    leaf counters_slice1_ifg1_ifgb_rx_port_17_undersized_dropped_packets {
      type oc-yang:counter64;
      description
        "Counter for packets that were dropped because they were smaller than 64B.";
    }
    leaf counters_slice1_ifg1_ifgb_rx_port_18_undersized_dropped_packets {
      type oc-yang:counter64;
      description
        "Counter for packets that were dropped because they were smaller than 64B.";
    }
    leaf counters_slice1_ifg1_ifgb_rx_port_19_undersized_dropped_packets {
      type oc-yang:counter64;
      description
        "Counter for packets that were dropped because they were smaller than 64B.";
    }
    leaf counters_slice1_ifg1_ifgb_rx_port_2_oobe_crc_errors {
      type oc-yang:counter64;
      description
        "OOB Extract CRC error counter per port";
    }
    leaf counters_slice1_ifg1_ifgb_rx_port_2_undersized_dropped_packets {
      type oc-yang:counter64;
      description
        "Counter for packets that were dropped because they were smaller than 64B.";
    }
    leaf counters_slice1_ifg1_ifgb_rx_port_20_undersized_dropped_packets {
      type oc-yang:counter64;
      description
        "Counter for packets that were dropped because they were smaller than 64B.";
    }
    leaf counters_slice1_ifg1_ifgb_rx_port_21_undersized_dropped_packets {
      type oc-yang:counter64;
      description
        "Counter for packets that were dropped because they were smaller than 64B.";
    }
    leaf counters_slice1_ifg1_ifgb_rx_port_22_undersized_dropped_packets {
      type oc-yang:counter64;
      description
        "Counter for packets that were dropped because they were smaller than 64B.";
    }
    leaf counters_slice1_ifg1_ifgb_rx_port_23_undersized_dropped_packets {
      type oc-yang:counter64;
      description
        "Counter for packets that were dropped because they were smaller than 64B.";
    }
    leaf counters_slice1_ifg1_ifgb_rx_port_24_undersized_dropped_packets {
      type oc-yang:counter64;
      description
        "Counter for packets that were dropped because they were smaller than 64B.";
    }
    leaf counters_slice1_ifg1_ifgb_rx_port_25_undersized_dropped_packets {
      type oc-yang:counter64;
      description
        "Counter for packets that were dropped because they were smaller than 64B.";
    }
    leaf counters_slice1_ifg1_ifgb_rx_port_26_undersized_dropped_packets {
      type oc-yang:counter64;
      description
        "Counter for packets that were dropped because they were smaller than 64B.";
    }
    leaf counters_slice1_ifg1_ifgb_rx_port_27_undersized_dropped_packets {
      type oc-yang:counter64;
      description
        "Counter for packets that were dropped because they were smaller than 64B.";
    }
    leaf counters_slice1_ifg1_ifgb_rx_port_28_undersized_dropped_packets {
      type oc-yang:counter64;
      description
        "Counter for packets that were dropped because they were smaller than 64B.";
    }
    leaf counters_slice1_ifg1_ifgb_rx_port_29_undersized_dropped_packets {
      type oc-yang:counter64;
      description
        "Counter for packets that were dropped because they were smaller than 64B.";
    }
    leaf counters_slice1_ifg1_ifgb_rx_port_3_oobe_crc_errors {
      type oc-yang:counter64;
      description
        "OOB Extract CRC error counter per port";
    }
    leaf counters_slice1_ifg1_ifgb_rx_port_3_undersized_dropped_packets {
      type oc-yang:counter64;
      description
        "Counter for packets that were dropped because they were smaller than 64B.";
    }
    leaf counters_slice1_ifg1_ifgb_rx_port_30_undersized_dropped_packets {
      type oc-yang:counter64;
      description
        "Counter for packets that were dropped because they were smaller than 64B.";
    }
    leaf counters_slice1_ifg1_ifgb_rx_port_31_undersized_dropped_packets {
      type oc-yang:counter64;
      description
        "Counter for packets that were dropped because they were smaller than 64B.";
    }
    leaf counters_slice1_ifg1_ifgb_rx_port_4_oobe_crc_errors {
      type oc-yang:counter64;
      description
        "OOB Extract CRC error counter per port";
    }
    leaf counters_slice1_ifg1_ifgb_rx_port_4_undersized_dropped_packets {
      type oc-yang:counter64;
      description
        "Counter for packets that were dropped because they were smaller than 64B.";
    }
    leaf counters_slice1_ifg1_ifgb_rx_port_5_oobe_crc_errors {
      type oc-yang:counter64;
      description
        "OOB Extract CRC error counter per port";
    }
    leaf counters_slice1_ifg1_ifgb_rx_port_5_undersized_dropped_packets {
      type oc-yang:counter64;
      description
        "Counter for packets that were dropped because they were smaller than 64B.";
    }
    leaf counters_slice1_ifg1_ifgb_rx_port_6_oobe_crc_errors {
      type oc-yang:counter64;
      description
        "OOB Extract CRC error counter per port";
    }
    leaf counters_slice1_ifg1_ifgb_rx_port_6_undersized_dropped_packets {
      type oc-yang:counter64;
      description
        "Counter for packets that were dropped because they were smaller than 64B.";
    }
    leaf counters_slice1_ifg1_ifgb_rx_port_7_oobe_crc_errors {
      type oc-yang:counter64;
      description
        "OOB Extract CRC error counter per port";
    }
    leaf counters_slice1_ifg1_ifgb_rx_port_7_undersized_dropped_packets {
      type oc-yang:counter64;
      description
        "Counter for packets that were dropped because they were smaller than 64B.";
    }
    leaf counters_slice1_ifg1_ifgb_rx_port_8_oobe_crc_errors {
      type oc-yang:counter64;
      description
        "OOB Extract CRC error counter per port";
    }
    leaf counters_slice1_ifg1_ifgb_rx_port_8_undersized_dropped_packets {
      type oc-yang:counter64;
      description
        "Counter for packets that were dropped because they were smaller than 64B.";
    }
    leaf counters_slice1_ifg1_ifgb_rx_port_9_oobe_crc_errors {
      type oc-yang:counter64;
      description
        "OOB Extract CRC error counter per port";
    }
    leaf counters_slice1_ifg1_ifgb_rx_port_9_undersized_dropped_packets {
      type oc-yang:counter64;
      description
        "Counter for packets that were dropped because they were smaller than 64B.";
    }
    leaf counters_slice1_ifg1_ifgb_rx_protection_dropped_fragments {
      type oc-yang:counter64;
      description
        "RXPP interface protection fragments drop counter.";
    }
    leaf counters_slice1_ifg1_ifgb_rx_protection_dropped_packets {
      type oc-yang:counter64;
      description
        "RXPP interface protection packet drop counter.";
    }
    leaf counters_slice1_ifg1_ifgbi_recycle_in_band_extract_npu_host_re_direct_drop {
      type oc-yang:counter64;
      description
        "InBand Extract NPU Host ReDirect drop counter. Increments based on the RcyDropCntrsCfg.";
    }
    leaf counters_slice1_ifg1_ifgbi_recycle_in_band_extract_packet_dma_re_direct_drop {
      type oc-yang:counter64;
      description
        "InBand Extract Pkt DMA ReDirect drop counter. Increments based on the RcyDropCntrsCfg.";
    }
    leaf counters_slice1_ifg1_npu_rxpp_fwd_post_npe_dropped_packets {
      type oc-yang:counter64;
      description
        "Counts packets dropped by the rxpp";
    }
    leaf counters_slice1_ifg1_npu_rxpp_fwd_post_npe_dropped_packets_due_destination {
      type oc-yang:counter64;
      description
        "nan";
    }
    leaf counters_slice1_ifg1_npu_rxpp_fwd_post_npe_dropped_packets_due_dummy {
      type oc-yang:counter64;
      description
        "nan";
    }
    leaf counters_slice1_ifg1_npu_rxpp_fwd_post_npe_dropped_packets_due_ecc {
      type oc-yang:counter64;
      description
        "nan";
    }
    leaf counters_slice1_ifg1_npu_rxpp_fwd_post_npe_dropped_packets_due_err_flag {
      type oc-yang:counter64;
      description
        "nan";
    }
    leaf counters_slice1_ifg1_npu_rxpp_fwd_post_npe_dropped_packets_due_frag_parity_error {
      type oc-yang:counter64;
      description
        "nan";
    }
    leaf counters_slice1_ifg1_npu_txpp_hw_editor_1_packets_with_error_bit {
      type oc-yang:counter64;
      description
        "Counts number of packet leaving HW Editor 1 inst 1 have error bit assered";
    }
    leaf counters_slice1_ifg1_npu_txpp_hw_editor_2_packets_with_error_bit {
      type oc-yang:counter64;
      description
        "Counts number of packet leaving HW Editor 2 towards ifg1 have error bit assered";
    }
    leaf counters_slice1_ifg1_npu_txpp_npe_packets_with_error_bit {
      type oc-yang:counter64;
      description
        "Counts number of packet leaving NPE 1 have error bit assered";
    }
    leaf counters_slice1_ifg1_npu_txpp_preprocess_packets_with_error_bit {
      type oc-yang:counter64;
      description
        "Counts number of packet leaving preprocessing 1 have error bit assered";
    }
    leaf counters_slice2_cluster0_ene_outgoing_headers_with_errors {
      type oc-yang:counter64;
      description
        "Number of headers Exiting the ENE with Error bit on";
    }
    leaf counters_slice2_cluster1_ene_outgoing_headers_with_errors {
      type oc-yang:counter64;
      description
        "Number of headers Exiting the ENE with Error bit on";
    }
    leaf counters_slice2_fllb_debug_register_dropped_p_ds {
      type oc-yang:counter64;
      description
        "Number of PDs dropped due to no eligible links";
    }
    leaf counters_slice2_ifg0_ifgb_rx_cgm_0_csms_dropped_packets {
      type oc-yang:counter64;
      description
        "RX CSMS packets drop counter.";
    }
    leaf counters_slice2_ifg0_ifgb_rx_cgm_0_frm_dropped_packets {
      type oc-yang:counter64;
      description
        "RX FRM packets drop counter.";
    }
    leaf counters_slice2_ifg0_ifgb_rx_cgm_0_fte_dropped_packets {
      type oc-yang:counter64;
      description
        "RX FTE packets drop counter.";
    }
    leaf counters_slice2_ifg0_ifgb_rx_cgm_1_csms_dropped_packets {
      type oc-yang:counter64;
      description
        "RX CSMS packets drop counter.";
    }
    leaf counters_slice2_ifg0_ifgb_rx_cgm_1_frm_dropped_packets {
      type oc-yang:counter64;
      description
        "RX FRM packets drop counter.";
    }
    leaf counters_slice2_ifg0_ifgb_rx_cgm_1_fte_dropped_packets {
      type oc-yang:counter64;
      description
        "RX FTE packets drop counter.";
    }
    leaf counters_slice2_ifg0_ifgb_rx_cgm_2_csms_dropped_packets {
      type oc-yang:counter64;
      description
        "RX CSMS packets drop counter.";
    }
    leaf counters_slice2_ifg0_ifgb_rx_cgm_2_frm_dropped_packets {
      type oc-yang:counter64;
      description
        "RX FRM packets drop counter.";
    }
    leaf counters_slice2_ifg0_ifgb_rx_cgm_2_fte_dropped_packets {
      type oc-yang:counter64;
      description
        "RX FTE packets drop counter.";
    }
    leaf counters_slice2_ifg0_ifgb_rx_cgm_3_csms_dropped_packets {
      type oc-yang:counter64;
      description
        "RX CSMS packets drop counter.";
    }
    leaf counters_slice2_ifg0_ifgb_rx_cgm_3_frm_dropped_packets {
      type oc-yang:counter64;
      description
        "RX FRM packets drop counter.";
    }
    leaf counters_slice2_ifg0_ifgb_rx_cgm_3_fte_dropped_packets {
      type oc-yang:counter64;
      description
        "RX FTE packets drop counter.";
    }
    leaf counters_slice2_ifg0_ifgb_rx_port_0_oobe_crc_errors {
      type oc-yang:counter64;
      description
        "OOB Extract CRC error counter per port";
    }
    leaf counters_slice2_ifg0_ifgb_rx_port_0_undersized_dropped_packets {
      type oc-yang:counter64;
      description
        "Counter for packets that were dropped because they were smaller than 64B.";
    }
    leaf counters_slice2_ifg0_ifgb_rx_port_1_oobe_crc_errors {
      type oc-yang:counter64;
      description
        "OOB Extract CRC error counter per port";
    }
    leaf counters_slice2_ifg0_ifgb_rx_port_1_undersized_dropped_packets {
      type oc-yang:counter64;
      description
        "Counter for packets that were dropped because they were smaller than 64B.";
    }
    leaf counters_slice2_ifg0_ifgb_rx_port_10_oobe_crc_errors {
      type oc-yang:counter64;
      description
        "OOB Extract CRC error counter per port";
    }
    leaf counters_slice2_ifg0_ifgb_rx_port_10_undersized_dropped_packets {
      type oc-yang:counter64;
      description
        "Counter for packets that were dropped because they were smaller than 64B.";
    }
    leaf counters_slice2_ifg0_ifgb_rx_port_11_oobe_crc_errors {
      type oc-yang:counter64;
      description
        "OOB Extract CRC error counter per port";
    }
    leaf counters_slice2_ifg0_ifgb_rx_port_11_undersized_dropped_packets {
      type oc-yang:counter64;
      description
        "Counter for packets that were dropped because they were smaller than 64B.";
    }
    leaf counters_slice2_ifg0_ifgb_rx_port_12_oobe_crc_errors {
      type oc-yang:counter64;
      description
        "OOB Extract CRC error counter per port";
    }
    leaf counters_slice2_ifg0_ifgb_rx_port_12_undersized_dropped_packets {
      type oc-yang:counter64;
      description
        "Counter for packets that were dropped because they were smaller than 64B.";
    }
    leaf counters_slice2_ifg0_ifgb_rx_port_13_oobe_crc_errors {
      type oc-yang:counter64;
      description
        "OOB Extract CRC error counter per port";
    }
    leaf counters_slice2_ifg0_ifgb_rx_port_13_undersized_dropped_packets {
      type oc-yang:counter64;
      description
        "Counter for packets that were dropped because they were smaller than 64B.";
    }
    leaf counters_slice2_ifg0_ifgb_rx_port_14_oobe_crc_errors {
      type oc-yang:counter64;
      description
        "OOB Extract CRC error counter per port";
    }
    leaf counters_slice2_ifg0_ifgb_rx_port_14_undersized_dropped_packets {
      type oc-yang:counter64;
      description
        "Counter for packets that were dropped because they were smaller than 64B.";
    }
    leaf counters_slice2_ifg0_ifgb_rx_port_15_oobe_crc_errors {
      type oc-yang:counter64;
      description
        "OOB Extract CRC error counter per port";
    }
    leaf counters_slice2_ifg0_ifgb_rx_port_15_undersized_dropped_packets {
      type oc-yang:counter64;
      description
        "Counter for packets that were dropped because they were smaller than 64B.";
    }
    leaf counters_slice2_ifg0_ifgb_rx_port_16_undersized_dropped_packets {
      type oc-yang:counter64;
      description
        "Counter for packets that were dropped because they were smaller than 64B.";
    }
    leaf counters_slice2_ifg0_ifgb_rx_port_17_undersized_dropped_packets {
      type oc-yang:counter64;
      description
        "Counter for packets that were dropped because they were smaller than 64B.";
    }
    leaf counters_slice2_ifg0_ifgb_rx_port_18_undersized_dropped_packets {
      type oc-yang:counter64;
      description
        "Counter for packets that were dropped because they were smaller than 64B.";
    }
    leaf counters_slice2_ifg0_ifgb_rx_port_19_undersized_dropped_packets {
      type oc-yang:counter64;
      description
        "Counter for packets that were dropped because they were smaller than 64B.";
    }
    leaf counters_slice2_ifg0_ifgb_rx_port_2_oobe_crc_errors {
      type oc-yang:counter64;
      description
        "OOB Extract CRC error counter per port";
    }
    leaf counters_slice2_ifg0_ifgb_rx_port_2_undersized_dropped_packets {
      type oc-yang:counter64;
      description
        "Counter for packets that were dropped because they were smaller than 64B.";
    }
    leaf counters_slice2_ifg0_ifgb_rx_port_20_undersized_dropped_packets {
      type oc-yang:counter64;
      description
        "Counter for packets that were dropped because they were smaller than 64B.";
    }
    leaf counters_slice2_ifg0_ifgb_rx_port_21_undersized_dropped_packets {
      type oc-yang:counter64;
      description
        "Counter for packets that were dropped because they were smaller than 64B.";
    }
    leaf counters_slice2_ifg0_ifgb_rx_port_22_undersized_dropped_packets {
      type oc-yang:counter64;
      description
        "Counter for packets that were dropped because they were smaller than 64B.";
    }
    leaf counters_slice2_ifg0_ifgb_rx_port_23_undersized_dropped_packets {
      type oc-yang:counter64;
      description
        "Counter for packets that were dropped because they were smaller than 64B.";
    }
    leaf counters_slice2_ifg0_ifgb_rx_port_24_undersized_dropped_packets {
      type oc-yang:counter64;
      description
        "Counter for packets that were dropped because they were smaller than 64B.";
    }
    leaf counters_slice2_ifg0_ifgb_rx_port_25_undersized_dropped_packets {
      type oc-yang:counter64;
      description
        "Counter for packets that were dropped because they were smaller than 64B.";
    }
    leaf counters_slice2_ifg0_ifgb_rx_port_26_undersized_dropped_packets {
      type oc-yang:counter64;
      description
        "Counter for packets that were dropped because they were smaller than 64B.";
    }
    leaf counters_slice2_ifg0_ifgb_rx_port_27_undersized_dropped_packets {
      type oc-yang:counter64;
      description
        "Counter for packets that were dropped because they were smaller than 64B.";
    }
    leaf counters_slice2_ifg0_ifgb_rx_port_28_undersized_dropped_packets {
      type oc-yang:counter64;
      description
        "Counter for packets that were dropped because they were smaller than 64B.";
    }
    leaf counters_slice2_ifg0_ifgb_rx_port_29_undersized_dropped_packets {
      type oc-yang:counter64;
      description
        "Counter for packets that were dropped because they were smaller than 64B.";
    }
    leaf counters_slice2_ifg0_ifgb_rx_port_3_oobe_crc_errors {
      type oc-yang:counter64;
      description
        "OOB Extract CRC error counter per port";
    }
    leaf counters_slice2_ifg0_ifgb_rx_port_3_undersized_dropped_packets {
      type oc-yang:counter64;
      description
        "Counter for packets that were dropped because they were smaller than 64B.";
    }
    leaf counters_slice2_ifg0_ifgb_rx_port_30_undersized_dropped_packets {
      type oc-yang:counter64;
      description
        "Counter for packets that were dropped because they were smaller than 64B.";
    }
    leaf counters_slice2_ifg0_ifgb_rx_port_31_undersized_dropped_packets {
      type oc-yang:counter64;
      description
        "Counter for packets that were dropped because they were smaller than 64B.";
    }
    leaf counters_slice2_ifg0_ifgb_rx_port_4_oobe_crc_errors {
      type oc-yang:counter64;
      description
        "OOB Extract CRC error counter per port";
    }
    leaf counters_slice2_ifg0_ifgb_rx_port_4_undersized_dropped_packets {
      type oc-yang:counter64;
      description
        "Counter for packets that were dropped because they were smaller than 64B.";
    }
    leaf counters_slice2_ifg0_ifgb_rx_port_5_oobe_crc_errors {
      type oc-yang:counter64;
      description
        "OOB Extract CRC error counter per port";
    }
    leaf counters_slice2_ifg0_ifgb_rx_port_5_undersized_dropped_packets {
      type oc-yang:counter64;
      description
        "Counter for packets that were dropped because they were smaller than 64B.";
    }
    leaf counters_slice2_ifg0_ifgb_rx_port_6_oobe_crc_errors {
      type oc-yang:counter64;
      description
        "OOB Extract CRC error counter per port";
    }
    leaf counters_slice2_ifg0_ifgb_rx_port_6_undersized_dropped_packets {
      type oc-yang:counter64;
      description
        "Counter for packets that were dropped because they were smaller than 64B.";
    }
    leaf counters_slice2_ifg0_ifgb_rx_port_7_oobe_crc_errors {
      type oc-yang:counter64;
      description
        "OOB Extract CRC error counter per port";
    }
    leaf counters_slice2_ifg0_ifgb_rx_port_7_undersized_dropped_packets {
      type oc-yang:counter64;
      description
        "Counter for packets that were dropped because they were smaller than 64B.";
    }
    leaf counters_slice2_ifg0_ifgb_rx_port_8_oobe_crc_errors {
      type oc-yang:counter64;
      description
        "OOB Extract CRC error counter per port";
    }
    leaf counters_slice2_ifg0_ifgb_rx_port_8_undersized_dropped_packets {
      type oc-yang:counter64;
      description
        "Counter for packets that were dropped because they were smaller than 64B.";
    }
    leaf counters_slice2_ifg0_ifgb_rx_port_9_oobe_crc_errors {
      type oc-yang:counter64;
      description
        "OOB Extract CRC error counter per port";
    }
    leaf counters_slice2_ifg0_ifgb_rx_port_9_undersized_dropped_packets {
      type oc-yang:counter64;
      description
        "Counter for packets that were dropped because they were smaller than 64B.";
    }
    leaf counters_slice2_ifg0_ifgb_rx_protection_dropped_fragments {
      type oc-yang:counter64;
      description
        "RXPP interface protection fragments drop counter.";
    }
    leaf counters_slice2_ifg0_ifgb_rx_protection_dropped_packets {
      type oc-yang:counter64;
      description
        "RXPP interface protection packet drop counter.";
    }
    leaf counters_slice2_ifg0_ifgbi_recycle_in_band_extract_npu_host_re_direct_drop {
      type oc-yang:counter64;
      description
        "InBand Extract NPU Host ReDirect drop counter. Increments based on the RcyDropCntrsCfg.";
    }
    leaf counters_slice2_ifg0_ifgbi_recycle_in_band_extract_packet_dma_re_direct_drop {
      type oc-yang:counter64;
      description
        "InBand Extract Pkt DMA ReDirect drop counter. Increments based on the RcyDropCntrsCfg.";
    }
    leaf counters_slice2_ifg0_npu_rxpp_fwd_post_npe_dropped_packets {
      type oc-yang:counter64;
      description
        "Counts packets dropped by the rxpp";
    }
    leaf counters_slice2_ifg0_npu_rxpp_fwd_post_npe_dropped_packets_due_destination {
      type oc-yang:counter64;
      description
        "nan";
    }
    leaf counters_slice2_ifg0_npu_rxpp_fwd_post_npe_dropped_packets_due_dummy {
      type oc-yang:counter64;
      description
        "nan";
    }
    leaf counters_slice2_ifg0_npu_rxpp_fwd_post_npe_dropped_packets_due_ecc {
      type oc-yang:counter64;
      description
        "nan";
    }
    leaf counters_slice2_ifg0_npu_rxpp_fwd_post_npe_dropped_packets_due_err_flag {
      type oc-yang:counter64;
      description
        "nan";
    }
    leaf counters_slice2_ifg0_npu_rxpp_fwd_post_npe_dropped_packets_due_frag_parity_error {
      type oc-yang:counter64;
      description
        "nan";
    }
    leaf counters_slice2_ifg0_npu_txpp_hw_editor_1_packets_with_error_bit {
      type oc-yang:counter64;
      description
        "Counts number of packet leaving HW Editor 1 inst 0 have error bit assered";
    }
    leaf counters_slice2_ifg0_npu_txpp_hw_editor_2_packets_with_error_bit {
      type oc-yang:counter64;
      description
        "Counts number of packet leaving HW Editor 2 towards ifg0 have error bit assered";
    }
    leaf counters_slice2_ifg0_npu_txpp_npe_packets_with_error_bit {
      type oc-yang:counter64;
      description
        "Counts number of packet leaving NPE 0 have error bit assered";
    }
    leaf counters_slice2_ifg0_npu_txpp_preprocess_packets_with_error_bit {
      type oc-yang:counter64;
      description
        "Counts number of packet leaving preprocessing 0 have error bit assered";
    }
    leaf counters_slice2_ifg1_ifgb_rx_cgm_0_csms_dropped_packets {
      type oc-yang:counter64;
      description
        "RX CSMS packets drop counter.";
    }
    leaf counters_slice2_ifg1_ifgb_rx_cgm_0_frm_dropped_packets {
      type oc-yang:counter64;
      description
        "RX FRM packets drop counter.";
    }
    leaf counters_slice2_ifg1_ifgb_rx_cgm_0_fte_dropped_packets {
      type oc-yang:counter64;
      description
        "RX FTE packets drop counter.";
    }
    leaf counters_slice2_ifg1_ifgb_rx_cgm_1_csms_dropped_packets {
      type oc-yang:counter64;
      description
        "RX CSMS packets drop counter.";
    }
    leaf counters_slice2_ifg1_ifgb_rx_cgm_1_frm_dropped_packets {
      type oc-yang:counter64;
      description
        "RX FRM packets drop counter.";
    }
    leaf counters_slice2_ifg1_ifgb_rx_cgm_1_fte_dropped_packets {
      type oc-yang:counter64;
      description
        "RX FTE packets drop counter.";
    }
    leaf counters_slice2_ifg1_ifgb_rx_cgm_2_csms_dropped_packets {
      type oc-yang:counter64;
      description
        "RX CSMS packets drop counter.";
    }
    leaf counters_slice2_ifg1_ifgb_rx_cgm_2_frm_dropped_packets {
      type oc-yang:counter64;
      description
        "RX FRM packets drop counter.";
    }
    leaf counters_slice2_ifg1_ifgb_rx_cgm_2_fte_dropped_packets {
      type oc-yang:counter64;
      description
        "RX FTE packets drop counter.";
    }
    leaf counters_slice2_ifg1_ifgb_rx_cgm_3_csms_dropped_packets {
      type oc-yang:counter64;
      description
        "RX CSMS packets drop counter.";
    }
    leaf counters_slice2_ifg1_ifgb_rx_cgm_3_frm_dropped_packets {
      type oc-yang:counter64;
      description
        "RX FRM packets drop counter.";
    }
    leaf counters_slice2_ifg1_ifgb_rx_cgm_3_fte_dropped_packets {
      type oc-yang:counter64;
      description
        "RX FTE packets drop counter.";
    }
    leaf counters_slice2_ifg1_ifgb_rx_port_0_oobe_crc_errors {
      type oc-yang:counter64;
      description
        "OOB Extract CRC error counter per port";
    }
    leaf counters_slice2_ifg1_ifgb_rx_port_0_undersized_dropped_packets {
      type oc-yang:counter64;
      description
        "Counter for packets that were dropped because they were smaller than 64B.";
    }
    leaf counters_slice2_ifg1_ifgb_rx_port_1_oobe_crc_errors {
      type oc-yang:counter64;
      description
        "OOB Extract CRC error counter per port";
    }
    leaf counters_slice2_ifg1_ifgb_rx_port_1_undersized_dropped_packets {
      type oc-yang:counter64;
      description
        "Counter for packets that were dropped because they were smaller than 64B.";
    }
    leaf counters_slice2_ifg1_ifgb_rx_port_10_oobe_crc_errors {
      type oc-yang:counter64;
      description
        "OOB Extract CRC error counter per port";
    }
    leaf counters_slice2_ifg1_ifgb_rx_port_10_undersized_dropped_packets {
      type oc-yang:counter64;
      description
        "Counter for packets that were dropped because they were smaller than 64B.";
    }
    leaf counters_slice2_ifg1_ifgb_rx_port_11_oobe_crc_errors {
      type oc-yang:counter64;
      description
        "OOB Extract CRC error counter per port";
    }
    leaf counters_slice2_ifg1_ifgb_rx_port_11_undersized_dropped_packets {
      type oc-yang:counter64;
      description
        "Counter for packets that were dropped because they were smaller than 64B.";
    }
    leaf counters_slice2_ifg1_ifgb_rx_port_12_oobe_crc_errors {
      type oc-yang:counter64;
      description
        "OOB Extract CRC error counter per port";
    }
    leaf counters_slice2_ifg1_ifgb_rx_port_12_undersized_dropped_packets {
      type oc-yang:counter64;
      description
        "Counter for packets that were dropped because they were smaller than 64B.";
    }
    leaf counters_slice2_ifg1_ifgb_rx_port_13_oobe_crc_errors {
      type oc-yang:counter64;
      description
        "OOB Extract CRC error counter per port";
    }
    leaf counters_slice2_ifg1_ifgb_rx_port_13_undersized_dropped_packets {
      type oc-yang:counter64;
      description
        "Counter for packets that were dropped because they were smaller than 64B.";
    }
    leaf counters_slice2_ifg1_ifgb_rx_port_14_oobe_crc_errors {
      type oc-yang:counter64;
      description
        "OOB Extract CRC error counter per port";
    }
    leaf counters_slice2_ifg1_ifgb_rx_port_14_undersized_dropped_packets {
      type oc-yang:counter64;
      description
        "Counter for packets that were dropped because they were smaller than 64B.";
    }
    leaf counters_slice2_ifg1_ifgb_rx_port_15_oobe_crc_errors {
      type oc-yang:counter64;
      description
        "OOB Extract CRC error counter per port";
    }
    leaf counters_slice2_ifg1_ifgb_rx_port_15_undersized_dropped_packets {
      type oc-yang:counter64;
      description
        "Counter for packets that were dropped because they were smaller than 64B.";
    }
    leaf counters_slice2_ifg1_ifgb_rx_port_16_undersized_dropped_packets {
      type oc-yang:counter64;
      description
        "Counter for packets that were dropped because they were smaller than 64B.";
    }
    leaf counters_slice2_ifg1_ifgb_rx_port_17_undersized_dropped_packets {
      type oc-yang:counter64;
      description
        "Counter for packets that were dropped because they were smaller than 64B.";
    }
    leaf counters_slice2_ifg1_ifgb_rx_port_18_undersized_dropped_packets {
      type oc-yang:counter64;
      description
        "Counter for packets that were dropped because they were smaller than 64B.";
    }
    leaf counters_slice2_ifg1_ifgb_rx_port_19_undersized_dropped_packets {
      type oc-yang:counter64;
      description
        "Counter for packets that were dropped because they were smaller than 64B.";
    }
    leaf counters_slice2_ifg1_ifgb_rx_port_2_oobe_crc_errors {
      type oc-yang:counter64;
      description
        "OOB Extract CRC error counter per port";
    }
    leaf counters_slice2_ifg1_ifgb_rx_port_2_undersized_dropped_packets {
      type oc-yang:counter64;
      description
        "Counter for packets that were dropped because they were smaller than 64B.";
    }
    leaf counters_slice2_ifg1_ifgb_rx_port_20_undersized_dropped_packets {
      type oc-yang:counter64;
      description
        "Counter for packets that were dropped because they were smaller than 64B.";
    }
    leaf counters_slice2_ifg1_ifgb_rx_port_21_undersized_dropped_packets {
      type oc-yang:counter64;
      description
        "Counter for packets that were dropped because they were smaller than 64B.";
    }
    leaf counters_slice2_ifg1_ifgb_rx_port_22_undersized_dropped_packets {
      type oc-yang:counter64;
      description
        "Counter for packets that were dropped because they were smaller than 64B.";
    }
    leaf counters_slice2_ifg1_ifgb_rx_port_23_undersized_dropped_packets {
      type oc-yang:counter64;
      description
        "Counter for packets that were dropped because they were smaller than 64B.";
    }
    leaf counters_slice2_ifg1_ifgb_rx_port_24_undersized_dropped_packets {
      type oc-yang:counter64;
      description
        "Counter for packets that were dropped because they were smaller than 64B.";
    }
    leaf counters_slice2_ifg1_ifgb_rx_port_25_undersized_dropped_packets {
      type oc-yang:counter64;
      description
        "Counter for packets that were dropped because they were smaller than 64B.";
    }
    leaf counters_slice2_ifg1_ifgb_rx_port_26_undersized_dropped_packets {
      type oc-yang:counter64;
      description
        "Counter for packets that were dropped because they were smaller than 64B.";
    }
    leaf counters_slice2_ifg1_ifgb_rx_port_27_undersized_dropped_packets {
      type oc-yang:counter64;
      description
        "Counter for packets that were dropped because they were smaller than 64B.";
    }
    leaf counters_slice2_ifg1_ifgb_rx_port_28_undersized_dropped_packets {
      type oc-yang:counter64;
      description
        "Counter for packets that were dropped because they were smaller than 64B.";
    }
    leaf counters_slice2_ifg1_ifgb_rx_port_29_undersized_dropped_packets {
      type oc-yang:counter64;
      description
        "Counter for packets that were dropped because they were smaller than 64B.";
    }
    leaf counters_slice2_ifg1_ifgb_rx_port_3_oobe_crc_errors {
      type oc-yang:counter64;
      description
        "OOB Extract CRC error counter per port";
    }
    leaf counters_slice2_ifg1_ifgb_rx_port_3_undersized_dropped_packets {
      type oc-yang:counter64;
      description
        "Counter for packets that were dropped because they were smaller than 64B.";
    }
    leaf counters_slice2_ifg1_ifgb_rx_port_30_undersized_dropped_packets {
      type oc-yang:counter64;
      description
        "Counter for packets that were dropped because they were smaller than 64B.";
    }
    leaf counters_slice2_ifg1_ifgb_rx_port_31_undersized_dropped_packets {
      type oc-yang:counter64;
      description
        "Counter for packets that were dropped because they were smaller than 64B.";
    }
    leaf counters_slice2_ifg1_ifgb_rx_port_4_oobe_crc_errors {
      type oc-yang:counter64;
      description
        "OOB Extract CRC error counter per port";
    }
    leaf counters_slice2_ifg1_ifgb_rx_port_4_undersized_dropped_packets {
      type oc-yang:counter64;
      description
        "Counter for packets that were dropped because they were smaller than 64B.";
    }
    leaf counters_slice2_ifg1_ifgb_rx_port_5_oobe_crc_errors {
      type oc-yang:counter64;
      description
        "OOB Extract CRC error counter per port";
    }
    leaf counters_slice2_ifg1_ifgb_rx_port_5_undersized_dropped_packets {
      type oc-yang:counter64;
      description
        "Counter for packets that were dropped because they were smaller than 64B.";
    }
    leaf counters_slice2_ifg1_ifgb_rx_port_6_oobe_crc_errors {
      type oc-yang:counter64;
      description
        "OOB Extract CRC error counter per port";
    }
    leaf counters_slice2_ifg1_ifgb_rx_port_6_undersized_dropped_packets {
      type oc-yang:counter64;
      description
        "Counter for packets that were dropped because they were smaller than 64B.";
    }
    leaf counters_slice2_ifg1_ifgb_rx_port_7_oobe_crc_errors {
      type oc-yang:counter64;
      description
        "OOB Extract CRC error counter per port";
    }
    leaf counters_slice2_ifg1_ifgb_rx_port_7_undersized_dropped_packets {
      type oc-yang:counter64;
      description
        "Counter for packets that were dropped because they were smaller than 64B.";
    }
    leaf counters_slice2_ifg1_ifgb_rx_port_8_oobe_crc_errors {
      type oc-yang:counter64;
      description
        "OOB Extract CRC error counter per port";
    }
    leaf counters_slice2_ifg1_ifgb_rx_port_8_undersized_dropped_packets {
      type oc-yang:counter64;
      description
        "Counter for packets that were dropped because they were smaller than 64B.";
    }
    leaf counters_slice2_ifg1_ifgb_rx_port_9_oobe_crc_errors {
      type oc-yang:counter64;
      description
        "OOB Extract CRC error counter per port";
    }
    leaf counters_slice2_ifg1_ifgb_rx_port_9_undersized_dropped_packets {
      type oc-yang:counter64;
      description
        "Counter for packets that were dropped because they were smaller than 64B.";
    }
    leaf counters_slice2_ifg1_ifgb_rx_protection_dropped_fragments {
      type oc-yang:counter64;
      description
        "RXPP interface protection fragments drop counter.";
    }
    leaf counters_slice2_ifg1_ifgb_rx_protection_dropped_packets {
      type oc-yang:counter64;
      description
        "RXPP interface protection packet drop counter.";
    }
    leaf counters_slice2_ifg1_ifgbi_recycle_in_band_extract_npu_host_re_direct_drop {
      type oc-yang:counter64;
      description
        "InBand Extract NPU Host ReDirect drop counter. Increments based on the RcyDropCntrsCfg.";
    }
    leaf counters_slice2_ifg1_ifgbi_recycle_in_band_extract_packet_dma_re_direct_drop {
      type oc-yang:counter64;
      description
        "InBand Extract Pkt DMA ReDirect drop counter. Increments based on the RcyDropCntrsCfg.";
    }
    leaf counters_slice2_ifg1_npu_rxpp_fwd_post_npe_dropped_packets {
      type oc-yang:counter64;
      description
        "Counts packets dropped by the rxpp";
    }
    leaf counters_slice2_ifg1_npu_rxpp_fwd_post_npe_dropped_packets_due_destination {
      type oc-yang:counter64;
      description
        "nan";
    }
    leaf counters_slice2_ifg1_npu_rxpp_fwd_post_npe_dropped_packets_due_dummy {
      type oc-yang:counter64;
      description
        "nan";
    }
    leaf counters_slice2_ifg1_npu_rxpp_fwd_post_npe_dropped_packets_due_ecc {
      type oc-yang:counter64;
      description
        "nan";
    }
    leaf counters_slice2_ifg1_npu_rxpp_fwd_post_npe_dropped_packets_due_err_flag {
      type oc-yang:counter64;
      description
        "nan";
    }
    leaf counters_slice2_ifg1_npu_rxpp_fwd_post_npe_dropped_packets_due_frag_parity_error {
      type oc-yang:counter64;
      description
        "nan";
    }
    leaf counters_slice2_ifg1_npu_txpp_hw_editor_1_packets_with_error_bit {
      type oc-yang:counter64;
      description
        "Counts number of packet leaving HW Editor 1 inst 1 have error bit assered";
    }
    leaf counters_slice2_ifg1_npu_txpp_hw_editor_2_packets_with_error_bit {
      type oc-yang:counter64;
      description
        "Counts number of packet leaving HW Editor 2 towards ifg1 have error bit assered";
    }
    leaf counters_slice2_ifg1_npu_txpp_npe_packets_with_error_bit {
      type oc-yang:counter64;
      description
        "Counts number of packet leaving NPE 1 have error bit assered";
    }
    leaf counters_slice2_ifg1_npu_txpp_preprocess_packets_with_error_bit {
      type oc-yang:counter64;
      description
        "Counts number of packet leaving preprocessing 1 have error bit assered";
    }
    leaf counters_slice3_cluster0_ene_outgoing_headers_with_errors {
      type oc-yang:counter64;
      description
        "Number of headers Exiting the ENE with Error bit on";
    }
    leaf counters_slice3_cluster1_ene_outgoing_headers_with_errors {
      type oc-yang:counter64;
      description
        "Number of headers Exiting the ENE with Error bit on";
    }
    leaf counters_slice3_fllb_debug_register_dropped_p_ds {
      type oc-yang:counter64;
      description
        "Number of PDs dropped due to no eligible links";
    }
    leaf counters_slice3_ifg0_ifgb_rx_cgm_0_csms_dropped_packets {
      type oc-yang:counter64;
      description
        "RX CSMS packets drop counter.";
    }
    leaf counters_slice3_ifg0_ifgb_rx_cgm_0_frm_dropped_packets {
      type oc-yang:counter64;
      description
        "RX FRM packets drop counter.";
    }
    leaf counters_slice3_ifg0_ifgb_rx_cgm_0_fte_dropped_packets {
      type oc-yang:counter64;
      description
        "RX FTE packets drop counter.";
    }
    leaf counters_slice3_ifg0_ifgb_rx_cgm_1_csms_dropped_packets {
      type oc-yang:counter64;
      description
        "RX CSMS packets drop counter.";
    }
    leaf counters_slice3_ifg0_ifgb_rx_cgm_1_frm_dropped_packets {
      type oc-yang:counter64;
      description
        "RX FRM packets drop counter.";
    }
    leaf counters_slice3_ifg0_ifgb_rx_cgm_1_fte_dropped_packets {
      type oc-yang:counter64;
      description
        "RX FTE packets drop counter.";
    }
    leaf counters_slice3_ifg0_ifgb_rx_cgm_2_csms_dropped_packets {
      type oc-yang:counter64;
      description
        "RX CSMS packets drop counter.";
    }
    leaf counters_slice3_ifg0_ifgb_rx_cgm_2_frm_dropped_packets {
      type oc-yang:counter64;
      description
        "RX FRM packets drop counter.";
    }
    leaf counters_slice3_ifg0_ifgb_rx_cgm_2_fte_dropped_packets {
      type oc-yang:counter64;
      description
        "RX FTE packets drop counter.";
    }
    leaf counters_slice3_ifg0_ifgb_rx_cgm_3_csms_dropped_packets {
      type oc-yang:counter64;
      description
        "RX CSMS packets drop counter.";
    }
    leaf counters_slice3_ifg0_ifgb_rx_cgm_3_frm_dropped_packets {
      type oc-yang:counter64;
      description
        "RX FRM packets drop counter.";
    }
    leaf counters_slice3_ifg0_ifgb_rx_cgm_3_fte_dropped_packets {
      type oc-yang:counter64;
      description
        "RX FTE packets drop counter.";
    }
    leaf counters_slice3_ifg0_ifgb_rx_port_0_oobe_crc_errors {
      type oc-yang:counter64;
      description
        "OOB Extract CRC error counter per port";
    }
    leaf counters_slice3_ifg0_ifgb_rx_port_0_undersized_dropped_packets {
      type oc-yang:counter64;
      description
        "Counter for packets that were dropped because they were smaller than 64B.";
    }
    leaf counters_slice3_ifg0_ifgb_rx_port_1_oobe_crc_errors {
      type oc-yang:counter64;
      description
        "OOB Extract CRC error counter per port";
    }
    leaf counters_slice3_ifg0_ifgb_rx_port_1_undersized_dropped_packets {
      type oc-yang:counter64;
      description
        "Counter for packets that were dropped because they were smaller than 64B.";
    }
    leaf counters_slice3_ifg0_ifgb_rx_port_10_oobe_crc_errors {
      type oc-yang:counter64;
      description
        "OOB Extract CRC error counter per port";
    }
    leaf counters_slice3_ifg0_ifgb_rx_port_10_undersized_dropped_packets {
      type oc-yang:counter64;
      description
        "Counter for packets that were dropped because they were smaller than 64B.";
    }
    leaf counters_slice3_ifg0_ifgb_rx_port_11_oobe_crc_errors {
      type oc-yang:counter64;
      description
        "OOB Extract CRC error counter per port";
    }
    leaf counters_slice3_ifg0_ifgb_rx_port_11_undersized_dropped_packets {
      type oc-yang:counter64;
      description
        "Counter for packets that were dropped because they were smaller than 64B.";
    }
    leaf counters_slice3_ifg0_ifgb_rx_port_12_oobe_crc_errors {
      type oc-yang:counter64;
      description
        "OOB Extract CRC error counter per port";
    }
    leaf counters_slice3_ifg0_ifgb_rx_port_12_undersized_dropped_packets {
      type oc-yang:counter64;
      description
        "Counter for packets that were dropped because they were smaller than 64B.";
    }
    leaf counters_slice3_ifg0_ifgb_rx_port_13_oobe_crc_errors {
      type oc-yang:counter64;
      description
        "OOB Extract CRC error counter per port";
    }
    leaf counters_slice3_ifg0_ifgb_rx_port_13_undersized_dropped_packets {
      type oc-yang:counter64;
      description
        "Counter for packets that were dropped because they were smaller than 64B.";
    }
    leaf counters_slice3_ifg0_ifgb_rx_port_14_oobe_crc_errors {
      type oc-yang:counter64;
      description
        "OOB Extract CRC error counter per port";
    }
    leaf counters_slice3_ifg0_ifgb_rx_port_14_undersized_dropped_packets {
      type oc-yang:counter64;
      description
        "Counter for packets that were dropped because they were smaller than 64B.";
    }
    leaf counters_slice3_ifg0_ifgb_rx_port_15_oobe_crc_errors {
      type oc-yang:counter64;
      description
        "OOB Extract CRC error counter per port";
    }
    leaf counters_slice3_ifg0_ifgb_rx_port_15_undersized_dropped_packets {
      type oc-yang:counter64;
      description
        "Counter for packets that were dropped because they were smaller than 64B.";
    }
    leaf counters_slice3_ifg0_ifgb_rx_port_16_undersized_dropped_packets {
      type oc-yang:counter64;
      description
        "Counter for packets that were dropped because they were smaller than 64B.";
    }
    leaf counters_slice3_ifg0_ifgb_rx_port_17_undersized_dropped_packets {
      type oc-yang:counter64;
      description
        "Counter for packets that were dropped because they were smaller than 64B.";
    }
    leaf counters_slice3_ifg0_ifgb_rx_port_18_undersized_dropped_packets {
      type oc-yang:counter64;
      description
        "Counter for packets that were dropped because they were smaller than 64B.";
    }
    leaf counters_slice3_ifg0_ifgb_rx_port_19_undersized_dropped_packets {
      type oc-yang:counter64;
      description
        "Counter for packets that were dropped because they were smaller than 64B.";
    }
    leaf counters_slice3_ifg0_ifgb_rx_port_2_oobe_crc_errors {
      type oc-yang:counter64;
      description
        "OOB Extract CRC error counter per port";
    }
    leaf counters_slice3_ifg0_ifgb_rx_port_2_undersized_dropped_packets {
      type oc-yang:counter64;
      description
        "Counter for packets that were dropped because they were smaller than 64B.";
    }
    leaf counters_slice3_ifg0_ifgb_rx_port_20_undersized_dropped_packets {
      type oc-yang:counter64;
      description
        "Counter for packets that were dropped because they were smaller than 64B.";
    }
    leaf counters_slice3_ifg0_ifgb_rx_port_21_undersized_dropped_packets {
      type oc-yang:counter64;
      description
        "Counter for packets that were dropped because they were smaller than 64B.";
    }
    leaf counters_slice3_ifg0_ifgb_rx_port_22_undersized_dropped_packets {
      type oc-yang:counter64;
      description
        "Counter for packets that were dropped because they were smaller than 64B.";
    }
    leaf counters_slice3_ifg0_ifgb_rx_port_23_undersized_dropped_packets {
      type oc-yang:counter64;
      description
        "Counter for packets that were dropped because they were smaller than 64B.";
    }
    leaf counters_slice3_ifg0_ifgb_rx_port_24_undersized_dropped_packets {
      type oc-yang:counter64;
      description
        "Counter for packets that were dropped because they were smaller than 64B.";
    }
    leaf counters_slice3_ifg0_ifgb_rx_port_25_undersized_dropped_packets {
      type oc-yang:counter64;
      description
        "Counter for packets that were dropped because they were smaller than 64B.";
    }
    leaf counters_slice3_ifg0_ifgb_rx_port_26_undersized_dropped_packets {
      type oc-yang:counter64;
      description
        "Counter for packets that were dropped because they were smaller than 64B.";
    }
    leaf counters_slice3_ifg0_ifgb_rx_port_27_undersized_dropped_packets {
      type oc-yang:counter64;
      description
        "Counter for packets that were dropped because they were smaller than 64B.";
    }
    leaf counters_slice3_ifg0_ifgb_rx_port_28_undersized_dropped_packets {
      type oc-yang:counter64;
      description
        "Counter for packets that were dropped because they were smaller than 64B.";
    }
    leaf counters_slice3_ifg0_ifgb_rx_port_29_undersized_dropped_packets {
      type oc-yang:counter64;
      description
        "Counter for packets that were dropped because they were smaller than 64B.";
    }
    leaf counters_slice3_ifg0_ifgb_rx_port_3_oobe_crc_errors {
      type oc-yang:counter64;
      description
        "OOB Extract CRC error counter per port";
    }
    leaf counters_slice3_ifg0_ifgb_rx_port_3_undersized_dropped_packets {
      type oc-yang:counter64;
      description
        "Counter for packets that were dropped because they were smaller than 64B.";
    }
    leaf counters_slice3_ifg0_ifgb_rx_port_30_undersized_dropped_packets {
      type oc-yang:counter64;
      description
        "Counter for packets that were dropped because they were smaller than 64B.";
    }
    leaf counters_slice3_ifg0_ifgb_rx_port_31_undersized_dropped_packets {
      type oc-yang:counter64;
      description
        "Counter for packets that were dropped because they were smaller than 64B.";
    }
    leaf counters_slice3_ifg0_ifgb_rx_port_4_oobe_crc_errors {
      type oc-yang:counter64;
      description
        "OOB Extract CRC error counter per port";
    }
    leaf counters_slice3_ifg0_ifgb_rx_port_4_undersized_dropped_packets {
      type oc-yang:counter64;
      description
        "Counter for packets that were dropped because they were smaller than 64B.";
    }
    leaf counters_slice3_ifg0_ifgb_rx_port_5_oobe_crc_errors {
      type oc-yang:counter64;
      description
        "OOB Extract CRC error counter per port";
    }
    leaf counters_slice3_ifg0_ifgb_rx_port_5_undersized_dropped_packets {
      type oc-yang:counter64;
      description
        "Counter for packets that were dropped because they were smaller than 64B.";
    }
    leaf counters_slice3_ifg0_ifgb_rx_port_6_oobe_crc_errors {
      type oc-yang:counter64;
      description
        "OOB Extract CRC error counter per port";
    }
    leaf counters_slice3_ifg0_ifgb_rx_port_6_undersized_dropped_packets {
      type oc-yang:counter64;
      description
        "Counter for packets that were dropped because they were smaller than 64B.";
    }
    leaf counters_slice3_ifg0_ifgb_rx_port_7_oobe_crc_errors {
      type oc-yang:counter64;
      description
        "OOB Extract CRC error counter per port";
    }
    leaf counters_slice3_ifg0_ifgb_rx_port_7_undersized_dropped_packets {
      type oc-yang:counter64;
      description
        "Counter for packets that were dropped because they were smaller than 64B.";
    }
    leaf counters_slice3_ifg0_ifgb_rx_port_8_oobe_crc_errors {
      type oc-yang:counter64;
      description
        "OOB Extract CRC error counter per port";
    }
    leaf counters_slice3_ifg0_ifgb_rx_port_8_undersized_dropped_packets {
      type oc-yang:counter64;
      description
        "Counter for packets that were dropped because they were smaller than 64B.";
    }
    leaf counters_slice3_ifg0_ifgb_rx_port_9_oobe_crc_errors {
      type oc-yang:counter64;
      description
        "OOB Extract CRC error counter per port";
    }
    leaf counters_slice3_ifg0_ifgb_rx_port_9_undersized_dropped_packets {
      type oc-yang:counter64;
      description
        "Counter for packets that were dropped because they were smaller than 64B.";
    }
    leaf counters_slice3_ifg0_ifgb_rx_protection_dropped_fragments {
      type oc-yang:counter64;
      description
        "RXPP interface protection fragments drop counter.";
    }
    leaf counters_slice3_ifg0_ifgb_rx_protection_dropped_packets {
      type oc-yang:counter64;
      description
        "RXPP interface protection packet drop counter.";
    }
    leaf counters_slice3_ifg0_ifgbi_recycle_in_band_extract_npu_host_re_direct_drop {
      type oc-yang:counter64;
      description
        "InBand Extract NPU Host ReDirect drop counter. Increments based on the RcyDropCntrsCfg.";
    }
    leaf counters_slice3_ifg0_ifgbi_recycle_in_band_extract_packet_dma_re_direct_drop {
      type oc-yang:counter64;
      description
        "InBand Extract Pkt DMA ReDirect drop counter. Increments based on the RcyDropCntrsCfg.";
    }
    leaf counters_slice3_ifg0_npu_rxpp_fwd_post_npe_dropped_packets {
      type oc-yang:counter64;
      description
        "Counts packets dropped by the rxpp";
    }
    leaf counters_slice3_ifg0_npu_rxpp_fwd_post_npe_dropped_packets_due_destination {
      type oc-yang:counter64;
      description
        "nan";
    }
    leaf counters_slice3_ifg0_npu_rxpp_fwd_post_npe_dropped_packets_due_dummy {
      type oc-yang:counter64;
      description
        "nan";
    }
    leaf counters_slice3_ifg0_npu_rxpp_fwd_post_npe_dropped_packets_due_ecc {
      type oc-yang:counter64;
      description
        "nan";
    }
    leaf counters_slice3_ifg0_npu_rxpp_fwd_post_npe_dropped_packets_due_err_flag {
      type oc-yang:counter64;
      description
        "nan";
    }
    leaf counters_slice3_ifg0_npu_rxpp_fwd_post_npe_dropped_packets_due_frag_parity_error {
      type oc-yang:counter64;
      description
        "nan";
    }
    leaf counters_slice3_ifg0_npu_txpp_hw_editor_1_packets_with_error_bit {
      type oc-yang:counter64;
      description
        "Counts number of packet leaving HW Editor 1 inst 0 have error bit assered";
    }
    leaf counters_slice3_ifg0_npu_txpp_hw_editor_2_packets_with_error_bit {
      type oc-yang:counter64;
      description
        "Counts number of packet leaving HW Editor 2 towards ifg0 have error bit assered";
    }
    leaf counters_slice3_ifg0_npu_txpp_npe_packets_with_error_bit {
      type oc-yang:counter64;
      description
        "Counts number of packet leaving NPE 0 have error bit assered";
    }
    leaf counters_slice3_ifg0_npu_txpp_preprocess_packets_with_error_bit {
      type oc-yang:counter64;
      description
        "Counts number of packet leaving preprocessing 0 have error bit assered";
    }
    leaf counters_slice3_ifg1_ifgb_rx_cgm_0_csms_dropped_packets {
      type oc-yang:counter64;
      description
        "RX CSMS packets drop counter.";
    }
    leaf counters_slice3_ifg1_ifgb_rx_cgm_0_frm_dropped_packets {
      type oc-yang:counter64;
      description
        "RX FRM packets drop counter.";
    }
    leaf counters_slice3_ifg1_ifgb_rx_cgm_0_fte_dropped_packets {
      type oc-yang:counter64;
      description
        "RX FTE packets drop counter.";
    }
    leaf counters_slice3_ifg1_ifgb_rx_cgm_1_csms_dropped_packets {
      type oc-yang:counter64;
      description
        "RX CSMS packets drop counter.";
    }
    leaf counters_slice3_ifg1_ifgb_rx_cgm_1_frm_dropped_packets {
      type oc-yang:counter64;
      description
        "RX FRM packets drop counter.";
    }
    leaf counters_slice3_ifg1_ifgb_rx_cgm_1_fte_dropped_packets {
      type oc-yang:counter64;
      description
        "RX FTE packets drop counter.";
    }
    leaf counters_slice3_ifg1_ifgb_rx_cgm_2_csms_dropped_packets {
      type oc-yang:counter64;
      description
        "RX CSMS packets drop counter.";
    }
    leaf counters_slice3_ifg1_ifgb_rx_cgm_2_frm_dropped_packets {
      type oc-yang:counter64;
      description
        "RX FRM packets drop counter.";
    }
    leaf counters_slice3_ifg1_ifgb_rx_cgm_2_fte_dropped_packets {
      type oc-yang:counter64;
      description
        "RX FTE packets drop counter.";
    }
    leaf counters_slice3_ifg1_ifgb_rx_cgm_3_csms_dropped_packets {
      type oc-yang:counter64;
      description
        "RX CSMS packets drop counter.";
    }
    leaf counters_slice3_ifg1_ifgb_rx_cgm_3_frm_dropped_packets {
      type oc-yang:counter64;
      description
        "RX FRM packets drop counter.";
    }
    leaf counters_slice3_ifg1_ifgb_rx_cgm_3_fte_dropped_packets {
      type oc-yang:counter64;
      description
        "RX FTE packets drop counter.";
    }
    leaf counters_slice3_ifg1_ifgb_rx_port_0_oobe_crc_errors {
      type oc-yang:counter64;
      description
        "OOB Extract CRC error counter per port";
    }
    leaf counters_slice3_ifg1_ifgb_rx_port_0_undersized_dropped_packets {
      type oc-yang:counter64;
      description
        "Counter for packets that were dropped because they were smaller than 64B.";
    }
    leaf counters_slice3_ifg1_ifgb_rx_port_1_oobe_crc_errors {
      type oc-yang:counter64;
      description
        "OOB Extract CRC error counter per port";
    }
    leaf counters_slice3_ifg1_ifgb_rx_port_1_undersized_dropped_packets {
      type oc-yang:counter64;
      description
        "Counter for packets that were dropped because they were smaller than 64B.";
    }
    leaf counters_slice3_ifg1_ifgb_rx_port_10_oobe_crc_errors {
      type oc-yang:counter64;
      description
        "OOB Extract CRC error counter per port";
    }
    leaf counters_slice3_ifg1_ifgb_rx_port_10_undersized_dropped_packets {
      type oc-yang:counter64;
      description
        "Counter for packets that were dropped because they were smaller than 64B.";
    }
    leaf counters_slice3_ifg1_ifgb_rx_port_11_oobe_crc_errors {
      type oc-yang:counter64;
      description
        "OOB Extract CRC error counter per port";
    }
    leaf counters_slice3_ifg1_ifgb_rx_port_11_undersized_dropped_packets {
      type oc-yang:counter64;
      description
        "Counter for packets that were dropped because they were smaller than 64B.";
    }
    leaf counters_slice3_ifg1_ifgb_rx_port_12_oobe_crc_errors {
      type oc-yang:counter64;
      description
        "OOB Extract CRC error counter per port";
    }
    leaf counters_slice3_ifg1_ifgb_rx_port_12_undersized_dropped_packets {
      type oc-yang:counter64;
      description
        "Counter for packets that were dropped because they were smaller than 64B.";
    }
    leaf counters_slice3_ifg1_ifgb_rx_port_13_oobe_crc_errors {
      type oc-yang:counter64;
      description
        "OOB Extract CRC error counter per port";
    }
    leaf counters_slice3_ifg1_ifgb_rx_port_13_undersized_dropped_packets {
      type oc-yang:counter64;
      description
        "Counter for packets that were dropped because they were smaller than 64B.";
    }
    leaf counters_slice3_ifg1_ifgb_rx_port_14_oobe_crc_errors {
      type oc-yang:counter64;
      description
        "OOB Extract CRC error counter per port";
    }
    leaf counters_slice3_ifg1_ifgb_rx_port_14_undersized_dropped_packets {
      type oc-yang:counter64;
      description
        "Counter for packets that were dropped because they were smaller than 64B.";
    }
    leaf counters_slice3_ifg1_ifgb_rx_port_15_oobe_crc_errors {
      type oc-yang:counter64;
      description
        "OOB Extract CRC error counter per port";
    }
    leaf counters_slice3_ifg1_ifgb_rx_port_15_undersized_dropped_packets {
      type oc-yang:counter64;
      description
        "Counter for packets that were dropped because they were smaller than 64B.";
    }
    leaf counters_slice3_ifg1_ifgb_rx_port_16_undersized_dropped_packets {
      type oc-yang:counter64;
      description
        "Counter for packets that were dropped because they were smaller than 64B.";
    }
    leaf counters_slice3_ifg1_ifgb_rx_port_17_undersized_dropped_packets {
      type oc-yang:counter64;
      description
        "Counter for packets that were dropped because they were smaller than 64B.";
    }
    leaf counters_slice3_ifg1_ifgb_rx_port_18_undersized_dropped_packets {
      type oc-yang:counter64;
      description
        "Counter for packets that were dropped because they were smaller than 64B.";
    }
    leaf counters_slice3_ifg1_ifgb_rx_port_19_undersized_dropped_packets {
      type oc-yang:counter64;
      description
        "Counter for packets that were dropped because they were smaller than 64B.";
    }
    leaf counters_slice3_ifg1_ifgb_rx_port_2_oobe_crc_errors {
      type oc-yang:counter64;
      description
        "OOB Extract CRC error counter per port";
    }
    leaf counters_slice3_ifg1_ifgb_rx_port_2_undersized_dropped_packets {
      type oc-yang:counter64;
      description
        "Counter for packets that were dropped because they were smaller than 64B.";
    }
    leaf counters_slice3_ifg1_ifgb_rx_port_20_undersized_dropped_packets {
      type oc-yang:counter64;
      description
        "Counter for packets that were dropped because they were smaller than 64B.";
    }
    leaf counters_slice3_ifg1_ifgb_rx_port_21_undersized_dropped_packets {
      type oc-yang:counter64;
      description
        "Counter for packets that were dropped because they were smaller than 64B.";
    }
    leaf counters_slice3_ifg1_ifgb_rx_port_22_undersized_dropped_packets {
      type oc-yang:counter64;
      description
        "Counter for packets that were dropped because they were smaller than 64B.";
    }
    leaf counters_slice3_ifg1_ifgb_rx_port_23_undersized_dropped_packets {
      type oc-yang:counter64;
      description
        "Counter for packets that were dropped because they were smaller than 64B.";
    }
    leaf counters_slice3_ifg1_ifgb_rx_port_24_undersized_dropped_packets {
      type oc-yang:counter64;
      description
        "Counter for packets that were dropped because they were smaller than 64B.";
    }
    leaf counters_slice3_ifg1_ifgb_rx_port_25_undersized_dropped_packets {
      type oc-yang:counter64;
      description
        "Counter for packets that were dropped because they were smaller than 64B.";
    }
    leaf counters_slice3_ifg1_ifgb_rx_port_26_undersized_dropped_packets {
      type oc-yang:counter64;
      description
        "Counter for packets that were dropped because they were smaller than 64B.";
    }
    leaf counters_slice3_ifg1_ifgb_rx_port_27_undersized_dropped_packets {
      type oc-yang:counter64;
      description
        "Counter for packets that were dropped because they were smaller than 64B.";
    }
    leaf counters_slice3_ifg1_ifgb_rx_port_28_undersized_dropped_packets {
      type oc-yang:counter64;
      description
        "Counter for packets that were dropped because they were smaller than 64B.";
    }
    leaf counters_slice3_ifg1_ifgb_rx_port_29_undersized_dropped_packets {
      type oc-yang:counter64;
      description
        "Counter for packets that were dropped because they were smaller than 64B.";
    }
    leaf counters_slice3_ifg1_ifgb_rx_port_3_oobe_crc_errors {
      type oc-yang:counter64;
      description
        "OOB Extract CRC error counter per port";
    }
    leaf counters_slice3_ifg1_ifgb_rx_port_3_undersized_dropped_packets {
      type oc-yang:counter64;
      description
        "Counter for packets that were dropped because they were smaller than 64B.";
    }
    leaf counters_slice3_ifg1_ifgb_rx_port_30_undersized_dropped_packets {
      type oc-yang:counter64;
      description
        "Counter for packets that were dropped because they were smaller than 64B.";
    }
    leaf counters_slice3_ifg1_ifgb_rx_port_31_undersized_dropped_packets {
      type oc-yang:counter64;
      description
        "Counter for packets that were dropped because they were smaller than 64B.";
    }
    leaf counters_slice3_ifg1_ifgb_rx_port_4_oobe_crc_errors {
      type oc-yang:counter64;
      description
        "OOB Extract CRC error counter per port";
    }
    leaf counters_slice3_ifg1_ifgb_rx_port_4_undersized_dropped_packets {
      type oc-yang:counter64;
      description
        "Counter for packets that were dropped because they were smaller than 64B.";
    }
    leaf counters_slice3_ifg1_ifgb_rx_port_5_oobe_crc_errors {
      type oc-yang:counter64;
      description
        "OOB Extract CRC error counter per port";
    }
    leaf counters_slice3_ifg1_ifgb_rx_port_5_undersized_dropped_packets {
      type oc-yang:counter64;
      description
        "Counter for packets that were dropped because they were smaller than 64B.";
    }
    leaf counters_slice3_ifg1_ifgb_rx_port_6_oobe_crc_errors {
      type oc-yang:counter64;
      description
        "OOB Extract CRC error counter per port";
    }
    leaf counters_slice3_ifg1_ifgb_rx_port_6_undersized_dropped_packets {
      type oc-yang:counter64;
      description
        "Counter for packets that were dropped because they were smaller than 64B.";
    }
    leaf counters_slice3_ifg1_ifgb_rx_port_7_oobe_crc_errors {
      type oc-yang:counter64;
      description
        "OOB Extract CRC error counter per port";
    }
    leaf counters_slice3_ifg1_ifgb_rx_port_7_undersized_dropped_packets {
      type oc-yang:counter64;
      description
        "Counter for packets that were dropped because they were smaller than 64B.";
    }
    leaf counters_slice3_ifg1_ifgb_rx_port_8_oobe_crc_errors {
      type oc-yang:counter64;
      description
        "OOB Extract CRC error counter per port";
    }
    leaf counters_slice3_ifg1_ifgb_rx_port_8_undersized_dropped_packets {
      type oc-yang:counter64;
      description
        "Counter for packets that were dropped because they were smaller than 64B.";
    }
    leaf counters_slice3_ifg1_ifgb_rx_port_9_oobe_crc_errors {
      type oc-yang:counter64;
      description
        "OOB Extract CRC error counter per port";
    }
    leaf counters_slice3_ifg1_ifgb_rx_port_9_undersized_dropped_packets {
      type oc-yang:counter64;
      description
        "Counter for packets that were dropped because they were smaller than 64B.";
    }
    leaf counters_slice3_ifg1_ifgb_rx_protection_dropped_fragments {
      type oc-yang:counter64;
      description
        "RXPP interface protection fragments drop counter.";
    }
    leaf counters_slice3_ifg1_ifgb_rx_protection_dropped_packets {
      type oc-yang:counter64;
      description
        "RXPP interface protection packet drop counter.";
    }
    leaf counters_slice3_ifg1_ifgbi_recycle_in_band_extract_npu_host_re_direct_drop {
      type oc-yang:counter64;
      description
        "InBand Extract NPU Host ReDirect drop counter. Increments based on the RcyDropCntrsCfg.";
    }
    leaf counters_slice3_ifg1_ifgbi_recycle_in_band_extract_packet_dma_re_direct_drop {
      type oc-yang:counter64;
      description
        "InBand Extract Pkt DMA ReDirect drop counter. Increments based on the RcyDropCntrsCfg.";
    }
    leaf counters_slice3_ifg1_npu_rxpp_fwd_post_npe_dropped_packets {
      type oc-yang:counter64;
      description
        "Counts packets dropped by the rxpp";
    }
    leaf counters_slice3_ifg1_npu_rxpp_fwd_post_npe_dropped_packets_due_destination {
      type oc-yang:counter64;
      description
        "nan";
    }
    leaf counters_slice3_ifg1_npu_rxpp_fwd_post_npe_dropped_packets_due_dummy {
      type oc-yang:counter64;
      description
        "nan";
    }
    leaf counters_slice3_ifg1_npu_rxpp_fwd_post_npe_dropped_packets_due_ecc {
      type oc-yang:counter64;
      description
        "nan";
    }
    leaf counters_slice3_ifg1_npu_rxpp_fwd_post_npe_dropped_packets_due_err_flag {
      type oc-yang:counter64;
      description
        "nan";
    }
    leaf counters_slice3_ifg1_npu_rxpp_fwd_post_npe_dropped_packets_due_frag_parity_error {
      type oc-yang:counter64;
      description
        "nan";
    }
    leaf counters_slice3_ifg1_npu_txpp_hw_editor_1_packets_with_error_bit {
      type oc-yang:counter64;
      description
        "Counts number of packet leaving HW Editor 1 inst 1 have error bit assered";
    }
    leaf counters_slice3_ifg1_npu_txpp_hw_editor_2_packets_with_error_bit {
      type oc-yang:counter64;
      description
        "Counts number of packet leaving HW Editor 2 towards ifg1 have error bit assered";
    }
    leaf counters_slice3_ifg1_npu_txpp_npe_packets_with_error_bit {
      type oc-yang:counter64;
      description
        "Counts number of packet leaving NPE 1 have error bit assered";
    }
    leaf counters_slice3_ifg1_npu_txpp_preprocess_packets_with_error_bit {
      type oc-yang:counter64;
      description
        "Counts number of packet leaving preprocessing 1 have error bit assered";
    }
    leaf counters_slice4_cluster0_ene_outgoing_headers_with_errors {
      type oc-yang:counter64;
      description
        "Number of headers Exiting the ENE with Error bit on";
    }
    leaf counters_slice4_cluster1_ene_outgoing_headers_with_errors {
      type oc-yang:counter64;
      description
        "Number of headers Exiting the ENE with Error bit on";
    }
    leaf counters_slice4_fllb_debug_register_dropped_p_ds {
      type oc-yang:counter64;
      description
        "Number of PDs dropped due to no eligible links";
    }
    leaf counters_slice4_ifg0_ifgb_rx_cgm_0_csms_dropped_packets {
      type oc-yang:counter64;
      description
        "RX CSMS packets drop counter.";
    }
    leaf counters_slice4_ifg0_ifgb_rx_cgm_0_frm_dropped_packets {
      type oc-yang:counter64;
      description
        "RX FRM packets drop counter.";
    }
    leaf counters_slice4_ifg0_ifgb_rx_cgm_0_fte_dropped_packets {
      type oc-yang:counter64;
      description
        "RX FTE packets drop counter.";
    }
    leaf counters_slice4_ifg0_ifgb_rx_cgm_1_csms_dropped_packets {
      type oc-yang:counter64;
      description
        "RX CSMS packets drop counter.";
    }
    leaf counters_slice4_ifg0_ifgb_rx_cgm_1_frm_dropped_packets {
      type oc-yang:counter64;
      description
        "RX FRM packets drop counter.";
    }
    leaf counters_slice4_ifg0_ifgb_rx_cgm_1_fte_dropped_packets {
      type oc-yang:counter64;
      description
        "RX FTE packets drop counter.";
    }
    leaf counters_slice4_ifg0_ifgb_rx_cgm_2_csms_dropped_packets {
      type oc-yang:counter64;
      description
        "RX CSMS packets drop counter.";
    }
    leaf counters_slice4_ifg0_ifgb_rx_cgm_2_frm_dropped_packets {
      type oc-yang:counter64;
      description
        "RX FRM packets drop counter.";
    }
    leaf counters_slice4_ifg0_ifgb_rx_cgm_2_fte_dropped_packets {
      type oc-yang:counter64;
      description
        "RX FTE packets drop counter.";
    }
    leaf counters_slice4_ifg0_ifgb_rx_cgm_3_csms_dropped_packets {
      type oc-yang:counter64;
      description
        "RX CSMS packets drop counter.";
    }
    leaf counters_slice4_ifg0_ifgb_rx_cgm_3_frm_dropped_packets {
      type oc-yang:counter64;
      description
        "RX FRM packets drop counter.";
    }
    leaf counters_slice4_ifg0_ifgb_rx_cgm_3_fte_dropped_packets {
      type oc-yang:counter64;
      description
        "RX FTE packets drop counter.";
    }
    leaf counters_slice4_ifg0_ifgb_rx_port_0_oobe_crc_errors {
      type oc-yang:counter64;
      description
        "OOB Extract CRC error counter per port";
    }
    leaf counters_slice4_ifg0_ifgb_rx_port_0_undersized_dropped_packets {
      type oc-yang:counter64;
      description
        "Counter for packets that were dropped because they were smaller than 64B.";
    }
    leaf counters_slice4_ifg0_ifgb_rx_port_1_oobe_crc_errors {
      type oc-yang:counter64;
      description
        "OOB Extract CRC error counter per port";
    }
    leaf counters_slice4_ifg0_ifgb_rx_port_1_undersized_dropped_packets {
      type oc-yang:counter64;
      description
        "Counter for packets that were dropped because they were smaller than 64B.";
    }
    leaf counters_slice4_ifg0_ifgb_rx_port_10_oobe_crc_errors {
      type oc-yang:counter64;
      description
        "OOB Extract CRC error counter per port";
    }
    leaf counters_slice4_ifg0_ifgb_rx_port_10_undersized_dropped_packets {
      type oc-yang:counter64;
      description
        "Counter for packets that were dropped because they were smaller than 64B.";
    }
    leaf counters_slice4_ifg0_ifgb_rx_port_11_oobe_crc_errors {
      type oc-yang:counter64;
      description
        "OOB Extract CRC error counter per port";
    }
    leaf counters_slice4_ifg0_ifgb_rx_port_11_undersized_dropped_packets {
      type oc-yang:counter64;
      description
        "Counter for packets that were dropped because they were smaller than 64B.";
    }
    leaf counters_slice4_ifg0_ifgb_rx_port_12_oobe_crc_errors {
      type oc-yang:counter64;
      description
        "OOB Extract CRC error counter per port";
    }
    leaf counters_slice4_ifg0_ifgb_rx_port_12_undersized_dropped_packets {
      type oc-yang:counter64;
      description
        "Counter for packets that were dropped because they were smaller than 64B.";
    }
    leaf counters_slice4_ifg0_ifgb_rx_port_13_oobe_crc_errors {
      type oc-yang:counter64;
      description
        "OOB Extract CRC error counter per port";
    }
    leaf counters_slice4_ifg0_ifgb_rx_port_13_undersized_dropped_packets {
      type oc-yang:counter64;
      description
        "Counter for packets that were dropped because they were smaller than 64B.";
    }
    leaf counters_slice4_ifg0_ifgb_rx_port_14_oobe_crc_errors {
      type oc-yang:counter64;
      description
        "OOB Extract CRC error counter per port";
    }
    leaf counters_slice4_ifg0_ifgb_rx_port_14_undersized_dropped_packets {
      type oc-yang:counter64;
      description
        "Counter for packets that were dropped because they were smaller than 64B.";
    }
    leaf counters_slice4_ifg0_ifgb_rx_port_15_oobe_crc_errors {
      type oc-yang:counter64;
      description
        "OOB Extract CRC error counter per port";
    }
    leaf counters_slice4_ifg0_ifgb_rx_port_15_undersized_dropped_packets {
      type oc-yang:counter64;
      description
        "Counter for packets that were dropped because they were smaller than 64B.";
    }
    leaf counters_slice4_ifg0_ifgb_rx_port_16_undersized_dropped_packets {
      type oc-yang:counter64;
      description
        "Counter for packets that were dropped because they were smaller than 64B.";
    }
    leaf counters_slice4_ifg0_ifgb_rx_port_17_undersized_dropped_packets {
      type oc-yang:counter64;
      description
        "Counter for packets that were dropped because they were smaller than 64B.";
    }
    leaf counters_slice4_ifg0_ifgb_rx_port_18_undersized_dropped_packets {
      type oc-yang:counter64;
      description
        "Counter for packets that were dropped because they were smaller than 64B.";
    }
    leaf counters_slice4_ifg0_ifgb_rx_port_19_undersized_dropped_packets {
      type oc-yang:counter64;
      description
        "Counter for packets that were dropped because they were smaller than 64B.";
    }
    leaf counters_slice4_ifg0_ifgb_rx_port_2_oobe_crc_errors {
      type oc-yang:counter64;
      description
        "OOB Extract CRC error counter per port";
    }
    leaf counters_slice4_ifg0_ifgb_rx_port_2_undersized_dropped_packets {
      type oc-yang:counter64;
      description
        "Counter for packets that were dropped because they were smaller than 64B.";
    }
    leaf counters_slice4_ifg0_ifgb_rx_port_20_undersized_dropped_packets {
      type oc-yang:counter64;
      description
        "Counter for packets that were dropped because they were smaller than 64B.";
    }
    leaf counters_slice4_ifg0_ifgb_rx_port_21_undersized_dropped_packets {
      type oc-yang:counter64;
      description
        "Counter for packets that were dropped because they were smaller than 64B.";
    }
    leaf counters_slice4_ifg0_ifgb_rx_port_22_undersized_dropped_packets {
      type oc-yang:counter64;
      description
        "Counter for packets that were dropped because they were smaller than 64B.";
    }
    leaf counters_slice4_ifg0_ifgb_rx_port_23_undersized_dropped_packets {
      type oc-yang:counter64;
      description
        "Counter for packets that were dropped because they were smaller than 64B.";
    }
    leaf counters_slice4_ifg0_ifgb_rx_port_24_undersized_dropped_packets {
      type oc-yang:counter64;
      description
        "Counter for packets that were dropped because they were smaller than 64B.";
    }
    leaf counters_slice4_ifg0_ifgb_rx_port_25_undersized_dropped_packets {
      type oc-yang:counter64;
      description
        "Counter for packets that were dropped because they were smaller than 64B.";
    }
    leaf counters_slice4_ifg0_ifgb_rx_port_26_undersized_dropped_packets {
      type oc-yang:counter64;
      description
        "Counter for packets that were dropped because they were smaller than 64B.";
    }
    leaf counters_slice4_ifg0_ifgb_rx_port_27_undersized_dropped_packets {
      type oc-yang:counter64;
      description
        "Counter for packets that were dropped because they were smaller than 64B.";
    }
    leaf counters_slice4_ifg0_ifgb_rx_port_28_undersized_dropped_packets {
      type oc-yang:counter64;
      description
        "Counter for packets that were dropped because they were smaller than 64B.";
    }
    leaf counters_slice4_ifg0_ifgb_rx_port_29_undersized_dropped_packets {
      type oc-yang:counter64;
      description
        "Counter for packets that were dropped because they were smaller than 64B.";
    }
    leaf counters_slice4_ifg0_ifgb_rx_port_3_oobe_crc_errors {
      type oc-yang:counter64;
      description
        "OOB Extract CRC error counter per port";
    }
    leaf counters_slice4_ifg0_ifgb_rx_port_3_undersized_dropped_packets {
      type oc-yang:counter64;
      description
        "Counter for packets that were dropped because they were smaller than 64B.";
    }
    leaf counters_slice4_ifg0_ifgb_rx_port_30_undersized_dropped_packets {
      type oc-yang:counter64;
      description
        "Counter for packets that were dropped because they were smaller than 64B.";
    }
    leaf counters_slice4_ifg0_ifgb_rx_port_31_undersized_dropped_packets {
      type oc-yang:counter64;
      description
        "Counter for packets that were dropped because they were smaller than 64B.";
    }
    leaf counters_slice4_ifg0_ifgb_rx_port_4_oobe_crc_errors {
      type oc-yang:counter64;
      description
        "OOB Extract CRC error counter per port";
    }
    leaf counters_slice4_ifg0_ifgb_rx_port_4_undersized_dropped_packets {
      type oc-yang:counter64;
      description
        "Counter for packets that were dropped because they were smaller than 64B.";
    }
    leaf counters_slice4_ifg0_ifgb_rx_port_5_oobe_crc_errors {
      type oc-yang:counter64;
      description
        "OOB Extract CRC error counter per port";
    }
    leaf counters_slice4_ifg0_ifgb_rx_port_5_undersized_dropped_packets {
      type oc-yang:counter64;
      description
        "Counter for packets that were dropped because they were smaller than 64B.";
    }
    leaf counters_slice4_ifg0_ifgb_rx_port_6_oobe_crc_errors {
      type oc-yang:counter64;
      description
        "OOB Extract CRC error counter per port";
    }
    leaf counters_slice4_ifg0_ifgb_rx_port_6_undersized_dropped_packets {
      type oc-yang:counter64;
      description
        "Counter for packets that were dropped because they were smaller than 64B.";
    }
    leaf counters_slice4_ifg0_ifgb_rx_port_7_oobe_crc_errors {
      type oc-yang:counter64;
      description
        "OOB Extract CRC error counter per port";
    }
    leaf counters_slice4_ifg0_ifgb_rx_port_7_undersized_dropped_packets {
      type oc-yang:counter64;
      description
        "Counter for packets that were dropped because they were smaller than 64B.";
    }
    leaf counters_slice4_ifg0_ifgb_rx_port_8_oobe_crc_errors {
      type oc-yang:counter64;
      description
        "OOB Extract CRC error counter per port";
    }
    leaf counters_slice4_ifg0_ifgb_rx_port_8_undersized_dropped_packets {
      type oc-yang:counter64;
      description
        "Counter for packets that were dropped because they were smaller than 64B.";
    }
    leaf counters_slice4_ifg0_ifgb_rx_port_9_oobe_crc_errors {
      type oc-yang:counter64;
      description
        "OOB Extract CRC error counter per port";
    }
    leaf counters_slice4_ifg0_ifgb_rx_port_9_undersized_dropped_packets {
      type oc-yang:counter64;
      description
        "Counter for packets that were dropped because they were smaller than 64B.";
    }
    leaf counters_slice4_ifg0_ifgb_rx_protection_dropped_fragments {
      type oc-yang:counter64;
      description
        "RXPP interface protection fragments drop counter.";
    }
    leaf counters_slice4_ifg0_ifgb_rx_protection_dropped_packets {
      type oc-yang:counter64;
      description
        "RXPP interface protection packet drop counter.";
    }
    leaf counters_slice4_ifg0_ifgbi_recycle_in_band_extract_npu_host_re_direct_drop {
      type oc-yang:counter64;
      description
        "InBand Extract NPU Host ReDirect drop counter. Increments based on the RcyDropCntrsCfg.";
    }
    leaf counters_slice4_ifg0_ifgbi_recycle_in_band_extract_packet_dma_re_direct_drop {
      type oc-yang:counter64;
      description
        "InBand Extract Pkt DMA ReDirect drop counter. Increments based on the RcyDropCntrsCfg.";
    }
    leaf counters_slice4_ifg0_npu_rxpp_fwd_post_npe_dropped_packets {
      type oc-yang:counter64;
      description
        "Counts packets dropped by the rxpp";
    }
    leaf counters_slice4_ifg0_npu_rxpp_fwd_post_npe_dropped_packets_due_destination {
      type oc-yang:counter64;
      description
        "nan";
    }
    leaf counters_slice4_ifg0_npu_rxpp_fwd_post_npe_dropped_packets_due_dummy {
      type oc-yang:counter64;
      description
        "nan";
    }
    leaf counters_slice4_ifg0_npu_rxpp_fwd_post_npe_dropped_packets_due_ecc {
      type oc-yang:counter64;
      description
        "nan";
    }
    leaf counters_slice4_ifg0_npu_rxpp_fwd_post_npe_dropped_packets_due_err_flag {
      type oc-yang:counter64;
      description
        "nan";
    }
    leaf counters_slice4_ifg0_npu_rxpp_fwd_post_npe_dropped_packets_due_frag_parity_error {
      type oc-yang:counter64;
      description
        "nan";
    }
    leaf counters_slice4_ifg0_npu_txpp_hw_editor_1_packets_with_error_bit {
      type oc-yang:counter64;
      description
        "Counts number of packet leaving HW Editor 1 inst 0 have error bit assered";
    }
    leaf counters_slice4_ifg0_npu_txpp_hw_editor_2_packets_with_error_bit {
      type oc-yang:counter64;
      description
        "Counts number of packet leaving HW Editor 2 towards ifg0 have error bit assered";
    }
    leaf counters_slice4_ifg0_npu_txpp_npe_packets_with_error_bit {
      type oc-yang:counter64;
      description
        "Counts number of packet leaving NPE 0 have error bit assered";
    }
    leaf counters_slice4_ifg0_npu_txpp_preprocess_packets_with_error_bit {
      type oc-yang:counter64;
      description
        "Counts number of packet leaving preprocessing 0 have error bit assered";
    }
    leaf counters_slice4_ifg1_ifgb_rx_cgm_0_csms_dropped_packets {
      type oc-yang:counter64;
      description
        "RX CSMS packets drop counter.";
    }
    leaf counters_slice4_ifg1_ifgb_rx_cgm_0_frm_dropped_packets {
      type oc-yang:counter64;
      description
        "RX FRM packets drop counter.";
    }
    leaf counters_slice4_ifg1_ifgb_rx_cgm_0_fte_dropped_packets {
      type oc-yang:counter64;
      description
        "RX FTE packets drop counter.";
    }
    leaf counters_slice4_ifg1_ifgb_rx_cgm_1_csms_dropped_packets {
      type oc-yang:counter64;
      description
        "RX CSMS packets drop counter.";
    }
    leaf counters_slice4_ifg1_ifgb_rx_cgm_1_frm_dropped_packets {
      type oc-yang:counter64;
      description
        "RX FRM packets drop counter.";
    }
    leaf counters_slice4_ifg1_ifgb_rx_cgm_1_fte_dropped_packets {
      type oc-yang:counter64;
      description
        "RX FTE packets drop counter.";
    }
    leaf counters_slice4_ifg1_ifgb_rx_cgm_2_csms_dropped_packets {
      type oc-yang:counter64;
      description
        "RX CSMS packets drop counter.";
    }
    leaf counters_slice4_ifg1_ifgb_rx_cgm_2_frm_dropped_packets {
      type oc-yang:counter64;
      description
        "RX FRM packets drop counter.";
    }
    leaf counters_slice4_ifg1_ifgb_rx_cgm_2_fte_dropped_packets {
      type oc-yang:counter64;
      description
        "RX FTE packets drop counter.";
    }
    leaf counters_slice4_ifg1_ifgb_rx_cgm_3_csms_dropped_packets {
      type oc-yang:counter64;
      description
        "RX CSMS packets drop counter.";
    }
    leaf counters_slice4_ifg1_ifgb_rx_cgm_3_frm_dropped_packets {
      type oc-yang:counter64;
      description
        "RX FRM packets drop counter.";
    }
    leaf counters_slice4_ifg1_ifgb_rx_cgm_3_fte_dropped_packets {
      type oc-yang:counter64;
      description
        "RX FTE packets drop counter.";
    }
    leaf counters_slice4_ifg1_ifgb_rx_port_0_oobe_crc_errors {
      type oc-yang:counter64;
      description
        "OOB Extract CRC error counter per port";
    }
    leaf counters_slice4_ifg1_ifgb_rx_port_0_undersized_dropped_packets {
      type oc-yang:counter64;
      description
        "Counter for packets that were dropped because they were smaller than 64B.";
    }
    leaf counters_slice4_ifg1_ifgb_rx_port_1_oobe_crc_errors {
      type oc-yang:counter64;
      description
        "OOB Extract CRC error counter per port";
    }
    leaf counters_slice4_ifg1_ifgb_rx_port_1_undersized_dropped_packets {
      type oc-yang:counter64;
      description
        "Counter for packets that were dropped because they were smaller than 64B.";
    }
    leaf counters_slice4_ifg1_ifgb_rx_port_10_oobe_crc_errors {
      type oc-yang:counter64;
      description
        "OOB Extract CRC error counter per port";
    }
    leaf counters_slice4_ifg1_ifgb_rx_port_10_undersized_dropped_packets {
      type oc-yang:counter64;
      description
        "Counter for packets that were dropped because they were smaller than 64B.";
    }
    leaf counters_slice4_ifg1_ifgb_rx_port_11_oobe_crc_errors {
      type oc-yang:counter64;
      description
        "OOB Extract CRC error counter per port";
    }
    leaf counters_slice4_ifg1_ifgb_rx_port_11_undersized_dropped_packets {
      type oc-yang:counter64;
      description
        "Counter for packets that were dropped because they were smaller than 64B.";
    }
    leaf counters_slice4_ifg1_ifgb_rx_port_12_oobe_crc_errors {
      type oc-yang:counter64;
      description
        "OOB Extract CRC error counter per port";
    }
    leaf counters_slice4_ifg1_ifgb_rx_port_12_undersized_dropped_packets {
      type oc-yang:counter64;
      description
        "Counter for packets that were dropped because they were smaller than 64B.";
    }
    leaf counters_slice4_ifg1_ifgb_rx_port_13_oobe_crc_errors {
      type oc-yang:counter64;
      description
        "OOB Extract CRC error counter per port";
    }
    leaf counters_slice4_ifg1_ifgb_rx_port_13_undersized_dropped_packets {
      type oc-yang:counter64;
      description
        "Counter for packets that were dropped because they were smaller than 64B.";
    }
    leaf counters_slice4_ifg1_ifgb_rx_port_14_oobe_crc_errors {
      type oc-yang:counter64;
      description
        "OOB Extract CRC error counter per port";
    }
    leaf counters_slice4_ifg1_ifgb_rx_port_14_undersized_dropped_packets {
      type oc-yang:counter64;
      description
        "Counter for packets that were dropped because they were smaller than 64B.";
    }
    leaf counters_slice4_ifg1_ifgb_rx_port_15_oobe_crc_errors {
      type oc-yang:counter64;
      description
        "OOB Extract CRC error counter per port";
    }
    leaf counters_slice4_ifg1_ifgb_rx_port_15_undersized_dropped_packets {
      type oc-yang:counter64;
      description
        "Counter for packets that were dropped because they were smaller than 64B.";
    }
    leaf counters_slice4_ifg1_ifgb_rx_port_16_undersized_dropped_packets {
      type oc-yang:counter64;
      description
        "Counter for packets that were dropped because they were smaller than 64B.";
    }
    leaf counters_slice4_ifg1_ifgb_rx_port_17_undersized_dropped_packets {
      type oc-yang:counter64;
      description
        "Counter for packets that were dropped because they were smaller than 64B.";
    }
    leaf counters_slice4_ifg1_ifgb_rx_port_18_undersized_dropped_packets {
      type oc-yang:counter64;
      description
        "Counter for packets that were dropped because they were smaller than 64B.";
    }
    leaf counters_slice4_ifg1_ifgb_rx_port_19_undersized_dropped_packets {
      type oc-yang:counter64;
      description
        "Counter for packets that were dropped because they were smaller than 64B.";
    }
    leaf counters_slice4_ifg1_ifgb_rx_port_2_oobe_crc_errors {
      type oc-yang:counter64;
      description
        "OOB Extract CRC error counter per port";
    }
    leaf counters_slice4_ifg1_ifgb_rx_port_2_undersized_dropped_packets {
      type oc-yang:counter64;
      description
        "Counter for packets that were dropped because they were smaller than 64B.";
    }
    leaf counters_slice4_ifg1_ifgb_rx_port_20_undersized_dropped_packets {
      type oc-yang:counter64;
      description
        "Counter for packets that were dropped because they were smaller than 64B.";
    }
    leaf counters_slice4_ifg1_ifgb_rx_port_21_undersized_dropped_packets {
      type oc-yang:counter64;
      description
        "Counter for packets that were dropped because they were smaller than 64B.";
    }
    leaf counters_slice4_ifg1_ifgb_rx_port_22_undersized_dropped_packets {
      type oc-yang:counter64;
      description
        "Counter for packets that were dropped because they were smaller than 64B.";
    }
    leaf counters_slice4_ifg1_ifgb_rx_port_23_undersized_dropped_packets {
      type oc-yang:counter64;
      description
        "Counter for packets that were dropped because they were smaller than 64B.";
    }
    leaf counters_slice4_ifg1_ifgb_rx_port_24_undersized_dropped_packets {
      type oc-yang:counter64;
      description
        "Counter for packets that were dropped because they were smaller than 64B.";
    }
    leaf counters_slice4_ifg1_ifgb_rx_port_25_undersized_dropped_packets {
      type oc-yang:counter64;
      description
        "Counter for packets that were dropped because they were smaller than 64B.";
    }
    leaf counters_slice4_ifg1_ifgb_rx_port_26_undersized_dropped_packets {
      type oc-yang:counter64;
      description
        "Counter for packets that were dropped because they were smaller than 64B.";
    }
    leaf counters_slice4_ifg1_ifgb_rx_port_27_undersized_dropped_packets {
      type oc-yang:counter64;
      description
        "Counter for packets that were dropped because they were smaller than 64B.";
    }
    leaf counters_slice4_ifg1_ifgb_rx_port_28_undersized_dropped_packets {
      type oc-yang:counter64;
      description
        "Counter for packets that were dropped because they were smaller than 64B.";
    }
    leaf counters_slice4_ifg1_ifgb_rx_port_29_undersized_dropped_packets {
      type oc-yang:counter64;
      description
        "Counter for packets that were dropped because they were smaller than 64B.";
    }
    leaf counters_slice4_ifg1_ifgb_rx_port_3_oobe_crc_errors {
      type oc-yang:counter64;
      description
        "OOB Extract CRC error counter per port";
    }
    leaf counters_slice4_ifg1_ifgb_rx_port_3_undersized_dropped_packets {
      type oc-yang:counter64;
      description
        "Counter for packets that were dropped because they were smaller than 64B.";
    }
    leaf counters_slice4_ifg1_ifgb_rx_port_30_undersized_dropped_packets {
      type oc-yang:counter64;
      description
        "Counter for packets that were dropped because they were smaller than 64B.";
    }
    leaf counters_slice4_ifg1_ifgb_rx_port_31_undersized_dropped_packets {
      type oc-yang:counter64;
      description
        "Counter for packets that were dropped because they were smaller than 64B.";
    }
    leaf counters_slice4_ifg1_ifgb_rx_port_4_oobe_crc_errors {
      type oc-yang:counter64;
      description
        "OOB Extract CRC error counter per port";
    }
    leaf counters_slice4_ifg1_ifgb_rx_port_4_undersized_dropped_packets {
      type oc-yang:counter64;
      description
        "Counter for packets that were dropped because they were smaller than 64B.";
    }
    leaf counters_slice4_ifg1_ifgb_rx_port_5_oobe_crc_errors {
      type oc-yang:counter64;
      description
        "OOB Extract CRC error counter per port";
    }
    leaf counters_slice4_ifg1_ifgb_rx_port_5_undersized_dropped_packets {
      type oc-yang:counter64;
      description
        "Counter for packets that were dropped because they were smaller than 64B.";
    }
    leaf counters_slice4_ifg1_ifgb_rx_port_6_oobe_crc_errors {
      type oc-yang:counter64;
      description
        "OOB Extract CRC error counter per port";
    }
    leaf counters_slice4_ifg1_ifgb_rx_port_6_undersized_dropped_packets {
      type oc-yang:counter64;
      description
        "Counter for packets that were dropped because they were smaller than 64B.";
    }
    leaf counters_slice4_ifg1_ifgb_rx_port_7_oobe_crc_errors {
      type oc-yang:counter64;
      description
        "OOB Extract CRC error counter per port";
    }
    leaf counters_slice4_ifg1_ifgb_rx_port_7_undersized_dropped_packets {
      type oc-yang:counter64;
      description
        "Counter for packets that were dropped because they were smaller than 64B.";
    }
    leaf counters_slice4_ifg1_ifgb_rx_port_8_oobe_crc_errors {
      type oc-yang:counter64;
      description
        "OOB Extract CRC error counter per port";
    }
    leaf counters_slice4_ifg1_ifgb_rx_port_8_undersized_dropped_packets {
      type oc-yang:counter64;
      description
        "Counter for packets that were dropped because they were smaller than 64B.";
    }
    leaf counters_slice4_ifg1_ifgb_rx_port_9_oobe_crc_errors {
      type oc-yang:counter64;
      description
        "OOB Extract CRC error counter per port";
    }
    leaf counters_slice4_ifg1_ifgb_rx_port_9_undersized_dropped_packets {
      type oc-yang:counter64;
      description
        "Counter for packets that were dropped because they were smaller than 64B.";
    }
    leaf counters_slice4_ifg1_ifgb_rx_protection_dropped_fragments {
      type oc-yang:counter64;
      description
        "RXPP interface protection fragments drop counter.";
    }
    leaf counters_slice4_ifg1_ifgb_rx_protection_dropped_packets {
      type oc-yang:counter64;
      description
        "RXPP interface protection packet drop counter.";
    }
    leaf counters_slice4_ifg1_ifgbi_recycle_in_band_extract_npu_host_re_direct_drop {
      type oc-yang:counter64;
      description
        "InBand Extract NPU Host ReDirect drop counter. Increments based on the RcyDropCntrsCfg.";
    }
    leaf counters_slice4_ifg1_ifgbi_recycle_in_band_extract_packet_dma_re_direct_drop {
      type oc-yang:counter64;
      description
        "InBand Extract Pkt DMA ReDirect drop counter. Increments based on the RcyDropCntrsCfg.";
    }
    leaf counters_slice4_ifg1_npu_rxpp_fwd_post_npe_dropped_packets {
      type oc-yang:counter64;
      description
        "Counts packets dropped by the rxpp";
    }
    leaf counters_slice4_ifg1_npu_rxpp_fwd_post_npe_dropped_packets_due_destination {
      type oc-yang:counter64;
      description
        "nan";
    }
    leaf counters_slice4_ifg1_npu_rxpp_fwd_post_npe_dropped_packets_due_dummy {
      type oc-yang:counter64;
      description
        "nan";
    }
    leaf counters_slice4_ifg1_npu_rxpp_fwd_post_npe_dropped_packets_due_ecc {
      type oc-yang:counter64;
      description
        "nan";
    }
    leaf counters_slice4_ifg1_npu_rxpp_fwd_post_npe_dropped_packets_due_err_flag {
      type oc-yang:counter64;
      description
        "nan";
    }
    leaf counters_slice4_ifg1_npu_rxpp_fwd_post_npe_dropped_packets_due_frag_parity_error {
      type oc-yang:counter64;
      description
        "nan";
    }
    leaf counters_slice4_ifg1_npu_txpp_hw_editor_1_packets_with_error_bit {
      type oc-yang:counter64;
      description
        "Counts number of packet leaving HW Editor 1 inst 1 have error bit assered";
    }
    leaf counters_slice4_ifg1_npu_txpp_hw_editor_2_packets_with_error_bit {
      type oc-yang:counter64;
      description
        "Counts number of packet leaving HW Editor 2 towards ifg1 have error bit assered";
    }
    leaf counters_slice4_ifg1_npu_txpp_npe_packets_with_error_bit {
      type oc-yang:counter64;
      description
        "Counts number of packet leaving NPE 1 have error bit assered";
    }
    leaf counters_slice4_ifg1_npu_txpp_preprocess_packets_with_error_bit {
      type oc-yang:counter64;
      description
        "Counts number of packet leaving preprocessing 1 have error bit assered";
    }
    leaf counters_slice5_cluster0_ene_outgoing_headers_with_errors {
      type oc-yang:counter64;
      description
        "Number of headers Exiting the ENE with Error bit on";
    }
    leaf counters_slice5_cluster1_ene_outgoing_headers_with_errors {
      type oc-yang:counter64;
      description
        "Number of headers Exiting the ENE with Error bit on";
    }
    leaf counters_slice5_fllb_debug_register_dropped_p_ds {
      type oc-yang:counter64;
      description
        "Number of PDs dropped due to no eligible links";
    }
    leaf counters_slice5_ifg0_ifgb_rx_cgm_0_csms_dropped_packets {
      type oc-yang:counter64;
      description
        "RX CSMS packets drop counter.";
    }
    leaf counters_slice5_ifg0_ifgb_rx_cgm_0_frm_dropped_packets {
      type oc-yang:counter64;
      description
        "RX FRM packets drop counter.";
    }
    leaf counters_slice5_ifg0_ifgb_rx_cgm_0_fte_dropped_packets {
      type oc-yang:counter64;
      description
        "RX FTE packets drop counter.";
    }
    leaf counters_slice5_ifg0_ifgb_rx_cgm_1_csms_dropped_packets {
      type oc-yang:counter64;
      description
        "RX CSMS packets drop counter.";
    }
    leaf counters_slice5_ifg0_ifgb_rx_cgm_1_frm_dropped_packets {
      type oc-yang:counter64;
      description
        "RX FRM packets drop counter.";
    }
    leaf counters_slice5_ifg0_ifgb_rx_cgm_1_fte_dropped_packets {
      type oc-yang:counter64;
      description
        "RX FTE packets drop counter.";
    }
    leaf counters_slice5_ifg0_ifgb_rx_cgm_2_csms_dropped_packets {
      type oc-yang:counter64;
      description
        "RX CSMS packets drop counter.";
    }
    leaf counters_slice5_ifg0_ifgb_rx_cgm_2_frm_dropped_packets {
      type oc-yang:counter64;
      description
        "RX FRM packets drop counter.";
    }
    leaf counters_slice5_ifg0_ifgb_rx_cgm_2_fte_dropped_packets {
      type oc-yang:counter64;
      description
        "RX FTE packets drop counter.";
    }
    leaf counters_slice5_ifg0_ifgb_rx_cgm_3_csms_dropped_packets {
      type oc-yang:counter64;
      description
        "RX CSMS packets drop counter.";
    }
    leaf counters_slice5_ifg0_ifgb_rx_cgm_3_frm_dropped_packets {
      type oc-yang:counter64;
      description
        "RX FRM packets drop counter.";
    }
    leaf counters_slice5_ifg0_ifgb_rx_cgm_3_fte_dropped_packets {
      type oc-yang:counter64;
      description
        "RX FTE packets drop counter.";
    }
    leaf counters_slice5_ifg0_ifgb_rx_port_0_oobe_crc_errors {
      type oc-yang:counter64;
      description
        "OOB Extract CRC error counter per port";
    }
    leaf counters_slice5_ifg0_ifgb_rx_port_0_undersized_dropped_packets {
      type oc-yang:counter64;
      description
        "Counter for packets that were dropped because they were smaller than 64B.";
    }
    leaf counters_slice5_ifg0_ifgb_rx_port_1_oobe_crc_errors {
      type oc-yang:counter64;
      description
        "OOB Extract CRC error counter per port";
    }
    leaf counters_slice5_ifg0_ifgb_rx_port_1_undersized_dropped_packets {
      type oc-yang:counter64;
      description
        "Counter for packets that were dropped because they were smaller than 64B.";
    }
    leaf counters_slice5_ifg0_ifgb_rx_port_10_oobe_crc_errors {
      type oc-yang:counter64;
      description
        "OOB Extract CRC error counter per port";
    }
    leaf counters_slice5_ifg0_ifgb_rx_port_10_undersized_dropped_packets {
      type oc-yang:counter64;
      description
        "Counter for packets that were dropped because they were smaller than 64B.";
    }
    leaf counters_slice5_ifg0_ifgb_rx_port_11_oobe_crc_errors {
      type oc-yang:counter64;
      description
        "OOB Extract CRC error counter per port";
    }
    leaf counters_slice5_ifg0_ifgb_rx_port_11_undersized_dropped_packets {
      type oc-yang:counter64;
      description
        "Counter for packets that were dropped because they were smaller than 64B.";
    }
    leaf counters_slice5_ifg0_ifgb_rx_port_12_oobe_crc_errors {
      type oc-yang:counter64;
      description
        "OOB Extract CRC error counter per port";
    }
    leaf counters_slice5_ifg0_ifgb_rx_port_12_undersized_dropped_packets {
      type oc-yang:counter64;
      description
        "Counter for packets that were dropped because they were smaller than 64B.";
    }
    leaf counters_slice5_ifg0_ifgb_rx_port_13_oobe_crc_errors {
      type oc-yang:counter64;
      description
        "OOB Extract CRC error counter per port";
    }
    leaf counters_slice5_ifg0_ifgb_rx_port_13_undersized_dropped_packets {
      type oc-yang:counter64;
      description
        "Counter for packets that were dropped because they were smaller than 64B.";
    }
    leaf counters_slice5_ifg0_ifgb_rx_port_14_oobe_crc_errors {
      type oc-yang:counter64;
      description
        "OOB Extract CRC error counter per port";
    }
    leaf counters_slice5_ifg0_ifgb_rx_port_14_undersized_dropped_packets {
      type oc-yang:counter64;
      description
        "Counter for packets that were dropped because they were smaller than 64B.";
    }
    leaf counters_slice5_ifg0_ifgb_rx_port_15_oobe_crc_errors {
      type oc-yang:counter64;
      description
        "OOB Extract CRC error counter per port";
    }
    leaf counters_slice5_ifg0_ifgb_rx_port_15_undersized_dropped_packets {
      type oc-yang:counter64;
      description
        "Counter for packets that were dropped because they were smaller than 64B.";
    }
    leaf counters_slice5_ifg0_ifgb_rx_port_16_undersized_dropped_packets {
      type oc-yang:counter64;
      description
        "Counter for packets that were dropped because they were smaller than 64B.";
    }
    leaf counters_slice5_ifg0_ifgb_rx_port_17_undersized_dropped_packets {
      type oc-yang:counter64;
      description
        "Counter for packets that were dropped because they were smaller than 64B.";
    }
    leaf counters_slice5_ifg0_ifgb_rx_port_18_undersized_dropped_packets {
      type oc-yang:counter64;
      description
        "Counter for packets that were dropped because they were smaller than 64B.";
    }
    leaf counters_slice5_ifg0_ifgb_rx_port_19_undersized_dropped_packets {
      type oc-yang:counter64;
      description
        "Counter for packets that were dropped because they were smaller than 64B.";
    }
    leaf counters_slice5_ifg0_ifgb_rx_port_2_oobe_crc_errors {
      type oc-yang:counter64;
      description
        "OOB Extract CRC error counter per port";
    }
    leaf counters_slice5_ifg0_ifgb_rx_port_2_undersized_dropped_packets {
      type oc-yang:counter64;
      description
        "Counter for packets that were dropped because they were smaller than 64B.";
    }
    leaf counters_slice5_ifg0_ifgb_rx_port_20_undersized_dropped_packets {
      type oc-yang:counter64;
      description
        "Counter for packets that were dropped because they were smaller than 64B.";
    }
    leaf counters_slice5_ifg0_ifgb_rx_port_21_undersized_dropped_packets {
      type oc-yang:counter64;
      description
        "Counter for packets that were dropped because they were smaller than 64B.";
    }
    leaf counters_slice5_ifg0_ifgb_rx_port_22_undersized_dropped_packets {
      type oc-yang:counter64;
      description
        "Counter for packets that were dropped because they were smaller than 64B.";
    }
    leaf counters_slice5_ifg0_ifgb_rx_port_23_undersized_dropped_packets {
      type oc-yang:counter64;
      description
        "Counter for packets that were dropped because they were smaller than 64B.";
    }
    leaf counters_slice5_ifg0_ifgb_rx_port_24_undersized_dropped_packets {
      type oc-yang:counter64;
      description
        "Counter for packets that were dropped because they were smaller than 64B.";
    }
    leaf counters_slice5_ifg0_ifgb_rx_port_25_undersized_dropped_packets {
      type oc-yang:counter64;
      description
        "Counter for packets that were dropped because they were smaller than 64B.";
    }
    leaf counters_slice5_ifg0_ifgb_rx_port_26_undersized_dropped_packets {
      type oc-yang:counter64;
      description
        "Counter for packets that were dropped because they were smaller than 64B.";
    }
    leaf counters_slice5_ifg0_ifgb_rx_port_27_undersized_dropped_packets {
      type oc-yang:counter64;
      description
        "Counter for packets that were dropped because they were smaller than 64B.";
    }
    leaf counters_slice5_ifg0_ifgb_rx_port_28_undersized_dropped_packets {
      type oc-yang:counter64;
      description
        "Counter for packets that were dropped because they were smaller than 64B.";
    }
    leaf counters_slice5_ifg0_ifgb_rx_port_29_undersized_dropped_packets {
      type oc-yang:counter64;
      description
        "Counter for packets that were dropped because they were smaller than 64B.";
    }
    leaf counters_slice5_ifg0_ifgb_rx_port_3_oobe_crc_errors {
      type oc-yang:counter64;
      description
        "OOB Extract CRC error counter per port";
    }
    leaf counters_slice5_ifg0_ifgb_rx_port_3_undersized_dropped_packets {
      type oc-yang:counter64;
      description
        "Counter for packets that were dropped because they were smaller than 64B.";
    }
    leaf counters_slice5_ifg0_ifgb_rx_port_30_undersized_dropped_packets {
      type oc-yang:counter64;
      description
        "Counter for packets that were dropped because they were smaller than 64B.";
    }
    leaf counters_slice5_ifg0_ifgb_rx_port_31_undersized_dropped_packets {
      type oc-yang:counter64;
      description
        "Counter for packets that were dropped because they were smaller than 64B.";
    }
    leaf counters_slice5_ifg0_ifgb_rx_port_4_oobe_crc_errors {
      type oc-yang:counter64;
      description
        "OOB Extract CRC error counter per port";
    }
    leaf counters_slice5_ifg0_ifgb_rx_port_4_undersized_dropped_packets {
      type oc-yang:counter64;
      description
        "Counter for packets that were dropped because they were smaller than 64B.";
    }
    leaf counters_slice5_ifg0_ifgb_rx_port_5_oobe_crc_errors {
      type oc-yang:counter64;
      description
        "OOB Extract CRC error counter per port";
    }
    leaf counters_slice5_ifg0_ifgb_rx_port_5_undersized_dropped_packets {
      type oc-yang:counter64;
      description
        "Counter for packets that were dropped because they were smaller than 64B.";
    }
    leaf counters_slice5_ifg0_ifgb_rx_port_6_oobe_crc_errors {
      type oc-yang:counter64;
      description
        "OOB Extract CRC error counter per port";
    }
    leaf counters_slice5_ifg0_ifgb_rx_port_6_undersized_dropped_packets {
      type oc-yang:counter64;
      description
        "Counter for packets that were dropped because they were smaller than 64B.";
    }
    leaf counters_slice5_ifg0_ifgb_rx_port_7_oobe_crc_errors {
      type oc-yang:counter64;
      description
        "OOB Extract CRC error counter per port";
    }
    leaf counters_slice5_ifg0_ifgb_rx_port_7_undersized_dropped_packets {
      type oc-yang:counter64;
      description
        "Counter for packets that were dropped because they were smaller than 64B.";
    }
    leaf counters_slice5_ifg0_ifgb_rx_port_8_oobe_crc_errors {
      type oc-yang:counter64;
      description
        "OOB Extract CRC error counter per port";
    }
    leaf counters_slice5_ifg0_ifgb_rx_port_8_undersized_dropped_packets {
      type oc-yang:counter64;
      description
        "Counter for packets that were dropped because they were smaller than 64B.";
    }
    leaf counters_slice5_ifg0_ifgb_rx_port_9_oobe_crc_errors {
      type oc-yang:counter64;
      description
        "OOB Extract CRC error counter per port";
    }
    leaf counters_slice5_ifg0_ifgb_rx_port_9_undersized_dropped_packets {
      type oc-yang:counter64;
      description
        "Counter for packets that were dropped because they were smaller than 64B.";
    }
    leaf counters_slice5_ifg0_ifgb_rx_protection_dropped_fragments {
      type oc-yang:counter64;
      description
        "RXPP interface protection fragments drop counter.";
    }
    leaf counters_slice5_ifg0_ifgb_rx_protection_dropped_packets {
      type oc-yang:counter64;
      description
        "RXPP interface protection packet drop counter.";
    }
    leaf counters_slice5_ifg0_ifgbi_recycle_in_band_extract_npu_host_re_direct_drop {
      type oc-yang:counter64;
      description
        "InBand Extract NPU Host ReDirect drop counter. Increments based on the RcyDropCntrsCfg.";
    }
    leaf counters_slice5_ifg0_ifgbi_recycle_in_band_extract_packet_dma_re_direct_drop {
      type oc-yang:counter64;
      description
        "InBand Extract Pkt DMA ReDirect drop counter. Increments based on the RcyDropCntrsCfg.";
    }
    leaf counters_slice5_ifg0_npu_rxpp_fwd_post_npe_dropped_packets {
      type oc-yang:counter64;
      description
        "Counts packets dropped by the rxpp";
    }
    leaf counters_slice5_ifg0_npu_rxpp_fwd_post_npe_dropped_packets_due_destination {
      type oc-yang:counter64;
      description
        "nan";
    }
    leaf counters_slice5_ifg0_npu_rxpp_fwd_post_npe_dropped_packets_due_dummy {
      type oc-yang:counter64;
      description
        "nan";
    }
    leaf counters_slice5_ifg0_npu_rxpp_fwd_post_npe_dropped_packets_due_ecc {
      type oc-yang:counter64;
      description
        "nan";
    }
    leaf counters_slice5_ifg0_npu_rxpp_fwd_post_npe_dropped_packets_due_err_flag {
      type oc-yang:counter64;
      description
        "nan";
    }
    leaf counters_slice5_ifg0_npu_rxpp_fwd_post_npe_dropped_packets_due_frag_parity_error {
      type oc-yang:counter64;
      description
        "nan";
    }
    leaf counters_slice5_ifg0_npu_txpp_hw_editor_1_packets_with_error_bit {
      type oc-yang:counter64;
      description
        "Counts number of packet leaving HW Editor 1 inst 0 have error bit assered";
    }
    leaf counters_slice5_ifg0_npu_txpp_hw_editor_2_packets_with_error_bit {
      type oc-yang:counter64;
      description
        "Counts number of packet leaving HW Editor 2 towards ifg0 have error bit assered";
    }
    leaf counters_slice5_ifg0_npu_txpp_npe_packets_with_error_bit {
      type oc-yang:counter64;
      description
        "Counts number of packet leaving NPE 0 have error bit assered";
    }
    leaf counters_slice5_ifg0_npu_txpp_preprocess_packets_with_error_bit {
      type oc-yang:counter64;
      description
        "Counts number of packet leaving preprocessing 0 have error bit assered";
    }
    leaf counters_slice5_ifg1_ifgb_rx_cgm_0_csms_dropped_packets {
      type oc-yang:counter64;
      description
        "RX CSMS packets drop counter.";
    }
    leaf counters_slice5_ifg1_ifgb_rx_cgm_0_frm_dropped_packets {
      type oc-yang:counter64;
      description
        "RX FRM packets drop counter.";
    }
    leaf counters_slice5_ifg1_ifgb_rx_cgm_0_fte_dropped_packets {
      type oc-yang:counter64;
      description
        "RX FTE packets drop counter.";
    }
    leaf counters_slice5_ifg1_ifgb_rx_cgm_1_csms_dropped_packets {
      type oc-yang:counter64;
      description
        "RX CSMS packets drop counter.";
    }
    leaf counters_slice5_ifg1_ifgb_rx_cgm_1_frm_dropped_packets {
      type oc-yang:counter64;
      description
        "RX FRM packets drop counter.";
    }
    leaf counters_slice5_ifg1_ifgb_rx_cgm_1_fte_dropped_packets {
      type oc-yang:counter64;
      description
        "RX FTE packets drop counter.";
    }
    leaf counters_slice5_ifg1_ifgb_rx_cgm_2_csms_dropped_packets {
      type oc-yang:counter64;
      description
        "RX CSMS packets drop counter.";
    }
    leaf counters_slice5_ifg1_ifgb_rx_cgm_2_frm_dropped_packets {
      type oc-yang:counter64;
      description
        "RX FRM packets drop counter.";
    }
    leaf counters_slice5_ifg1_ifgb_rx_cgm_2_fte_dropped_packets {
      type oc-yang:counter64;
      description
        "RX FTE packets drop counter.";
    }
    leaf counters_slice5_ifg1_ifgb_rx_cgm_3_csms_dropped_packets {
      type oc-yang:counter64;
      description
        "RX CSMS packets drop counter.";
    }
    leaf counters_slice5_ifg1_ifgb_rx_cgm_3_frm_dropped_packets {
      type oc-yang:counter64;
      description
        "RX FRM packets drop counter.";
    }
    leaf counters_slice5_ifg1_ifgb_rx_cgm_3_fte_dropped_packets {
      type oc-yang:counter64;
      description
        "RX FTE packets drop counter.";
    }
    leaf counters_slice5_ifg1_ifgb_rx_port_0_oobe_crc_errors {
      type oc-yang:counter64;
      description
        "OOB Extract CRC error counter per port";
    }
    leaf counters_slice5_ifg1_ifgb_rx_port_0_undersized_dropped_packets {
      type oc-yang:counter64;
      description
        "Counter for packets that were dropped because they were smaller than 64B.";
    }
    leaf counters_slice5_ifg1_ifgb_rx_port_1_oobe_crc_errors {
      type oc-yang:counter64;
      description
        "OOB Extract CRC error counter per port";
    }
    leaf counters_slice5_ifg1_ifgb_rx_port_1_undersized_dropped_packets {
      type oc-yang:counter64;
      description
        "Counter for packets that were dropped because they were smaller than 64B.";
    }
    leaf counters_slice5_ifg1_ifgb_rx_port_10_oobe_crc_errors {
      type oc-yang:counter64;
      description
        "OOB Extract CRC error counter per port";
    }
    leaf counters_slice5_ifg1_ifgb_rx_port_10_undersized_dropped_packets {
      type oc-yang:counter64;
      description
        "Counter for packets that were dropped because they were smaller than 64B.";
    }
    leaf counters_slice5_ifg1_ifgb_rx_port_11_oobe_crc_errors {
      type oc-yang:counter64;
      description
        "OOB Extract CRC error counter per port";
    }
    leaf counters_slice5_ifg1_ifgb_rx_port_11_undersized_dropped_packets {
      type oc-yang:counter64;
      description
        "Counter for packets that were dropped because they were smaller than 64B.";
    }
    leaf counters_slice5_ifg1_ifgb_rx_port_12_oobe_crc_errors {
      type oc-yang:counter64;
      description
        "OOB Extract CRC error counter per port";
    }
    leaf counters_slice5_ifg1_ifgb_rx_port_12_undersized_dropped_packets {
      type oc-yang:counter64;
      description
        "Counter for packets that were dropped because they were smaller than 64B.";
    }
    leaf counters_slice5_ifg1_ifgb_rx_port_13_oobe_crc_errors {
      type oc-yang:counter64;
      description
        "OOB Extract CRC error counter per port";
    }
    leaf counters_slice5_ifg1_ifgb_rx_port_13_undersized_dropped_packets {
      type oc-yang:counter64;
      description
        "Counter for packets that were dropped because they were smaller than 64B.";
    }
    leaf counters_slice5_ifg1_ifgb_rx_port_14_oobe_crc_errors {
      type oc-yang:counter64;
      description
        "OOB Extract CRC error counter per port";
    }
    leaf counters_slice5_ifg1_ifgb_rx_port_14_undersized_dropped_packets {
      type oc-yang:counter64;
      description
        "Counter for packets that were dropped because they were smaller than 64B.";
    }
    leaf counters_slice5_ifg1_ifgb_rx_port_15_oobe_crc_errors {
      type oc-yang:counter64;
      description
        "OOB Extract CRC error counter per port";
    }
    leaf counters_slice5_ifg1_ifgb_rx_port_15_undersized_dropped_packets {
      type oc-yang:counter64;
      description
        "Counter for packets that were dropped because they were smaller than 64B.";
    }
    leaf counters_slice5_ifg1_ifgb_rx_port_16_undersized_dropped_packets {
      type oc-yang:counter64;
      description
        "Counter for packets that were dropped because they were smaller than 64B.";
    }
    leaf counters_slice5_ifg1_ifgb_rx_port_17_undersized_dropped_packets {
      type oc-yang:counter64;
      description
        "Counter for packets that were dropped because they were smaller than 64B.";
    }
    leaf counters_slice5_ifg1_ifgb_rx_port_18_undersized_dropped_packets {
      type oc-yang:counter64;
      description
        "Counter for packets that were dropped because they were smaller than 64B.";
    }
    leaf counters_slice5_ifg1_ifgb_rx_port_19_undersized_dropped_packets {
      type oc-yang:counter64;
      description
        "Counter for packets that were dropped because they were smaller than 64B.";
    }
    leaf counters_slice5_ifg1_ifgb_rx_port_2_oobe_crc_errors {
      type oc-yang:counter64;
      description
        "OOB Extract CRC error counter per port";
    }
    leaf counters_slice5_ifg1_ifgb_rx_port_2_undersized_dropped_packets {
      type oc-yang:counter64;
      description
        "Counter for packets that were dropped because they were smaller than 64B.";
    }
    leaf counters_slice5_ifg1_ifgb_rx_port_20_undersized_dropped_packets {
      type oc-yang:counter64;
      description
        "Counter for packets that were dropped because they were smaller than 64B.";
    }
    leaf counters_slice5_ifg1_ifgb_rx_port_21_undersized_dropped_packets {
      type oc-yang:counter64;
      description
        "Counter for packets that were dropped because they were smaller than 64B.";
    }
    leaf counters_slice5_ifg1_ifgb_rx_port_22_undersized_dropped_packets {
      type oc-yang:counter64;
      description
        "Counter for packets that were dropped because they were smaller than 64B.";
    }
    leaf counters_slice5_ifg1_ifgb_rx_port_23_undersized_dropped_packets {
      type oc-yang:counter64;
      description
        "Counter for packets that were dropped because they were smaller than 64B.";
    }
    leaf counters_slice5_ifg1_ifgb_rx_port_24_undersized_dropped_packets {
      type oc-yang:counter64;
      description
        "Counter for packets that were dropped because they were smaller than 64B.";
    }
    leaf counters_slice5_ifg1_ifgb_rx_port_25_undersized_dropped_packets {
      type oc-yang:counter64;
      description
        "Counter for packets that were dropped because they were smaller than 64B.";
    }
    leaf counters_slice5_ifg1_ifgb_rx_port_26_undersized_dropped_packets {
      type oc-yang:counter64;
      description
        "Counter for packets that were dropped because they were smaller than 64B.";
    }
    leaf counters_slice5_ifg1_ifgb_rx_port_27_undersized_dropped_packets {
      type oc-yang:counter64;
      description
        "Counter for packets that were dropped because they were smaller than 64B.";
    }
    leaf counters_slice5_ifg1_ifgb_rx_port_28_undersized_dropped_packets {
      type oc-yang:counter64;
      description
        "Counter for packets that were dropped because they were smaller than 64B.";
    }
    leaf counters_slice5_ifg1_ifgb_rx_port_29_undersized_dropped_packets {
      type oc-yang:counter64;
      description
        "Counter for packets that were dropped because they were smaller than 64B.";
    }
    leaf counters_slice5_ifg1_ifgb_rx_port_3_oobe_crc_errors {
      type oc-yang:counter64;
      description
        "OOB Extract CRC error counter per port";
    }
    leaf counters_slice5_ifg1_ifgb_rx_port_3_undersized_dropped_packets {
      type oc-yang:counter64;
      description
        "Counter for packets that were dropped because they were smaller than 64B.";
    }
    leaf counters_slice5_ifg1_ifgb_rx_port_30_undersized_dropped_packets {
      type oc-yang:counter64;
      description
        "Counter for packets that were dropped because they were smaller than 64B.";
    }
    leaf counters_slice5_ifg1_ifgb_rx_port_31_undersized_dropped_packets {
      type oc-yang:counter64;
      description
        "Counter for packets that were dropped because they were smaller than 64B.";
    }
    leaf counters_slice5_ifg1_ifgb_rx_port_4_oobe_crc_errors {
      type oc-yang:counter64;
      description
        "OOB Extract CRC error counter per port";
    }
    leaf counters_slice5_ifg1_ifgb_rx_port_4_undersized_dropped_packets {
      type oc-yang:counter64;
      description
        "Counter for packets that were dropped because they were smaller than 64B.";
    }
    leaf counters_slice5_ifg1_ifgb_rx_port_5_oobe_crc_errors {
      type oc-yang:counter64;
      description
        "OOB Extract CRC error counter per port";
    }
    leaf counters_slice5_ifg1_ifgb_rx_port_5_undersized_dropped_packets {
      type oc-yang:counter64;
      description
        "Counter for packets that were dropped because they were smaller than 64B.";
    }
    leaf counters_slice5_ifg1_ifgb_rx_port_6_oobe_crc_errors {
      type oc-yang:counter64;
      description
        "OOB Extract CRC error counter per port";
    }
    leaf counters_slice5_ifg1_ifgb_rx_port_6_undersized_dropped_packets {
      type oc-yang:counter64;
      description
        "Counter for packets that were dropped because they were smaller than 64B.";
    }
    leaf counters_slice5_ifg1_ifgb_rx_port_7_oobe_crc_errors {
      type oc-yang:counter64;
      description
        "OOB Extract CRC error counter per port";
    }
    leaf counters_slice5_ifg1_ifgb_rx_port_7_undersized_dropped_packets {
      type oc-yang:counter64;
      description
        "Counter for packets that were dropped because they were smaller than 64B.";
    }
    leaf counters_slice5_ifg1_ifgb_rx_port_8_oobe_crc_errors {
      type oc-yang:counter64;
      description
        "OOB Extract CRC error counter per port";
    }
    leaf counters_slice5_ifg1_ifgb_rx_port_8_undersized_dropped_packets {
      type oc-yang:counter64;
      description
        "Counter for packets that were dropped because they were smaller than 64B.";
    }
    leaf counters_slice5_ifg1_ifgb_rx_port_9_oobe_crc_errors {
      type oc-yang:counter64;
      description
        "OOB Extract CRC error counter per port";
    }
    leaf counters_slice5_ifg1_ifgb_rx_port_9_undersized_dropped_packets {
      type oc-yang:counter64;
      description
        "Counter for packets that were dropped because they were smaller than 64B.";
    }
    leaf counters_slice5_ifg1_ifgb_rx_protection_dropped_fragments {
      type oc-yang:counter64;
      description
        "RXPP interface protection fragments drop counter.";
    }
    leaf counters_slice5_ifg1_ifgb_rx_protection_dropped_packets {
      type oc-yang:counter64;
      description
        "RXPP interface protection packet drop counter.";
    }
    leaf counters_slice5_ifg1_ifgbi_recycle_in_band_extract_npu_host_re_direct_drop {
      type oc-yang:counter64;
      description
        "InBand Extract NPU Host ReDirect drop counter. Increments based on the RcyDropCntrsCfg.";
    }
    leaf counters_slice5_ifg1_ifgbi_recycle_in_band_extract_packet_dma_re_direct_drop {
      type oc-yang:counter64;
      description
        "InBand Extract Pkt DMA ReDirect drop counter. Increments based on the RcyDropCntrsCfg.";
    }
    leaf counters_slice5_ifg1_npu_rxpp_fwd_post_npe_dropped_packets {
      type oc-yang:counter64;
      description
        "Counts packets dropped by the rxpp";
    }
    leaf counters_slice5_ifg1_npu_rxpp_fwd_post_npe_dropped_packets_due_destination {
      type oc-yang:counter64;
      description
        "nan";
    }
    leaf counters_slice5_ifg1_npu_rxpp_fwd_post_npe_dropped_packets_due_dummy {
      type oc-yang:counter64;
      description
        "nan";
    }
    leaf counters_slice5_ifg1_npu_rxpp_fwd_post_npe_dropped_packets_due_ecc {
      type oc-yang:counter64;
      description
        "nan";
    }
    leaf counters_slice5_ifg1_npu_rxpp_fwd_post_npe_dropped_packets_due_err_flag {
      type oc-yang:counter64;
      description
        "nan";
    }
    leaf counters_slice5_ifg1_npu_rxpp_fwd_post_npe_dropped_packets_due_frag_parity_error {
      type oc-yang:counter64;
      description
        "nan";
    }
    leaf counters_slice5_ifg1_npu_txpp_hw_editor_1_packets_with_error_bit {
      type oc-yang:counter64;
      description
        "Counts number of packet leaving HW Editor 1 inst 1 have error bit assered";
    }
    leaf counters_slice5_ifg1_npu_txpp_hw_editor_2_packets_with_error_bit {
      type oc-yang:counter64;
      description
        "Counts number of packet leaving HW Editor 2 towards ifg1 have error bit assered";
    }
    leaf counters_slice5_ifg1_npu_txpp_npe_packets_with_error_bit {
      type oc-yang:counter64;
      description
        "Counts number of packet leaving NPE 1 have error bit assered";
    }
    leaf counters_slice5_ifg1_npu_txpp_preprocess_packets_with_error_bit {
      type oc-yang:counter64;
      description
        "Counts number of packet leaving preprocessing 1 have error bit assered";
    }
    leaf counters_sms_error_read_crc_errors {
      type oc-yang:counter64;
      description
        "This field counts the number of read Crc errors";
    }
    leaf counters_ts_mon0_empty_p_ds {
      type oc-yang:counter64;
      description
        "nan";
    }
    leaf counters_ts_mon0_mc_dropped_packets {
      type oc-yang:counter64;
      description
        "Counter of MC dropped packets";
    }
    leaf counters_ts_mon0_uch_dropped_packets {
      type oc-yang:counter64;
      description
        "Counter of UCH dropped packets";
    }
    leaf counters_ts_mon0_ucl_dropped_packets {
      type oc-yang:counter64;
      description
        "Counter of UCL dropped packets";
    }
    leaf counters_ts_mon1_empty_p_ds {
      type oc-yang:counter64;
      description
        "nan";
    }
    leaf counters_ts_mon1_mc_dropped_packets {
      type oc-yang:counter64;
      description
        "Counter of MC dropped packets";
    }
    leaf counters_ts_mon1_uch_dropped_packets {
      type oc-yang:counter64;
      description
        "Counter of UCH dropped packets";
    }
    leaf counters_ts_mon1_ucl_dropped_packets {
      type oc-yang:counter64;
      description
        "Counter of UCL dropped packets";
    }
    leaf counters_ts_mon2_empty_p_ds {
      type oc-yang:counter64;
      description
        "nan";
    }
    leaf counters_ts_mon2_mc_dropped_packets {
      type oc-yang:counter64;
      description
        "Counter of MC dropped packets";
    }
    leaf counters_ts_mon2_uch_dropped_packets {
      type oc-yang:counter64;
      description
        "Counter of UCH dropped packets";
    }
    leaf counters_ts_mon2_ucl_dropped_packets {
      type oc-yang:counter64;
      description
        "Counter of UCL dropped packets";
    }
    leaf counters_ts_mon3_empty_p_ds {
      type oc-yang:counter64;
      description
        "nan";
    }
    leaf counters_ts_mon3_mc_dropped_packets {
      type oc-yang:counter64;
      description
        "Counter of MC dropped packets";
    }
    leaf counters_ts_mon3_uch_dropped_packets {
      type oc-yang:counter64;
      description
        "Counter of UCH dropped packets";
    }
    leaf counters_ts_mon3_ucl_dropped_packets {
      type oc-yang:counter64;
      description
        "Counter of UCL dropped packets";
    }
    leaf counters_ts_mon4_empty_p_ds {
      type oc-yang:counter64;
      description
        "nan";
    }
    leaf counters_ts_mon4_mc_dropped_packets {
      type oc-yang:counter64;
      description
        "Counter of MC dropped packets";
    }
    leaf counters_ts_mon4_uch_dropped_packets {
      type oc-yang:counter64;
      description
        "Counter of UCH dropped packets";
    }
    leaf counters_ts_mon4_ucl_dropped_packets {
      type oc-yang:counter64;
      description
        "Counter of UCL dropped packets";
    }
    leaf counters_ts_mon5_empty_p_ds {
      type oc-yang:counter64;
      description
        "nan";
    }
    leaf counters_ts_mon5_mc_dropped_packets {
      type oc-yang:counter64;
      description
        "Counter of MC dropped packets";
    }
    leaf counters_ts_mon5_uch_dropped_packets {
      type oc-yang:counter64;
      description
        "Counter of UCH dropped packets";
    }
    leaf counters_ts_mon5_ucl_dropped_packets {
      type oc-yang:counter64;
      description
        "Counter of UCL dropped packets";
    }
    leaf events_drop_ts_mon0_fte_test {
      type oc-yang:counter64;
      description
        "FTE test caused drops";
    }
    leaf events_drop_ts_mon0_monotonic_test {
      type oc-yang:counter64;
      description
        "Monotonic test caused drops";
    }
    leaf events_drop_ts_mon0_skew_test {
      type oc-yang:counter64;
      description
        "Skew test caused drops";
    }
    leaf events_drop_ts_mon1_fte_test {
      type oc-yang:counter64;
      description
        "FTE test caused drops";
    }
    leaf events_drop_ts_mon1_monotonic_test {
      type oc-yang:counter64;
      description
        "Monotonic test caused drops";
    }
    leaf events_drop_ts_mon1_skew_test {
      type oc-yang:counter64;
      description
        "Skew test caused drops";
    }
    leaf events_drop_ts_mon2_fte_test {
      type oc-yang:counter64;
      description
        "FTE test caused drops";
    }
    leaf events_drop_ts_mon2_monotonic_test {
      type oc-yang:counter64;
      description
        "Monotonic test caused drops";
    }
    leaf events_drop_ts_mon2_skew_test {
      type oc-yang:counter64;
      description
        "Skew test caused drops";
    }
    leaf events_drop_ts_mon3_fte_test {
      type oc-yang:counter64;
      description
        "FTE test caused drops";
    }
    leaf events_drop_ts_mon3_monotonic_test {
      type oc-yang:counter64;
      description
        "Monotonic test caused drops";
    }
    leaf events_drop_ts_mon3_skew_test {
      type oc-yang:counter64;
      description
        "Skew test caused drops";
    }
    leaf events_drop_ts_mon4_fte_test {
      type oc-yang:counter64;
      description
        "FTE test caused drops";
    }
    leaf events_drop_ts_mon4_monotonic_test {
      type oc-yang:counter64;
      description
        "Monotonic test caused drops";
    }
    leaf events_drop_ts_mon4_skew_test {
      type oc-yang:counter64;
      description
        "Skew test caused drops";
    }
    leaf events_drop_ts_mon5_fte_test {
      type oc-yang:counter64;
      description
        "FTE test caused drops";
    }
    leaf events_drop_ts_mon5_monotonic_test {
      type oc-yang:counter64;
      description
        "Monotonic test caused drops";
    }
    leaf events_drop_ts_mon5_skew_test {
      type oc-yang:counter64;
      description
        "Skew test caused drops";
    }
  }

  augment "/oc-platform:components/oc-platform:component/oc-platform:integrated-circuit/oc-ppc:pipeline-counters/oc-ppc:drop/oc-ppc:vendor/cisco:cisco" {
    description
      "Cisco container";
    container p100 {
      description
        "Si-One p100 Drop container";
      uses oc-ppc:pipeline-vendor-drop-containers;
    }
  }
  augment "/oc-platform:components/oc-platform:component/oc-platform:integrated-circuit/oc-ppc:pipeline-counters/oc-ppc:drop/oc-ppc:vendor/cisco:cisco/p100:p100/p100:adverse/p100:state" {
    description
      "Adverse drop container for p100";
    uses cisco-p100-adverse-drop-counters;
  }
  augment "/oc-platform:components/oc-platform:component/oc-platform:integrated-circuit/oc-ppc:pipeline-counters/oc-ppc:drop/oc-ppc:vendor/cisco:cisco/p100:p100/p100:congestion/p100:state" {
    description
      "Congestion drop container for p100";
    uses cisco-p100-congestion-drop-counters;
  }
  augment "/oc-platform:components/oc-platform:component/oc-platform:integrated-circuit/oc-ppc:pipeline-counters/oc-ppc:drop/oc-ppc:vendor/cisco:cisco/p100:p100/p100:packet-processing/p100:state" {
    description
      "Packet Processing drop container for p100";
    uses cisco-p100-packet-processing-drop-counters;
  }
  oc-ext:openconfig-version "0.1.0";
  oc-ext:catalog-organization "openconfig";
  oc-ext:origin "openconfig";
}
