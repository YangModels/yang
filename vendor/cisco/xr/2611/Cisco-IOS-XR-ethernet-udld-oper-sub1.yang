submodule Cisco-IOS-XR-ethernet-udld-oper-sub1 {
  belongs-to Cisco-IOS-XR-ethernet-udld-oper {
    prefix Cisco-IOS-XR-ethernet-udld-oper;
  }

  import ietf-yang-types {
    prefix yang;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR ethernet-udld package operational data.
     
     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  typedef Udld-bag-item-string {
    type string;
    description
      "Udld bag item string";
  }

  typedef Mac-address {
    type yang:mac-address;
    description
      "MAC address type";
  }

  typedef Udld-detect-state {
    type enumeration {
      enum "unknown" {
        description
          "Unknown";
      }
      enum "unidirectional" {
        description
          "Unidirectional";
      }
      enum "bidirectional" {
        description
          "Bidirectional";
      }
      enum "loopback" {
        description
          "Loopback";
      }
      enum "neighbor-mismatch" {
        description
          "Neighbor mismatch";
      }
      enum "empty-echo" {
        description
          "Empty echo";
      }
      enum "invalid" {
        description
          "Invalid";
      }
    }
    description
      "Detection FSM state of a port";
  }

  typedef Udld-main-state {
    type enumeration {
      enum "init" {
        value 0;
        description
          "Initializing";
      }
      enum "up" {
        value 1;
        description
          "Link Up";
      }
      enum "detection" {
        value 2;
        description
          "Detection";
      }
      enum "advertise" {
        value 3;
        description
          "Advertise";
      }
      enum "udld-inactive" {
        value 4;
        description
          "UDLD inactive";
      }
      enum "port-shutdown" {
        value 5;
        description
          "Port shutdown";
      }
      enum "invalid" {
        value 6;
        description
          "Invalid";
      }
    }
    description
      "Main FSM state of a port";
  }

  typedef Udld-port-brief-state-enum {
    type enumeration {
      enum "admin-down" {
        description
          "Port is admin down";
      }
      enum "error-disabled" {
        description
          "Port is error-disabled";
      }
      enum "down" {
        description
          "Port is down";
      }
      enum "initializing" {
        description
          "Port is initializing";
      }
      enum "detecting" {
        description
          "Port is detecting";
      }
      enum "loopback" {
        description
          "Port is a loopback";
      }
      enum "unidirectional" {
        description
          "Port is unidirectional";
      }
      enum "neighbor-mismatch" {
        description
          "Port has mismatched neighbors";
      }
      enum "no-neighbors" {
        description
          "Port doesn't have any neighbors";
      }
      enum "bidirectional" {
        description
          "Port is bidirectional";
      }
      enum "unkown" {
        description
          "Port state unknown";
      }
    }
    description
      "Brief description of port state";
  }

  typedef Udld-errdis-reason {
    type enumeration {
      enum "unknown" {
        description
          "Unknown";
      }
      enum "none" {
        description
          "None: Port is not error disabled";
      }
      enum "not-udld" {
        description
          "Reason unrelated to UDLD";
      }
      enum "aggressive-timeout" {
        description
          "Time out (UDLD in aggressive mode)";
      }
      enum "unidirectional" {
        description
          "Unidirectional port";
      }
      enum "neighbor-mismatch" {
        description
          "Neighbor mismatch";
      }
      enum "loopback" {
        description
          "Tx/Rx loopback detected";
      }
      enum "across-issu" {
        description
          "Across ISSU";
      }
    }
    description
      "Reason for port being error disabled";
  }

  typedef Udld-port-state-enum {
    type enumeration {
      enum "up" {
        description
          "Port is up";
      }
      enum "down" {
        description
          "Port is down";
      }
      enum "error-disabled" {
        description
          "Port is error-disabled";
      }
      enum "admin-down" {
        description
          "Port is admin down";
      }
    }
    description
      "State of a port";
  }

  grouping UDLD-PKT-COUNTS-TYPE {
    description
      "Packet counters";
    leaf probe {
      type uint32;
      description
        "Probe";
    }
    leaf echo {
      type uint32;
      description
        "Echo";
    }
    leaf flush {
      type uint32;
      description
        "Flush";
    }
    leaf dropped {
      type uint32;
      description
        "Dropped";
    }
  }

  grouping UDLD-DETECTION-FSM-STATS-TYPE {
    description
      "Number of detection FSM transitions (to each
       state)";
    leaf unknown {
      type uint32;
      description
        "Unknown";
    }
    leaf bidirectional {
      type uint32;
      description
        "Bidirectional";
    }
    leaf unidirectional {
      type uint32;
      description
        "Unidirectional";
    }
    leaf neighbor-mismatch {
      type uint32;
      description
        "Neighbor mismatch";
    }
    leaf loopback {
      type uint32;
      description
        "Loopback";
    }
  }

  grouping UDLD-MAIN-FSM-STATS-TYPE {
    description
      "Number of main FSM transitions (to each state)";
    leaf link-up {
      type uint32;
      description
        "Link up";
    }
    leaf detection {
      type uint32;
      description
        "Detection";
    }
    leaf advertise {
      type uint32;
      description
        "Advertise";
    }
    leaf port-shutdown {
      type uint32;
      description
        "Port shutdown";
    }
    leaf udld-inactive {
      type uint32;
      description
        "UDLD inactive";
    }
  }

  grouping UDLD-BAG-STATS-PORT-DATA {
    description
      "Counters for UDLD per port events";
    container main-fsm-transitions {
      description
        "Main FSM transitions";
      uses UDLD-MAIN-FSM-STATS-TYPE;
    }
    container detection-fsm-transitions {
      description
        "Detection FSM transitions";
      uses UDLD-DETECTION-FSM-STATS-TYPE;
    }
    container receive-packets {
      description
        "Receive packet counters";
      uses UDLD-PKT-COUNTS-TYPE;
    }
    container transmit-packets {
      description
        "Transmit packet counters";
      uses UDLD-PKT-COUNTS-TYPE;
    }
    leaf last-cleared {
      type uint64;
      units "nanosecond";
      description
        "Time in nanoseconds since counters were last
         cleared";
    }
  }

  grouping UDLD-ECHO-DATA-TYPE {
    description
      "UDLD Echo data";
    leaf device-id {
      type string;
      description
        "Device ID";
    }
    leaf port {
      type string;
      description
        "Port";
    }
  }

  grouping UDLD-DEVICE-TYPE {
    description
      "Information identifying a UDLD device";
    leaf id {
      type string;
      description
        "ID";
    }
    leaf name {
      type string;
      description
        "Name";
    }
  }

  grouping UDLD-NBOR-DATA-TYPE {
    description
      "Information for a UDLD port's neighbor";
    container device {
      description
        "Device";
      uses UDLD-DEVICE-TYPE;
    }
    container udld-parameters {
      description
        "UDLD parameters";
      uses UDLD-PARAM-TYPE;
    }
    leaf port {
      type string;
      description
        "Port";
    }
    list echo-data {
      description
        "Echo Data";
      uses UDLD-ECHO-DATA-TYPE;
    }
  }

  grouping UDLD-PARAM-TYPE {
    description
      "UDLD parameters";
    leaf message-interval {
      type uint8;
      units "second";
      description
        "Message interval (seconds)";
    }
    leaf timeout-interval {
      type uint8;
      units "second";
      description
        "Timeout interval (seconds)";
    }
  }

  grouping UDLD-PORT-STATE-DATA-TYPE {
    description
      "Information about the UDLD state of a port";
    leaf state {
      type Udld-port-state-enum;
      description
        "State of the port";
    }
    leaf error-disable-reason {
      type Udld-errdis-reason;
      description
        "Reason why port is error disabled";
    }
  }

  grouping UDLD-BAG-PORT-DATA {
    description
      "Information for a UDLD port";
    container state {
      description
        "State";
      uses UDLD-PORT-STATE-DATA-TYPE;
    }
    container udld-parameters {
      description
        "UDLD port parameters";
      uses UDLD-PARAM-TYPE;
    }
    leaf port-id {
      type string;
      description
        "Port ID";
    }
    leaf brief-state {
      type Udld-port-brief-state-enum;
      description
        "Brief description of port's state";
    }
    leaf main-fsm-state {
      type Udld-main-state;
      description
        "Main FSM state";
    }
    leaf detect-fsm-state {
      type Udld-detect-state;
      description
        "Detect FSM state";
    }
    leaf destination-mac-address {
      type Mac-address;
      description
        "Destination MAC address in use";
    }
    leaf device-id {
      type Udld-bag-item-string;
      description
        "Device ID override";
    }
    list neighbor-data {
      description
        "Information about a port's neighbors";
      uses UDLD-NBOR-DATA-TYPE;
    }
  }

  grouping UDLD-BAG-STATS-NODE-DATA {
    description
      "Counters for UDLD per node events";
    leaf last-cleared {
      type uint64;
      units "nanosecond";
      description
        "Time in nanoseconds since counters were last
         cleared";
    }
    leaf non-udld-port-packets {
      type uint32;
      description
        "Number of packets received on a non UDLD
         configured port";
    }
    leaf last-non-udld-port {
      type string;
      description
        "Last port (non UDLD configured) for which a
         packet was received";
    }
    leaf unknown-receive-port-packets {
      type uint32;
      description
        "Number of packets received for an unknown port";
    }
  }
}
