module Cisco-IOS-XR-um-lpts-pifib-police-acl-cfg {
  namespace "http://cisco.com/ns/yang/Cisco-IOS-XR-um-lpts-pifib-police-acl-cfg";
  prefix um-lpts-pifib-police-acl-cfg;

  import Cisco-IOS-XR-types {
    prefix xr;
  }
  import Cisco-IOS-XR-um-lpts-pifib-cfg {
    prefix a1;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR lpts-pifib-police-acl package configuration.
     
     This YANG module augments the
     modules with configuration data.
     
     Copyright (c) 2020-2025 by Cisco Systems, Inc., and/or its affiliates.
     All rights reserved.";

  revision 2022-07-11 {
    description
      "Added missing description statement to nodes";
    semver:module-version "1.1.0";
  }
  revision 2020-09-11 {
    description
      "Initial release";
    semver:module-version "1.0.0";
  }

  grouping LPTS-POLICE {
    description
      "Grouping for lpts-police";
    container acls {
      description
        "pre-ifib acl name";
      list acl {
        must "ipv4/vrf or ipv6/vrf";
        key "acl-name";
        description
          "pre-ifib acl name";
        leaf acl-name {
          type xr:Cisco-ios-xr-string {
            length "1..32" {
              description
                "ACL name";
            }
          }
          description
            "pre-ifib acl name";
        }
        container ipv4 {
          description
            "IP Version 4";
          list vrf {
            key "vrf-name";
            description
              "Specify the Vrf Id";
            leaf vrf-name {
              type union {
                type string {
                  pattern "default" {
                    description
                      "Default VRF";
                  }
                }
                type xr:Cisco-ios-xr-string {
                  length "1..32" {
                    description
                      "Name of VRF";
                  }
                }
              }
              description
                "Name of VRF";
            }
            leaf rate {
              type uint32 {
                range "0..100000" {
                  description
                    "Rate value";
                }
              }
              mandatory true;
              description
                "pre-ifib policer rate config commands";
            }
          }
        }
        container ipv6 {
          description
            "IP Version 6";
          list vrf {
            key "vrf-name";
            description
              "Specify the Vrf Id";
            leaf vrf-name {
              type union {
                type string {
                  pattern "default" {
                    description
                      "Default VRF";
                  }
                }
                type xr:Cisco-ios-xr-string {
                  length "1..32" {
                    description
                      "Name of VRF";
                  }
                }
              }
              description
                "Name of VRF";
            }
            leaf rate {
              type uint32 {
                range "0..100000" {
                  description
                    "Rate value";
                }
              }
              mandatory true;
              description
                "pre-ifib policer rate config commands";
            }
          }
        }
      }
    }
  }

  augment "/a1:lpts/a1:pifib/a1:hardware/a1:police" {
    description
      "This augment extends lpts pifib hardware police nodes
       configuration";
    uses LPTS-POLICE;
  }
}
