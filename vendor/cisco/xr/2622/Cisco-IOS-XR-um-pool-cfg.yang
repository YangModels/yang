module Cisco-IOS-XR-um-pool-cfg {
  namespace "http://cisco.com/ns/yang/Cisco-IOS-XR-um-pool-cfg";
  prefix um-pool-cfg;

  import Cisco-IOS-XR-types {
    prefix xr;
  }
  import ietf-inet-types {
    prefix inet;
  }
  import Cisco-IOS-XR-um-snmp-server-cfg {
    prefix a1;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR pool package configuration.
     
     This YANG module augments the
     modules with configuration data.
     
     Copyright (c) 2021-2025 by Cisco Systems, Inc., and/or its affiliates.
     All rights reserved.";

  revision 2023-05-15 {
    description
      "Added must statements for ipv4 & ipv6 lists
       2022-07-11
         Added missing description statement to nodes";
    semver:module-version "2.0.0";
  }
  revision 2021-05-10 {
    description
      "Initial release";
    semver:module-version "1.0.0";
  }

  augment "/a1:snmp-server/a1:traps" {
    description
      "This augment extends snmp-server traps nodes
       configuration";
    container addrpool {
      description
        "Enable SNMP Address Pool traps";
      container high {
        presence "Indicates a high node is configured.";
        description
          "Enable SNMP Address Pool High Threshold trap";
      }
      container low {
        presence "Indicates a low node is configured.";
        description
          "Enable SNMP Address Pool Low Threshold trap";
      }
    }
  }
  container pool {
    description
      "Distributed Address Pool Service";
    container vrfs {
      description
        "Specify VRF name";
      list vrf {
        must "ipv4s/ipv4 or ipv6s/ipv6";
        key "vrf-name";
        description
          "Enter the VRF name";
        leaf vrf-name {
          type union {
            type string {
              pattern "all" {
                description
                  "Global Pool";
              }
            }
            type string {
              pattern "default" {
                description
                  "Default VRF";
              }
            }
            type xr:Cisco-ios-xr-string {
              length "1..63" {
                description
                  "Enter the VRF name";
              }
            }
          }
          description
            "Enter the VRF name";
        }
        container ipv6s {
          description
            "Specify IPv6 Pool name";
          list ipv6 {
            key "pool-name";
            description
              "Enter the IPv6 Pool name";
            leaf pool-name {
              type xr:Cisco-ios-xr-string {
                length "1..63" {
                  description
                    "Enter the IPv6 Pool name";
                }
              }
              description
                "Enter the IPv6 Pool name";
            }
            container address-ranges {
              description
                "Specify address range for allocation";
              list address-range {
                must "last-address-in-range";
                key "first-address-in-range";
                description
                  "Specify address range for allocation";
                leaf first-address-in-range {
                  type inet:ipv6-address-no-zone;
                  description
                    "Specify address range for allocation";
                }
                leaf last-address-in-range {
                  type inet:ipv6-address-no-zone;
                  description
                    "Enter the last IPv6 address in range";
                }
                container block {
                  must "../last-address-in-range";
                  presence "Indicates a block node is configured.";
                  description
                    "block address-range";
                }
              }
            }
            container prefix-ranges {
              description
                "Specify prefix range for allocation";
              list prefix-range {
                must "last-prefix-in-range";
                key "first-prefix-in-range";
                description
                  "Specify prefix range for allocation";
                leaf first-prefix-in-range {
                  type inet:ipv6-address-no-zone;
                  description
                    "Specify prefix range for allocation";
                }
                leaf last-prefix-in-range {
                  type inet:ipv6-address-no-zone;
                  description
                    "Enter the last IPv6 prefix in range";
                }
                container block {
                  must "../last-prefix-in-range";
                  presence "Indicates a block node is configured.";
                  description
                    "block address-range";
                }
              }
            }
            container networks {
              description
                "Specify network for allocation";
              list network {
                key "address";
                description
                  "Specify network for allocation";
                leaf address {
                  type inet:ipv6-address-no-zone;
                  description
                    "Specify network for allocation";
                }
                leaf length {
                  type uint32 {
                    range "0..128" {
                      description
                        "Network address mask length";
                    }
                  }
                  mandatory true;
                  description
                    "Specify network address mask length";
                }
                container block {
                  presence "Indicates a block node is configured.";
                  description
                    "block address-range";
                }
              }
            }
            leaf prefix-length {
              type uint32 {
                range "1..128" {
                  description
                    "Enter the prefix-length";
                }
              }
              description
                "Specify prefix-length to be used";
            }
            container excludes {
              description
                "Exclude IPv6 addresses / prefixes";
              list exclude {
                key "first-address-in-range";
                description
                  "Exclude IPv6 addresses / prefixes";
                leaf first-address-in-range {
                  type inet:ipv6-address-no-zone;
                  description
                    "Exclude IPv6 addresses / prefixes";
                }
                leaf last-address-in-range {
                  type inet:ipv6-address-no-zone;
                  description
                    "Last IPv6 address / prefix in range";
                }
              }
            }
            container utilization-mark {
              description
                "Specify utilization mark";
              leaf high {
                type uint32 {
                  range "0..100" {
                    description
                      "Specify numerical value as percentage";
                  }
                }
                must "../low";
                description
                  "Specify high mark";
              }
              leaf low {
                type uint32 {
                  range "0..100" {
                    description
                      "Specify numerical value as percentage";
                  }
                }
                must "../high";
                description
                  "Specify low mark";
              }
            }
          }
        }
        container ipv4s {
          description
            "Specify IPv4 Pool name";
          list ipv4 {
            when "../../vrf-name != 'all'";
            key "ipv4-name";
            description
              "Specify IPv4 Pool name";
            leaf ipv4-name {
              type xr:Cisco-ios-xr-string {
                length "1..63" {
                  description
                    "Enter the IPv4 Pool name";
                }
              }
              description
                "Specify IPv4 Pool name";
            }
            container networks {
              description
                "Specify network for allocation";
              list network {
                key "address";
                description
                  "Specify network for allocation";
                leaf address {
                  type inet:ipv4-address-no-zone;
                  description
                    "Specify network for allocation";
                }
                leaf length {
                  type uint32 {
                    range "0..32" {
                      description
                        "Network address mask length";
                    }
                  }
                  mandatory true;
                  description
                    "Specify network address mask length";
                }
                leaf default-router {
                  type inet:ipv4-address-no-zone;
                  description
                    "Default Gateway for subnet";
                }
                container block {
                  presence "Indicates a block node is configured.";
                  description
                    "block subnet test";
                }
              }
            }
            container excludes {
              description
                "Exclude addresses";
              list exclude {
                key "first-address-in-range";
                description
                  "Exclude addresses";
                leaf first-address-in-range {
                  type inet:ipv4-address-no-zone;
                  description
                    "Exclude addresses";
                }
                leaf last-address-in-range {
                  type inet:ipv4-address-no-zone;
                  description
                    "Last exclude address in range";
                }
              }
            }
            container utilization-mark {
              description
                "Specify utilization mark";
              leaf high {
                type uint32 {
                  range "0..100" {
                    description
                      "Specify numerical value as percentage";
                  }
                }
                must "../low";
                description
                  "Specify high mark";
              }
              leaf low {
                type uint32 {
                  range "0..100" {
                    description
                      "Specify numerical value as percentage";
                  }
                }
                must "../high";
                description
                  "Specify low mark";
              }
            }
            container address-ranges {
              description
                "Specify address range for allocation";
              list address-range {
                must "last-address-in-range";
                key "first-address-in-range";
                description
                  "Specify address range for allocation";
                leaf first-address-in-range {
                  type inet:ipv4-address-no-zone;
                  description
                    "Specify address range for allocation";
                }
                leaf last-address-in-range {
                  type inet:ipv4-address-no-zone;
                  description
                    "Enter the last address in range";
                }
                container block {
                  must "../last-address-in-range";
                  presence "Indicates a block node is configured.";
                  description
                    "block address-range";
                }
              }
            }
          }
        }
      }
    }
    container onfly {
      description
        "Allow to delete/edit pool and release subscriber IP for ipv4";
      container pppoe {
        presence "Indicates a pppoe node is configured.";
        description
          "Enable onfly feature for pppoe subscriber";
      }
    }
  }
}
