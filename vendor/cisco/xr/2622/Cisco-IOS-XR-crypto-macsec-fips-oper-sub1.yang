submodule Cisco-IOS-XR-crypto-macsec-fips-oper-sub1 {
  belongs-to Cisco-IOS-XR-crypto-macsec-fips-oper {
    prefix Cisco-IOS-XR-crypto-macsec-fips-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR crypto-macsec-fips package operational data.
     
     Copyright (c) 2013-2024 by Cisco Systems, Inc.
     All rights reserved.";

  revision 2024-09-06 {
    description
      "Added MACsec FIPS operational info";
    semver:module-version "1.0.0";
  }
  revision 2019-04-05 {
    description
      "Establish semantic version baseline.";
  }
  revision 2015-11-09 {
    description
      "IOS XR 6.0 revision.";
  }

  grouping MACSEC-FIPS-STATUS {
    description
      "MACSEC FIPS STATUS";
    leaf fips-mode {
      type boolean;
      description
        "MACsec FIPS mode State";
    }
  }
}
