module Cisco-IOS-XR-fia-internal-tcam-oper {
  namespace "http://cisco.com/ns/yang/Cisco-IOS-XR-fia-internal-tcam-oper";
  prefix fia-internal-tcam-oper;

  import Cisco-IOS-XR-types {
    prefix xr;
  }
  import cisco-semver {
    prefix semver;
  }
  include Cisco-IOS-XR-fia-internal-tcam-oper-sub1 {
    revision-date 2022-07-09;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR fia-internal-tcam package operational data.
     
     This module contains definitions
     for the following management objects:
       controller: Controller Resources
     
     Copyright (c) 2013-2022 by Cisco Systems, Inc.
     All rights reserved.";

  revision 2022-07-09 {
    description
      "Updated type fia-max-asic-instances to fia-max-npu-instances
       2022-04-28
         Added TCAM utilization support
       2022-02-16
         Added key for db-id, bank-id, npu-id. Updated internal-tcam-resources/external-tcam-resources container and added container for maintaining NPU lists. Updated task-id";
    semver:module-version "2.0.0";
  }
  revision 2019-04-05 {
    description
      "Establish semantic version baseline.";
    semver:module-version "1.0.1";
  }
  revision 2015-11-09 {
    description
      "IOS XR 6.0 revision.";
  }

  typedef Fia-max-npu-instances {
    type uint32 {
      range "0..255";
    }
    description
      "Fia max npu instances";
  }

  container controller {
    config false;
    description
      "Controller Resources";
    container dpa {
      description
        "Controller DPA operational data";
      container nodes {
        description
          "DPA data for available nodes";
        list node {
          key "node-name";
          description
            "DPA operational data for a particular node";
          container external-tcam-resources {
            description
              "External TCAM Resource Information";
            container npu-instance-exts {
              description
                "instance table for tcam resources";
              list npu-instance-ext {
                key "instance";
                description
                  "Instance number for tcam resources";
                leaf instance {
                  type Fia-max-npu-instances;
                  description
                    "Asic instance";
                }
                uses FIA-NPU-TCAM;
              }
            }
          }
          container internal-tcam-resources {
            description
              "Internal TCAM Resource Information";
            container npu-instance-ints {
              description
                "instance table for tcam resources";
              list npu-instance-int {
                key "instance";
                description
                  "Instance number for tcam resources";
                leaf instance {
                  type Fia-max-npu-instances;
                  description
                    "Asic instance";
                }
                uses FIA-NPU-TCAM;
              }
            }
          }
          leaf node-name {
            type xr:Node-id;
            description
              "Node ID";
          }
        }
      }
    }
  }
}
