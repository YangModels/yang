submodule Cisco-IOS-XR-infra-objmgr-oper-sub1 {
  belongs-to Cisco-IOS-XR-infra-objmgr-oper {
    prefix Cisco-IOS-XR-infra-objmgr-oper;
  }

  import ietf-inet-types {
    prefix inet;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR infra-objmgr package operational data.
     
     Copyright (c) 2013-2019 by Cisco Systems, Inc.
     All rights reserved.";

  revision 2019-04-05 {
    description
      "Establish semantic version baseline.";
    semver:module-version "1.0.0";
  }
  revision 2017-05-01 {
    description
      "Fixing backward compatibility error in module.";
  }
  revision 2015-11-09 {
    description
      "IOS XR 6.0 revision.";
  }

  grouping OBJ-GROUP-IPV4-MEMBER-HOST {
    description
      "Member host address bag";
    leaf host-address-xr {
      type inet:ipv4-address;
      description
        "Host address";
    }
  }

  grouping OBJ-GROUP-IPV4-MEMBER-RANGE {
    description
      "Member range bag";
    leaf start-address-xr {
      type inet:ipv4-address;
      description
        "Range start address";
    }
    leaf end-address-xr {
      type inet:ipv4-address;
      description
        "Range end address";
    }
  }

  grouping OBJ-GROUP-IPV4-MEMBER-ADDRESS {
    description
      "Member address bag";
    leaf prefix-xr {
      type inet:ipv4-address;
      description
        "IPv4 Address";
    }
    leaf prefix-length-xr {
      type uint32;
      description
        "Prefix length";
    }
  }

  grouping OBJ-GROUP-IPV6-MEMBER-HOST {
    description
      "Member host address bag";
    leaf host-address-xr {
      type inet:ipv6-address;
      description
        "Host address";
    }
  }

  grouping OBJ-GROUP-IPV6-MEMBER-RANGE {
    description
      "Member range bag";
    leaf start-address-xr {
      type inet:ipv6-address;
      description
        "Range start address";
    }
    leaf end-address-xr {
      type inet:ipv6-address;
      description
        "Range end address";
    }
  }

  grouping OBJ-GROUP-IPV6-MEMBER-ADDRESS {
    description
      "Member address bag";
    leaf prefix-xr {
      type inet:ipv6-address;
      description
        "IPv4 Address";
    }
    leaf prefix-length-xr {
      type uint32;
      description
        "Prefix length";
    }
  }

  grouping OBJ-GROUP-PARENT {
    description
      "Group parent bag";
    leaf parent-name {
      type string;
      description
        "Parent node";
    }
  }

  grouping OBJ-GROUP-PORT-MEMBER-RANGE {
    description
      "Member port range bag";
    leaf start-port-xr {
      type uint32;
      description
        "Port start address";
    }
    leaf end-port-xr {
      type uint32;
      description
        "Port end address";
    }
  }

  grouping OBJ-GROUP-PORT-MEMBER-PORT {
    description
      "Member port operator port bag";
    leaf operator-type-xr {
      type uint32;
      description
        "Operator";
    }
    leaf port-xr {
      type uint32;
      description
        "Port";
    }
  }

  grouping OBJ-GROUP-MEMBER-NESTED {
    description
      "Member nested bag";
    leaf nested-group-name-xr {
      type string;
      description
        "Nested group";
    }
  }
}
