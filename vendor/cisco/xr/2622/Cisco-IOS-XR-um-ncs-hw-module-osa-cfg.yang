module Cisco-IOS-XR-um-ncs-hw-module-osa-cfg {
  namespace "http://cisco.com/ns/yang/Cisco-IOS-XR-um-ncs-hw-module-osa-cfg";
  prefix um-ncs-hw-module-osa-cfg;

  import Cisco-IOS-XR-types {
    prefix xr;
  }
  import Cisco-IOS-XR-um-location-cfg {
    prefix location;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ncs-hw-module-osa package configuration.
     
     This YANG module augments the
     modules with configuration data.
     
     Copyright (c) 2022-2025 by Cisco Systems, Inc., and/or its affiliates.
     All rights reserved.";

  revision 2025-11-16 {
    description
      "Added new client rate CLI for SKBO under regen-slice";
    semver:module-version "1.0.0";
  }
  revision 2025-10-24 {
    description
      "Increased Slice limit to 15 and lane limit to 8";
  }
  revision 2025-07-29 {
    description
      "Regenerated at 2025";
  }
  revision 2022-07-11 {
    description
      "Added missing description statement to nodes";
  }
  revision 2022-07-04 {
    description
      "Added new card-types nodes";
  }
  revision 2022-03-21 {
    description
      "Added missing nodes";
  }
  revision 2021-11-22 {
    description
      "Initial release";
  }

  feature mxponder {
    description
      "mxponder";
  }

  feature client-rate {
    description
      "client-rate";
  }

  feature trunk-rate {
    description
      "trunk-rate";
  }

  feature client-port-rate {
    description
      "client-port-rate";
  }

  feature client-port-ains-soak {
    description
      "client-port-ains-soak";
  }

  feature drop-lldp {
    description
      "drop-lldp";
  }

  feature arp-snoop {
    description
      "arp-snoop";
  }

  feature split-client-port-mapping {
    description
      "split-client-port-mapping";
  }

  feature regen {
    description
      "regen";
  }

  feature mxponder-slice {
    description
      "mxponder-slice";
  }

  feature attention-led {
    description
      "attention-led";
  }

  feature all-ports {
    description
      "all-ports";
  }

  feature port {
    description
      "port";
  }

  feature terminal-ampli {
    description
      "terminal-ampli";
  }

  feature grid-mode {
    description
      "grid-mode";
  }

  feature channel-id {
    description
      "channel-id";
  }

  feature inline-ampli {
    description
      "inline-ampli";
  }

  grouping LOCATION-BODY {
    description
      "Grouping for location";
    container hw-module {
      description
        "Configure h/w module";
      container mxponder {
        if-feature "mxponder";
        description
          "Module configuration";
        leaf client-rate {
          if-feature "client-rate";
          type enumeration {
            enum "100GE" {
              value 2;
              description
                "client type 100G Ethernet";
            }
            enum "OTU4" {
              value 3;
              description
                "client type OTU4";
            }
            enum "400GE" {
              value 8;
              description
                "client type 400G Ethernet";
            }
          }
          description
            "Client side parameters";
        }
        leaf trunk-rate {
          if-feature "trunk-rate";
          type enumeration {
            enum "50G" {
              value 1;
              description
                "trunk bitrate 50Gbps";
            }
            enum "100G" {
              value 2;
              description
                "trunk bitrate 100Gbps";
            }
            enum "150G" {
              value 3;
              description
                "trunk bitrate 150Gbps";
            }
            enum "200G" {
              value 4;
              description
                "trunk bitrate 200Gbps";
            }
            enum "250G" {
              value 5;
              description
                "trunk bitrate 250Gbps";
            }
            enum "300G" {
              value 6;
              description
                "trunk bitrate 300Gbps";
            }
            enum "350G" {
              value 7;
              description
                "trunk bitrate 350Gbps";
            }
            enum "400G" {
              value 8;
              description
                "trunk bitrate 400Gbps";
            }
            enum "450G" {
              value 9;
              description
                "trunk bitrate 450Gbps";
            }
            enum "500G" {
              value 10;
              description
                "trunk bitrate 500Gbps";
            }
            enum "550G" {
              value 11;
              description
                "trunk bitrate 550Gbps";
            }
            enum "600G" {
              value 12;
              description
                "trunk bitrate 600Gbps";
            }
            enum "700G" {
              value 13;
              description
                "trunk bitrate 700Gbps";
            }
            enum "800G" {
              value 14;
              description
                "trunk bitrate 800Gbps";
            }
            enum "900G" {
              value 15;
              description
                "trunk bitrate 900Gbps";
            }
            enum "1000G" {
              value 16;
              description
                "trunk bitrate 1000Gbps";
            }
            enum "1100G" {
              value 17;
              description
                "trunk bitrate 1100Gbps";
            }
            enum "1200G" {
              value 18;
              description
                "trunk bitrate 1200Gbps";
            }
          }
          description
            "Trunk side parameters";
        }
        container client-port-rates {
          description
            "client port rate configuration";
          list client-port-rate {
            if-feature "client-port-rate";
            key "port-number lane-number";
            description
              "client port rate configuration";
            leaf port-number {
              type uint32 {
                range "0..11" {
                  description
                    "Enter port number";
                }
              }
              description
                "client port rate configuration";
            }
            leaf lane-number {
              type uint32 {
                range "1..4" {
                  description
                    "Enter Lane number";
                }
              }
              description
                "If port is in Breakout mode, specify optics lane number";
            }
            leaf client-type {
              type enumeration {
                enum "100GE" {
                  value 2;
                  description
                    "client 100GE";
                }
                enum "OTU4" {
                  value 3;
                  description
                    "client OTU4";
                }
                enum "400GE" {
                  value 8;
                  description
                    "client 400GE";
                }
                enum "800GE" {
                  value 14;
                  description
                    "client 800GE";
                }
              }
              mandatory true;
              description
                "Client Rate to be configured";
            }
          }
        }
        container client-port-ains-soak {
          if-feature "client-port-ains-soak";
          description
            "Client ports AINS configuration";
          leaf hours {
            type uint32 {
              range "0..48" {
                description
                  "Default AINS soak interval hours value";
              }
            }
            must "../minutes";
            description
              "Default AINS soak interval hours value";
          }
          leaf minutes {
            type uint32 {
              range "0..59" {
                description
                  "Default AINS soak interval minutes value";
              }
            }
            must "../hours";
            description
              "Default AINS soak interval minutes value";
          }
        }
        container drop-lldp {
          if-feature "drop-lldp";
          presence "Indicates a drop-lldp node is configured.";
          description
            "Drop LLDP packets coming on client ports on this slice";
        }
        container arp-snoop {
          if-feature "arp-snoop";
          presence "Indicates a arp-snoop node is configured.";
          description
            "Enable ARP packet snooping on client ports on this slice";
        }
        container split-client-port-mapping {
          if-feature "split-client-port-mapping";
          presence "Indicates a split-client-port-mapping node is configured.";
          description
            "Config to choose new port mapping";
        }
        container protected {
          presence "Indicates a protected node is configured.";
          description
            "Enable ARP packet snooping on client ports on this slice";
        }
      }
      container regen {
        if-feature "regen";
        description
          "regenerator Module configuration";
        leaf trunk-rate {
          if-feature "trunk-rate";
          type enumeration {
            enum "100G" {
              value 2;
              description
                "trunk bitrate 100Gbps";
            }
            enum "200G" {
              value 4;
              description
                "trunk bitrate 200Gbps";
            }
            enum "300G" {
              value 6;
              description
                "trunk bitrate 300Gbps";
            }
            enum "400G" {
              value 8;
              description
                "trunk bitrate 400Gbps";
            }
            enum "500G" {
              value 10;
              description
                "trunk bitrate 500Gbps";
            }
            enum "600G" {
              value 12;
              description
                "trunk bitrate 600Gbps";
            }
            enum "700G" {
              value 13;
              description
                "trunk bitrate 700Gbps";
            }
            enum "800G" {
              value 14;
              description
                "trunk bitrate 800Gbps";
            }
            enum "900G" {
              value 15;
              description
                "trunk bitrate 900Gbps";
            }
            enum "1000G" {
              value 16;
              description
                "trunk bitrate 1000Gbps";
            }
            enum "1100G" {
              value 17;
              description
                "trunk bitrate 1100Gbps";
            }
            enum "1200G" {
              value 18;
              description
                "trunk bitrate 1200Gbps";
            }
          }
          description
            "Trunk side parameters";
        }
      }
      container regen-slices {
        description
          "regenerator Module configuration";
        list regen-slice {
          key "regen-slice-id";
          description
            "regenerator Module configuration";
          leaf regen-slice-id {
            type uint32 {
              range "0..15" {
                description
                  "Enter the slice number";
              }
            }
            description
              "regenerator Module configuration";
          }
          leaf trunk-rate {
            type enumeration {
              enum "100G" {
                value 2;
                description
                  "trunk bitrate 100Gbps";
              }
              enum "200G" {
                value 4;
                description
                  "trunk bitrate 200Gbps";
              }
              enum "300G" {
                value 6;
                description
                  "trunk bitrate 300Gbps";
              }
              enum "400G" {
                value 8;
                description
                  "trunk bitrate 400Gbps";
              }
              enum "500G" {
                value 10;
                description
                  "trunk bitrate 500Gbps";
              }
              enum "600G" {
                value 12;
                description
                  "trunk bitrate 600Gbps";
              }
              enum "800G" {
                value 14;
                description
                  "trunk bitrate 800Gbps";
              }
            }
            description
              "Trunk side parameters";
          }
          leaf client-rate {
            type enumeration {
              enum "100G" {
                value 2;
                description
                  "client type 100G Ethernets";
              }
              enum "400G" {
                value 8;
                description
                  "client type 400G Ethernet";
              }
            }
            description
              "Regen Client to select";
          }
        }
      }
      container ols-ports {
        description
          "ols port  configuration";
        list ols-port {
          key "ols-port-id";
          description
            "ols port  configuration";
          leaf ols-port-id {
            type uint32 {
              range "0..15" {
                description
                  "Enter the port number";
              }
            }
            description
              "ols port  configuration";
          }
          leaf mode {
            type enumeration {
              enum "edfa" {
                value 1;
                description
                  "mode edfa";
              }
            }
            description
              "mode parameters";
          }
        }
      }
      container mxponder-slices {
        description
          "Slice configuration";
        list mxponder-slice {
          if-feature "mxponder-slice";
          key "slice-number";
          description
            "Slice configuration";
          leaf slice-number {
            type uint32 {
              range "0..15" {
                description
                  "Enter the slice number";
              }
            }
            description
              "Slice configuration";
          }
          leaf client-rate {
            if-feature "client-rate";
            type enumeration {
              enum "100GE" {
                value 2;
                description
                  "client type 100G Ethernet";
              }
              enum "OTU4" {
                value 3;
                description
                  "client type OTU4";
              }
              enum "400GE" {
                value 8;
                description
                  "client type 400G Ethernet";
              }
              enum "800GE" {
                value 14;
                description
                  "client type 800G Ethernet";
              }
            }
            description
              "Client side parameters";
          }
          leaf trunk-mode {
            type enumeration {
              enum "OR" {
                value 1;
                description
                  "trunk mode openroadm";
              }
              enum "ZR" {
                value 2;
                description
                  "trunk mode ZR";
              }
            }
            description
              "Trunk mode to select";
          }
          leaf trunk-rate {
            if-feature "trunk-rate";
            type enumeration {
              enum "100G" {
                value 2;
                description
                  "trunk bitrate 100Gbps";
              }
              enum "150G" {
                value 3;
                description
                  "trunk bitrate 150Gbps";
              }
              enum "200G" {
                value 4;
                description
                  "trunk bitrate 200Gbps";
              }
              enum "250G" {
                value 5;
                description
                  "trunk bitrate 250Gbps";
              }
              enum "300G" {
                value 6;
                description
                  "trunk bitrate 300Gbps";
              }
              enum "350G" {
                value 7;
                description
                  "trunk bitrate 350Gbps";
              }
              enum "400G" {
                value 8;
                description
                  "trunk bitrate 400Gbps";
              }
              enum "450G" {
                value 9;
                description
                  "trunk bitrate 450Gbps";
              }
              enum "500G" {
                value 10;
                description
                  "trunk bitrate 500Gbps";
              }
              enum "550G" {
                value 11;
                description
                  "trunk bitrate 550Gbps";
              }
              enum "600G" {
                value 12;
                description
                  "trunk bitrate 600Gbps";
              }
              enum "700G" {
                value 13;
                description
                  "trunk bitrate 700Gbps";
              }
              enum "800G" {
                value 14;
                description
                  "trunk bitrate 800Gbps";
              }
              enum "900G" {
                value 15;
                description
                  "trunk bitrate 900Gbps";
              }
              enum "1000G" {
                value 16;
                description
                  "trunk bitrate 1000Gbps";
              }
              enum "1100G" {
                value 17;
                description
                  "trunk bitrate 1100Gbps";
              }
              enum "1200G" {
                value 18;
                description
                  "trunk bitrate 1200Gbps";
              }
            }
            description
              "Trunk side parameters";
          }
          container client-port-rates {
            description
              "client port rate configuration";
            list client-port-rate {
              if-feature "client-port-rate";
              key "port-number lane-number";
              description
                "client port rate configuration";
              leaf port-number {
                type uint32 {
                  range "0..31" {
                    description
                      "Enter port number";
                  }
                }
                description
                  "client port rate configuration";
              }
              leaf lane-number {
                type uint32 {
                  range "1..8" {
                    description
                      "Enter Lane number";
                  }
                }
                description
                  "If port is in Breakout mode, specify optics lane number";
              }
              leaf client-type {
                type enumeration {
                  enum "100GE" {
                    value 2;
                    description
                      "client 100GE";
                  }
                  enum "OTU4" {
                    value 3;
                    description
                      "client OTU4";
                  }
                  enum "400GE" {
                    value 8;
                    description
                      "client 400GE";
                  }
                  enum "800GE" {
                    value 14;
                    description
                      "client 800GE";
                  }
                }
                mandatory true;
                description
                  "Client Rate to be configured";
              }
            }
          }
          container client-port-ains-soak {
            if-feature "client-port-ains-soak";
            description
              "Client ports AINS configuration";
            leaf hours {
              type uint32 {
                range "0..48" {
                  description
                    "Default AINS soak interval hours value";
                }
              }
              must "../minutes";
              description
                "Default AINS soak interval hours value";
            }
            leaf minutes {
              type uint32 {
                range "0..59" {
                  description
                    "Default AINS soak interval minutes value";
                }
              }
              must "../hours";
              description
                "Default AINS soak interval minutes value";
            }
          }
          container drop-lldp {
            if-feature "drop-lldp";
            presence "Indicates a drop-lldp node is configured.";
            description
              "Drop LLDP packets coming on client ports on this slice";
          }
          container arp-snoop {
            if-feature "arp-snoop";
            presence "Indicates a arp-snoop node is configured.";
            description
              "Enable ARP packet snooping on client ports on this slice";
          }
        }
      }
      container attention-led {
        if-feature "attention-led";
        description
          "Attention LED Configuration";
        container all-ports {
          if-feature "all-ports";
          presence "Indicates a all-ports node is configured.";
          description
            "Enable Attention LED on all the Ports of Line Card";
        }
        container ports {
          description
            "Enable Attention LED on given Port Number of Line Card";
          list port {
            if-feature "port";
            key "port-id";
            description
              "Enable Attention LED on given Port Number of Line Card";
            leaf port-id {
              type uint32 {
                range "0..15" {
                  description
                    "Enter port number";
                }
              }
              description
                "Enable Attention LED on given Port Number of Line Card";
            }
          }
        }
      }
      container terminal-ampli {
        if-feature "terminal-ampli";
        description
          "OLT configuration";
        container grid-mode {
          if-feature "grid-mode";
          description
            "Grid Mode Configuration";
          container flex {
            description
              "Flexible Grid Channel Configuration";
            container channel-ids {
              description
                "Channel ID Configuration";
              list channel-id {
                if-feature "channel-id";
                key "channel-id";
                description
                  "Channel ID Configuration";
                leaf channel-id {
                  type uint32 {
                    range "0..4294967295" {
                      description
                        "Enter Channel-id";
                    }
                  }
                  description
                    "Channel ID Configuration";
                }
                leaf centre-freq {
                  type xr:Cisco-ios-xr-string {
                    length "1..11" {
                      description
                        "Enter Centre Frequency in THz(resolution 100MHz)";
                    }
                  }
                  must "../width";
                  description
                    "Centre Frequency Configuration";
                }
                leaf width {
                  type xr:Cisco-ios-xr-string {
                    length "1..11" {
                      description
                        "Enter Channel Width in GHz(resolution 100MHz)";
                    }
                  }
                  must "../centre-freq";
                  description
                    "Channel Width Configuration";
                }
                container ase-loading {
                  description
                    "ASE Loading Configuration on per Channel";
                  container disable {
                    presence "Indicates a disable node is configured.";
                    description
                      "Disable the ASE Loading per channel";
                  }
                }
                container ase-loading-force {
                  presence "Indicates ase-loading-force node is configured.";
                  description
                    "ASE Loading Force Configuration on per Channel";
                }
              }
            }
          }
        }
        container ase-loading {
          description
            "ASE Loading configuration at module level";
          container disable {
            presence "Indicates a disable node is configured.";
            description
              "Disable ASE loading at module level";
          }
        }
        container static-ase-disable {
          presence "Indicates a static-ase-disable node is configured.";
          description
            "Disable Static ASE at module level";
        }
        leaf ase-guard-band-width {
          type xr:Cisco-ios-xr-string {
            length "1..7" {
              description
                "Enter ASE Guard Band Width in GHz in range of 0 to 12.5 GHz with maximum of 3 digits after decimal";
            }
          }
          description
            "ASE Guard Band Width Configuration";
        }
        leaf ase-tx-voa {
          type uint32 {
            range "0..200" {
              description
                "Select attenuation level (in units of 0.1dB)";
            }
          }
          description
            "Configure ASE TX voa Attenuation Setpoint";
        }
        leaf channel-restoration-holdoff-timer {
          type uint32 {
            range "1..600" {
              description
                "Sets the delay (in seconds) before restoring a failed channel. Range: 1-600s.";
            }
          }
          description
            "Channel Restoration Holdoff Timer Configuration";
        }
      }
      container inline-ampli {
        if-feature "inline-ampli";
        description
          "ILA configuration";
        container grid-mode {
          if-feature "grid-mode";
          description
            "Grid Mode Configuration";
          container flex {
            description
              "Flexible Grid Channel Configuration";
            container channel-ids {
              description
                "Channel ID Configuration";
              list channel-id {
                if-feature "channel-id";
                key "channel-id";
                description
                  "Channel ID Configuration";
                leaf channel-id {
                  type uint32 {
                    range "0..4294967295" {
                      description
                        "Enter Channel-id";
                    }
                  }
                  description
                    "Channel ID Configuration";
                }
                leaf centre-freq {
                  type xr:Cisco-ios-xr-string {
                    length "1..11" {
                      description
                        "Enter Centre Frequency in THz(resolution 100MHz)";
                    }
                  }
                  must "../width";
                  description
                    "Centre Frequency Configuration";
                }
                leaf width {
                  type xr:Cisco-ios-xr-string {
                    length "1..11" {
                      description
                        "Enter Channel Width in GHz(resolution 100MHz)";
                    }
                  }
                  must "../centre-freq";
                  description
                    "Channel Width Configuration";
                }
              }
            }
          }
        }
      }
    }
  }

  augment "/location:locations/location:location" {
    description
      "This augment extends active nodes configuration";
    uses LOCATION-BODY;
  }
  augment "/location:locations/location:preconfigured-location" {
    description
      "This augment extends preconfigured nodes
       configuration";
    uses LOCATION-BODY;
  }
  container ains-soak {
    description
      "AINS configuration";
    leaf hours {
      type uint32 {
        range "0..48" {
          description
            "Default AINS soak interval hours value";
        }
      }
      must "../minutes";
      description
        "Default AINS soak interval hours value";
    }
    leaf minutes {
      type uint32 {
        range "0..59" {
          description
            "Default AINS soak interval minutes value";
        }
      }
      must "../hours";
      description
        "Default AINS soak interval minutes value";
    }
  }
  container reserve-slot {
    description
      "reserve_slot configuration";
    container locations {
      description
        "Fully qualified location specification";
      list location {
        key "location-name";
        description
          "Fully qualified location specification";
        leaf location-name {
          type xr:Cisco-ios-xr-string;
          description
            "Fully qualified location specification";
        }
        container cardtype {
          description
            "cardtype specification";
          container ncs1k4-1-2t-k9 {
            must
              "not(../ncs1k4-1-2t-l-k9 or ../ncs1k4-1-2tl-k9
               or ../ncs1k4-otn-xp or ../ncs1k4-otn-xpl
               or ../ncs1k4-2-qdd-c-k9 or ../ncs1k4-lc-filler
               or ../ncs1k4-qxp-k9 or ../ncs1k4-qxp-l-k9
               or ../ncs1k4-2-qdd-ck9l or ../ncs1k14-2-4t-k9
               or ../ncs1k14-2-4t-l-k9 or ../ncs1k14-blank
               or ../ncs1k14-ccmd-16-c or ../ncs1k14-ccmd-16-l
               or ../ncs1k14-2-4t-x-k9 or ../ncs1k14-2-4txl-k9
               or ../ncs1k14-edfa2 or ../ncs1k14-2-4t-a-k9
               or ../ncs1k14-2-4tal-k9)";
            presence "Indicates a ncs1k4-1-2t-k9 node is configured.";
            description
              "   NCS1K4 12x QSFP28 2 Trunk C-Band DWDM card";
          }
          container ncs1k4-1-2t-l-k9 {
            must
              "not(../ncs1k4-1-2t-k9 or ../ncs1k4-1-2tl-k9
               or ../ncs1k4-otn-xp or ../ncs1k4-otn-xpl
               or ../ncs1k4-2-qdd-c-k9 or ../ncs1k4-lc-filler
               or ../ncs1k4-qxp-k9 or ../ncs1k4-qxp-l-k9
               or ../ncs1k4-2-qdd-ck9l or ../ncs1k14-2-4t-k9
               or ../ncs1k14-2-4t-l-k9 or ../ncs1k14-blank
               or ../ncs1k14-ccmd-16-c or ../ncs1k14-ccmd-16-l
               or ../ncs1k14-2-4t-x-k9 or ../ncs1k14-2-4txl-k9
               or ../ncs1k14-edfa2 or ../ncs1k14-2-4t-a-k9
               or ../ncs1k14-2-4tal-k9)";
            presence "Indicates a ncs1k4-1-2t-l-k9 node is configured.";
            description
              "NCS1K4 12x QSFP28 2 Trunk C-Band DWDM Licenced card";
          }
          container ncs1k4-1-2tl-k9 {
            must
              "not(../ncs1k4-1-2t-k9 or ../ncs1k4-1-2t-l-k9
               or ../ncs1k4-otn-xp or ../ncs1k4-otn-xpl
               or ../ncs1k4-2-qdd-c-k9 or ../ncs1k4-lc-filler
               or ../ncs1k4-qxp-k9 or ../ncs1k4-qxp-l-k9
               or ../ncs1k4-2-qdd-ck9l or ../ncs1k14-2-4t-k9
               or ../ncs1k14-2-4t-l-k9 or ../ncs1k14-blank
               or ../ncs1k14-ccmd-16-c or ../ncs1k14-ccmd-16-l
               or ../ncs1k14-2-4t-x-k9 or ../ncs1k14-2-4txl-k9
               or ../ncs1k14-edfa2 or ../ncs1k14-2-4t-a-k9
               or ../ncs1k14-2-4tal-k9)";
            presence "Indicates a ncs1k4-1-2tl-k9 node is configured.";
            description
              "NCS1K4 12x QSFP28 2 Trunk L-Band DWDM card";
          }
          container ncs1k4-otn-xp {
            must
              "not(../ncs1k4-1-2t-k9 or ../ncs1k4-1-2t-l-k9
               or ../ncs1k4-1-2tl-k9 or ../ncs1k4-otn-xpl
               or ../ncs1k4-2-qdd-c-k9 or ../ncs1k4-lc-filler
               or ../ncs1k4-qxp-k9 or ../ncs1k4-qxp-l-k9
               or ../ncs1k4-2-qdd-ck9l or ../ncs1k14-2-4t-k9
               or ../ncs1k14-2-4t-l-k9 or ../ncs1k14-blank
               or ../ncs1k14-ccmd-16-c or ../ncs1k14-ccmd-16-l
               or ../ncs1k14-2-4t-x-k9 or ../ncs1k14-2-4txl-k9
               or ../ncs1k14-edfa2 or ../ncs1k14-2-4t-a-k9
               or ../ncs1k14-2-4tal-k9)";
            presence "Indicates a ncs1k4-otn-xp node is configured.";
            description
              "    Cisco NCS1004 BO LC";
          }
          container ncs1k4-otn-xpl {
            must
              "not(../ncs1k4-1-2t-k9 or ../ncs1k4-1-2t-l-k9
               or ../ncs1k4-1-2tl-k9 or ../ncs1k4-otn-xp
               or ../ncs1k4-2-qdd-c-k9 or ../ncs1k4-lc-filler
               or ../ncs1k4-qxp-k9 or ../ncs1k4-qxp-l-k9
               or ../ncs1k4-2-qdd-ck9l or ../ncs1k14-2-4t-k9
               or ../ncs1k14-2-4t-l-k9 or ../ncs1k14-blank
               or ../ncs1k14-ccmd-16-c or ../ncs1k14-ccmd-16-l
               or ../ncs1k14-2-4t-x-k9 or ../ncs1k14-2-4txl-k9
               or ../ncs1k14-edfa2 or ../ncs1k14-2-4t-a-k9
               or ../ncs1k14-2-4tal-k9)";
            presence "Indicates a ncs1k4-otn-xpl node is configured.";
            description
              "    Cisco NCS1004 BO Licensed LC";
          }
          container ncs1k4-2-qdd-c-k9 {
            must
              "not(../ncs1k4-1-2t-k9 or ../ncs1k4-1-2t-l-k9
               or ../ncs1k4-1-2tl-k9 or ../ncs1k4-otn-xp
               or ../ncs1k4-otn-xpl or ../ncs1k4-lc-filler
               or ../ncs1k4-qxp-k9 or ../ncs1k4-qxp-l-k9
               or ../ncs1k4-2-qdd-ck9l or ../ncs1k14-2-4t-k9
               or ../ncs1k14-2-4t-l-k9 or ../ncs1k14-blank
               or ../ncs1k14-ccmd-16-c or ../ncs1k14-ccmd-16-l
               or ../ncs1k14-2-4t-x-k9 or ../ncs1k14-2-4txl-k9
               or ../ncs1k14-edfa2 or ../ncs1k14-2-4t-a-k9
               or ../ncs1k14-2-4tal-k9)";
            presence "Indicates a ncs1k4-2-qdd-c-k9 node is configured.";
            description
              "NCS1K4 8x QSFP28/2x QSFPDD 2 Trunk C-Band DWDM LC";
          }
          container ncs1k4-lc-filler {
            must
              "not(../ncs1k4-1-2t-k9 or ../ncs1k4-1-2t-l-k9
               or ../ncs1k4-1-2tl-k9 or ../ncs1k4-otn-xp
               or ../ncs1k4-otn-xpl or ../ncs1k4-2-qdd-c-k9
               or ../ncs1k4-qxp-k9 or ../ncs1k4-qxp-l-k9
               or ../ncs1k4-2-qdd-ck9l or ../ncs1k14-2-4t-k9
               or ../ncs1k14-2-4t-l-k9 or ../ncs1k14-blank
               or ../ncs1k14-ccmd-16-c or ../ncs1k14-ccmd-16-l
               or ../ncs1k14-2-4t-x-k9 or ../ncs1k14-2-4txl-k9
               or ../ncs1k14-edfa2 or ../ncs1k14-2-4t-a-k9
               or ../ncs1k14-2-4tal-k9)";
            presence "Indicates a ncs1k4-lc-filler node is configured.";
            description
              "   Network Convergence System 1004 Filler";
          }
          container ncs1k4-qxp-k9 {
            must
              "not(../ncs1k4-1-2t-k9 or ../ncs1k4-1-2t-l-k9
               or ../ncs1k4-1-2tl-k9 or ../ncs1k4-otn-xp
               or ../ncs1k4-otn-xpl or ../ncs1k4-2-qdd-c-k9
               or ../ncs1k4-lc-filler or ../ncs1k4-qxp-l-k9
               or ../ncs1k4-2-qdd-ck9l or ../ncs1k14-2-4t-k9
               or ../ncs1k14-2-4t-l-k9 or ../ncs1k14-blank
               or ../ncs1k14-ccmd-16-c or ../ncs1k14-ccmd-16-l
               or ../ncs1k14-2-4t-x-k9 or ../ncs1k14-2-4txl-k9
               or ../ncs1k14-edfa2 or ../ncs1k14-2-4t-a-k9
               or ../ncs1k14-2-4tal-k9)";
            presence "Indicates a ncs1k4-qxp-k9 node is configured.";
            description
              "NCS1004 3.2T QSFP-DD DCO Transponder";
          }
          container ncs1k4-qxp-l-k9 {
            must
              "not(../ncs1k4-1-2t-k9 or ../ncs1k4-1-2t-l-k9
               or ../ncs1k4-1-2tl-k9 or ../ncs1k4-otn-xp
               or ../ncs1k4-otn-xpl or ../ncs1k4-2-qdd-c-k9
               or ../ncs1k4-lc-filler or ../ncs1k4-qxp-k9
               or ../ncs1k4-2-qdd-ck9l or ../ncs1k14-2-4t-k9
               or ../ncs1k14-2-4t-l-k9 or ../ncs1k14-blank
               or ../ncs1k14-ccmd-16-c or ../ncs1k14-ccmd-16-l
               or ../ncs1k14-2-4t-x-k9 or ../ncs1k14-2-4txl-k9
               or ../ncs1k14-edfa2 or ../ncs1k14-2-4t-a-k9
               or ../ncs1k14-2-4tal-k9)";
            presence "Indicates a ncs1k4-qxp-l-k9 node is configured.";
            description
              "NCS1004 3.2T Licenced QSFP-DD DCO Transponder";
          }
          container NCS1K-OLT-C {
            must
              "not(../NCS1K-OLT-R-C or ../NCS1K-ILA-C
               or ../NCS1K-ILA-R-C or ../NCS1K-ILA-2R-C
               or ../NCS1K-OLT-L or ../NCS1K-ILA-L
               or ../NCS1K-E-OLT-L or ../NCS1K-E-OLT-C
               or ../NCS1K-E-OLT-R-C or ../NCS1K-E-ILA-R-C
               or ../NCS1K-E-ILA-R-C-2 or ../NCS1K-E-ILA-2R-C)";
            presence "Indicates a NCS1K-OLT-C node is configured.";
            description
              "NCS1K Optical Line Terminal C-band Card";
          }
          container NCS1K-OLT-R-C {
            must
              "not(../NCS1K-OLT-C or ../NCS1K-ILA-C
               or ../NCS1K-ILA-R-C or ../NCS1K-ILA-2R-C
               or ../NCS1K-OLT-L or ../NCS1K-ILA-L
               or ../NCS1K-E-OLT-L or ../NCS1K-E-OLT-C
               or ../NCS1K-E-OLT-R-C or ../NCS1K-E-ILA-R-C
               or ../NCS1K-E-ILA-R-C-2 or ../NCS1K-E-ILA-2R-C)";
            presence "Indicates a NCS1K-OLT-R-C node is configured.";
            description
              "NCS1K Optical Line Terminal C-band Card + Raman Card";
          }
          container NCS1K-ILA-C {
            must
              "not(../NCS1K-OLT-C or ../NCS1K-OLT-R-C
               or ../NCS1K-ILA-R-C or ../NCS1K-ILA-2R-C
               or ../NCS1K-OLT-L or ../NCS1K-ILA-L
               or ../NCS1K-E-OLT-L or ../NCS1K-E-OLT-C
               or ../NCS1K-E-OLT-R-C or ../NCS1K-E-ILA-R-C
               or ../NCS1K-E-ILA-R-C-2 or ../NCS1K-E-ILA-2R-C)";
            presence "Indicates a NCS1K-ILA-C node is configured.";
            description
              "NCS1K In-Line Amplifier C-band Card";
          }
          container NCS1K-ILA-R-C {
            must
              "not(../NCS1K-OLT-C or ../NCS1K-OLT-R-C
               or ../NCS1K-ILA-C or ../NCS1K-ILA-2R-C
               or ../NCS1K-OLT-L or ../NCS1K-ILA-L
               or ../NCS1K-E-OLT-L or ../NCS1K-E-OLT-C
               or ../NCS1K-E-OLT-R-C or ../NCS1K-E-ILA-R-C
               or ../NCS1K-E-ILA-R-C-2 or ../NCS1K-E-ILA-2R-C)";
            presence "Indicates a NCS1K-ILA-R-C node is configured.";
            description
              "NCS1K In-Line Amplifier C-band Card + Raman Card";
          }
          container NCS1K-ILA-2R-C {
            must
              "not(../NCS1K-OLT-C or ../NCS1K-OLT-R-C
               or ../NCS1K-ILA-C or ../NCS1K-ILA-R-C
               or ../NCS1K-OLT-L or ../NCS1K-ILA-L
               or ../NCS1K-E-OLT-L or ../NCS1K-E-OLT-C
               or ../NCS1K-E-OLT-R-C or ../NCS1K-E-ILA-R-C
               or ../NCS1K-E-ILA-R-C-2 or ../NCS1K-E-ILA-2R-C)";
            presence "Indicates a NCS1K-ILA-2R-C node is configured.";
            description
              "NCS1K In-Line Amplifier C-band Card + 2 Raman Card";
          }
          container NCS1K-OLT-L {
            must
              "not(../NCS1K-OLT-C or ../NCS1K-OLT-R-C
               or ../NCS1K-ILA-C or ../NCS1K-ILA-R-C
               or ../NCS1K-ILA-2R-C or ../NCS1K-ILA-L
               or ../NCS1K-E-OLT-L or ../NCS1K-E-OLT-C
               or ../NCS1K-E-OLT-R-C or ../NCS1K-E-ILA-R-C
               or ../NCS1K-E-ILA-R-C-2 or ../NCS1K-E-ILA-2R-C)";
            presence "Indicates a NCS1K-OLT-L node is configured.";
            description
              "NCS1K Optical Line Terminal L-band Card";
          }
          container NCS1K-ILA-L {
            must
              "not(../NCS1K-OLT-C or ../NCS1K-OLT-R-C
               or ../NCS1K-ILA-C or ../NCS1K-ILA-R-C
               or ../NCS1K-ILA-2R-C or ../NCS1K-OLT-L
               or ../NCS1K-E-OLT-L or ../NCS1K-E-OLT-C
               or ../NCS1K-E-OLT-R-C or ../NCS1K-E-ILA-R-C
               or ../NCS1K-E-ILA-R-C-2 or ../NCS1K-E-ILA-2R-C)";
            presence "Indicates a NCS1K-ILA-L node is configured.";
            description
              "NCS1K In-Line Amplifier L-band Card";
          }
          container NCS1K-E-OLT-L {
            must
              "not(../NCS1K-OLT-C or ../NCS1K-OLT-R-C
               or ../NCS1K-ILA-C or ../NCS1K-ILA-R-C
               or ../NCS1K-ILA-2R-C or ../NCS1K-OLT-L
               or ../NCS1K-ILA-L or ../NCS1K-E-OLT-C
               or ../NCS1K-E-OLT-R-C or ../NCS1K-E-ILA-R-C
               or ../NCS1K-E-ILA-R-C-2 or ../NCS1K-E-ILA-2R-C)";
            presence "Indicates a NCS1K-E-OLT-L node is configured.";
            description
              "NCS1K Enceladus Optical Line Terminal L-band Card";
          }
          container NCS1K-E-OLT-C {
            must
              "not(../NCS1K-OLT-C or ../NCS1K-OLT-R-C
               or ../NCS1K-ILA-C or ../NCS1K-ILA-R-C
               or ../NCS1K-ILA-2R-C or ../NCS1K-OLT-L
               or ../NCS1K-ILA-L or ../NCS1K-E-OLT-L
               or ../NCS1K-E-OLT-R-C or ../NCS1K-E-ILA-R-C
               or ../NCS1K-E-ILA-R-C-2 or ../NCS1K-E-ILA-2R-C)";
            presence "Indicates a NCS1K-E-OLT-C node is configured.";
            description
              "NCS1K Enceladus Optical Line Terminal C-band Card";
          }
          container NCS1K-E-OLT-R-C {
            must
              "not(../NCS1K-OLT-C or ../NCS1K-OLT-R-C
               or ../NCS1K-ILA-C or ../NCS1K-ILA-R-C
               or ../NCS1K-ILA-2R-C or ../NCS1K-OLT-L
               or ../NCS1K-ILA-L or ../NCS1K-E-OLT-L
               or ../NCS1K-E-OLT-C or ../NCS1K-E-ILA-R-C
               or ../NCS1K-E-ILA-R-C-2 or ../NCS1K-E-ILA-2R-C)";
            presence "Indicates a NCS1K-E-OLT-R-C node is configured.";
            description
              "NCS1K Enceladus Optical Line Terminal C-band Card + Raman Card";
          }
          container NCS1K-E-ILA-R-C {
            must
              "not(../NCS1K-OLT-C or ../NCS1K-OLT-R-C
               or ../NCS1K-ILA-C or ../NCS1K-ILA-R-C
               or ../NCS1K-ILA-2R-C or ../NCS1K-OLT-L
               or ../NCS1K-ILA-L or ../NCS1K-E-OLT-L
               or ../NCS1K-E-OLT-C or ../NCS1K-E-OLT-R-C
               or ../NCS1K-E-ILA-R-C-2 or ../NCS1K-E-ILA-2R-C)";
            presence "Indicates a NCS1K-E-ILA-R-C node is configured.";
            description
              "NCS1K Enceladus In-Line Amplifier C-band Card + Raman Card";
          }
          container NCS1K-E-ILA-R-C-2 {
            must
              "not(../NCS1K-OLT-C or ../NCS1K-OLT-R-C
               or ../NCS1K-ILA-C or ../NCS1K-ILA-R-C
               or ../NCS1K-ILA-2R-C or ../NCS1K-OLT-L
               or ../NCS1K-ILA-L or ../NCS1K-E-OLT-L
               or ../NCS1K-E-OLT-C or ../NCS1K-E-OLT-R-C
               or ../NCS1K-E-ILA-R-C or ../NCS1K-E-ILA-2R-C)";
            presence "Indicates a NCS1K-E-ILA-R-C-2 node is configured.";
            description
              "NCS1K Enceladus In-Line Amplifier C-band Card + Raman2 Card";
          }
          container NCS1K-E-ILA-2R-C {
            must
              "not(../NCS1K-OLT-C or ../NCS1K-OLT-R-C
               or ../NCS1K-ILA-C or ../NCS1K-ILA-R-C
               or ../NCS1K-ILA-2R-C or ../NCS1K-OLT-L
               or ../NCS1K-ILA-L or ../NCS1K-E-OLT-L
               or ../NCS1K-E-OLT-C or ../NCS1K-E-OLT-R-C
               or ../NCS1K-E-ILA-R-C or ../NCS1K-E-ILA-R-C-2)";
            presence "Indicates a NCS1K-E-ILA-2R-C node is configured.";
            description
              "NCS1K Enceladus In-Line Amplifier L-band Card + 2 Raman Card";
          }
          container ncs1k4-2-qdd-ck9l {
            must
              "not(../ncs1k4-1-2t-k9 or ../ncs1k4-1-2t-l-k9
               or ../ncs1k4-1-2tl-k9 or ../ncs1k4-otn-xp
               or ../ncs1k4-otn-xpl or ../ncs1k4-2-qdd-c-k9
               or ../ncs1k4-lc-filler or ../ncs1k4-qxp-k9
               or ../ncs1k4-qxp-l-k9 or ../ncs1k14-2-4t-k9
               or ../ncs1k14-2-4t-l-k9 or ../ncs1k14-blank
               or ../ncs1k14-ccmd-16-c or ../ncs1k14-ccmd-16-l
               or ../ncs1k14-2-4t-x-k9 or ../ncs1k14-2-4txl-k9
               or ../ncs1k14-edfa2 or ../ncs1k14-2-4t-a-k9
               or ../ncs1k14-2-4tal-k9)";
            presence "Indicates a ncs1k4-2-qdd-ck9l node is configured.";
            description
              "NCS 1004 800G QDD Licensed Line Card - C-band";
          }
          container ncs1k14-2-4t-k9 {
            must
              "not(../ncs1k4-1-2t-k9 or ../ncs1k4-1-2t-l-k9
               or ../ncs1k4-1-2tl-k9 or ../ncs1k4-otn-xp
               or ../ncs1k4-otn-xpl or ../ncs1k4-2-qdd-c-k9
               or ../ncs1k4-lc-filler or ../ncs1k4-qxp-k9
               or ../ncs1k4-qxp-l-k9 or ../ncs1k4-2-qdd-ck9l
               or ../ncs1k14-2-4t-l-k9 or ../ncs1k14-blank
               or ../ncs1k14-ccmd-16-c or ../ncs1k14-ccmd-16-l
               or ../ncs1k14-2-4t-x-k9 or ../ncs1k14-2-4txl-k9
               or ../ncs1k14-edfa2 or ../ncs1k14-2-4t-a-k9
               or ../ncs1k14-2-4tal-k9)";
            presence "Indicates a ncs1k14-2-4t-k9 node is configured.";
            description
              "    NCS1K14 Pulsar line card";
          }
          container ncs1k14-2-4t-l-k9 {
            must
              "not(../ncs1k4-1-2t-k9 or ../ncs1k4-1-2t-l-k9
               or ../ncs1k4-1-2tl-k9 or ../ncs1k4-otn-xp
               or ../ncs1k4-otn-xpl or ../ncs1k4-2-qdd-c-k9
               or ../ncs1k4-lc-filler or ../ncs1k4-qxp-k9
               or ../ncs1k4-qxp-l-k9 or ../ncs1k4-2-qdd-ck9l
               or ../ncs1k14-2-4t-k9 or ../ncs1k14-blank
               or ../ncs1k14-ccmd-16-c or ../ncs1k14-ccmd-16-l
               or ../ncs1k14-2-4t-x-k9 or ../ncs1k14-2-4txl-k9
               or ../ncs1k14-edfa2 or ../ncs1k14-2-4t-a-k9
               or ../ncs1k14-2-4tal-k9)";
            presence "Indicates a ncs1k14-2-4t-l-k9 node is configured.";
            description
              "NCS1K14 Pulsar Licensed card";
          }
          container ncs1k14-blank {
            must
              "not(../ncs1k4-1-2t-k9 or ../ncs1k4-1-2t-l-k9
               or ../ncs1k4-1-2tl-k9 or ../ncs1k4-otn-xp
               or ../ncs1k4-otn-xpl or ../ncs1k4-2-qdd-c-k9
               or ../ncs1k4-lc-filler or ../ncs1k4-qxp-k9
               or ../ncs1k4-qxp-l-k9 or ../ncs1k4-2-qdd-ck9l
               or ../ncs1k14-2-4t-k9 or ../ncs1k14-2-4t-l-k9
               or ../ncs1k14-ccmd-16-c or ../ncs1k14-ccmd-16-l
               or ../ncs1k14-2-4t-x-k9 or ../ncs1k14-2-4txl-k9
               or ../ncs1k14-edfa2 or ../ncs1k14-2-4t-a-k9
               or ../ncs1k14-2-4tal-k9)";
            presence "Indicates a ncs1k14-blank node is configured.";
            description
              "Network Convergence System 1014 Filler";
          }
          container ncs1k14-ccmd-16-c {
            must
              "not(../ncs1k4-1-2t-k9 or ../ncs1k4-1-2t-l-k9
               or ../ncs1k4-1-2tl-k9 or ../ncs1k4-otn-xp
               or ../ncs1k4-otn-xpl or ../ncs1k4-2-qdd-c-k9
               or ../ncs1k4-lc-filler or ../ncs1k4-qxp-k9
               or ../ncs1k4-qxp-l-k9 or ../ncs1k4-2-qdd-ck9l
               or ../ncs1k14-2-4t-k9 or ../ncs1k14-2-4t-l-k9
               or ../ncs1k14-blank or ../ncs1k14-ccmd-16-l
               or ../ncs1k14-2-4t-x-k9 or ../ncs1k14-2-4txl-k9
               or ../ncs1k14-edfa2 or ../ncs1k14-2-4t-a-k9
               or ../ncs1k14-2-4tal-k9)";
            presence "Indicates a ncs1k14-ccmd-16-c node is configured.";
            description
              "NCS1014 16 port Colorless Direct attach LC with EDFA C-band";
          }
          container ncs1k14-ccmd-16-l {
            must
              "not(../ncs1k4-1-2t-k9 or ../ncs1k4-1-2t-l-k9
               or ../ncs1k4-1-2tl-k9 or ../ncs1k4-otn-xp
               or ../ncs1k4-otn-xpl or ../ncs1k4-2-qdd-c-k9
               or ../ncs1k4-lc-filler or ../ncs1k4-qxp-k9
               or ../ncs1k4-qxp-l-k9 or ../ncs1k4-2-qdd-ck9l
               or ../ncs1k14-2-4t-k9 or ../ncs1k14-2-4t-l-k9
               or ../ncs1k14-blank or ../ncs1k14-ccmd-16-c
               or ../ncs1k14-2-4t-x-k9 or ../ncs1k14-2-4txl-k9
               or ../ncs1k14-edfa2 or ../ncs1k14-2-4t-a-k9
               or ../ncs1k14-2-4tal-k9)";
            presence "Indicates a ncs1k14-ccmd-16-l node is configured.";
            description
              "NCS1014 16 port Colorless Direct attach LC with EDFA L-band";
          }
          container ncs1k14-2-4t-x-k9 {
            must
              "not(../ncs1k4-1-2t-k9 or ../ncs1k4-1-2t-l-k9
               or ../ncs1k4-1-2tl-k9 or ../ncs1k4-otn-xp
               or ../ncs1k4-otn-xpl or ../ncs1k4-2-qdd-c-k9
               or ../ncs1k4-lc-filler or ../ncs1k4-qxp-k9
               or ../ncs1k4-qxp-l-k9 or ../ncs1k4-2-qdd-ck9l
               or ../ncs1k14-2-4t-k9 or ../ncs1k14-2-4t-l-k9
               or ../ncs1k14-blank or ../ncs1k14-ccmd-16-c
               or ../ncs1k14-ccmd-16-l or ../ncs1k14-2-4txl-k9
               or ../ncs1k14-edfa2 or ../ncs1k14-2-4t-a-k9
               or ../ncs1k14-2-4tal-k9)";
            presence "Indicates a ncs1k14-2-4t-x-k9 node is configured.";
            description
              "NCS1K14 DIONE line card";
          }
          container ncs1k14-2-4txl-k9 {
            must
              "not(../ncs1k4-1-2t-k9 or ../ncs1k4-1-2t-l-k9
               or ../ncs1k4-1-2tl-k9 or ../ncs1k4-otn-xp
               or ../ncs1k4-otn-xpl or ../ncs1k4-2-qdd-c-k9
               or ../ncs1k4-lc-filler or ../ncs1k4-qxp-k9
               or ../ncs1k4-qxp-l-k9 or ../ncs1k4-2-qdd-ck9l
               or ../ncs1k14-2-4t-k9 or ../ncs1k14-2-4t-l-k9
               or ../ncs1k14-blank or ../ncs1k14-ccmd-16-c
               or ../ncs1k14-ccmd-16-l or ../ncs1k14-2-4t-x-k9
               or ../ncs1k14-edfa2 or ../ncs1k14-2-4t-a-k9
               or ../ncs1k14-2-4tal-k9)";
            presence "Indicates a ncs1k14-2-4txl-k9 node is configured.";
            description
              "NCS1K14 DIONE lincesed line card";
          }
          container ncs1k14-edfa2 {
            must
              "not(../ncs1k4-1-2t-k9 or ../ncs1k4-1-2t-l-k9
               or ../ncs1k4-1-2tl-k9 or ../ncs1k4-otn-xp
               or ../ncs1k4-otn-xpl or ../ncs1k4-2-qdd-c-k9
               or ../ncs1k4-lc-filler or ../ncs1k4-qxp-k9
               or ../ncs1k4-qxp-l-k9 or ../ncs1k4-2-qdd-ck9l
               or ../ncs1k14-2-4t-k9 or ../ncs1k14-2-4t-l-k9
               or ../ncs1k14-blank or ../ncs1k14-ccmd-16-c
               or ../ncs1k14-ccmd-16-l or ../ncs1k14-2-4t-x-k9
               or ../ncs1k14-2-4txl-k9 or ../ncs1k14-2-4t-a-k9
               or ../ncs1k14-2-4tal-k9)";
            presence "Indicates a ncs1k14-edfa2 node is configured.";
            description
              "NCS1014 Callisto EDFA C-band";
          }
          container ncs1k14-2-4t-a-k9 {
            must
              "not(../ncs1k4-1-2t-k9 or ../ncs1k4-1-2t-l-k9
               or ../ncs1k4-1-2tl-k9 or ../ncs1k4-otn-xp
               or ../ncs1k4-otn-xpl or ../ncs1k4-2-qdd-c-k9
               or ../ncs1k4-lc-filler or ../ncs1k4-qxp-k9
               or ../ncs1k4-qxp-l-k9 or ../ncs1k4-2-qdd-ck9l
               or ../ncs1k14-2-4t-k9 or ../ncs1k14-2-4t-l-k9
               or ../ncs1k14-blank or ../ncs1k14-ccmd-16-c
               or ../ncs1k14-ccmd-16-l or ../ncs1k14-2-4t-x-k9
               or ../ncs1k14-2-4txl-k9 or ../ncs1k14-edfa2
               or ../ncs1k14-2-4tal-k9)";
            presence "Indicates a ncs1k14-2-4t-a-k9 node is configured.";
            description
              "    NCS1K14 Aquila line card";
          }
          container ncs1k14-2-4tal-k9 {
            must
              "not(../ncs1k4-1-2t-k9 or ../ncs1k4-1-2t-l-k9
               or ../ncs1k4-1-2tl-k9 or ../ncs1k4-otn-xp
               or ../ncs1k4-otn-xpl or ../ncs1k4-2-qdd-c-k9
               or ../ncs1k4-lc-filler or ../ncs1k4-qxp-k9
               or ../ncs1k4-qxp-l-k9 or ../ncs1k4-2-qdd-ck9l
               or ../ncs1k14-2-4t-k9 or ../ncs1k14-2-4t-l-k9
               or ../ncs1k14-blank or ../ncs1k14-ccmd-16-c
               or ../ncs1k14-ccmd-16-l or ../ncs1k14-2-4t-x-k9
               or ../ncs1k14-2-4txl-k9 or ../ncs1k14-edfa2
               or ../ncs1k14-2-4t-a-k9)";
            presence "Indicates a ncs1k14-2-4tal-k9 node is configured.";
            description
              "NCS1K14 Aquila licensed line card";
          }
        }
      }
    }
  }
}
