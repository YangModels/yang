module Cisco-IOS-XR-mpls-traceroute-act {
  namespace "http://cisco.com/ns/yang/Cisco-IOS-XR-mpls-traceroute-act";
  prefix mpls-traceroute-act;

  import ietf-inet-types {
    prefix inet;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR mpls traceroute action package configuration
     
     Copyright (c) 2020-2026 by Cisco Systems, Inc., and/or its affiliates.
     All rights reserved.";

  revision 2026-07-08 {
    description
      "Added task authorization for the MPLS traceroute RPC.
       2025-08-06
         Added no-dsmap.
       2023-05-18
         Added SR IPv6 support and new nil-fec mode.";
    semver:module-version "3.0.0";
  }
  revision 2021-07-12 {
    description
      "Added ddmap return code leaf
       2021-05-10
          Added multipath support";
    semver:module-version "2.0.0";
  }
  revision 2021-04-27 {
    description
      "Added missing descriptions";
    semver:module-version "1.0.0";
  }
  revision 2021-04-05 {
    description
      "Added range values for lsp-id and pseudowire leaf values";
  }
  revision 2021-03-25 {
    description
      "Added IP netmask leaf for MPLS and SR traceroute";
  }
  revision 2021-02-03 {
    description
      "Range added for EXP leaf";
  }
  revision 2020-06-05 {
    description
      "Initial revision.";
  }

  typedef mpls-fec-type {
    type enumeration {
      enum "bgp" {
        description
          "MPLS BGP FEC";
      }
      enum "generic" {
        description
          "MPLS Generic FEC";
      }
      enum "ldp" {
        description
          "MPLS LDP FEC";
      }
    }
    description
      "MPLS Forwarding Equivalence Class type";
  }

  typedef sr-fec-type {
    type enumeration {
      enum "bgp" {
        description
          "SR IGP BGP FEC";
      }
      enum "ospf" {
        description
          "SR IGP OSPF FEC";
      }
      enum "isis" {
        description
          "SR IGP ISIS FEC";
      }
    }
    description
      "SR Forwarding Equivalence Class type";
  }

  typedef request-reply-mode {
    type enumeration {
      enum "ipv4" {
        description
          "Reply Mode IPv4";
      }
      enum "router-alert" {
        description
          "Reply Mode Router Alert";
      }
    }
    description
      "Reply mode";
  }

  rpc mpls-traceroute {
    description
      "Send echo messages";
    input {
      choice traceroute-type {
        mandatory true;
        description
          "Specify traceroute type";
        case type-mpls {
          container mpls {
            description
              "MPLS traceroute";
            choice mpls-subtype {
              mandatory true;
              description
                "Traceroute MPLS subtype";
              case subtype-ipv4 {
                container ipv4 {
                  description
                    "Traceroute mpls IPv4 address";
                  leaf ip {
                    type inet:ipv4-address;
                    mandatory true;
                    description
                      "Destination x.x.x.x of traceroute";
                  }
                  choice subnet {
                    mandatory true;
                    description
                      "The subnet can be specified as a prefix-length or as
                       a netmask.";
                    case prefix-length {
                      leaf prefix-length {
                        type uint8 {
                          range "0..32";
                        }
                        default "32";
                        description
                          "The length of the subnet prefix.";
                      }
                    }
                    case netmask {
                      leaf netmask {
                        type inet:ipv4-address;
                        description
                          "The subnet specified as a netmask";
                      }
                    }
                  }
                  leaf fec-type {
                    type mpls-fec-type;
                    description
                      "TLV FEC type to use in request";
                  }
                  leaf multipath {
                    type boolean;
                    default "false";
                    description
                      "Enable LSP multipath traceroute (treetrace)";
                  }
                }
              }
              case subtype-traffic-eng {
                container traffic-eng {
                  description
                    "Trace mpls tunnel";
                  choice tunnel-identifier {
                    mandatory true;
                    description
                      "Tunnel Identifier (LSP name or tunnel-interface)";
                    case subtype-tunnel-name {
                      leaf tunnel-name {
                        type string;
                        description
                          "Next hop tunnel lsp name";
                      }
                    }
                    case subtype-tunnel-interface {
                      leaf tunnel-interface {
                        type string;
                        description
                          "Next hop Interface with form tunnel-te<number>";
                      }
                    }
                  }
                  choice te-lsp-option {
                    description
                      "Specify which LSP to use";
                    case te-lsp-option-active {
                      leaf active-lsp {
                        type boolean;
                        description
                          "Enforce active LSP selection for tunnel";
                      }
                    }
                    case te-lsp-option-id {
                      leaf lsp-id {
                        type uint32 {
                          range "1..10000";
                        }
                        default "1";
                        description
                          "Tunnel Label Switched Path Identifier";
                      }
                    }
                    case te-lsp-option-path-protected {
                      leaf path-protected {
                        type boolean;
                        description
                          "Test path protected LSP for tunnel";
                      }
                    }
                    case te-lsp-option-reoptimized {
                      leaf reoptimized {
                        type boolean;
                        description
                          "Test reoptimized LSP for tunnel";
                      }
                    }
                  }
                }
              }
            }
          }
        }
        case type-sr {
          container sr-mpls {
            description
              "Trace sr-mpls";
            choice sr-target {
              description
                "Trace sr-mpls target type";
              case target_ipv4_prefix {
                container ipv4 {
                  description
                    "Trace sr-mpls IPv4 Prefix SID";
                  leaf ip {
                    type inet:ipv4-address;
                    mandatory true;
                    description
                      "SR LSP Egress IP x.x.x.x";
                  }
                  choice subnet {
                    mandatory true;
                    description
                      "The subnet can be specified as a prefix-length or as
                       a netmask.";
                    case prefix-length {
                      leaf prefix-length {
                        type uint8 {
                          range "0..32";
                        }
                        default "32";
                        description
                          "The length of the subnet prefix.";
                      }
                    }
                    case netmask {
                      leaf netmask {
                        type inet:ipv4-address;
                        description
                          "The subnet specified as a netmask";
                      }
                    }
                  }
                  leaf fec-type {
                    type sr-fec-type;
                    description
                      "SR OAM IGP FEC TLV type to use in request";
                  }
                  leaf nil-fec {
                    type boolean;
                    description
                      "Use Nil-FEC TLV and Append Explicit Null";
                  }
                  leaf multipath {
                    type boolean;
                    default "false";
                    description
                      "Enable LSP multipath traceroute (treetrace)";
                  }
                }
              }
              case target_ipv6_prefix {
                container ipv6 {
                  description
                    "Trace sr-mpls IPv6 Prefix SID";
                  leaf ip {
                    type inet:ipv6-address;
                    mandatory true;
                    description
                      "SR LSP Egress IP X:X::X";
                  }
                  leaf prefix-length {
                    type uint8 {
                      range "0..128";
                    }
                    default "128";
                    description
                      "The length of the subnet prefix.";
                  }
                  leaf fec-type {
                    type sr-fec-type;
                    description
                      "SR OAM IGP FEC TLV type to use in request";
                  }
                  leaf nil-fec {
                    type boolean;
                    description
                      "Use Nil-FEC TLV and Append Explicit Null";
                  }
                  leaf multipath {
                    type boolean;
                    default "false";
                    description
                      "Enable LSP multipath traceroute (treetrace)";
                  }
                }
              }
              case target_labels {
                container labels {
                  description
                    "Trace sr-mpls label stack (up to 12 labels)";
                  list label {
                    key "index";
                    description
                      "Specify label index and value";
                    leaf index {
                      type uint32 {
                        range "0..9";
                      }
                      mandatory true;
                      description
                        "Label index";
                    }
                    leaf label {
                      type uint32 {
                        range "16..1048575";
                      }
                      mandatory true;
                      description
                        "Label value";
                    }
                  }
                  leaf nil-fec {
                    type boolean;
                    description
                      "Use Nil-FEC TLV and Append Explicit Null";
                  }
                  leaf lsp-endpoint {
                    type inet:ip-address;
                    description
                      "Specify the IP of the LSP endpoint";
                  }
                  leaf multipath {
                    type boolean;
                    default "false";
                    description
                      "Enable LSP multipath traceroute (treetrace)";
                  }
                }
              }
              case target_policy {
                container policy {
                  description
                    "Trace sr-mpls policy";
                  choice sr-policy-id {
                    mandatory true;
                    description
                      "SR Policy Identifier (binding sid or policy name)";
                    case sr-policy-id-bsid {
                      leaf bsid {
                        type uint32 {
                          range "16..1048575";
                        }
                        default "16";
                        description
                          "SR Policy Binding SID";
                      }
                    }
                    case sr-policy-id-name {
                      leaf name {
                        type string;
                        description
                          "SR Policy Name";
                      }
                    }
                  }
                  leaf fec-type {
                    type sr-fec-type;
                    description
                      "SR OAM IGP FEC TLV type to use in request";
                  }
                  leaf nil-fec {
                    type boolean;
                    description
                      "Use Nil-FEC TLV and Append Explicit Null";
                  }
                  leaf lsp-endpoint {
                    type inet:ip-address;
                    description
                      "Specify the IP of the LSP endpoint";
                  }
                  leaf multipath {
                    type boolean;
                    default "false";
                    description
                      "Enable LSP multipath traceroute (treetrace)";
                  }
                }
              }
            }
          }
        }
      }
      container request-options-parameters {
        description
          "MPLS echo request options";
        leaf exp {
          type uint8 {
            range "0..7";
          }
          description
            "EXP Bits To Set";
        }
        leaf fec {
          type boolean;
          description
            "Force FEC TLV Checks";
        }
        leaf ddmap {
          type boolean;
          description
            "Use DDMAP (Default is DSMAP)";
        }
        leaf no-dsmap {
          type boolean;
          description
            "No DSMAP (Default is DSMAP)";
        }
        leaf force-explicit-null {
          type boolean;
          description
            "Force explicit null to be added";
        }
        container packet-output {
          description
            "Packet output options";
          leaf interface-name {
            type string;
            description
              "Outgoing interface for echo packet";
          }
          leaf next-hop {
            type inet:ip-address;
            description
              "Outgoing next hop IP for echo packet";
          }
        }
        container reply {
          description
            "Echo Reply options";
          leaf dscp {
            type uint8 {
              range "0..63";
            }
            description
              "Set DSCP reply value 0-63 (decimal)";
          }
          leaf reply-mode {
            type request-reply-mode;
            description
              "Echo Reply Mode";
          }
        }
        leaf source {
          type inet:ip-address;
          description
            "Source IP address to use in the IP header (used as the return address for the reply)";
        }
        leaf destination {
          type inet:ip-address;
          description
            "Destination IP address (127.x.y.z or ::ffff:127.x.y.z))";
        }
        leaf brief {
          type boolean;
          description
            "Brief mode. Does not include statistical data in result";
        }
        leaf timeout {
          type uint32 {
            range "0..3600";
          }
          description
            "Time in seconds before the lack of a reply invalidates a request";
        }
        leaf ttl {
          type uint32 {
            range "1..255";
          }
          description
            "Time to live (hops to until forced punt)";
        }
        leaf retry-count {
          type uint8 {
            range "0..10";
          }
          description
            "Maximum treetrace retry count";
        }
        container hashkey {
          description
            "Downstream map multipath settings";
          container ipv4 {
            description
              "IPv4 bitmap options";
            leaf bitmap {
              type uint16 {
                range "1..256";
              }
              description
                "Multipath bitmap size";
            }
          }
        }
        leaf interval {
          type uint32 {
            range "0..3600000";
          }
          description
            "Send interval between treetrace requests";
        }
      }
    }
    output {
      container mpls-traceroute-response {
        description
          "MPLS traceroute Response";
        container request-options-parameters {
          description
            "Echo Request Options";
          leaf exp {
            type uint8 {
              range "0..7";
            }
            description
              "EXP Bits To Set";
          }
          leaf fec {
            type boolean;
            description
              "Force FEC TLV Checks";
          }
          leaf ddmap {
            type boolean;
            description
              "Use DDMAP (Default is DSMAP)";
          }
          leaf no-dsmap {
            type boolean;
            description
              "No DSMAP (Default is DSMAP)";
          }
          leaf force-explicit-null {
            type boolean;
            description
              "Force an explicit null label to be added";
          }
          leaf force-ipv6-explicit-null {
            type boolean;
            description
              "Force an ipv6 explicit null label to be added";
          }
          container packet-output {
            description
              "Packet output options";
            leaf interface-name {
              type string;
              description
                "Outgoing interface for echo packet";
            }
            leaf next-hop {
              type inet:ip-address;
              description
                "Outgoing next hop IP for echo packet";
            }
          }
          container reply {
            description
              "Reply options";
            leaf dscp {
              type uint8 {
                range "0..63";
              }
              description
                "Set DSCP reply value 0-63 (decimal)";
            }
            leaf reply-mode {
              type request-reply-mode;
              description
                "Echo Reply Mode";
            }
          }
          leaf source {
            type inet:ip-address;
            description
              "Source IP address to use in the IP header (used as the return address for the reply)";
          }
          leaf destination {
            type inet:ip-address;
            description
              "Destination IP address (127.x.y.z or ::ffff:127.x.y.z)";
          }
          leaf brief {
            type boolean;
            description
              "Brief mode. Does not include statistical data in result";
          }
          leaf timeout {
            type uint32 {
              range "0..3600";
            }
            description
              "Time in seconds before the lack of a reply invalidates a request";
          }
          leaf ttl {
            type uint32 {
              range "1..255";
            }
            description
              "Time to live (hops to until forced punt)";
          }
          leaf retry-count {
            type uint8 {
              range "0..10";
            }
            description
              "Maximum treetrace retry count";
          }
          container hashkey {
            description
              "Downstream map multipath settings";
            container ipv4 {
              description
                "IPv4 bitmap options";
              leaf bitmap {
                type uint16 {
                  range "1..256";
                }
                description
                  "Multipath bitmap size";
              }
            }
          }
          leaf interval {
            type uint32 {
              range "0..3600000";
            }
            description
              "Send interval between treetrace requests";
          }
        }
        container paths {
          description
            "Traceroute paths";
          list path {
            key "path-index";
            description
              "Traceroute path";
            leaf path-index {
              type uint64 {
                range "1..2147483647";
              }
              description
                "Index of the path list";
            }
            leaf path-status {
              type string;
              description
                "Treetrace path status (Found, Broken, Unexplored)";
            }
            leaf source {
              type string;
              description
                "Source IP address used in the IP header";
            }
            leaf destination {
              type string;
              description
                "Destination IP address (127.x.y.z) or (::ffff:127.x.y.z)";
            }
            leaf output-interface {
              type string;
              description
                "Outgoing interface for echo packet";
            }
            leaf nexthop {
              type string;
              description
                "Outgoing next hop IP for echo packet";
            }
            container hops {
              description
                "Traceroute Hops";
              list hop {
                key "hop-index";
                description
                  "Traceroute Hop";
                leaf hop-index {
                  type uint64 {
                    range "1..2147483647";
                  }
                  description
                    "Index of the hop list";
                }
                leaf hop-origin-ip {
                  type string;
                  description
                    "Hop origin interface ip";
                }
                leaf hop-destination-ip {
                  type string;
                  description
                    "Hop destination interface ip";
                }
                leaf mtu {
                  type string;
                  description
                    "Maximum Transmission Unit";
                }
                container dsmap-label-stack {
                  description
                    "Label Stack from the DSMAP received
                     in the Echo Response Payload.";
                  list dsmap-label {
                    key "label";
                    description
                      "DSMAP labels";
                    leaf label {
                      type uint32 {
                        range "16..1048575";
                      }
                      description
                        "DSMAP label";
                    }
                  }
                }
                leaf paths-count {
                  type int32;
                  description
                    "Number of outgoing paths. For multipath requests only.";
                }
                leaf return-code {
                  type uint8;
                  description
                    "Return Code of the echo request";
                }
                leaf return-char {
                  type string;
                  description
                    "Return Char of the echo request";
                }
                leaf duration {
                  type uint32;
                  description
                    "Trip duration (msec)";
                }
                container ddmaps {
                  description
                    "Downstream Detailed Mapping received";
                  list ddmap {
                    key "ddmap-index";
                    description
                      "DDMAP";
                    leaf ddmap-index {
                      type uint64 {
                        range "1..2147483647";
                      }
                      description
                        "Index of the hop list";
                    }
                    leaf ddmap-mtu {
                      type int16;
                      description
                        "MTU from the DDMAP received in
                         the Echo Response Payload";
                    }
                    leaf ddmap-downstream-address {
                      type inet:ip-address;
                      description
                        "Downstream Address from the DDMAP
                         received in the Echo Response Payload";
                    }
                    leaf ddmap-downstream-intf-index {
                      type int32 {
                        range "1..2147483647";
                      }
                      description
                        "Downstream Interface Address from the DDMAP
                         received in the Echo Response Payload.";
                    }
                    leaf ddmap-return-char {
                      type string;
                      description
                        "Return Char from the DDMAP received
                         in the Echo Response Payload.";
                    }
                    leaf ddmap-return-code {
                      type uint8;
                      description
                        "Return Code from the DDMAP received
                         in the Echo Response Payload.";
                    }
                    leaf ddmap-return-subcode {
                      type int16;
                      description
                        "Return Sub Code from the DDMAP
                         received in the Echo Response Payload.";
                    }
                    container ddmap-label-stack {
                      description
                        "Label Stack from the DDMAP received
                         in the Echo Response Payload.";
                      list ddmap-label {
                        key "label";
                        description
                          "ddmap labels";
                        leaf label {
                          type uint32 {
                            range "16..1048575";
                          }
                          description
                            "ddmap label";
                        }
                      }
                    }
                    leaf paths-count {
                      type int32;
                      description
                        "Number of outgoing paths. For multipath request only";
                    }
                  }
                }
              }
            }
          }
        }
        container statistics {
          description
            "Treetrace Statistics";
          leaf paths-found {
            type uint32;
            description
              "Number of paths found";
          }
          leaf paths-broken {
            type uint32;
            description
              "Number of paths broken";
          }
          leaf paths-unexplored {
            type uint32;
            description
              "Number of paths unexplored";
          }
          leaf requests-sent {
            type uint32;
            description
              "Number of echo requests sent";
          }
          leaf requests-failed {
            type uint32;
            description
              "Number of echo requests failed";
          }
          leaf requests-received {
            type uint32;
            description
              "Number of echo requests received";
          }
          leaf requests-timeout {
            type uint32;
            description
              "Number of echo requests timed out";
          }
          leaf total-time-elapsed {
            type uint64;
            description
              "The total time taken for the request in ms";
          }
        }
      }
    }
  }
}
