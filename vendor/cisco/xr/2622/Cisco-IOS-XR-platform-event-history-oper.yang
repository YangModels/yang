module Cisco-IOS-XR-platform-event-history-oper {
  namespace "http://cisco.com/ns/yang/Cisco-IOS-XR-platform-event-history-oper";
  prefix platform-event-history-oper;

  import Cisco-IOS-XR-types {
    prefix xr;
  }
  import cisco-semver {
    prefix semver;
  }
  include Cisco-IOS-XR-platform-event-history-oper-sub1 {
    revision-date 2020-04-17;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR platform-event-history package operational data.
     
     This module contains definitions
     for the following management objects:
       platform-event-history: Event History information
     
     Copyright (c) 2013-2020 by Cisco Systems, Inc.
     All rights reserved.";

  revision 2020-04-17 {
    description
      "IOS XR 7.0.14 revision. Deprecate event-discarded field in bag";
    semver:module-version "1.1.0";
  }
  revision 2019-04-05 {
    description
      "Establish semantic version baseline.";
    semver:module-version "1.0.0";
  }
  revision 2015-11-09 {
    description
      "IOS XR 6.0 revision.";
  }

  container platform-event-history {
    config false;
    description
      "Event History information";
    list node {
      key "node-name";
      description
        "Node ID";
      leaf node-name {
        type xr:Node-id;
        description
          "Node name";
      }
      uses EVENT-HISTORY;
    }
  }
}
