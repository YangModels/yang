module Cisco-IOS-XR-install-profile-cfg {
  namespace "http://cisco.com/ns/yang/Cisco-IOS-XR-install-profile-cfg";
  prefix install-profile-cfg;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR install-profile package configuration.
     
     This module contains definitions
     for the following management objects:
       install-shared: Install shared config data
     
     Copyright (c) 2013-2022 by Cisco Systems, Inc.
     All rights reserved.";

  revision 2022-03-25 {
    description
      "Added support for install profile configurations";
    semver:module-version "1.0.0";
  }
  revision 2022-03-09 {
    description
      "Config schema updated";
  }
  revision 2019-04-05 {
    description
      "Establish semantic version baseline.";
  }
  revision 2015-11-09 {
    description
      "IOS XR 6.0 revision.";
  }

  typedef Cleanup-metric-name {
    type enumeration {
      enum "core-cleanup" {
        value 11;
        description
          "core-cleanup metric";
      }
      enum "file-cleanup" {
        value 12;
        description
          "file-cleanup metric";
      }
    }
    description
      "Cleanup metric name";
  }

  typedef Metric-name {
    type enumeration {
      enum "communication-timeout" {
        value 0;
        description
          "communication-timeout metric";
      }
      enum "config-inconsistency" {
        value 1;
        description
          "config-inconsistency metric";
      }
      enum "process-resource" {
        value 2;
        description
          "process-resource metric";
      }
      enum "process-status" {
        value 3;
        description
          "process-status metric";
      }
      enum "system-clock" {
        value 4;
        description
          "system-clock metric";
      }
      enum "hw-monitoring" {
        value 5;
        description
          "hw-monitoring metric";
      }
      enum "lc-monitoring" {
        value 6;
        description
          "lc-monitoring metric";
      }
      enum "pci-monitoring" {
        value 7;
        description
          "pci-monitoring metric";
      }
      enum "wd-monitoring" {
        value 8;
        description
          "wd-monitoring metric";
      }
      enum "disk-space" {
        value 9;
        description
          "disk-space metric";
      }
      enum "upgrade-matrix" {
        value 10;
        description
          "upgrade-matrix metric";
      }
    }
    description
      "Metric name";
  }

  grouping ERROR-ON-FAILURE {
    description
      "Common node of prechecks-metric,
       postchecks-metric";
    leaf error-on-failure {
      type empty;
      description
        "Set the metric action to error-on-failure";
    }
  }

  grouping DISABLE {
    description
      "Common node of prechecks-metric,
       postchecks-metric";
    leaf disable {
      type empty;
      description
        "Disable the specified metric";
    }
  }

  grouping INSTALL-SHARED-CONFIG-DISABLE {
    description
      "Common node of prechecks-metric,
       postchecks-metricCommon node of precheck,
       postcheck";
    leaf disable {
      type empty;
      description
        "Disable pre or post checks";
    }
  }

  grouping WARN-ON-FAILURE {
    description
      "Common node of prechecks-metric,
       postchecks-metric";
    leaf warn-on-failure {
      type empty;
      description
        "Set the metric action to warn-on-failure";
    }
  }

  container install-shared {
    description
      "Install shared config data";
    container profile {
      description
        "Install profile config";
      container default {
        description
          "Supported profile list";
        container precheck {
          description
            "Default profile prechecks";
          container prechecks-metrics {
            description
              "Metric list for prechecks";
            list prechecks-metric {
              key "metric";
              description
                "Name of the metric";
              leaf metric {
                type Metric-name;
                description
                  "Name of the precheck metric";
              }
              uses ERROR-ON-FAILURE;
              uses WARN-ON-FAILURE;
              uses DISABLE;
            }
          }
          container cleanup-metrics {
            description
              "Metric list for pre-upgrade cleanups";
            list cleanup-metric {
              key "metric";
              description
                "Name of the metric";
              leaf enable {
                type empty;
                description
                  "Enable the specified cleanup metric";
              }
              leaf metric {
                type Cleanup-metric-name;
                description
                  "Name of the pre-upgrade cleanup metric";
              }
            }
          }
          uses INSTALL-SHARED-CONFIG-DISABLE;
        }
        container postcheck {
          description
            "Default profile postchecks";
          container postchecks-metrics {
            description
              "Metric list for postchecks";
            list postchecks-metric {
              key "metric";
              description
                "Name of the metric";
              leaf revert-on-failure {
                type empty;
                description
                  "Set the metric action to revert";
              }
              leaf metric {
                type Metric-name;
                description
                  "Name of the postcheck metric";
              }
              uses ERROR-ON-FAILURE;
              uses WARN-ON-FAILURE;
              uses DISABLE;
            }
          }
          uses INSTALL-SHARED-CONFIG-DISABLE;
        }
        leaf disable {
          type empty;
          description
            "Disable the specified profile";
        }
      }
      leaf disable {
        type empty;
        description
          "Disable all supported profiles, checks and
           metrics";
      }
    }
  }
}
