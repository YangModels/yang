submodule Cisco-IOS-XR-issu-oper-sub1 {
  belongs-to Cisco-IOS-XR-issu-oper {
    prefix Cisco-IOS-XR-issu-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR issu package operational data.
     
     Copyright (c) 2013-2024 by Cisco Systems, Inc.
     All rights reserved.";

  revision 2024-07-10 {
    description
      "Make ISSU manageability timestamps 64 bit";
    semver:module-version "1.1.0";
  }
  revision 2019-04-05 {
    description
      "Establish semantic version baseline.";
    semver:module-version "1.0.0";
  }
  revision 2015-11-09 {
    description
      "IOS XR 6.0 revision.";
  }

  typedef Issu-mgbl-node-status {
    type enumeration {
      enum "does-not-exist" {
        description
          "Does not exist";
      }
      enum "exists" {
        description
          "Exists";
      }
      enum "connected" {
        description
          "Connected";
      }
      enum "in-sync" {
        description
          "In sync";
      }
    }
    description
      "Node status type";
  }

  typedef Issu-mgbl-ha-role {
    type enumeration {
      enum "active" {
        description
          "Active";
      }
      enum "standby" {
        description
          "Standby";
      }
      enum "unknown" {
        description
          "Unknown";
      }
    }
    description
      "HA role information";
  }

  typedef Issu-mgbl-role {
    type enumeration {
      enum "primary" {
        description
          "Primary";
      }
      enum "secondary" {
        description
          "Secondary";
      }
      enum "tertiary" {
        description
          "Tertiary";
      }
    }
    description
      "ISSU role information";
  }

  typedef Issu-mgbl-version {
    type enumeration {
      enum "v1" {
        description
          "Version 1";
      }
      enum "v2" {
        description
          "Version 2";
      }
    }
    description
      "ISSU version information";
  }

  typedef Issu-mgbl-service {
    type enumeration {
      enum "none" {
        description
          "None";
      }
      enum "cfg-mgr" {
        description
          "Config Mgr";
      }
      enum "gsp" {
        description
          "GSP";
      }
      enum "install" {
        description
          "Install";
      }
      enum "install-mgr" {
        description
          "Install Mgr";
      }
      enum "install-agt" {
        description
          "Install Agent";
      }
      enum "sdrnm" {
        description
          "SDR Node Mgr";
      }
      enum "sdrsm" {
        description
          "SDR System Mgr";
      }
      enum "im" {
        description
          "Inventory Mgr";
      }
      enum "wd" {
        description
          "Watchdog";
      }
      enum "capi" {
        description
          "CAPI";
      }
      enum "pd-lib" {
        description
          "PD Lib";
      }
      enum "lrd" {
        description
          "LRD";
      }
      enum "chkpt" {
        description
          "Checkpoint";
      }
      enum "process-mgr" {
        description
          "Process Mgr";
      }
      enum "cmpat-infra" {
        description
          "Compat Infra";
      }
      enum "fault-mgr" {
        description
          "Fault Mgr";
      }
      enum "system-mgr" {
        description
          "System Mgr";
      }
    }
    description
      "Service type";
  }

  typedef Issu-mgbl-trigger-details-options {
    type enumeration {
      enum "service" {
        description
          "Service";
      }
      enum "client" {
        description
          "Client";
      }
    }
    description
      "Type of trigger details";
  }

  typedef Issu-mgbl-trigger {
    type enumeration {
      enum "isdv1" {
        description
          "ISD V1";
      }
      enum "isdv2" {
        description
          "ISD V2";
      }
      enum "ism" {
        description
          "ISM";
      }
      enum "client" {
        description
          "Client";
      }
    }
    description
      "Trigger type";
  }

  grouping ISSU-NODE-SUBPHASE-DATA {
    description
      "ISSU node subphase data";
    container completion-time {
      description
        "Completion time";
      uses ISSU-MGBL-TIMESTAMP-TYPE;
    }
    leaf ready {
      type boolean;
      description
        "Ready";
    }
    leaf complete {
      type boolean;
      description
        "Complete";
    }
  }

  grouping ISSU-NODE-DATA {
    description
      "ISSU NODE DATA";
    container prepare-check-completion {
      description
        "Prepare check completion";
      uses ISSU-NODE-SUBPHASE-DATA;
    }
    container prepare-disk-completion {
      description
        "Prepare disk completion";
      uses ISSU-NODE-SUBPHASE-DATA;
    }
    container load-prepare-completion {
      description
        "Load prepare completion";
      uses ISSU-NODE-SUBPHASE-DATA;
    }
    container load-exec-completion {
      description
        "Load exec completion";
      uses ISSU-NODE-SUBPHASE-DATA;
    }
    container run-prepare-completion {
      description
        "Run prepare completion";
      uses ISSU-NODE-SUBPHASE-DATA;
    }
    container run-exec-completion {
      description
        "Run exec completion";
      uses ISSU-NODE-SUBPHASE-DATA;
    }
    container cleanup-completion {
      description
        "Cleanup completion";
      uses ISSU-NODE-SUBPHASE-DATA;
    }
    container abort-completion {
      description
        "Abort completion";
      uses ISSU-NODE-SUBPHASE-DATA;
    }
    container abort-cleanup-completion {
      description
        "Abort cleanup completion";
      uses ISSU-NODE-SUBPHASE-DATA;
    }
    leaf issuid {
      type uint32;
      description
        "ISSU ID";
    }
    leaf node-id {
      type uint32;
      description
        "Node ID";
    }
    leaf role {
      type Issu-mgbl-role;
      description
        "ISSU role";
    }
    leaf ha-role {
      type Issu-mgbl-ha-role;
      description
        "HA role";
    }
    leaf version {
      type Issu-mgbl-version;
      description
        "Version";
    }
    leaf partner-node-id {
      type uint32;
      description
        "Partner node ID";
    }
    leaf rp {
      type boolean;
      description
        "RP";
    }
    leaf status {
      type Issu-mgbl-node-status;
      description
        "Status";
    }
    list warning {
      description
        "Warnings";
      uses ISSU-WARNING-DETAIL-DATA;
    }
  }

  grouping ISSU-RUN-DATA {
    description
      "ISSU run phase data";
    container complete {
      description
        "Complete";
      uses ISSU-PHASE-COMPLETION-DATA;
    }
    list warning {
      description
        "Warnings";
      uses ISSU-WARNING-DATA;
    }
  }

  grouping ISSU-MILESTONE-DATA {
    description
      "ISSU milestone data";
    container start-timestamp {
      description
        "Milestone start timestamp";
      uses ISSU-MGBL-TIMESTAMP-TYPE;
    }
    container end-timestamp {
      description
        "Milestone end timestamp";
      uses ISSU-MGBL-TIMESTAMP-TYPE;
    }
    leaf id {
      type uint32;
      description
        "Milestone ID";
    }
    leaf name {
      type string;
      description
        "Milestone name";
    }
  }

  grouping ISSU-LOAD-DATA {
    description
      "ISSU load phase data";
    container complete {
      description
        "Complete";
      uses ISSU-PHASE-COMPLETION-DATA;
    }
    list milestone {
      description
        "Milestones";
      uses ISSU-MILESTONE-DATA;
    }
  }

  grouping ISSU-PREP-CHECK-WARNING-DATA {
    description
      "ISSU client prepare check warning data";
    container time {
      description
        "Time";
      uses ISSU-MGBL-TIMESTAMP-TYPE;
    }
    leaf headline {
      type string;
      description
        "Headline";
    }
    leaf details {
      type string;
      description
        "Details";
    }
    leaf unresolved-impact {
      type string;
      description
        "Unresolved impact";
    }
    leaf resolution {
      type string;
      description
        "Resolution";
    }
  }

  grouping ISSU-PHASE-COMPLETION-DATA {
    description
      "ISSU phase completion data";
    container completion-time {
      description
        "Completion time";
      uses ISSU-MGBL-TIMESTAMP-TYPE;
    }
    leaf complete {
      type boolean;
      description
        "Complete";
    }
  }

  grouping ISSU-PREP-DATA {
    description
      "ISSU prepare phase data";
    container complete {
      description
        "Complete";
      uses ISSU-PHASE-COMPLETION-DATA;
    }
    list warning {
      description
        "Warnings";
      uses ISSU-PREP-CHECK-WARNING-DATA;
    }
  }

  grouping ISSU-CLIENT-DATA {
    description
      "ISSU CLIENT DATA";
    container time-registered {
      description
        "Time registered";
      uses ISSU-MGBL-TIMESTAMP-TYPE;
    }
    container prep-info {
      description
        "Prepare phase info";
      uses ISSU-PREP-DATA;
    }
    container load-info {
      description
        "Load phase info";
      uses ISSU-LOAD-DATA;
    }
    container run-prep-info {
      description
        "Run prepare phase info";
      uses ISSU-RUN-DATA;
    }
    container run-exec-info {
      description
        "Run exec phase info";
      uses ISSU-RUN-DATA;
    }
    leaf issuid {
      type uint32;
      description
        "Client ISSU ID";
    }
    leaf node-id {
      type uint32;
      description
        "Client node ID";
    }
    leaf process-name-xr {
      type string;
      description
        "Client process name";
    }
    leaf instance {
      type string;
      description
        "Client instance";
    }
    leaf jid-xr {
      type uint32;
      description
        "Client JID";
    }
    leaf connected {
      type boolean;
      description
        "Connected";
    }
  }

  grouping ISSU-ORCHESTRATION-SUBPHASE-DATA {
    description
      "ISSU orchestration subphase data";
    container start-time {
      description
        "Start time";
      uses ISSU-MGBL-TIMESTAMP-TYPE;
    }
    container end {
      description
        "End time";
      uses ISSU-MGBL-TIMESTAMP-TYPE;
    }
    leaf started {
      type boolean;
      description
        "Started";
    }
    leaf complete {
      type boolean;
      description
        "Complete";
    }
  }

  grouping ISSU-ABORT-REQUEST-DETAIL-DATA {
    description
      "ISSU orchestration abort request data";
    container trigger-details {
      description
        "Trigger details";
      uses ISSU-TRIGGER-DATA;
    }
    container time {
      description
        "Time";
      uses ISSU-MGBL-TIMESTAMP-TYPE;
    }
    leaf headline {
      type string;
      description
        "Headline";
    }
    leaf details {
      type string;
      description
        "Details";
    }
    leaf diagnostics {
      type string;
      description
        "Diagnostics";
    }
    leaf next-steps {
      type string;
      description
        "Next steps";
    }
  }

  grouping ISSU-MGBL-TIMESTAMP-TYPE {
    description
      "ISSU MGBL TIMESTAMP TYPE";
    leaf tv-sec {
      type int64;
      description
        "tv sec";
    }
    leaf tv-nsec {
      type int64;
      description
        "tv nsec";
    }
  }

  grouping ISSU-WARNING-DATA {
    description
      "ISSU client run warning data";
    container time {
      description
        "Time";
      uses ISSU-MGBL-TIMESTAMP-TYPE;
    }
    leaf headline {
      type string;
      description
        "Headline";
    }
    leaf details {
      type string;
      description
        "Details";
    }
    leaf impact {
      type string;
      description
        "Impact";
    }
    leaf diagnostics {
      type string;
      description
        "Diagnostics";
    }
    leaf next-steps {
      type string;
      description
        "Next steps";
    }
  }

  grouping ISSU-MGBL-CLIENT-KEY {
    description
      "ISSU client key";
    leaf process-name {
      type string;
      description
        "Client process name";
    }
    leaf instance {
      type string;
      description
        "Client instance";
    }
    leaf jid {
      type uint32;
      description
        "Client JID";
    }
  }

  grouping ISSU-MGBL-TRIGGER-DETAILS {
    description
      "Trigger details for an abort request or warning";
    container client-key {
      when "../option = 'client'" {
        description
          "../Option = 'Client'";
      }
      description
        "Client Key";
      uses ISSU-MGBL-CLIENT-KEY;
    }
    leaf option {
      type Issu-mgbl-trigger-details-options;
      description
        "Option";
    }
    leaf service {
      when "../option = 'service'" {
        description
          "../Option = 'Service'";
      }
      type Issu-mgbl-service;
      description
        "Service";
    }
  }

  grouping ISSU-TRIGGER-DATA {
    description
      "ISSU trigger detail data";
    container details {
      description
        "Trigger Details";
      uses ISSU-MGBL-TRIGGER-DETAILS;
    }
    leaf trigger {
      type Issu-mgbl-trigger;
      description
        "Trigger";
    }
    leaf node-id {
      type uint32;
      description
        "Node ID";
    }
  }

  grouping ISSU-WARNING-DETAIL-DATA {
    description
      "ISSU orchestration warning data";
    container trigger-details {
      description
        "Trigger details";
      uses ISSU-TRIGGER-DATA;
    }
    container warning {
      description
        "Warning";
      uses ISSU-WARNING-DATA;
    }
  }

  grouping ISSU-ORCHESTRATION-DATA {
    description
      "ISSU ORCHESTRATION DATA";
    container abort-request-acted {
      description
        "Abort request acted upon";
      uses ISSU-ABORT-REQUEST-DETAIL-DATA;
    }
    container start-time {
      description
        "Start time";
      uses ISSU-MGBL-TIMESTAMP-TYPE;
    }
    container completion-time {
      description
        "Completion time";
      uses ISSU-MGBL-TIMESTAMP-TYPE;
    }
    container prepare-check-data {
      description
        "Prepare check data";
      uses ISSU-ORCHESTRATION-SUBPHASE-DATA;
    }
    container prepare-disk-data {
      description
        "Prepare disk data";
      uses ISSU-ORCHESTRATION-SUBPHASE-DATA;
    }
    container load-prepare-data {
      description
        "Load prepare data";
      uses ISSU-ORCHESTRATION-SUBPHASE-DATA;
    }
    container load-exec-data {
      description
        "Load exec data";
      uses ISSU-ORCHESTRATION-SUBPHASE-DATA;
    }
    container run-prepare-data {
      description
        "Run prepare data";
      uses ISSU-ORCHESTRATION-SUBPHASE-DATA;
    }
    container run-exec-data {
      description
        "Run exec data";
      uses ISSU-ORCHESTRATION-SUBPHASE-DATA;
    }
    container cleanup-data {
      description
        "Cleanup data";
      uses ISSU-ORCHESTRATION-SUBPHASE-DATA;
    }
    container abort-data {
      description
        "Abort data";
      uses ISSU-ORCHESTRATION-SUBPHASE-DATA;
    }
    container abort-cleanup-data {
      description
        "Abort cleanup data";
      uses ISSU-ORCHESTRATION-SUBPHASE-DATA;
    }
    leaf issuid {
      type uint32;
      description
        "ISSU ID";
    }
    leaf started {
      type boolean;
      description
        "Started";
    }
    leaf complete {
      type boolean;
      description
        "Complete";
    }
    leaf install-id {
      type uint32;
      description
        "Install ID";
    }
    leaf version {
      type Issu-mgbl-version;
      description
        "Version";
    }
    leaf milestones-recorded {
      type boolean;
      description
        "Milestones record";
    }
    leaf is-smuissu {
      type boolean;
      description
        "Is SMU ISSU?";
    }
    leaf software-version-from {
      type string;
      description
        "Software version from";
    }
    leaf software-version-to {
      type string;
      description
        "Software version to";
    }
    leaf auto-abort-cleanup {
      type boolean;
      description
        "Auto abort cleanup";
    }
    leaf aborts-disabled {
      type boolean;
      description
        "Aborts disabled";
    }
    list warning {
      description
        "Warnings";
      uses ISSU-WARNING-DETAIL-DATA;
    }
    list abort-requests-not-acted {
      description
        "Abort requests not acted upon";
      uses ISSU-ABORT-REQUEST-DETAIL-DATA;
    }
  }
}
