module Cisco-IOS-XR-drivers-mpa-infra-cfg {
  namespace "http://cisco.com/ns/yang/Cisco-IOS-XR-drivers-mpa-infra-cfg";
  prefix drivers-mpa-infra-cfg;

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR drivers-mpa-infra package configuration.
     
     This module contains definitions
     for the following management objects:
       hardware-module: Configure subslot h/w module
     
     Copyright (c) 2013-2025 by Cisco Systems, Inc.
     All rights reserved.";

  revision 2025-03-03 {
    description
      "New configuration added to support ejector disable functionality";
    semver:module-version "1.1.0";
  }
  revision 2019-04-05 {
    description
      "Establish semantic version baseline.";
    semver:module-version "1.0.0";
  }
  revision 2015-11-09 {
    description
      "IOS XR 6.0 revision.";
  }

  typedef Hw-module-ejector-mode {
    type enumeration {
      enum "disable" {
        value 1;
        description
          "Keep the Ejector switch disable (default)";
      }
    }
    description
      "Hw module ejector mode";
  }

  typedef Hw-module-shutdown-power-mode {
    type enumeration {
      enum "powered" {
        value 2;
        description
          "Keep the showdown module powered (default)";
      }
    }
    description
      "Hw module shutdown power mode";
  }

  grouping EJECTOR {
    description
      "Common node of node, all-node";
    leaf ejector {
      type Hw-module-ejector-mode;
      description
        "Ejector switch disable";
    }
  }

  container hardware-module {
    description
      "Configure subslot h/w module";
    container nodes {
      description
        " subslot h/w module";
      list node {
        key "node-name";
        description
          "The identifier for a SPA node";
        leaf shutdown {
          type Hw-module-shutdown-power-mode;
          description
            "Shutdown a subslot h/w module";
        }
        leaf node-name {
          type xr:Node-id;
          description
            "A SPA node";
        }
        uses EJECTOR;
      }
    }
    container all-node {
      description
        "The identifier for all subslots/hw modules";
      uses EJECTOR;
    }
  }
}
