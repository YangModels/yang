module Cisco-IOS-XR-filesysinv-cfg {
  namespace "http://cisco.com/ns/yang/Cisco-IOS-XR-filesysinv-cfg";
  prefix filesysinv-cfg;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR filesysinv package configuration.
     
     This module contains definitions
     for the following management objects:
       filesystem-inventory: Filesystem inventory config
     
     Copyright (c) 2013-2021 by Cisco Systems, Inc.
     All rights reserved.";

  revision 2021-08-13 {
    description
      "Support for OnDemand DirSet and SkipList.";
    semver:module-version "1.1.0";
  }
  revision 2019-04-05 {
    description
      "Establish semantic version baseline.";
    semver:module-version "1.0.0";
  }
  revision 2015-11-09 {
    description
      "IOS XR 6.0 revision.";
  }

  typedef Filesysinv-snapshot {
    type enumeration {
      enum "incremental" {
        value 0;
        description
          "Incremental";
      }
      enum "full" {
        value 1;
        description
          "Full";
      }
    }
    description
      "Filesysinv snapshot";
  }

  container filesystem-inventory {
    description
      "Filesystem inventory config";
    container dir-sets {
      description
        "OnDemand config";
      list dir-set {
        key "dir-set";
        description
          "OnDemand config";
        leaf value {
          type string;
          description
            "List of directories seperated by
             space(enclosed in quotes)";
        }
        leaf dir-set {
          type uint32 {
            range "1..5";
          }
          description
            "Dir Set";
        }
      }
    }
    leaf skip-files {
      type string;
      description
        "Space seperated list of files to be
         skipped(enclosed in quotes)";
    }
    leaf skip-list {
      type string;
      description
        "Space seperated list of directories to be
         skipped(enclosed in quotes)";
    }
    leaf enable {
      type empty;
      description
        "Enable Filesystem inventory";
    }
    leaf snapshot-type {
      type Filesysinv-snapshot;
      description
        "Type of snapshot to be taken at periodic
         intervals. Default is incremental";
    }
    leaf snapshot-interval {
      type uint32 {
        range "1..720";
      }
      description
        "Snapshot Time interval in 1 hour blocks eg 2 is
         120 minutes";
    }
  }
}
