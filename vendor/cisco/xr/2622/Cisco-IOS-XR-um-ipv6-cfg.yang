module Cisco-IOS-XR-um-ipv6-cfg {
  namespace "http://cisco.com/ns/yang/Cisco-IOS-XR-um-ipv6-cfg";
  prefix um-ipv6-cfg;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ipv6 package configuration.
     
     This YANG module augments the
     modules with configuration data.
     
     Copyright (c) 2021-2025 by Cisco Systems, Inc., and/or its affiliates.
     All rights reserved.";

  revision 2025-09-01 {
    description
      "Deprecated IPv6 Source Route Configuration.";
    semver:module-version "1.1.0";
  }
  revision 2021-05-06 {
    description
      "Initial release";
    semver:module-version "1.0.0";
  }

  container ipv6 {
    description
      "Global IPv6 configuration commands";
    leaf hop-limit {
      type uint32 {
        range "1..255" {
          description
            "Hop Limit value";
        }
      }
      description
        "Configure hop count limit";
    }
    container icmp {
      description
        "Configure ICMP parameters";
      container error-interval {
        presence "Indicates a error-interval node is configured.";
        description
          "Interval between ICMP error messages";
        leaf interval-time {
          type uint32 {
            range "0..2147483647" {
              description
                "Interval between tokens in milliseconds";
            }
          }
          mandatory true;
          description
            "Interval between ICMP error messages";
        }
        leaf bucket-size {
          type uint32 {
            range "1..200" {
              description
                "Bucket size";
            }
          }
          description
            "Bucket size";
        }
      }
    }
    container source-route {
      presence "Indicates a source-route node is configured.";
      status deprecated;
      description
        "Process packets with source routing header options (This is deprecated since 25.4.1)";
    }
    container assembler {
      description
        "IPv6 Fragmented Packet Assembler";
      leaf timeout {
        type uint32 {
          range "1..120" {
            description
              "Number of seconds an assembly queue will hold before timeout";
          }
        }
        description
          "Number of seconds an assembly queue will hold before timeout";
      }
      leaf max-packets {
        type uint32 {
          range "1..50" {
            description
              "Percentage of total packets available in the system (default: 1000 packets)";
          }
        }
        description
          "Maxinum packets allowed in assembly queues";
      }
      container reassembler-drop {
        description
          "Drop the reassembled packet";
        container enable {
          presence "Indicates a enable node is configured.";
          description
            "Enable dropping of reassembled ND packet";
        }
      }
      container frag-hdr-incomplete {
        description
          "Drop the frags with incomplete headers";
        container enable {
          presence "Indicates a enable node is configured.";
          description
            "Enable dropping the frags with incomplete header";
        }
      }
      container overlap-frag-drop {
        description
          "Drop the fragments which are overlapping";
        container enable {
          presence "Indicates a enable node is configured.";
          description
            "Enable dropping the frags which are overlapping";
        }
      }
    }
    container path-mtu {
      description
        "IPv6 path-mtu configuration";
      container enable {
        presence "Indicates a enable node is configured.";
        description
          "Enable ipv6 path-mtu feature";
      }
      leaf timeout {
        type uint32 {
          range "1..15" {
            description
              "path-mtu timeout value in minutes";
          }
        }
        description
          "Configure path-mtu timeout value";
      }
    }
  }
}
