module Cisco-IOS-XR-sysadmin-show-diskenc-status {
  namespace "http://www.cisco.com/ns/yang/Cisco-IOS-XR-sysadmin-show-diskenc-status";
  prefix media_enc;

  import cisco-semver {
    prefix semver;
  }

  organization
    "Cisco Systems Inc.";
  contact
    "Cisco Systems, Inc.
     Customer Service
     
     Postal: 170 West Tasman Drive
     San Jose, CA 95134
     
     Tel: +1 800 553-NETS
     
     E-mail: cs-yang@cisco.com";
  description
    "This module contains a collection of YANG
     definitions for Cisco IOS-XR SysAdmin to
     report back memory utilization in sysadmin.
     
     Copyright (c) 2018-2020 by Cisco Systems, Inc.
     All rights reserved.";

  revision 2021-02-26 {
    description
      "Initial revision";
    semver:module-version "1.0.0";
  }

  typedef node-name-type {
    type string;
  }

  container disk-encryption {
    config false;
    description
      "Show disk encryption status in sysadmin";
    list all-locations {
      key "location";
      description
        "Disk encryption status for system";
      leaf location {
        type string;
        description
          "Disk encryption status for one node";
      }
      list all_mountpts {
        key "mountpt";
        leaf mountpt {
          type string;
          description
            "Media partition name";
        }
        leaf enc_status {
          type string;
          description
            "Media enc status";
        }
        leaf mount_status {
          type string;
          description
            "Media mount status";
        }
        leaf prep_status {
          type string;
          description
            "Media prepare status";
        }
      }
    }
  }
}
