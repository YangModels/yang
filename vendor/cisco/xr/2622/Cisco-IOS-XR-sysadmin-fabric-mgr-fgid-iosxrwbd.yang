module Cisco-IOS-XR-sysadmin-fabric-mgr-fgid-iosxrwbd {
  namespace "http://www.cisco.com/ns/yang/Cisco-IOS-XR-sysadmin-fabric-mgr-fgid-iosxrwbd";
  prefix fabric_fgid;

  import Cisco-IOS-XR-sysadmin-fabric-types {
    prefix fabric-types;
  }
  import Cisco-IOS-XR-sysadmin-show-trace {
    prefix show-trace;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains definitions
     for the Calvados model objects.
     
     Copyright (c) 2012-2020 by Cisco Systems, Inc.
     All rights reserved.";

  revision 2019-04-15 {
    description
      "Establish semantic version baseline.";
    semver:module-version "1.0.0";
  }
  revision 2018-04-09 {
    description
      "Required changes for ConfD 6.4.5";
  }
  revision 2017-05-01 {
    description
      "Namespace change to comply with Cisco guidelines on namespace";
  }

  grouping fgid_conf_resource {
    container fgid {
      container resource {
        container sdr {
          container allocation {
            leaf percent {
              type int32 {
                range "20..50";
              }
            }
          }
        }
      }
    }
  }

  grouping fgid_information_show {
    list id {
      key "fgid_id";
      leaf fgid_id {
        type fabric-types:fabric_fgid_id_type_iosxrwbd;
      }
      list hex_bitmaps {
        key "rack_number";
        leaf rack_number {
          type int32;
        }
        leaf bitmap {
          type string;
        }
      }
      list binary_bitmaps {
        key "rack_number";
        leaf rack_number {
          type int32;
        }
        leaf bitmap {
          type string;
        }
      }
      leaf total_asso_fabricq_ids {
        type int32;
      }
      list asso_fabricq_ids {
        key "fabricq_id";
        leaf fabricq_id {
          type string;
        }
      }
      leaf asso_client_info {
        type string;
      }
      list drivers {
        key "rack_number";
        leaf rack_number {
          type int32;
        }
        list clients {
          key "client_idx";
          leaf client_idx {
            type int32;
          }
          leaf show_asic_0 {
            type boolean;
            default "false";
          }
          leaf asic_0_bitmap {
            type string;
          }
          leaf show_asic_1 {
            type boolean;
            default "false";
          }
          leaf asic_1_bitmap {
            type string;
          }
          leaf show_asic_2 {
            type boolean;
            default "false";
          }
          leaf asic_2_bitmap {
            type string;
          }
          leaf show_asic_3 {
            type boolean;
            default "false";
          }
          leaf asic_3_bitmap {
            type string;
          }
          leaf show_asic_4 {
            type boolean;
            default "false";
          }
          leaf asic_4_bitmap {
            type string;
          }
          leaf show_asic_5 {
            type boolean;
            default "false";
          }
          leaf asic_5_bitmap {
            type string;
          }
          leaf show_asic_6 {
            type boolean;
            default "false";
          }
          leaf asic_6_bitmap {
            type string;
          }
          leaf show_asic_7 {
            type boolean;
            default "false";
          }
          leaf asic_7_bitmap {
            type string;
          }
          leaf show_asic_8 {
            type boolean;
            default "false";
          }
          leaf asic_8_bitmap {
            type string;
          }
          leaf show_asic_9 {
            type boolean;
            default "false";
          }
          leaf asic_9_bitmap {
            type string;
          }
          leaf show_asic_10 {
            type boolean;
            default "false";
          }
          leaf asic_10_bitmap {
            type string;
          }
          leaf show_asic_11 {
            type boolean;
            default "false";
          }
          leaf asic_11_bitmap {
            type string;
          }
          leaf show_asic_12 {
            type boolean;
            default "false";
          }
          leaf asic_12_bitmap {
            type string;
          }
          leaf show_asic_13 {
            type boolean;
            default "false";
          }
          leaf asic_13_bitmap {
            type string;
          }
          leaf show_asic_14 {
            type boolean;
            default "false";
          }
          leaf asic_14_bitmap {
            type string;
          }
          leaf show_asic_15 {
            type boolean;
            default "false";
          }
          leaf asic_15_bitmap {
            type string;
          }
          leaf show_asic_16 {
            type boolean;
            default "false";
          }
          leaf asic_16_bitmap {
            type string;
          }
          leaf show_asic_17 {
            type boolean;
            default "false";
          }
          leaf asic_17_bitmap {
            type string;
          }
          leaf show_asic_18 {
            type boolean;
            default "false";
          }
          leaf asic_18_bitmap {
            type string;
          }
          leaf show_asic_19 {
            type boolean;
            default "false";
          }
          leaf asic_19_bitmap {
            type string;
          }
          leaf show_asic_20 {
            type boolean;
            default "false";
          }
          leaf asic_20_bitmap {
            type string;
          }
          leaf show_asic_21 {
            type boolean;
            default "false";
          }
          leaf asic_21_bitmap {
            type string;
          }
          leaf show_asic_22 {
            type boolean;
            default "false";
          }
          leaf asic_22_bitmap {
            type string;
          }
          leaf show_asic_23 {
            type boolean;
            default "false";
          }
          leaf asic_23_bitmap {
            type string;
          }
          leaf show_asic_24 {
            type boolean;
            default "false";
          }
          leaf asic_24_bitmap {
            type string;
          }
          leaf show_asic_25 {
            type boolean;
            default "false";
          }
          leaf asic_25_bitmap {
            type string;
          }
          leaf show_asic_26 {
            type boolean;
            default "false";
          }
          leaf asic_26_bitmap {
            type string;
          }
          leaf show_asic_27 {
            type boolean;
            default "false";
          }
          leaf asic_27_bitmap {
            type string;
          }
          leaf show_asic_28 {
            type boolean;
            default "false";
          }
          leaf asic_28_bitmap {
            type string;
          }
          leaf show_asic_29 {
            type boolean;
            default "false";
          }
          leaf asic_29_bitmap {
            type string;
          }
          leaf show_asic_30 {
            type boolean;
            default "false";
          }
          leaf asic_30_bitmap {
            type string;
          }
          leaf show_asic_31 {
            type boolean;
            default "false";
          }
          leaf asic_31_bitmap {
            type string;
          }
          leaf show_asic_32 {
            type boolean;
            default "false";
          }
          leaf asic_32_bitmap {
            type string;
          }
          leaf show_asic_33 {
            type boolean;
            default "false";
          }
          leaf asic_33_bitmap {
            type string;
          }
          leaf show_asic_34 {
            type boolean;
            default "false";
          }
          leaf asic_34_bitmap {
            type string;
          }
          leaf show_asic_35 {
            type boolean;
            default "false";
          }
          leaf asic_35_bitmap {
            type string;
          }
        }
      }
    }
  }

  grouping fgid_resource_show {
    list sdr {
      key "sdr_name";
      leaf sdr_name {
        type string;
      }
      leaf description {
        type string;
        default "Secure Domain Router name.";
      }
      list application {
        key "app_name";
        leaf app_name {
          type string;
        }
        leaf description {
          type string;
          default "application.";
        }
        list ids_range {
          key "id elements";
          leaf id {
            type fabric-types:fabric_fgid_id_type_iosxrwbd;
          }
          leaf elements {
            type fabric-types:fabric_fgid_elements_type_iosxrwbd;
          }
          list fgid_ids {
            key "fgid_id line_idx";
            leaf fgid_id {
              type string;
            }
            leaf line_idx {
              type int32;
            }
            leaf sdr_name_h {
              type string;
            }
            leaf app_name_h {
              type string;
            }
          }
        }
      }
    }
  }

  grouping fgid_trace {
    container fgid_mgr {
      uses show-trace:traceable;
    }
  }

  grouping fgid_statistics_app_show {
    list application {
      key "app_name";
      leaf app_name {
        type string;
      }
      leaf description {
        type string;
        default "application.";
      }
      leaf app_id {
        type uint32;
      }
      leaf pool_id {
        type uint32;
      }
      leaf inuse_fgids {
        type uint32;
      }
      leaf hwm_fgids {
        type uint32;
      }
    }
  }

  grouping fgid_statistics_pool_show {
    list pool_list {
      key "pool_id";
      leaf pool_id {
        type uint32;
      }
      leaf pool_name {
        type string;
      }
      leaf pool_type {
        type string;
      }
      leaf start_fgid {
        type string;
      }
      leaf total_fgids {
        type uint32;
      }
      leaf current_fgids {
        type uint32;
      }
      leaf hwm_fgids {
        type uint32;
      }
    }
  }

  grouping fgid_statistics_sdr_show {
    list sdr_list {
      key "sdr_name";
      leaf sdr_name {
        type string;
      }
      leaf description {
        type string;
        default "Secure Domain Router name.";
      }
      leaf sdr_total_fgids {
        type uint32;
      }
      leaf sdr_inuse_fgids {
        type uint32;
      }
      leaf sdr_hwm_fgids {
        type uint32;
      }
      uses fgid_statistics_app_show;
    }
  }

  grouping fgid_statistics_system_show {
    list stats_list {
      key "system_stats";
      leaf system_stats {
        type int32;
      }
      leaf system_total_fgids {
        type uint32;
      }
      leaf system_inuse_fgids {
        type uint32;
      }
      leaf system_hwm_fgids {
        type uint32;
      }
    }
  }

  grouping fgid_statistics_show {
    uses fgid_statistics_system_show;
    uses fgid_statistics_sdr_show;
    uses fgid_statistics_pool_show;
  }

  grouping fgid_program_error_show {
    list program_error {
      key "start end";
      leaf start {
        type fabric-types:fabric_fgid_start_id_type_iosxrwbd;
      }
      leaf end {
        type fabric-types:fabric_fgid_end_id_type_iosxrwbd;
      }
      list rack {
        key "rack_id";
        leaf rack_id {
          type int32;
        }
        leaf rack_id_str {
          type string;
        }
        leaf fgids_in_error {
          type string;
        }
        leaf found_fgids_in_error {
          type boolean;
        }
        leaf total_error_fgids {
          type int32;
        }
        leaf incorrect_fgids_range {
          type boolean;
        }
        leaf cmd_not_supported {
          type boolean;
        }
      }
    }
  }

  grouping fgid {
    container fgid {
      description
        "FGID management information";
      container information {
        uses fgid_information_show;
      }
      container resource {
        uses fgid_resource_show;
      }
      container statistics {
        container all {
          uses fgid_statistics_show;
        }
        container sdr {
          uses fgid_statistics_sdr_show;
        }
        container pool {
          uses fgid_statistics_pool_show;
        }
        container system {
          uses fgid_statistics_system_show;
        }
      }
      uses fgid_trace;
      uses fgid_program_error_show;
    }
  }
}
