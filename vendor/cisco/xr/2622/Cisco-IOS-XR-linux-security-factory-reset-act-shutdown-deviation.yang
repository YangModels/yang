module Cisco-IOS-XR-linux-security-factory-reset-act-shutdown-deviation {
  namespace "http://cisco.com/ns/yang/Cisco-IOS-XR-linux-security-factory-reset-act-shutdown-deviation";
  prefix factory-reset-act-shut-dev;

  import Cisco-IOS-XR-linux-security-factory-reset-act {
    prefix factory-reset-act;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a set of deviations for unsupported platforms
     for Cisco-IOS-XR-linux-security-factory-reset-act
     
     Copyright (c) 2025 by Cisco Systems, Inc., and/or its affiliates.
     All rights reserved.";

  revision 2025-04-18 {
    description
      "IOS XR 25.4.1 revision.";
    semver:module-version "1.0.0";
  }

  deviation "/factory-reset-act:factory-reset-shut" {
    deviate not-supported;
  }
}
