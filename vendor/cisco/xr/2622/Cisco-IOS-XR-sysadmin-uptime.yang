module Cisco-IOS-XR-sysadmin-uptime {
  namespace "http://www.cisco.com/ns/yang/Cisco-IOS-XR-sysadmin-uptime";
  prefix uptime;

  import Cisco-IOS-XR-sysadmin-types {
    prefix calvados;
  }
  import ietf-inet-types {
    prefix inet;
  }
  import cisco-semver {
    prefix semver;
  }

  organization
    "Cisco Systems Inc.";
  contact
    "Cisco Systems, Inc.
     Customer Service
     
     Postal: 170 West Tasman Drive
     San Jose, CA 95134
     
     Tel: +1 800 553-NETS
     
     E-mail: cs-yang@cisco.com";
  description
    "This module contains a collection of YANG
     definitions for accessing the uptime of each node.
     
     Copyright (c) 2012-2020 by Cisco Systems, Inc.
     All rights reserved.";

  revision 2020-11-09 {
    description
      "Initial revision";
    semver:module-version "1.0.0";
  }

  grouping nodeInfo {
    description
      "All parameters needed to describe a node uptime.";
    leaf type {
      type string;
      description
        "Node Type";
    }
    leaf ip_address {
      type inet:ip-address;
      description
        "IP address of the node";
    }
    leaf uptime {
      type string;
      description
        "Node Up Time";
    }
  }

  grouping node_uptime {
    list node_locations {
      key "node_location";
      leaf node_location {
        type calvados:location-id;
      }
      list nodei {
        key "ip_address";
        uses nodeInfo;
      }
    }
  }
}
