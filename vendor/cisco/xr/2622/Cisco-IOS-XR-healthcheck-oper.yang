module Cisco-IOS-XR-healthcheck-oper {
  namespace "http://cisco.com/ns/yang/Cisco-IOS-XR-healthcheck-oper";
  prefix healthcheck-oper;

  import Cisco-IOS-XR-types {
    prefix xr;
  }
  import cisco-semver {
    prefix semver;
  }
  include Cisco-IOS-XR-healthcheck-oper-sub2 {
    revision-date 2026-07-10;
  }
  include Cisco-IOS-XR-healthcheck-oper-sub1 {
    revision-date 2026-07-10;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR healthcheck package operational data.
     
     This module contains definitions
     for the following management objects:
       health-check: Health check operational data space
     
     Copyright (c) 2013-2026 by Cisco Systems, Inc.
     All rights reserved.";

  revision 2026-07-10 {
    description
      "Added deprecation message for Healthcheck packet-drop and asic-reset use-cases
       2026-04-15
         created a new oper yang for NCS1004 and retained support for performing a get operation on individual HC metrics
       2026-03-24
         Made the drop-tolerance field specific to ASIC reset and tolerance-levels low, medium and high specific to the packet-drop use case
       2026-03-11
         Removed the support for report metric and status metric
       2026-01-21
         Deprecated Healthcheck legacy metrics
       2025-09-30
         Updated version in which legacy metrics are getting deprecated
       2025-04-28
         Added deprecation message for Healthcheck legacy metrics in oper yang
       2024-04-04
         Added history under packet-drop usecase with node-name and npu id
       2024-03-27
         Timestamp removed from ASIC reset and Packet drop usecase summary
       2023-10-10
         Updated usecase status to have tolerance low, medium and high
       2022-04-07
         Updated Install Metric
       2021-10-19
         Updated Custom Metric
       2021-07-22
         ASIC reset and packet drops use case updated
       2021-05-25
         ASIC reset and packet drops usecases added";
    semver:module-version "2.0.0";
  }
  revision 2020-09-18 {
    description
      "Fabric health metric updated.";
    semver:module-version "1.0.0";
  }
  revision 2019-04-05 {
    description
      "Establish semantic version baseline.";
  }
  revision 2015-11-09 {
    description
      "IOS XR 6.0 revision.";
  }

  feature ncs1004-upgrade-metrics {
    description
      "Enabled on NCS1004 only.";
  }

  grouping SUMMARY {
    description
      "Common node of asic-reset, packet-drop";
    container summary {
      status deprecated;
      description
        "ASIC reset and packet drop summary. Note: This
         container is deprecated and will be removed in
         the 27.1.1 release";
      uses HCMGR-USE-CASE-SUMMARY-DATA;
    }
  }

  grouping NODE-TABLE {
    description
      "Common node of asic-reset, packet-drop";
    container node-entries {
      description
        "Node";
      list node-entry {
        key "node-name";
        description
          "Node name";
        container npus {
          description
            "NPU ID";
          list npu {
            key "npu-id";
            status deprecated;
            description
              "NPU ID. Note: This container is deprecated
               and will be removed in the 27.1.1 release";
            leaf npu-id {
              type uint32;
              description
                "NPU ID";
            }
            uses HCMGR-USE-CASE-DETAIL-DATA;
          }
        }
        leaf node-name {
          type xr:Node-id;
          description
            "Node name";
        }
      }
    }
  }

  container health-check {
    config false;
    description
      "Health check operational data space";
    container metric-info {
      if-feature "ncs1004-upgrade-metrics";
      description
        "Metric";
      container fpd {
        description
          "FPD metric";
        uses HCMGR-FPD-METRIC-DATA;
      }
      container pci-monitoring {
        description
          "PCI monitoring info";
        uses HCMGR-PCIMON-METRIC-DATA;
      }
      container hw-monitoring {
        description
          "Hardware monitoring";
        uses HCMGR-HWMON-METRIC-DATA;
      }
      container platform {
        description
          "Platform metric";
        uses HCMGR-PLATFORM-METRIC-DATA;
      }
      container communication-timeout {
        description
          "Process communication timeout metric";
        uses HCMGR-COMMUNICATION-TIMEOUT-METRIC-DATA;
      }
      container free-memory {
        description
          "Free memory metric";
        uses HCMGR-FREE-MEM-METRIC-DATA;
      }
      container process-resource {
        description
          "Process resource metric";
        uses HCMGR-PROCESS-RESOURCE-METRIC-DATA;
      }
      container lc-monitoring {
        description
          "LC monitoring";
        uses HCMGR-LCMON-METRIC-DATA;
      }
      container filesystem {
        description
          "Filesystem metric";
        uses HCMGR-FILESYSTEM-METRIC-DATA;
      }
      container config-inconsistency {
        description
          "Config inconsistency Alarm metric";
        uses HCMGR-CONFIG-INCONSISTENCY-METRIC-DATA;
      }
      container shared-memory {
        description
          "Shared memory metric";
        uses HCMGR-SHARED-MEM-METRIC-DATA;
      }
      container wd-monitoring {
        description
          "Watchdog monitoring";
        uses HCMGR-WDMON-METRIC-DATA;
      }
      container process-status {
        description
          "Process state metric";
        uses HCMGR-PROCESS-STATE-METRIC-DATA;
      }
      container system-clock {
        description
          "Systemclock timezone info";
        uses HCMGR-SYSTEMCLOCK-METRIC-DATA;
      }
      container cpu {
        description
          "CPU metric";
        uses HCMGR-CPU-METRIC-DATA;
      }
    }
    container report-info {
      status deprecated;
      description
        "Report data. Note: This container is deprecated
         and will be removed in the 27.1.1 release";
      uses HCMGR-REPORT-DATA;
    }
    container use-case {
      status deprecated;
      description
        "Use case. Note: This container is deprecated and
         will be removed in the 27.1.1 release";
      container asic-reset {
        status deprecated;
        description
          "ASIC reset use case. Note: This use-case is
           deprecated and will be removed in the 27.1.1
           release";
        uses NODE-TABLE;
        uses SUMMARY;
      }
      container packet-drop {
        status deprecated;
        description
          "Packet drop use case. Note: This use-case is
           deprecated and will be removed in the 27.1.1
           release";
        container history {
          description
            "Node";
          container history-nodes {
            description
              "Node";
            list history-node {
              key "node-name";
              description
                "Node name";
              container history-npus {
                description
                  "NPU ID";
                list history-npu {
                  key "npu-id";
                  status deprecated;
                  description
                    "NPU ID. Note: This container is deprecated
                     and will be removed in the 27.1.1 release";
                  leaf npu-id {
                    type uint32;
                    description
                      "NPU ID";
                  }
                  uses HCMGR-USE-CASE-HISTORY-DATA;
                }
              }
              leaf node-name {
                type xr:Node-id;
                description
                  "Node name";
              }
            }
          }
        }
        uses NODE-TABLE;
        uses SUMMARY;
      }
    }
    container status {
      description
        "Health check status data";
      container status-use-cases {
        status deprecated;
        description
          "Enabled use cases information. Note: This
           container is deprecated and will be removed in
           the 27.1.1 release";
        list status-use-case {
          key "use-case";
          status deprecated;
          description
            "Specific use case information from list of
             different use cases. Note: This container is
             deprecated and will be removed in the 27.1.1
             release";
          leaf use-case {
            type xr:Cisco-ios-xr-string;
            description
              "Use case";
          }
          uses HCMGR-STATUS-USECASE-DATA;
        }
      }
    }
    container status-info {
      status deprecated;
      description
        "Status. Note: This container is deprecated and
         will be removed in the 27.1.1 release";
      uses HCMGR-STATUS-DATA;
    }
    container report {
      description
        "Report data";
      container use-cases {
        status deprecated;
        description
          "Enabled use cases information. Note: This
           container is deprecated and will be removed in
           the 27.1.1 release";
        list use-case {
          key "use-case";
          status deprecated;
          description
            "Specific use case information from list of
             different use cases. Note: This container is
             deprecated and will be removed in the 27.1.1
             release";
          leaf use-case {
            type xr:Cisco-ios-xr-string;
            description
              "Use case";
          }
          uses HCMGR-USE-CASE-REPORT-DATA;
        }
      }
    }
  }
}
