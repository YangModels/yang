submodule Cisco-IOS-XR-8000-lpts-oper-sub1 {
  belongs-to Cisco-IOS-XR-8000-lpts-oper {
    prefix Cisco-IOS-XR-8000-lpts-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR 8000-lpts package operational data.
     
     Copyright (c) 2013-2022 by Cisco Systems, Inc.
     All rights reserved.";

  revision 2022-07-26 {
    description
      "Add policer-level leaf to grouping PL-PIFIB-POLICER-INFO
       2022-05-05
         Add is_compressed leaf to grouping PL-PIFIB-SHOW-ENTRY";
    semver:module-version "1.1.0";
  }
  revision 2021-03-30 {
    description
      "LPTS Pre-ifib Oper Yang added.";
    semver:module-version "1.0.0";
  }
  revision 2019-04-05 {
    description
      "Establish semantic version baseline.";
  }
  revision 2015-11-09 {
    description
      "IOS XR 6.0 revision.";
  }

  grouping PL-PIFIB-SHOW-OG-ENTRY {
    description
      "LPTS TCAM Pre-IFIB OG Entry Information";
    leaf l3protocol {
      type uint32;
      description
        "Layer 3 Protocol";
    }
    leaf l4protocol {
      type uint32;
      description
        "Layer 4 Protocol";
    }
    leaf intf-handle {
      type uint32;
      description
        "Interface Handle";
    }
    leaf local-addr {
      type string;
      description
        "Destination IP Address";
    }
    leaf remote-addr {
      type string;
      description
        "Source IP Address";
    }
    leaf local-prefix-len {
      type uint32;
      description
        "Local Prefix Length";
    }
    leaf remote-prefix-len {
      type uint32;
      description
        "Remote Prefix Length";
    }
    leaf remote-port {
      type uint16;
      description
        "Remote port";
    }
    leaf policer-id {
      type uint32;
      description
        "Policer Pointer";
    }
    leaf accepted {
      type uint64;
      description
        "Accepted Packets Counter";
    }
    leaf dropped {
      type uint64;
      description
        "Dropped Packets Counter";
    }
    leaf flow-type {
      type uint16;
      description
        "Flow type";
    }
    leaf npu-id {
      type uint32;
      description
        "npu id";
    }
    leaf vrf {
      type uint32;
      description
        "vrf";
    }
    leaf queue-priority {
      type uint16;
      description
        "punt queue priority";
    }
    leaf entry-stat {
      type boolean;
      description
        "Entry has stat or share global FT stat";
    }
    leaf is-compressed {
      type boolean;
      description
        "True if entry is compressed";
    }
    leaf remote-object-group-id {
      type uint16;
      description
        "Source object ID";
    }
  }

  grouping PL-PIFIB-SHOW-ENTRY {
    description
      "LPTS TCAM Pre-IFIB Entry Information";
    leaf l3protocol {
      type uint32;
      description
        "Layer 3 Protocol";
    }
    leaf l4protocol {
      type uint32;
      description
        "Layer 4 Protocol";
    }
    leaf intf-handle {
      type uint32;
      description
        "Interface Handle";
    }
    leaf local-addr {
      type string;
      description
        "Destination IP Address";
    }
    leaf remote-addr {
      type string;
      description
        "Source IP Address";
    }
    leaf local-prefix-len {
      type uint32;
      description
        "Local Prefix Length";
    }
    leaf remote-prefix-len {
      type uint32;
      description
        "Remote Prefix Length";
    }
    leaf remote-port {
      type uint16;
      description
        "Remote port";
    }
    leaf policer-id {
      type uint32;
      description
        "Policer Pointer";
    }
    leaf accepted {
      type uint64;
      description
        "Accepted Packets Counter";
    }
    leaf dropped {
      type uint64;
      description
        "Dropped Packets Counter";
    }
    leaf flow-type {
      type uint16;
      description
        "Flow type";
    }
    leaf npu-id {
      type uint32;
      description
        "npu id";
    }
    leaf vrf {
      type uint32;
      description
        "vrf";
    }
    leaf queue-priority {
      type uint16;
      description
        "punt queue priority";
    }
    leaf entry-stat {
      type boolean;
      description
        "Entry has stat or share global FT stat";
    }
    leaf is-compressed {
      type boolean;
      description
        "True if entry is compressed";
    }
  }

  grouping PL-PIFIB-POLICER-INFO {
    description
      "PD Pre-IFIB policer information";
    leaf avgrate {
      type uint32;
      units "packet/s";
      description
        "Average policer value in packets per second";
    }
    leaf burst {
      type uint32;
      description
        "Burst policer value in msec";
    }
    leaf static-avgrate {
      type uint32;
      description
        "Default value of average policer value";
    }
    leaf avgrate-type {
      type uint32;
      description
        "policer value type (local,global,static)";
    }
    leaf hw-policer-addr {
      type uint32;
      description
        "HW policer address - need this for display";
    }
    leaf sw-police-id {
      type uint16;
      description
        "SW policer ID - reserved";
    }
    leaf npu-id {
      type uint32;
      description
        "npu id";
    }
    leaf policer-level {
      type uint32;
      description
        "Policer level - NPU or slice";
    }
  }
}
