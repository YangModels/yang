module Cisco-IOS-XR-um-mpls-static-cfg {
  namespace "http://cisco.com/ns/yang/Cisco-IOS-XR-um-mpls-static-cfg";
  prefix um-mpls-static-cfg;

  import Cisco-IOS-XR-types {
    prefix xr;
  }
  import ietf-inet-types {
    prefix inet;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR mpls-static package configuration.
     
     This YANG module augments the
     modules with configuration data.
     
     Copyright (c) 2021-2025 by Cisco Systems, Inc., and/or its affiliates.
     All rights reserved.";

  revision 2025-12-12 {
    description
      "Added per-vrf-46 support
       2025-07-22
         Fixed canonical ordering.
       2025-04-29
         Added forward mode nexthop group, and distance support.
       2023-02-17
         Added l2-bypass flag.
       2022-10-03
         Added support for disabling default route for resolve nexthops globally.";
    semver:module-version "1.1.0";
  }
  revision 2021-08-05 {
    description
      "Initial release";
    semver:module-version "1.0.0";
  }

  container mpls {
    description
      "Global MPLS configuration subcommands";
    container static {
      presence "Indicates a static node is configured.";
      description
        "MPLS Static label and LSP configuration commands";
      container interfaces {
        description
          "Enable MPLS Static on an interface";
        list interface {
          key "interface-name";
          description
            "Enable MPLS Static on an interface";
          leaf interface-name {
            type xr:Interface-name;
            description
              "Enable MPLS Static on an interface";
          }
        }
      }
      container vrfs {
        description
          "Configure VRF parameters";
        list vrf {
          key "vrf-name";
          description
            "Configure VRF parameters";
          leaf vrf-name {
            type xr:Cisco-ios-xr-string {
              length "1..32" {
                description
                  "Specify the VRF Name";
              }
            }
            description
              "Configure VRF parameters";
          }
          container address-family {
            description
              "Configure Address Family and its parameters";
            container ipv4 {
              description
                "Configure IPv4 Address Family parameters";
              container unicast {
                presence "Indicates a unicast node is configured.";
                description
                  "Unicast";
                container local-labels {
                  description
                    "Configure local label assignment and forwarding";
                  list local-label {
                    must "allocate/per-prefix or allocate/per-vrf/enable";
                    key "label-value";
                    description
                      "Configure local label assignment and forwarding";
                    leaf label-value {
                      type uint32 {
                        range "16..1048575" {
                          description
                            "Label value";
                        }
                      }
                      description
                        "Configure local label assignment and forwarding";
                    }
                    container allocate {
                      description
                        "Label Allocation Option";
                      container per-prefix {
                        must "not(../per-vrf/enable)";
                        presence "Indicates a per-prefix node is configured.";
                        description
                          "For a given prefix";
                        leaf prefix-address {
                          type inet:ipv4-address-no-zone;
                          mandatory true;
                          description
                            "IPv4 Prefix address";
                        }
                        leaf prefix-length {
                          type xr:Ipv4-prefix-length;
                          mandatory true;
                          description
                            "IPv4 Prefix length";
                        }
                      }
                      container per-vrf {
                        description
                          "For a VRF";
                        container enable {
                          presence "Indicates an enable node is configured.";
                          description
                            "For a VRF";
                        }
                        container forward {
                          description
                            "Configure forwarding rewrites";
                          list path {
                            must "../../enable and pop-and-lookup";
                            key "path-count";
                            description
                              "Configure path parameters";
                            leaf path-count {
                              type uint32 {
                                range "1" {
                                  description
                                    "Path count";
                                }
                              }
                              description
                                "Configure path parameters";
                            }
                            container pop-and-lookup {
                              presence "Indicates a pop-and-lookup node is configured.";
                              description
                                "Pop and lookup";
                            }
                          }
                        }
                      }
                    }
                  }
                }
              }
            }
          }
          container lsps {
            description
              "Configure lsp name";
            list lsp {
              key "lsp-name";
              description
                "Configure lsp name";
              leaf lsp-name {
                type xr:Cisco-ios-xr-string {
                  length "1..64" {
                    description
                      "Specify the LSP Name";
                  }
                }
                description
                  "Configure lsp name";
              }
              container in-label {
                presence "Indicates a in-label node is configured.";
                description
                  "Configure in label assignment and forwarding";
                leaf label-value {
                  type uint32 {
                    range "16..1048575" {
                      description
                        "Label value";
                    }
                  }
                  mandatory true;
                  description
                    "Configure in label assignment and forwarding";
                }
                container allocate {
                  description
                    "Label Allocation Option";
                  container per-prefix {
                    must "not(../per-vrf) and not(../per-vrf-46)";
                    presence "Indicates a per-prefix node is configured.";
                    description
                      "For a given prefix";
                    leaf prefix-address {
                      type inet:ip-address-no-zone;
                      mandatory true;
                      description
                        "IPv4 or IPv6 Prefix address";
                    }
                    leaf prefix-length {
                      type union {
                        type xr:Ipv4-prefix-length;
                        type xr:Ipv6-prefix-length;
                      }
                      mandatory true;
                      description
                        "Prefix length";
                    }
                  }
                  container per-vrf {
                    must "not(../per-prefix) and not(../per-vrf-46)";
                    presence "Indicates a per-vrf node is configured.";
                    description
                      "For a VRF";
                  }
                  container per-vrf-46 {
                    must "not(../per-prefix) and not(../per-vrf)";
                    presence "Indicates a per-vrf-46 node is configured.";
                    description
                      "For a VRF (IPv4 and IPv6)";
                  }
                }
              }
              container forward {
                description
                  "Configure forwarding rewrites";
                list path {
                  must "pop-and-lookup";
                  key "path-count";
                  description
                    "Configure path parameters";
                  leaf path-count {
                    type uint32 {
                      range "1" {
                        description
                          "Path count";
                      }
                    }
                    description
                      "Configure path parameters";
                  }
                  container pop-and-lookup {
                    presence "Indicates a pop-and-lookup node is configured.";
                    description
                      "Pop and lookup";
                  }
                }
              }
            }
          }
        }
      }
      container address-family {
        description
          "Configure Address Family and its parameters";
        container ipv4 {
          description
            "Configure IPv4 Address Family parameters";
          container unicast {
            presence "Indicates a unicast node is configured.";
            description
              "Unicast";
            container local-labels {
              description
                "Configure local label assignment and forwarding";
              list local-label {
                must "allocate";
                key "label-value";
                description
                  "Configure local label assignment and forwarding";
                leaf label-value {
                  type uint32 {
                    range "16..1048575" {
                      description
                        "Label value";
                    }
                  }
                  description
                    "Configure local label assignment and forwarding";
                }
                container allocate {
                  presence "Indicates a nexthop node is configured.";
                  description
                    "Label Allocation Option";
                  container per-prefix {
                    description
                      "For a given prefix";
                    leaf prefix-address {
                      type inet:ipv4-address-no-zone;
                      must "../prefix-length";
                      description
                        "IPv4 Prefix address";
                    }
                    leaf prefix-length {
                      type xr:Ipv4-prefix-length;
                      must "../prefix-address";
                      description
                        "IPv4 Prefix length";
                    }
                  }
                }
                container forward {
                  description
                    "Configure forwarding rewrites";
                  list path {
                    must "nexthop and nexthop/out-label";
                    key "path-count";
                    description
                      "Configure path parameters";
                    leaf path-count {
                      type uint32 {
                        range "1" {
                          description
                            "Path count";
                        }
                      }
                      description
                        "Configure path parameters";
                    }
                    container nexthop {
                      must "address or interface";
                      presence "Indicates a nexthop node is configured.";
                      description
                        "nexthop";
                      leaf address {
                        type inet:ipv4-address-no-zone;
                        description
                          "nexthop";
                      }
                      leaf interface {
                        type xr:Interface-name;
                        description
                          "Next-hop interface";
                      }
                      container out-label {
                        must "label-value or pop or explicit-null";
                        presence "Indicates a out-label node is configured.";
                        description
                          "Outgoing label";
                        leaf label-value {
                          type uint32 {
                            range "16..1048575" {
                              description
                                "MPLS label value";
                            }
                          }
                          must "not(../pop or ../explicit-null)";
                          description
                            "MPLS label value";
                        }
                        container pop {
                          must "not(../label-value or ../explicit-null)";
                          presence "Indicates a pop node is configured.";
                          description
                            "Pop off the top of the label stack";
                        }
                        container explicit-null {
                          must "not(../label-value or ../pop)";
                          presence "Indicates a explicit-null node is configured.";
                          description
                            "Set the outgoing label to ipv4 explicit-null";
                        }
                      }
                    }
                  }
                }
              }
            }
            container top-label-hash {
              description
                "Configure top label hash entries";
              container local-labels {
                description
                  "Configure local label assignment and forwarding";
                list local-label {
                  must "allocate/enable";
                  key "label-value";
                  description
                    "Configure local label assignment and forwarding";
                  leaf label-value {
                    type uint32 {
                      range "16..1048575" {
                        description
                          "Label value";
                      }
                    }
                    description
                      "Configure local label assignment and forwarding";
                  }
                  container allocate {
                    description
                      "Label Allocation Option";
                    container enable {
                      presence "Indicates a allocate node is configured.";
                      description
                        "Label Allocation Option";
                    }
                    container forward {
                      description
                        "Configure forwarding rewrites";
                      list path {
                        must "nexthop and nexthop/out-label";
                        key "path-count";
                        description
                          "Configure path parameters";
                        leaf path-count {
                          type uint32 {
                            range "1" {
                              description
                                "Path count";
                            }
                          }
                          description
                            "Configure path parameters";
                        }
                        container nexthop {
                          must "address or interface";
                          presence "Indicates a nexthop node is configured.";
                          description
                            "nexthop";
                          leaf address {
                            type inet:ipv4-address-no-zone;
                            description
                              "nexthop";
                          }
                          leaf interface {
                            type xr:Interface-name;
                            description
                              "Next-hop Interface";
                          }
                          container out-label {
                            must "label-value or pop or explicit-null";
                            presence "Indicates a out-label node is configured.";
                            description
                              "Outgoing label";
                            leaf label-value {
                              type uint32 {
                                range "16..1048575" {
                                  description
                                    "MPLS label value";
                                }
                              }
                              must "not(../pop or ../explicit-null)";
                              description
                                "MPLS label value";
                            }
                            container pop {
                              must "not(../label-value or ../explicit-null)";
                              presence "Indicates a pop node is configured.";
                              description
                                "Pop off the top of the label stack";
                            }
                            container explicit-null {
                              must "not(../label-value or ../pop)";
                              presence "Indicates a explicit-null node is configured.";
                              description
                                "Set the outgoing label to ipv4 explicit-null";
                            }
                          }
                        }
                      }
                    }
                  }
                }
              }
            }
          }
        }
      }
      container lsps {
        description
          "Configure lsp name";
        list lsp {
          key "lsp-name";
          description
            "Configure lsp name";
          leaf lsp-name {
            type xr:Cisco-ios-xr-string {
              length "1..64" {
                description
                  "Specify the LSP Name";
              }
            }
            description
              "Configure lsp name";
          }
          container in-label {
            presence "Indicates a in-label node is configured.";
            description
              "Configure in label assignment and forwarding";
            leaf label-value {
              type uint32 {
                range "16..1048575" {
                  description
                    "Label value";
                }
              }
              mandatory true;
              description
                "Configure in label assignment and forwarding";
            }
            container allocate {
              presence "Indicates a allocate node is configured.";
              description
                "Label Allocation Option";
              container per-prefix {
                presence "Indicates a per-prefix node is configured.";
                description
                  "For a given prefix";
                leaf prefix-address {
                  type inet:ip-address-no-zone;
                  mandatory true;
                  description
                    "IPv4 or IPv6 Prefix address";
                }
                leaf prefix-length {
                  type union {
                    type xr:Ipv4-prefix-length;
                    type xr:Ipv6-prefix-length;
                  }
                  mandatory true;
                  description
                    "Prefix length";
                }
              }
              container top-label-hash {
                must "not(../per-prefix)";
                presence "Indicates a top-label-hash node is configured.";
                description
                  "Configure top label hash entries for this LSP";
              }
            }
          }
          container resolve-options {
            description
              "Configure resolve-nexthop options";
            container disable-default-route {
              presence "Indicates a disable-default-route node is configured.";
              description
                "Disable RIB default route";
            }
          }
          container l2-bypass {
            presence "Indicates a l2-bypass node is configured.";
            description
              "Special flag to notify data plane to send l2 packet as is.";
          }
          container forward {
            description
              "Configure forwarding rewrites";
            list path {
              must "nexthop or resolve-nexthop";
              key "path-count";
              description
                "Configure path parameters";
              leaf path-count {
                type uint32 {
                  range "1..16" {
                    description
                      "Path count";
                  }
                }
                description
                  "Configure path parameters";
              }
              container resolve-nexthop {
                must "(ipv4-address or ipv6-address) and not(../nexthop)";
                presence "Indicates a resolve-nexthop node is configured.";
                description
                  "RIB path resolution mode";
                leaf ipv4-address {
                  type inet:ipv4-address-no-zone;
                  must "not(../ipv6-address)";
                  description
                    "Next-hop IPv4 address";
                }
                leaf ipv6-address {
                  type inet:ipv6-address-no-zone;
                  must "not(../ipv4-address)";
                  description
                    "Next-hop IPv6 address";
                }
                container out-label {
                  must "label-value or pop or explicit-null or ipv6-explicit-null";
                  presence "Indicates a out-label node is configured.";
                  description
                    "Outgoing label";
                  leaf label-value {
                    type uint32 {
                      range "16..1048575" {
                        description
                          "MPLS label value";
                      }
                    }
                    must "not(../pop or ../explicit-null or ../ipv6-explicit-null)";
                    description
                      "MPLS label value";
                  }
                  container pop {
                    must "not(../label-value or ../explicit-null or ../ipv6-explicit-null)";
                    presence "Indicates a pop node is configured.";
                    description
                      "Pop off the top of the label stack";
                  }
                  container explicit-null {
                    must "not(../label-value or ../pop or ../ipv6-explicit-null)";
                    presence "Indicates a explicit-null node is configured.";
                    description
                      "Set the outgoing label to ipv4 explicit-null";
                  }
                  container ipv6-explicit-null {
                    must "not(../label-value or ../pop or ../explicit-null)";
                    presence "Indicates a explicit-null node is configured.";
                    description
                      "Set the outgoing label to ipv4 explicit-null";
                  }
                }
              }
              container nexthop {
                must "ipv4-address or ipv6-address or interface";
                presence "Indicates a nexthop node is configured.";
                description
                  "nexthop";
                leaf interface {
                  type xr:Interface-name;
                  description
                    "Next-hop Interface";
                }
                leaf ipv4-address {
                  type inet:ipv4-address-no-zone;
                  must "not(../ipv6-address)";
                  description
                    "Next-hop IPv4 address";
                }
                leaf ipv6-address {
                  type inet:ipv6-address-no-zone;
                  must "not(../ipv4-address)";
                  description
                    "Next-hop IPv6 address";
                }
                container out-label {
                  must "label-value or pop or explicit-null or ipv6-explicit-null";
                  presence "Indicates a out-label node is configured.";
                  description
                    "Outgoing label";
                  leaf label-value {
                    type uint32 {
                      range "16..1048575" {
                        description
                          "MPLS label value";
                      }
                    }
                    must "not(../pop or ../explicit-null or ../ipv6-explicit-null)";
                    description
                      "MPLS label value";
                  }
                  container pop {
                    must "not(../label-value or ../explicit-null or ../ipv6-explicit-null)";
                    presence "Indicates a pop node is configured.";
                    description
                      "Pop off the top of the label stack";
                  }
                  container explicit-null {
                    must "not(../label-value or ../pop or ../ipv6-explicit-null)";
                    presence "Indicates a explicit-null node is configured.";
                    description
                      "Set the outgoing label to ipv4 explicit-null";
                  }
                  container ipv6-explicit-null {
                    must "not(../label-value or ../pop or ../explicit-null)";
                    presence "Indicates a explicit-null node is configured.";
                    description
                      "Set the outgoing label to ipv4 explicit-null";
                  }
                }
                container backup {
                  must "not(../primary-and-backup)";
                  presence "Indicates a backup node is configured.";
                  description
                    "Path acts as backup only";
                }
                container primary-and-backup {
                  must "not(../backup)";
                  presence "Indicates a primary-and-backup node is configured.";
                  description
                    "Path acts as primary and backup simultaneously";
                }
                leaf backup-id {
                  type uint32 {
                    range "1..16" {
                      description
                        "Backup path ID";
                    }
                  }
                  must "not(../backup)";
                  description
                    "Path ID of the backup path to protect this path";
                }
              }
              container mode {
                description
                  "Configure forwarding NHG parameters";
                container nhg {
                  description
                    "Configure forwarding NHG mode";
                  leaf name {
                    type xr:Cisco-ios-xr-string {
                      length "1..127" {
                        description
                          "Specify the NHG Name";
                      }
                    }
                    description
                      "Specify the NHG Name";
                  }
                  leaf distance {
                    type uint32 {
                      range "1..254" {
                        description
                          "NHG distance value";
                      }
                    }
                    description
                      "NHG distance value";
                  }
                }
              }
            }
          }
          container backup {
            description
              "Configure forwarding backup rewrites";
            list path {
              must "nexthop or resolve-nexthop";
              key "path-count";
              description
                "Configure path parameters";
              leaf path-count {
                type uint32 {
                  range "1..16" {
                    description
                      "Path count";
                  }
                }
                description
                  "Configure path parameters";
              }
              container resolve-nexthop {
                must "(ipv4-address or ipv6-address) and not(../nexthop)";
                presence "Indicates a resolve-nexthop node is configured.";
                description
                  "RIB path resolution mode";
                leaf ipv4-address {
                  type inet:ipv4-address-no-zone;
                  must "not(../ipv6-address)";
                  description
                    "Next-hop IPv4 address";
                }
                leaf ipv6-address {
                  type inet:ipv6-address-no-zone;
                  must "not(../ipv4-address)";
                  description
                    "Next-hop IPv6 address";
                }
                container out-label {
                  must "label-value or pop or explicit-null or ipv6-explicit-null";
                  presence "Indicates a out-label node is configured.";
                  description
                    "Outgoing label";
                  leaf label-value {
                    type uint32 {
                      range "16..1048575" {
                        description
                          "MPLS label value";
                      }
                    }
                    must "not(../pop or ../explicit-null or ../ipv6-explicit-null)";
                    description
                      "MPLS label value";
                  }
                  container pop {
                    must "not(../label-value or ../explicit-null or ../ipv6-explicit-null)";
                    presence "Indicates a pop node is configured.";
                    description
                      "Pop off the top of the label stack";
                  }
                  container explicit-null {
                    must "not(../label-value or ../pop or ../ipv6-explicit-null)";
                    presence "Indicates a explicit-null node is configured.";
                    description
                      "Set the outgoing label to ipv4 explicit-null";
                  }
                  container ipv6-explicit-null {
                    must "not(../label-value or ../pop or ../explicit-null)";
                    presence "Indicates a explicit-null node is configured.";
                    description
                      "Set the outgoing label to ipv4 explicit-null";
                  }
                }
              }
              container nexthop {
                must "ipv4-address or ipv6-address or interface";
                presence "Indicates a nexthop node is configured.";
                description
                  "nexthop";
                leaf interface {
                  type xr:Interface-name;
                  description
                    "Next-hop Interface";
                }
                leaf ipv4-address {
                  type inet:ipv4-address-no-zone;
                  must "not(../ipv6-address)";
                  description
                    "Next-hop IPv4 address";
                }
                leaf ipv6-address {
                  type inet:ipv6-address-no-zone;
                  must "not(../ipv4-address)";
                  description
                    "Next-hop IPv6 address";
                }
                container out-label {
                  must "label-value or pop or explicit-null or ipv6-explicit-null";
                  presence "Indicates a out-label node is configured.";
                  description
                    "Outgoing label";
                  leaf label-value {
                    type uint32 {
                      range "16..1048575" {
                        description
                          "MPLS label value";
                      }
                    }
                    must "not(../pop or ../explicit-null or ../ipv6-explicit-null)";
                    description
                      "MPLS label value";
                  }
                  container pop {
                    must "not(../label-value or ../explicit-null or ../ipv6-explicit-null)";
                    presence "Indicates a pop node is configured.";
                    description
                      "Pop off the top of the label stack";
                  }
                  container explicit-null {
                    must "not(../label-value or ../pop or ../ipv6-explicit-null)";
                    presence "Indicates a explicit-null node is configured.";
                    description
                      "Set the outgoing label to ipv4 explicit-null";
                  }
                  container ipv6-explicit-null {
                    must "not(../label-value or ../pop or ../explicit-null)";
                    presence "Indicates a explicit-null node is configured.";
                    description
                      "Set the outgoing label to ipv4 explicit-null";
                  }
                }
                container backup {
                  must "not(../primary-and-backup)";
                  presence "Indicates a backup node is configured.";
                  description
                    "Path acts as backup only";
                }
                container primary-and-backup {
                  must "not(../backup)";
                  presence "Indicates a primary-and-backup node is configured.";
                  description
                    "Path acts as primary and backup simultaneously";
                }
                leaf backup-id {
                  type uint32 {
                    range "1..16" {
                      description
                        "Backup path ID";
                    }
                  }
                  must "not(../backup)";
                  description
                    "Path ID of the backup path to protect this path";
                }
              }
            }
          }
        }
      }
      container resolve-options {
        description
          "Configure resolve-nexthop options";
        container disable-default-route {
          presence "Indicates a disable-default-route node is configured.";
          description
            "Disable RIB default route";
        }
      }
    }
  }
}
