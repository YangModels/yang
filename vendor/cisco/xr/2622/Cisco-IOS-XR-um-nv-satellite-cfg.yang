module Cisco-IOS-XR-um-nv-satellite-cfg {
  namespace "http://cisco.com/ns/yang/Cisco-IOS-XR-um-nv-satellite-cfg";
  prefix um-nv-satellite-cfg;

  import Cisco-IOS-XR-types {
    prefix xr;
  }
  import ietf-inet-types {
    prefix inet;
  }
  import ietf-yang-types {
    prefix yang;
  }
  import Cisco-IOS-XR-um-interface-cfg {
    prefix a1;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR nv-satellite package configuration.
     
     This YANG module augments the
     modules with configuration data.
     
     Copyright (c) 2021-2025 by Cisco Systems, Inc., and/or its affiliates.
     All rights reserved.";

  revision 2025-12-10 {
    description
      "Addition of secret 10 option
       2025-12-08
         Add support for 25G APs and 400G ICLs
       2025-09-05
         Changes to ensure yang meets RFC6020";
    semver:module-version "1.1.0";
  }
  revision 2021-03-26 {
    description
      "Initial release";
    semver:module-version "1.0.0";
  }

  grouping IF-BODY {
    description
      "Grouping for inteface configuration";
    container nv {
      description
        "Network Virtualisation interface configuration";
      container satellite-fabric-link {
        description
          "Satellite Fabric Link configuration";
        container network {
          presence "Indicates a network node is configured.";
          description
            "Network of satellites";
          container satellites {
            description
              "Satellite";
            list satellite {
              key "satellite-id";
              description
                "Satellite";
              leaf satellite-id {
                type uint32 {
                  range "100..65534" {
                    description
                      "Satellite ID";
                  }
                }
                description
                  "Satellite";
              }
              container remote-ports {
                description
                  "Remote ports configuration";
                container gigabit-ethernet {
                  description
                    "Remote ports type";
                  list remote-slot {
                    key "slot-number subslot-number";
                    description
                      "Remote slot";
                    leaf slot-number {
                      type uint32 {
                        range "0..5" {
                          description
                            "Remote slot";
                        }
                      }
                      description
                        "Remote slot";
                    }
                    leaf subslot-number {
                      type uint32 {
                        range "0..5" {
                          description
                            "Remote subslot";
                        }
                      }
                      description
                        "Remote subslot";
                    }
                    leaf mapped-ports {
                      type string {
                        length "1..800" {
                          description
                            "List of ports mapped to this satellite-fabric link; e.g. 1,3-8,9. Must be in ascending order";
                        }
                      }
                      mandatory true;
                      description
                        "List of ports mapped to this satellite-fabric link; e.g. 1,3-8,9. Must be in ascending order";
                    }
                  }
                }
                container ten-gig-e {
                  description
                    "Remote ports type";
                  list remote-slot {
                    key "slot-number subslot-number";
                    description
                      "Remote slot";
                    leaf slot-number {
                      type uint32 {
                        range "0..5" {
                          description
                            "Remote slot";
                        }
                      }
                      description
                        "Remote slot";
                    }
                    leaf subslot-number {
                      type uint32 {
                        range "0..5" {
                          description
                            "Remote subslot";
                        }
                      }
                      description
                        "Remote subslot";
                    }
                    leaf mapped-ports {
                      type string {
                        length "1..800" {
                          description
                            "List of ports mapped to this satellite-fabric link; e.g. 1,3-8,9. Must be in ascending order";
                        }
                      }
                      mandatory true;
                      description
                        "List of ports mapped to this satellite-fabric link; e.g. 1,3-8,9. Must be in ascending order";
                    }
                  }
                }
                container twentyfive-gig-e {
                  description
                    "Remote ports type";
                  list remote-slot {
                    key "slot-number subslot-number";
                    description
                      "Remote slot";
                    leaf slot-number {
                      type uint32 {
                        range "0..5" {
                          description
                            "Remote slot";
                        }
                      }
                      description
                        "Remote slot";
                    }
                    leaf subslot-number {
                      type uint32 {
                        range "0..5" {
                          description
                            "Remote subslot";
                        }
                      }
                      description
                        "Remote subslot";
                    }
                    leaf mapped-ports {
                      type string {
                        length "1..800" {
                          description
                            "List of ports mapped to this satellite-fabric link; e.g. 1,3-8,9. Must be in ascending order";
                        }
                      }
                      mandatory true;
                      description
                        "List of ports mapped to this satellite-fabric link; e.g. 1,3-8,9. Must be in ascending order";
                    }
                  }
                }
              }
            }
          }
          container redundancy {
            description
              "Redundancy configuration";
            leaf iccp-group {
              type uint32 {
                range "1..4294967295" {
                  description
                    "Redundancy group ID";
                }
              }
              description
                "Redundancy group ID";
            }
          }
        }
        container satellite {
          presence "Indicates a satellite node is configured.";
          description
            "Satellite ID";
          leaf satellite-id {
            type uint32 {
              range "100..65534" {
                description
                  "Satellite ID";
              }
            }
            mandatory true;
            description
              "Satellite ID";
          }
          container minimum {
            description
              "Min-links configuration";
            container required {
              description
                "Hard Min-links";
              leaf links {
                type uint32 {
                  range "1..64" {
                    description
                      "Required minimum number of active links";
                  }
                }
                description
                  "Active links";
              }
            }
          }
          container remote-ports {
            description
              "Remote ports configuration";
            container gigabit-ethernet {
              description
                "Remote ports type";
              list remote-slot {
                key "slot-number subslot-number";
                description
                  "Remote slot";
                leaf slot-number {
                  type uint32 {
                    range "0..5" {
                      description
                        "Remote slot";
                    }
                  }
                  description
                    "Remote slot";
                }
                leaf subslot-number {
                  type uint32 {
                    range "0..5" {
                      description
                        "Remote subslot";
                    }
                  }
                  description
                    "Remote subslot";
                }
                leaf mapped-ports {
                  type string {
                    length "1..800" {
                      description
                        "List of ports mapped to this satellite-fabric link; e.g. 1,3-8,9. Must be in ascending order";
                    }
                  }
                  mandatory true;
                  description
                    "List of ports mapped to this satellite-fabric link; e.g. 1,3-8,9. Must be in ascending order";
                }
              }
            }
            container ten-gig-e {
              description
                "Remote ports type";
              list remote-slot {
                key "slot-number subslot-number";
                description
                  "Remote slot";
                leaf slot-number {
                  type uint32 {
                    range "0..5" {
                      description
                        "Remote slot";
                    }
                  }
                  description
                    "Remote slot";
                }
                leaf subslot-number {
                  type uint32 {
                    range "0..5" {
                      description
                        "Remote subslot";
                    }
                  }
                  description
                    "Remote subslot";
                }
                leaf mapped-ports {
                  type string {
                    length "1..800" {
                      description
                        "List of ports mapped to this satellite-fabric link; e.g. 1,3-8,9. Must be in ascending order";
                    }
                  }
                  mandatory true;
                  description
                    "List of ports mapped to this satellite-fabric link; e.g. 1,3-8,9. Must be in ascending order";
                }
              }
            }
            container twentyfive-gig-e {
              description
                "Remote ports type";
              list remote-slot {
                key "slot-number subslot-number";
                description
                  "Remote slot";
                leaf slot-number {
                  type uint32 {
                    range "0..5" {
                      description
                        "Remote slot";
                    }
                  }
                  description
                    "Remote slot";
                }
                leaf subslot-number {
                  type uint32 {
                    range "0..5" {
                      description
                        "Remote subslot";
                    }
                  }
                  description
                    "Remote subslot";
                }
                leaf mapped-ports {
                  type string {
                    length "1..800" {
                      description
                        "List of ports mapped to this satellite-fabric link; e.g. 1,3-8,9. Must be in ascending order";
                    }
                  }
                  mandatory true;
                  description
                    "List of ports mapped to this satellite-fabric link; e.g. 1,3-8,9. Must be in ascending order";
                }
              }
            }
          }
          container redundancy {
            description
              "Redundancy configuration";
            leaf iccp-group {
              type uint32 {
                range "1..4294967295" {
                  description
                    "Redundancy group ID";
                }
              }
              description
                "Redundancy group ID";
            }
            container minimum {
              description
                "Min-links configuration";
              container preferred {
                description
                  "Soft Min-links";
                leaf links {
                  type uint32 {
                    range "1..64" {
                      description
                        "Preferred minimum number of active links";
                    }
                  }
                  description
                    "Active links";
                }
              }
            }
          }
        }
      }
    }
  }

  augment "/a1:interfaces/a1:interface" {
    description
      "nV satellite interface configuration augmentation";
    uses IF-BODY;
  }
  augment "/a1:interfaces/a1:interface-preconfigure" {
    description
      "nV satellite interface configuration augmentation";
    uses IF-BODY;
  }
  container nv {
    description
      "Network Virtualisation configuration";
    container satellites {
      description
        "Satellite configuration";
      list satellite {
        key "satellite-id";
        description
          "Satellite configuration";
        leaf satellite-id {
          type uint32 {
            range "100..65534" {
              description
                "Satellite ID";
            }
          }
          description
            "Satellite configuration";
        }
        leaf description {
          type string {
            length "1..256" {
              description
                "Satellite description";
            }
          }
          description
            "Satellite description";
        }
        leaf type {
          type xr:Cisco-ios-xr-string {
            length "1..800" {
              description
                "Satellite type";
            }
          }
          description
            "Satellite type";
        }
        container ip {
          description
            "IP parameters";
          leaf address {
            type inet:ip-address-no-zone;
            description
              "IP address";
          }
        }
        leaf vrf {
          type xr:Cisco-ios-xr-string {
            length "1..800" {
              description
                "VRF name";
            }
          }
          description
            "Local VRF name";
        }
        leaf serial-number {
          type xr:Cisco-ios-xr-string {
            length "1..800" {
              description
                "Satellite serial number";
            }
          }
          description
            "Serial number of the connected satellite";
        }
        leaf secret {
          type xr:Md5-password;
          description
            "Secure password for local access to nV Ethernet satellite";
        }
        leaf secret-ten {
          type xr:Type10-password;
          description
            "Secure password for local access to nV Ethernet satellite";
        }
        leaf device-name {
          type xr:Cisco-ios-xr-string {
            length "1..800" {
              description
                "name for the satellite";
            }
            pattern "[a-zA-Z0-9_-]+";
          }
          description
            "Satellite name";
        }
        container redundancy {
          description
            "Redundancy configuration";
          leaf host-priority {
            type uint32 {
              range "0..255" {
                description
                  "Priority. A lower number denotes a higher priority. (Default: 128)";
              }
            }
            description
              "Priority of this host for the given satellite";
          }
          leaf delayed-switchback {
            type uint32 {
              range "0..600" {
                description
                  "Duration (in seconds) for the delayed switchback timer (default: 300s)";
              }
            }
            description
              "Change the delay switchback timer";
          }
        }
        container candidate-fabric-ports {
          description
            "Candidate fabric ports";
          container nv-fabric-gig-e {
            description
              "Gigabit Ethernet fabric port type";
            container fabric-port-slots {
              description
                "Fabric port slot";
              list fabric-port-slot {
                key "fabric-port-slot-id fabric-port-subslot-id";
                description
                  "Fabric port slot";
                leaf fabric-port-slot-id {
                  type uint32 {
                    range "0..5" {
                      description
                        "Fabric port slot";
                    }
                  }
                  description
                    "Fabric port slot";
                }
                leaf fabric-port-subslot-id {
                  type uint32 {
                    range "0..5" {
                      description
                        "Fabric port subslot";
                    }
                  }
                  description
                    "Fabric port subslot";
                }
                leaf list-of-candidate-fabric-ports {
                  type string {
                    length "1..800" {
                      description
                        "List of candidate fabric ports; e.g. 1,3-8,9. Must be in ascending order";
                    }
                  }
                  mandatory true;
                  description
                    "List of candidate fabric ports; e.g. 1,3-8,9. Must be in ascending order";
                }
              }
            }
          }
          container nv-fabric-ten-gig-e {
            description
              "Ten Gigabit Ethernet fabric port type";
            container fabric-port-slots {
              description
                "Fabric port slot";
              list fabric-port-slot {
                key "fabric-port-slot-id fabric-port-subslot-id";
                description
                  "Fabric port slot";
                leaf fabric-port-slot-id {
                  type uint32 {
                    range "0..5" {
                      description
                        "Fabric port slot";
                    }
                  }
                  description
                    "Fabric port slot";
                }
                leaf fabric-port-subslot-id {
                  type uint32 {
                    range "0..5" {
                      description
                        "Fabric port subslot";
                    }
                  }
                  description
                    "Fabric port subslot";
                }
                leaf list-of-candidate-fabric-ports {
                  type string {
                    length "1..800" {
                      description
                        "List of candidate fabric ports; e.g. 1,3-8,9. Must be in ascending order";
                    }
                  }
                  mandatory true;
                  description
                    "List of candidate fabric ports; e.g. 1,3-8,9. Must be in ascending order";
                }
              }
            }
          }
          container nv-fabric-forty-gig-e {
            description
              "Forty Gigabit Ethernet fabric port type";
            container fabric-port-slots {
              description
                "Fabric port slot";
              list fabric-port-slot {
                key "fabric-port-slot-id fabric-port-subslot-id";
                description
                  "Fabric port slot";
                leaf fabric-port-slot-id {
                  type uint32 {
                    range "0..5" {
                      description
                        "Fabric port slot";
                    }
                  }
                  description
                    "Fabric port slot";
                }
                leaf fabric-port-subslot-id {
                  type uint32 {
                    range "0..5" {
                      description
                        "Fabric port subslot";
                    }
                  }
                  description
                    "Fabric port subslot";
                }
                leaf list-of-candidate-fabric-ports {
                  type string {
                    length "1..800" {
                      description
                        "List of candidate fabric ports; e.g. 1,3-8,9. Must be in ascending order";
                    }
                  }
                  mandatory true;
                  description
                    "List of candidate fabric ports; e.g. 1,3-8,9. Must be in ascending order";
                }
              }
            }
          }
          container nv-fabric-hundred-gig-e {
            description
              "Hundred Gigabit Ethernet fabric port type";
            container fabric-port-slots {
              description
                "Fabric port slot";
              list fabric-port-slot {
                key "fabric-port-slot-id fabric-port-subslot-id";
                description
                  "Fabric port slot";
                leaf fabric-port-slot-id {
                  type uint32 {
                    range "0..5" {
                      description
                        "Fabric port slot";
                    }
                  }
                  description
                    "Fabric port slot";
                }
                leaf fabric-port-subslot-id {
                  type uint32 {
                    range "0..5" {
                      description
                        "Fabric port subslot";
                    }
                  }
                  description
                    "Fabric port subslot";
                }
                leaf list-of-candidate-fabric-ports {
                  type string {
                    length "1..800" {
                      description
                        "List of candidate fabric ports; e.g. 1,3-8,9. Must be in ascending order";
                    }
                  }
                  mandatory true;
                  description
                    "List of candidate fabric ports; e.g. 1,3-8,9. Must be in ascending order";
                }
              }
            }
          }
          container nv-fabric-four-hundred-gig-e {
            description
              "Four Hundred Gigabit Ethernet fabric port type";
            container fabric-port-slots {
              description
                "Fabric port slot";
              list fabric-port-slot {
                key "fabric-port-slot-id fabric-port-subslot-id";
                description
                  "Fabric port slot";
                leaf fabric-port-slot-id {
                  type uint32 {
                    range "0..5" {
                      description
                        "Fabric port slot";
                    }
                  }
                  description
                    "Fabric port slot";
                }
                leaf fabric-port-subslot-id {
                  type uint32 {
                    range "0..5" {
                      description
                        "Fabric port subslot";
                    }
                  }
                  description
                    "Fabric port subslot";
                }
                leaf list-of-candidate-fabric-ports {
                  type string {
                    length "1..800" {
                      description
                        "List of candidate fabric ports; e.g. 1,3-8,9. Must be in ascending order";
                    }
                  }
                  mandatory true;
                  description
                    "List of candidate fabric ports; e.g. 1,3-8,9. Must be in ascending order";
                }
              }
            }
          }
        }
        container upgrade {
          description
            "Satellite upgrade configuration";
          container on-connect {
            must "not(../on-first-connect)";
            presence "Indicates a on-connect node is configured.";
            description
              "Auto-upgrade on connection as required";
            container image-reference {
              description
                "Specify an image reference";
              leaf reference-name {
                type xr:Cisco-ios-xr-string {
                  length "1..800" {
                    description
                      "Reference name";
                  }
                }
                description
                  "Reference name";
              }
            }
            container reference {
              description
                "Specify a reference";
              leaf reference-name {
                type xr:Cisco-ios-xr-string {
                  length "1..800" {
                    description
                      "Reference name";
                  }
                }
                description
                  "Reference name";
              }
            }
          }
          container on-first-connect {
            must "not(../on-connect)";
            presence "Indicates a on-first-connect node is configured.";
            description
              "Auto-upgrade on first connection after configuration or host boot";
            container image-reference {
              description
                "Specify an image reference";
              leaf reference-name {
                type xr:Cisco-ios-xr-string {
                  length "1..800" {
                    description
                      "Reference name";
                  }
                }
                description
                  "Reference name";
              }
            }
            container reference {
              description
                "Specify a reference";
              leaf reference-name {
                type xr:Cisco-ios-xr-string {
                  length "1..800" {
                    description
                      "Reference name";
                  }
                }
                description
                  "Reference name";
              }
            }
          }
        }
        container discovery {
          description
            "Per satellite options for Discovery";
          leaf timeout {
            type uint32 {
              range "30..4294967295" {
                description
                  "Time (in seconds) for the Discovery timeout.";
              }
            }
            description
              "Satellite discovery timeout";
          }
          leaf warning {
            type uint32 {
              range "3..4294967295" {
                description
                  "Number of missed discovery packets before outputting warning syslog.";
              }
            }
            description
              "Satellite discovery warning";
          }
        }
      }
    }
    container satellite {
      description
        "satellite mac configuration";
      leaf chassis-mac {
        type yang:mac-address;
        description
          "MAC address to use as chassis MAC of the host device";
      }
    }
  }
}
