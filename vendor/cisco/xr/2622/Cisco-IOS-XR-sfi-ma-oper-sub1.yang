submodule Cisco-IOS-XR-sfi-ma-oper-sub1 {
  belongs-to Cisco-IOS-XR-sfi-ma-oper {
    prefix Cisco-IOS-XR-sfi-ma-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR sfi-ma package operational data.
     
     Copyright (c) 2013-2021 by Cisco Systems, Inc.
     All rights reserved.";

  revision 2021-08-25 {
    description
      "Added registered-table-id and registered-proto-id leafs to SFI VRF RIB AFI registration information";
    semver:module-version "1.1.0";
  }
  revision 2021-08-12 {
    description
      "Added MPLS v4/v6 label leaves to SFI-DETAIL";
    semver:module-version "1.0.0";
  }
  revision 2020-12-08 {
    description
      "Added SFI VRF Bag and respective oper commands";
  }
  revision 2020-01-06 {
    description
      "Initial version";
  }
  revision 2019-04-05 {
    description
      "Establish semantic version baseline.";
  }
  revision 2015-11-09 {
    description
      "IOS XR 6.0 revision.";
  }

  typedef Sfi-state {
    type enumeration {
      enum "unknown" {
        value 0;
        description
          "Unknown";
      }
      enum "down" {
        value 1;
        description
          "Down";
      }
      enum "up" {
        value 2;
        description
          "Up";
      }
    }
    description
      "SFI states";
  }

  grouping SFI-DETAIL {
    description
      "Service Function Interface Detailed Information";
    leaf interface-name-xr {
      type string;
      description
        "Interface name";
    }
    leaf interface-state {
      type Sfi-state;
      description
        "Interface state";
    }
    leaf admin-state {
      type Sfi-state;
      description
        "Interface admin state";
    }
    leaf vrf-name {
      type string;
      description
        "VRF name";
    }
    leaf group-name {
      type string;
      description
        "Group name";
    }
    leaf mpls-v4-label {
      type uint32;
      description
        "MPLS V4 Label";
    }
    leaf mpls-v6-label {
      type uint32;
      description
        "MPLS V6 Label";
    }
  }

  grouping SFI-VRF-RIB-AF-INFO {
    description
      "SFI VRF RIB AFI registration information bag";
    leaf table-id {
      type uint32;
      description
        "Table ID";
    }
    leaf registered-table-id {
      type uint32;
      description
        "Registered Table ID";
    }
    leaf registered-proto-id {
      type uint32;
      description
        "Registered Proto ID";
    }
    leaf sfi-count {
      type uint32;
      description
        "SFI Count";
    }
  }

  grouping SFI-VRF-INFO {
    description
      "SFI VRF bag";
    leaf vrf-name {
      type string;
      description
        "VRF Name";
    }
    leaf vrf-id {
      type uint32;
      description
        "VRF ID";
    }
    list rib-afi-info {
      description
        "per AFI RIB conn handles";
      uses SFI-VRF-RIB-AF-INFO;
    }
  }
}
