module Cisco-IOS-XR-sks-server-cfg {
  namespace "http://cisco.com/ns/yang/Cisco-IOS-XR-sks-server-cfg";
  prefix sks-server-cfg;

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR sks-server package configuration.
     
     This module contains definitions
     for the following management objects:
       sks: Session key server configuration
     
     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  container sks {
    description
      "Session key server configuration";
    list profile-name {
      key "name";
      description
        "Profile name";
      leaf name {
        type xr:Cisco-ios-xr-string;
        description
          "Profile Name";
      }
      list device-identifier-name {
        key "name";
        description
          "Device identifier name";
        container peer-identifier-names {
          description
            "peer identifier";
          list peer-identifier-name {
            key "name";
            description
              "peer identifier name";
            leaf name {
              type xr:Cisco-ios-xr-string;
              description
                "peer identifier name";
            }
            leaf master {
              type uint32 {
                range "0..1";
              }
              mandatory true;
              description
                "1 for master, 0 for slave";
            }
          }
        }
        leaf pool {
          type uint32 {
            range "0..1";
          }
          default "0";
          description
            "1 for single pool, 0 for double pool";
        }
        leaf live-keys {
          type uint32 {
            range "1..120";
          }
          default "1";
          description
            "value between 1-120, default is 1";
        }
        leaf name {
          type xr:Cisco-ios-xr-string;
          description
            "device identifier name";
        }
      }
    }
  }
}
