module Cisco-IOS-XR-portmode-oper {
  namespace "http://cisco.com/ns/yang/Cisco-IOS-XR-portmode-oper";
  prefix portmode-oper;

  import Cisco-IOS-XR-types {
    prefix xr;
  }
  import cisco-semver {
    prefix semver;
  }
  include Cisco-IOS-XR-portmode-oper-sub1 {
    revision-date 2023-10-03;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR portmode package operational data.
     
     This module contains definitions
     for the following management objects:
       port-mode: PortMode operational data
     
     Copyright (c) 2013-2023 by Cisco Systems, Inc.
     All rights reserved.";

  revision 2023-10-03 {
    description
      "Interface name length size is updated
       2023-02-06
         Client controller name is added under portmode details";
    semver:module-version "2.1.0";
  }
  revision 2020-10-27 {
    description
      "New framing type cem-packetize is added.";
    semver:module-version "2.0.0";
  }
  revision 2020-04-03 {
    description
      "Portmode Oper Yang and Oper Sub-Yang Model added.";
    semver:module-version "1.1.0";
  }
  revision 2019-07-05 {
    description
      "Portmode Oper Yang and Oper Sub-Yang Model added.";
    semver:module-version "1.0.0";
  }
  revision 2019-04-05 {
    description
      "Establish semantic version baseline.";
  }
  revision 2015-11-09 {
    description
      "IOS XR 6.0 revision.";
  }

  container port-mode {
    config false;
    description
      "PortMode operational data";
    container controllers {
      description
        "All PortMode Port operational data";
      list controller {
        key "controller-name";
        description
          "PortMode Port operational data";
        container portmode-info {
          description
            "PortMode operational data";
          uses PORTMODE-DETAILS;
        }
        container portmode-info-all {
          description
            "PortMode operational data";
          uses PORTMODE-DETAILS-ALL;
        }
        container capability-info {
          description
            "PortMode operational data";
          uses PORTMODE-CAPABILITY-ALL;
        }
        leaf controller-name {
          type xr:Cisco-ios-xr-string;
          description
            "Port name";
        }
      }
    }
  }
}
