module Cisco-IOS-XR-healthcheck-cfg {
  namespace "http://cisco.com/ns/yang/Cisco-IOS-XR-healthcheck-cfg";
  prefix healthcheck-cfg;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR healthcheck package configuration.
     
     This module contains definitions
     for the following management objects:
       health-check: System Health Check operational data space
     
     Copyright (c) 2013-2026 by Cisco Systems, Inc.
     All rights reserved.";

  revision 2026-07-10 {
    description
      "Added deprecation message for Healthcheck packet-drop and asic-reset use-cases
       2026-01-21
         Deprecated Healthcheck legacy metrics
       2025-09-30
         Updated version in which legacy metrics are getting deprecated
       2025-04-28
         Added deprecation message for Healthcheck legacy metrics in config yang
       2024-04-04
         Modified description of low and medium tolerance under packet-drop usecase
       2024-01-18
         Removed Drop-Tolerance leaf from packet-drop
       2023-10-03
         Added tolerance container and window leaf in packet-drop
       2023-07-19
         Removed default cadence
       2023-01-18
         Updated Metric Threshold Ranges";
    semver:module-version "2.0.0";
  }
  revision 2022-05-25 {
    description
      "Changed the counter-size start value";
  }
  revision 2022-04-07 {
    description
      "Migrate NBC and rev build control to mgbl-yangref component";
  }
  revision 2020-07-14 {
    description
      "Platform Stats metrics and Custom Metrics configurations added";
    semver:module-version "1.0.0";
  }
  revision 2019-04-05 {
    description
      "Establish semantic version baseline.";
  }
  revision 2015-11-09 {
    description
      "IOS XR 6.0 revision.";
  }

  container health-check {
    description
      "System Health Check operational data space";
    container ord-z {
      description
        "Healthcheck config";
      leaf enable {
        type empty;
        description
          "Enable or disable health check";
      }
    }
    container use-case {
      status deprecated;
      description
        "Use case to monitor. Note: This container is
         deprecated and will be removed in the 27.1.1
         release";
      container asic-reset {
        status deprecated;
        description
          "Use case Asic reset. Note: This use-case is
           deprecated and will be removed in the 27.1.1
           release";
        leaf disable {
          type empty;
          status deprecated;
          description
            "Disable Asic reset use case monitoring. Note:
             This leaf is deprecated and will be removed in
             the 27.1.1 release";
        }
        leaf drop-tolerance {
          type uint32 {
            range "0..100";
          }
          units "percentage";
          default "10";
          status deprecated;
          description
            "Drop tolerance as a percentage of total
             incoming bytes/packets. Note: This leaf is
             deprecated and will be removed in the 27.1.1
             release";
        }
      }
      container packet-drop {
        status deprecated;
        description
          "Use case Packet drop. Note: This use-case is
           deprecated and will be removed in the 27.1.1
           release";
        container tolerance {
          status deprecated;
          description
            "Use case Packet drop. Note: This container is
             deprecated and will be removed in the 27.1.1
             release";
          leaf tolerance-level-low {
            type uint32 {
              range "0..1000000";
            }
            default "100";
            status deprecated;
            description
              "Drop tolerance as traps per second for low
               classified traps. Note: This leaf is
               deprecated and will be removed in the 27.1.1
               release";
          }
          leaf tolerance-level-medium {
            type uint32 {
              range "0..1000000";
            }
            default "1000";
            status deprecated;
            description
              "Drop tolerance as traps per second for medium
               classified traps. Note: This leaf is
               deprecated and will be removed in the 27.1.1
               release";
          }
          leaf tolerance-level-high {
            type uint32 {
              range "0..1000000";
            }
            default "10000";
            status deprecated;
            description
              "Drop tolerance as traps per second for high
               classified traps. Note: This leaf is
               deprecated and will be removed in the 27.1.1
               release";
          }
        }
        leaf disable {
          type empty;
          status deprecated;
          description
            "Disable Packet drop use case monitoring. Note:
             This leaf is deprecated and will be removed in
             the 27.1.1 release";
        }
        leaf drop-window {
          type uint32 {
            range "5..20";
          }
          default "10";
          status deprecated;
          description
            "Drop window is the number of cadence intervals
             to detect traffic failure. Note: This leaf is
             deprecated and will be removed in the 27.1.1
             release";
        }
      }
    }
    container ord-a {
      description
        "Healthcheck config";
      leaf cadence {
        type uint32 {
          range "30..1800";
        }
        description
          "health check cadence";
      }
    }
  }
}
