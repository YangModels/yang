module Cisco-IOS-XR-hw-module-cfg-deviations {
  namespace "http://cisco.com/ns/yang/Cisco-IOS-XR-hw-module-cfg-deviations";
  prefix cisco-ios-xr-hw-module-cfg-dev;

  import Cisco-IOS-XR-hw-module-cfg {
    prefix hw-module-cfg;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a set of deviations of HW-module cfg data
     model set for Cisco IOS-XR.
     
     Copyright (c) 2013-2026 by Cisco Systems, Inc., and/or its affiliates.
     All rights reserved.";

  revision 2026-07-08 {
    description
      "Deleted the hw-module config container 'must' on eXR. Because
       attention-led, auto-reset-disable and fault-recovery-count are
       deviated not-supported on eXR, the base model 'must' referenced
       nodes absent from the effective eXR schema, producing an
       undefined-node warning in NED/NSO builds. Deleting the 'must'
       clears that warning.";
  }
  revision 2023-09-26 {
    description
      "Added deviation for fault-recovery-count";
  }
  revision 2022-02-24 {
    description
      "Added deviation for ejector close";
  }
  revision 2020-05-27 {
    description
      "Initial revision applicable to IOS-XR 7. 3. 1 and older releases";
  }

  deviation "/hw-module-cfg:hw-module/hw-module-cfg:nodes/hw-module-cfg:node/hw-module-cfg:config" {
    deviate delete {
      must "attention-led or admin-state or auto-reset-disable or fault-recovery-count";
    }
  }
  deviation "/hw-module-cfg:hw-module/hw-module-cfg:nodes/hw-module-cfg:node/hw-module-cfg:config/hw-module-cfg:auto-reset-disable" {
    deviate not-supported;
  }
  deviation "/hw-module-cfg:hw-module/hw-module-cfg:nodes/hw-module-cfg:node/hw-module-cfg:config/hw-module-cfg:attention-led" {
    deviate not-supported;
  }
  deviation "/hw-module-cfg:wait-ejector-close" {
    deviate not-supported;
  }
  deviation "/hw-module-cfg:hw-module/hw-module-cfg:nodes/hw-module-cfg:node/hw-module-cfg:config/hw-module-cfg:fault-recovery-count" {
    deviate not-supported;
  }
}
