module Cisco-IOS-XR-8000-platforms-npu-pfc-pause-duration-oper {
  namespace "http://cisco.com/ns/yang/Cisco-IOS-XR-8000-platforms-npu-pfc-pause-duration-oper";
  prefix xr-8000-platforms-npu-pfc-pause-duration-oper;

  import Cisco-IOS-XR-types {
    prefix xr;
  }
  import cisco-semver {
    prefix semver;
  }
  import Cisco-IOS-XR-platforms-ofa-oper {
    prefix a1;
  }
  include Cisco-IOS-XR-8000-platforms-npu-pfc-pause-duration-oper-sub1 {
    revision-date 2024-08-15;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR 8000-platforms-npu-pfc-pause-duration package operational data.
     
     This YANG module augments the
       Cisco-IOS-XR-platforms-ofa-oper
     module with state data.
     
     Copyright (c) 2013-2024 by Cisco Systems, Inc.
     All rights reserved.";

  revision 2024-08-15 {
    description
      "Added pause time in ns support in oper yang model.";
    semver:module-version "1.0.0";
  }
  revision 2024-02-09 {
    description
      "Added all interface support in oper yang model.";
  }
  revision 2019-04-05 {
    description
      "Establish semantic version baseline.";
  }
  revision 2015-11-09 {
    description
      "IOS XR 6.0 revision.";
  }

  augment "/a1:ofa/a1:stats/a1:nodes/a1:node" {
    description
      "This augment extends the operational data of
       'Cisco-IOS-XR-platforms-ofa-oper'";
    container pause-duration-stats {
      description
        "Pause duration for TX and RX";
      container tx-pause-time-all-interface {
        description
          "TX Pause duration info for all interfaces";
        container tx-pause-time {
          description
            "TX all interface PauseTime in us";
          uses OFA-PFC-PAUSE-DURATION-USAGE-ARRAY-ST;
        }
      }
      container tx-interfaces {
        description
          "Pause duration percent for TX";
        list tx-interface {
          key "interface-name";
          description
            "Pause duration percent for TX interface";
          container five-minute {
            description
              "TX-RX Pause Duration In Five-Minute Window";
            uses OFA-PFC-PAUSE-DURATION-USAGE-ARRAY-ST;
          }
          container detail {
            description
              "TX-RX Pause Duration In Detail Window";
            uses OFA-PFC-PAUSE-DURATION-USAGE-ARRAY-ST;
          }
          container one-minute {
            description
              "TX-RX Pause Duration In One-Minute Window";
            uses OFA-PFC-PAUSE-DURATION-USAGE-ARRAY-ST;
          }
          container default {
            description
              "TX-RX Pause Duration In Default Window";
            uses OFA-PFC-PAUSE-DURATION-USAGE-ARRAY-ST;
          }
          leaf interface-name {
            type xr:Interface-name;
            description
              "The name of the interface";
          }
        }
      }
      container rx-interfaces {
        description
          "Pause duration percent for RX";
        list rx-interface {
          key "interface-name";
          description
            "Pause duration percent for RX interface";
          container five-minute {
            description
              "TX-RX Pause Duration In Five-Minute Window";
            uses OFA-PFC-PAUSE-DURATION-USAGE-ARRAY-ST;
          }
          container detail {
            description
              "TX-RX Pause Duration In Detail Window";
            uses OFA-PFC-PAUSE-DURATION-USAGE-ARRAY-ST;
          }
          container one-minute {
            description
              "TX-RX Pause Duration In One-Minute Window";
            uses OFA-PFC-PAUSE-DURATION-USAGE-ARRAY-ST;
          }
          container default {
            description
              "TX-RX Pause Duration In Default Window";
            uses OFA-PFC-PAUSE-DURATION-USAGE-ARRAY-ST;
          }
          leaf interface-name {
            type xr:Interface-name;
            description
              "The name of the interface";
          }
        }
      }
      container rx-pause-time-interfaces {
        description
          "Pause duration in microseconds for RX";
        list rx-pause-time-interface {
          key "interface-name";
          description
            "Pause duration in microseconds for RX
             interface";
          container pause-duration {
            description
              "TX-RX Pause Duration In ms";
            uses OFA-PFC-PAUSE-DURATION-USAGE-ARRAY-ST;
          }
          leaf interface-name {
            type xr:Interface-name;
            description
              "The name of the interface";
          }
        }
      }
      container rx-all-interface {
        description
          "RX all interface One/five-minure-window";
        container rx-one-minute {
          description
            "RX all interface One-minute-window";
          uses OFA-PFC-PAUSE-DURATION-USAGE-ARRAY-ST;
        }
        container rx-five-minute {
          description
            "RX all interface Five-minute-window";
          uses OFA-PFC-PAUSE-DURATION-USAGE-ARRAY-ST;
        }
      }
      container rx-pause-time-all-interface {
        description
          "RX Pause duration info for all interfaces";
        container rx-pause-time {
          description
            "RX all interface PauseTime in us";
          uses OFA-PFC-PAUSE-DURATION-USAGE-ARRAY-ST;
        }
      }
      container tx-pause-time-interfaces {
        description
          "Pause duration in microseconds for TX";
        list tx-pause-time-interface {
          key "interface-name";
          description
            "Pause duration in microseconds for TX
             interface";
          container pause-duration {
            description
              "TX-RX Pause Duration In ms";
            uses OFA-PFC-PAUSE-DURATION-USAGE-ARRAY-ST;
          }
          leaf interface-name {
            type xr:Interface-name;
            description
              "The name of the interface";
          }
        }
      }
      container tx-all-interface {
        description
          "TX all interface One/five-minute-window";
        container tx-five-minute {
          description
            "TX all interface Five-minute-window";
          uses OFA-PFC-PAUSE-DURATION-USAGE-ARRAY-ST;
        }
        container tx-one-minute {
          description
            "TX all interface One-minute-window";
          uses OFA-PFC-PAUSE-DURATION-USAGE-ARRAY-ST;
        }
      }
    }
  }
}
