module Cisco-IOS-XR-cnbng-nal-aipc-client-oper {
  namespace "http://cisco.com/ns/yang/Cisco-IOS-XR-cnbng-nal-aipc-client-oper";
  prefix cnbng-nal-aipc-client-oper;

  import Cisco-IOS-XR-types {
    prefix xr;
  }
  import cisco-semver {
    prefix semver;
  }
  include Cisco-IOS-XR-cnbng-nal-aipc-client-oper-sub1 {
    revision-date 2026-04-04;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR cnbng-nal-aipc-client package operational data.
     
     This module contains definitions
     for the following management objects:
       cnbng-nal-client: cnBNG NAL Client operational data
     
     Copyright (c) 2013-2026 by Cisco Systems, Inc.
     All rights reserved.";

  revision 2026-04-04 {
    description
      "Updated AIPC client stats.
       2023-02-19
         Changed readable strings like server/service names from type char to string.
       2021-10-19
         AIPC client stats display command updated.";
    semver:module-version "2.0.0";
  }
  revision 2020-08-14 {
    description
      "adding schema support for aipc client.";
    semver:module-version "1.0.0";
  }
  revision 2019-04-05 {
    description
      "Establish semantic version baseline.";
  }
  revision 2015-11-09 {
    description
      "IOS XR 6.0 revision.";
  }

  container cnbng-nal-client {
    config false;
    description
      "cnBNG NAL Client operational data";
    container nodes {
      description
        "List of cnBNg NAL supported nodes";
      list node {
        key "node-name";
        description
          "cnBNg NAL operational data for a particular
           node";
        leaf node-name {
          type xr:Node-id;
          description
            "Node name";
        }
        list aipc-client-table {
          key "clientpath";
          description
            "operational data for NAL AIPC client stats";
          container aipc-client-servers {
            description
              "operational data for aipc client stats ";
            list aipc-client-server {
              key "server-name";
              description
                "operational data for aipc client stats ";
              leaf server-name {
                type xr:Cisco-ios-xr-string;
                description
                  "Server Name";
              }
              leaf service-name {
                type xr:Cisco-ios-xr-string;
                description
                  "Service Name";
              }
              uses NAL-AIPC-STATS-DATA;
            }
          }
          leaf clientpath {
            type xr:Cisco-ios-xr-string;
            description
              "client";
          }
        }
      }
    }
  }
}
