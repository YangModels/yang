module Cisco-IOS-XR-dot1x-portauth-oper {
  namespace "http://cisco.com/ns/yang/Cisco-IOS-XR-dot1x-portauth-oper";
  prefix dot1x-portauth-oper;

  import Cisco-IOS-XR-types {
    prefix xr;
  }
  import cisco-semver {
    prefix semver;
  }
  include Cisco-IOS-XR-dot1x-portauth-oper-sub1 {
    revision-date 2025-03-04;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR dot1x-portauth package operational data.
     
     This module contains definitions
     for the following management objects:
       dot1x-port-auth: Port authentication operational data for both
         Dot1x and MAB
     
     Copyright (c) 2013-2025 by Cisco Systems, Inc.
     All rights reserved.";

  revision 2025-03-04 {
    description
      "Introduced support for dot1x portauth statistics";
    semver:module-version "1.0.0";
  }
  revision 2024-12-12 {
    description
      "Addition of dot1x portauth oper model";
  }
  revision 2019-04-05 {
    description
      "Establish semantic version baseline.";
  }
  revision 2015-11-09 {
    description
      "IOS XR 6.0 revision.";
  }

  container dot1x-port-auth {
    config false;
    description
      "Port authentication operational data for both
       Dot1x and MAB";
    container interfaces {
      description
        "Dot1x and MAB enabled interfaces";
      list interface {
        key "name";
        description
          "Dot1x or MAB enabled interface name";
        container detail {
          description
            "Port authentication details for the given
             interface";
          uses DOT1X-PORT-AUTH-DETAIL;
        }
        container summary {
          description
            "Port authentication summary for the given
             interface";
          uses DOT1X-PORT-AUTH-SUMMARY;
        }
        container statistics {
          description
            "Port authentication statistics for the given
             interface";
          uses DOT1X-PORT-AUTH-IF-STATS;
        }
        leaf name {
          type xr:Interface-name;
          description
            "Interface Name";
        }
      }
    }
    container nodes {
      description
        "Node-specific port authentication operational
         info";
      list node {
        key "node-name";
        description
          "port authentication operational info for a
           particular node";
        container interface-summaries {
          description
            "Port Authentication Summary for both Dot1x and
             MAB";
          list interface-summary {
            key "name";
            description
              "Port Authentication summary for a given
               interface ";
            leaf name {
              type xr:Interface-name;
              description
                "Interface Name";
            }
            uses DOT1X-PORT-AUTH-SUMMARY;
          }
        }
        container interface-details {
          description
            "Port authentication details for a specific
             interface";
          list interface-detail {
            key "name";
            description
              "Detailed Port authentication for a given
               interface";
            leaf name {
              type xr:Interface-name;
              description
                "Interface Name";
            }
            uses DOT1X-PORT-AUTH-DETAIL;
          }
        }
        container statistics {
          description
            "Port Authentication statistics";
          uses DOT1X-PORT-AUTH-STATS;
        }
        leaf node-name {
          type xr:Node-id;
          description
            "The node name";
        }
      }
    }
  }
}
