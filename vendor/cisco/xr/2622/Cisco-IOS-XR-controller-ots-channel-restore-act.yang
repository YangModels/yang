module Cisco-IOS-XR-controller-ots-channel-restore-act {
  namespace "http://cisco.com/ns/yang/Cisco-IOS-XR-controller-ots-channel-restore-act";
  prefix controller-ots-channel-restore-act;

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR Channel restore for controller-ots module channels.
     
     Copyright (c) 2018-2023 by Cisco Systems, Inc.
     All rights reserved.";

  revision 2023-01-23 {
    description
      "Channel Restore action support for ots controllers and
       on Ots-Och controllers";
    semver:module-version "1.0.0";
  }

  rpc ots-controller-channel-restore {
    description
      "ots controller channel";
    input {
      leaf controller-name {
        type xr:Interface-name;
        mandatory true;
        description
          "Controller name in R/S/I/P/CH format";
      }
    }
  }
}
