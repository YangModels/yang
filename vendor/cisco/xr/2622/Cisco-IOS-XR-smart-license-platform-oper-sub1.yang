submodule Cisco-IOS-XR-smart-license-platform-oper-sub1 {
  belongs-to Cisco-IOS-XR-smart-license-platform-oper {
    prefix Cisco-IOS-XR-smart-license-platform-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR smart-license-platform package operational data.
     
     Copyright (c) 2013-2022 by Cisco Systems, Inc.
     All rights reserved.";

  revision 2022-09-28 {
    description
      "Added zr-zrp-dco under ft-feature-name-enum enum.
       2022-07-27
         Renamed node-deactivated enum to perpetual-without-sia-renewal in Sia-status-enum type.
       2022-05-09
         Traffic-Eng Advantage license feature renamed to SR-TE Advantage license in feature-details container.";
    semver:module-version "2.0.0";
  }
  revision 2021-06-03 {
    description
      "Added support for enum node-deactivated.";
    semver:module-version "1.1.0";
  }
  revision 2020-09-15 {
    description
      "Structured the yang response for show CLIs.";
    semver:module-version "1.0.0";
  }
  revision 2019-04-05 {
    description
      "Establish semantic version baseline.";
  }
  revision 2015-11-09 {
    description
      "IOS XR 6.0 revision.";
  }

  typedef Ft-feature-name-enum {
    type enumeration {
      enum "essential" {
        description
          "essential";
      }
      enum "l3vpn-advantage" {
        description
          "l3vpn advantage";
      }
      enum "macsec-advantage" {
        description
          "macsec advantage";
      }
      enum "peering-scale-advantage" {
        description
          "peering scale advantage";
      }
      enum "sr-te-advantage" {
        description
          "sr te advantage";
      }
      enum "flex-algo-advantage" {
        description
          "flex algo advantage";
      }
      enum "service-layer-advantage" {
        description
          "service layer advantage";
      }
      enum "evpn-advantage" {
        description
          "evpn advantage";
      }
      enum "vpls-advantage" {
        description
          "vpls advantage";
      }
      enum "iccp-advantage" {
        description
          "iccp advantage";
      }
      enum "l2vpn-advantage" {
        description
          "l2vpn advantage";
      }
      enum "zr-zrp-dco" {
        description
          "zr zrp dco";
      }
    }
    description
      "Feature Name in the feature table";
  }

  typedef Feature-status-enum {
    type enumeration {
      enum "active" {
        description
          "active";
      }
      enum "inactive" {
        description
          "inactive";
      }
    }
    description
      "Feature Name";
  }

  typedef Feature-name-enum {
    type enumeration {
      enum "fcm" {
        description
          "fcm";
      }
      enum "system" {
        description
          "system";
      }
    }
    description
      "Feature Name";
  }

  typedef Bool-state {
    type enumeration {
      enum "no" {
        value 0;
        description
          "No";
      }
      enum "yes" {
        value 1;
        description
          "Yes";
      }
    }
    description
      "Boolean State ";
  }

  typedef Sia-status-enum {
    type enumeration {
      enum "incompliance" {
        description
          "incompliance";
      }
      enum "out-of-compliance" {
        description
          "out of compliance";
      }
      enum "perpetual-without-sia-renewal" {
        description
          "perpetual without sia renewal";
      }
    }
    description
      "SIA Status";
  }

  grouping FEATURE-LIST {
    description
      "FEATURE LIST";
    container count {
      description
        "Count";
      uses PLAT-ENTITLEMENT;
    }
    leaf feature-area {
      type Feature-name-enum;
      description
        "Feature Name";
    }
    leaf entitlement {
      type string;
      description
        "Entitlement";
    }
  }

  grouping PLAT-SL-SUMMARY {
    description
      "SL Summary";
    container collection {
      description
        "Last and Next collection times";
      uses PLAT-INTERVALS;
    }
    container reporting {
      description
        "Last and Next reporting times";
      uses PLAT-INTERVALS;
    }
    container sia-status {
      description
        "SIA Status";
      uses PLAT-SIA-STATUS;
    }
    container upgrade-license-status {
      description
        "Upgrade License Status";
      uses PLAT-UPGRADE-LICENSE-STATUS;
    }
    list license {
      description
        "List of licenses consumed";
      uses FEATURE-LIST;
    }
  }

  grouping PLAT-ENTITLEMENT {
    description
      "PLAT ENTITLEMENT";
    leaf last {
      type uint32;
      description
        "Last count";
    }
    leaf next {
      type uint32;
      description
        "Next count";
    }
  }

  grouping PLAT-ENTITLEMENT-LIST {
    description
      "PLAT ENTITLEMENT LIST";
    container count {
      description
        "Count";
      uses PLAT-ENTITLEMENT;
    }
    leaf name {
      type string;
      description
        "Entitlement Name";
    }
    leaf entitlement-tag {
      type string;
      description
        "Entitlement Tag";
    }
  }

  grouping PLAT-FEATURE-TABLE {
    description
      "PLAT FEATURE TABLE";
    leaf feature {
      type Ft-feature-name-enum;
      description
        "Feature Name";
    }
    leaf location {
      type string;
      description
        "Location";
    }
    leaf interface-list {
      type string;
      description
        "Interface List";
    }
  }

  grouping PLAT-DETAIL-FLAGS {
    description
      "PLAT DETAIL FLAGS";
    leaf need-running-config {
      type Bool-state;
      description
        "Is running config needed";
    }
    leaf need-throughput {
      type Bool-state;
      description
        "Is throughput needed";
    }
  }

  grouping FEATURE-DETAILS {
    description
      "FEATURE DETAILS";
    container flags {
      description
        "Flags for is running config and is throughput";
      uses PLAT-DETAIL-FLAGS;
    }
    leaf name {
      type Feature-name-enum;
      description
        "Feature Name";
    }
    leaf status {
      type Feature-status-enum;
      description
        "Status";
    }
    list feature-table {
      description
        "Feature Table";
      uses PLAT-FEATURE-TABLE;
    }
    list entitlement {
      description
        "List of entitlements";
      uses PLAT-ENTITLEMENT-LIST;
    }
  }

  grouping PLAT-PARAMETERS {
    description
      "PLAT PARAMETERS";
    leaf collection-interval {
      type int32;
      units "minute";
      description
        "Collection Interval in minutes";
    }
    leaf reporting-interval {
      type int32;
      units "minute";
      description
        "Reporting Interval minutes";
    }
    leaf throughput-guage {
      type int32;
      units "kbit/s";
      description
        "Throughput Guage in Kbps";
    }
  }

  grouping PLAT-UPGRADE-LICENSE-STATUS {
    description
      "PLAT UPGRADE LICENSE STATUS";
    container grace-period-remaining {
      description
        "Remaining grace period";
      uses PLAT-GRACE-PERIOD;
    }
    leaf upgrade-license-state {
      type Sia-status-enum;
      description
        "Upgrade License status enum";
    }
    leaf grace-period-expired {
      type Bool-state;
      description
        "Has grace period expired";
    }
    leaf ooc-reason {
      type string;
      description
        "Reason for Upgrade License ooc";
    }
  }

  grouping PLAT-GRACE-PERIOD {
    description
      "PLAT GRACE PERIOD";
    leaf days {
      type int32;
      units "day";
      description
        "Number of days remaining in grace period";
    }
    leaf hours {
      type int32;
      units "hour";
      description
        "Number of hours remaining in grace period";
    }
  }

  grouping PLAT-SIA-STATUS {
    description
      "PLAT SIA STATUS";
    container grace-period-remaining {
      description
        "Remaining grace period";
      uses PLAT-GRACE-PERIOD;
    }
    leaf sia-state {
      type Sia-status-enum;
      description
        "SIA status enum";
    }
    leaf grace-period-expired {
      type Bool-state;
      description
        "Has grace period expired";
    }
    leaf ooc-reason {
      type string;
      description
        "Reason for SIA ooc";
    }
  }

  grouping PLAT-INTERVALS {
    description
      "PLAT INTERVALS";
    leaf last {
      type string;
      description
        "Last collection or reporting interval";
    }
    leaf next {
      type string;
      description
        "Next collection or reporting interval";
    }
  }

  grouping PLAT-SL-DETAIL {
    description
      "SL Detail";
    container collection {
      description
        "Last and Next collection times";
      uses PLAT-INTERVALS;
    }
    container reporting {
      description
        "Last and Next reporting times";
      uses PLAT-INTERVALS;
    }
    container sia-status {
      description
        "SIA Status";
      uses PLAT-SIA-STATUS;
    }
    container upgrade-license-status {
      description
        "Upgrade License Status";
      uses PLAT-UPGRADE-LICENSE-STATUS;
    }
    container parameters {
      description
        "Parameters";
      uses PLAT-PARAMETERS;
    }
    container feature-details {
      description
        "Feature Details";
      uses FEATURE-DETAILS;
    }
  }
}
