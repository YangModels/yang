module openconfig-intf-private {
  namespace "http://openconfig.net/yang/intf-private";
  prefix oc-intf-priv;
  
  import cisco-semver { prefix semver; }
  import openconfig-interfaces { prefix "oc-intf"; }

  organization
    "Cisco Systems, Inc.";
  contact
    "Cisco Systems, Inc.
     Customer Service

     Postal: 170 West Tasman Drive
     San Jose, CA 95134

     Tel: +1 800 553-NETS

     E-mail: cs-yang@cisco.com";
  description
    "Internal private nodes for interface mapping.

     Copyright (c) 2025-2026 by Cisco Systems, Inc., and/or its affiliates.
     All rights reserved.";

  revision 2025-08-20 {
    description
      "Initial commit";
  }

  augment "/oc-intf:interfaces/oc-intf:interface/oc-intf:subinterfaces/oc-intf:subinterface" {
    container LIST_INSTANCE_NODE {
      description "Intermediary node in subinterface itree";
    }
  }

}
