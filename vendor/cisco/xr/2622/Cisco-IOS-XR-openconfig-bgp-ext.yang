module Cisco-IOS-XR-openconfig-bgp-ext {
  yang-version 1;
  namespace "http://cisco.com/ns/yang/Cisco-IOS-XR-openconfig-bgp-ext";
  prefix oc-bgp-cisco-xr-ext;

  import openconfig-extensions {
    prefix oc-ext;
  }
  import openconfig-network-instance {
    prefix oc-ni;
  }
  import openconfig-types {
    prefix oc-types;
  }
  import openconfig-yang-types {
    prefix oc-yang;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module adds extensions to the OpenConfig BGP model to
     provide extensions which allows exposing certain Cisco specific
     BGP Operational data into OC BGP model. These operational data
     are primarily from BGP neighbor containers. It augments the
     existing OpenConfig BGP model where required.";

  revision 2023-06-05 {
    description
      "Initial version";
    reference "0.1.0";
  }

  grouping neighbor-level-oper-info {
    description
      "AFI Independent Operational data that are specific to a neighbor";
    container cisco {
      description
        "Vendor specific operational data that are not yet available in OC model.
         This container contains Cisco IOS-XR specific BGP neighbor data";
      leaf in-bytes {
        type oc-yang:counter32;
        units "bytes";
        description
          "Total bytes read from the socket";
      }
      leaf out-bytes {
        type oc-yang:counter32;
        units "bytes";
        description
          "Total bytes written to the socket";
      }
      leaf connection-down-count {
        type oc-yang:counter32;
        description
          "Number of connection down events";
      }
      leaf dmz-link-bandwidth {
        type uint32;
        description
          "Bandwidth of link to single-hop eBGP peer";
      }
      leaf previous-connection-state {
        type enumeration {
          enum "IDLE" {
            description
              "neighbor is down, and in the Idle state of the
               FSM";
          }
          enum "CONNECT" {
            description
              "neighbor is down, and the session is waiting for
               the underlying transport session to be established";
          }
          enum "ACTIVE" {
            description
              "neighbor is down, and the local system is awaiting
               a conncetion from the remote peer";
          }
          enum "OPENSENT" {
            description
              "neighbor is in the process of being established.
               The local system has sent an OPEN message";
          }
          enum "OPENCONFIRM" {
            description
              "neighbor is in the process of being established.
               The local system is awaiting a NOTIFICATION or
               KEEPALIVE message";
          }
          enum "ESTABLISHED" {
            description
              "neighbor is up - the BGP session with the peer is
               established";
          }
        }
        description
          "Previous state of neighbor connection";
      }
      leaf all-msg-rx-count {
        type oc-yang:counter32;
        description
          "Count of Total number of all types of messages received from the neighbor";
      }
      leaf last-msg-rx-timestamp {
        type oc-types:timeticks64;
        description
          "Timestamp of the last message[of any type] received from the neighbor. Unit in nanoseconds";
      }
      leaf all-msg-tx-count {
        type oc-yang:counter32;
        description
          "Count of Total number of all types of messages sent to the neighbor";
      }
      leaf last-msg-tx-timestamp {
        type oc-types:timeticks64;
        description
          "Timestamp of the last message[of any type] sent to the neighbor. Unit in nanoseconds";
      }
    }
  }

  grouping neighbor-afi-level-oper-info {
    description
      "AFI Specific Operational data of a neighbor. The information pertians to each Address-Family under a neighbor";
    container cisco {
      description
        "Vendor specific operational data that are not yet available in OC model.
         This container contains Cisco IOS-XR specific BGP neighbor data";
      leaf neighbor-version {
        type uint64;
        description
          "BGP neighbor version for the address-family.
           Version number corresponds to the prefix that was last sent to the neighbor.";
      }
      leaf best-externalpaths-count {
        type oc-yang:counter32;
        description
          "No. of best-external paths from this neighbor";
      }
      leaf max-prefix-exceed-paths-discarded {
        type boolean;
        description
          "Did we discard extra paths when prefix limit reached";
      }
      leaf max-prefix-discard-extra-paths {
        type boolean;
        description
          "Discard extra paths when prefix limit reached";
      }
      leaf prefixes-denied-count {
        type oc-yang:counter32;
        description
          "Cumulative number of prefixes denied (for any reason) from this neighbor";
      }
      leaf prefixes-denied-no-policy {
        type oc-yang:counter32;
        description
          "Number of prefixes denied from this neighbor because there was no inbound policy";
      }
      leaf prefixes-denied-rt-permit {
        type oc-yang:counter32;
        description
          "Number of prefixes denied because RT extended
           community is not imported locally";
      }
      leaf prefixes-denied-orf-policy {
        type oc-yang:counter32;
        description
          "Number of prefixes denied by prefix based ORF policy";
      }
      leaf prefixes-denied-policy {
        type oc-yang:counter32;
        description
          "Number of prefixes denied by inbound policy";
      }
      leaf prefixes-suppressed {
        type oc-yang:counter32;
        description
          "Number of prefixes suppressed for this neighbor";
      }
      leaf prefixes-withdrawn {
        type oc-yang:counter32;
        description
          "Number of prefixes withdrawn to this neighbor";
      }
      leaf route-policy-prefix-orf {
        type string;
        description
          "Prefix based Outbound Route Filtering[ORF] policy for incoming updates";
      }
      leaf rx-processed-messages {
        type oc-yang:counter32;
        description
          "Number of messages processed before sending to the neighbor";
      }
    }
  }

  augment "/oc-ni:network-instances/oc-ni:network-instance/oc-ni:protocols/oc-ni:protocol/oc-ni:bgp/oc-ni:neighbors/oc-ni:neighbor/oc-ni:state" {
    description
      "Add neighbor AF-independent operational data under neighbor
       state hierarchy.";
    uses neighbor-level-oper-info;
  }
  augment "/oc-ni:network-instances/oc-ni:network-instance/oc-ni:protocols/oc-ni:protocol/oc-ni:bgp/oc-ni:neighbors/oc-ni:neighbor/oc-ni:afi-safis/oc-ni:afi-safi/oc-ni:state" {
    description
      "Add neighbor AF-specific operational data under neighbor
       afi-safi state hierarchy.";
    uses neighbor-afi-level-oper-info;
  }
  oc-ext:openconfig-version "0.1.0";
}
