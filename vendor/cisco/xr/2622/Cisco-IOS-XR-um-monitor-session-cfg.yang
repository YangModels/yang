module Cisco-IOS-XR-um-monitor-session-cfg {
  namespace "http://cisco.com/ns/yang/Cisco-IOS-XR-um-monitor-session-cfg";
  prefix um-monitor-session-cfg;

  import Cisco-IOS-XR-types {
    prefix xr;
  }
  import ietf-inet-types {
    prefix inet;
  }
  import Cisco-IOS-XR-um-interface-cfg {
    prefix a1;
  }
  import Cisco-IOS-XR-um-if-l2transport-cfg {
    prefix a2;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR monitor-session package configuration.
     
     This YANG module augments the
     modules with configuration data.
     
     Copyright (c) 2021-2026 by Cisco Systems, Inc., and/or its affiliates.
     All rights reserved.";

  revision 2026-05-29 {
    description
      "Restrict session name characters.
       2025-04-04
         Add application destination class
       2025-03-27
         Move rate-limiting to destination tuple
       2024-12-01
         Add unique-port and unique-punt drops filters
       2024-09-10
         Remove forward and TM drop config options.
       2024-07-23
         Increasing acl name length to 128 characters.
       2024-06-26
         Add support for pcap filter in drops config item
       2024-03-01
         Remove unique-port and unique-punt until supported by platform
       2024-01-26
         Add option to mirror all dropped packets
       2023-12-07
         Add sflow destination support
       2023-10-17
         Added default session, always-on config, periodic write interval, maximum capture capacity, and mirroring for unique drop-reasons and interfaces
       2023-09-22
         Remove sflow destination, replace MPLS-IPv4 and MPLS-IPv6 ACLs with a single MPLS ACL
       2022-10-17
         Added rate-limiting
       2022-10-03
         Added SPAN features for 781 and 791
       2022-07-11
         Added missing description statement to nodes
       2021-12-17
         Added container mirror/first & leaf router-id, updated enum values for leaf interval";
    semver:module-version "2.0.0";
  }
  revision 2021-03-03 {
    description
      "Initial release";
    semver:module-version "1.0.0";
  }

  typedef span-session-name {
    type string {
      length "1..79";
      pattern "[A-Za-z0-9_.-]+" {
        description
          "Only letters, digits, underscore, period, and hyphen are allowed.";
      }
    }
    description
      "SPAN session name.";
  }

  grouping IF-BODY {
    description
      "Grouping for interface";
    container monitor-sessions {
      description
        "Monitor-session configuration commands";
      list monitor-session {
        must "ethernet or ipv4 or ipv6 or mpls-ipv4 or mpls-ipv6";
        key "session-name";
        description
          "Monitor-session configuration commands";
        leaf session-name {
          type span-session-name;
          description
            "Monitor-session configuration commands";
        }
        container ethernet {
          must "not(../ipv4 or ../ipv6 or ../mpls-ipv4 or ../mpls-ipv6)";
          presence "Indicates a ethernet node is configured.";
          description
            "Replicate Ethernet traffic";
        }
        container ipv4 {
          must "not(../ethernet or ../ipv6 or ../mpls-ipv4 or ../mpls-ipv6)";
          presence "Indicates a ipv4 node is configured.";
          description
            "Replicate IPv4 traffic";
        }
        container ipv6 {
          must "not(../ipv4 or ../ethernet or ../mpls-ipv4 or ../mpls-ipv6)";
          presence "Indicates a ipv6 node is configured.";
          description
            "Replicate IPv6 traffic";
        }
        container mpls-ipv4 {
          must "not(../ipv4 or ../ipv6 or ../ethernet or ../mpls-ipv6)";
          presence "Indicates a mpls-ipv4 node is configured.";
          description
            "Replicate MPLS-IPv4 traffic";
        }
        container mpls-ipv6 {
          must "not(../ipv4 or ../ipv6 or ../mpls-ipv4 or ../ethernet)";
          presence "Indicates a mpls-ipv6 node is configured.";
          description
            "Replicate MPLS-IPv6 traffic";
        }
        container direction {
          description
            "Specify the direction of traffic to replicate";
          container rx-only {
            must "not(../tx-only)";
            presence "Indicates a rx-only node is configured.";
            description
              "Replicate only received (ingress) traffic";
          }
          container tx-only {
            must "not(../rx-only)";
            presence "Indicates a tx-only node is configured.";
            description
              "Replicate only transmitted (egress) traffic";
          }
        }
        container port-level {
          presence "Indicates a port-level node is configured.";
          description
            "Replicate traffic on all interfaces of a main interface";
        }
        container acl {
          presence "Indicates a acl node is configured.";
          description
            "Enable acl based mirroring";
          leaf acl-name {
            type xr:Cisco-ios-xr-string {
              length "1..128" {
                description
                  "ACL name";
              }
            }
            description
              "ACL name";
          }
          leaf merge-group {
            type uint32 {
              range "1..65535" {
                description
                  "Group number to add ACL to";
              }
            }
            description
              "Group multiple ACLs into a group";
          }
          leaf priority {
            type uint32 {
              range "1..65535" {
                description
                  "Lower number takes greater priority over other ACLs";
              }
            }
            must "../merge-group";
            description
              "Determines which acl takes priority over another in the group (will take lowest priority by default)";
          }
        }
        container acl-ipv4 {
          description
            "Enable IPv4 ACL based mirroring";
          leaf acl-name {
            type xr:Cisco-ios-xr-string {
              length "1..128" {
                description
                  "IPv4 ACL name";
              }
            }
            description
              "IPV4 ACL name";
          }
          leaf merge-group {
            type uint32 {
              range "1..65535" {
                description
                  "Group number to add ACL to";
              }
            }
            description
              "Group multiple ACLs into a group";
          }
          leaf priority {
            type uint32 {
              range "1..65535" {
                description
                  "Lower number takes greater priority over other ACLs";
              }
            }
            must "../merge-group";
            description
              "Determines which acl takes priority over another in the group (will take lowest priority by default)";
          }
        }
        container acl-ipv6 {
          description
            "Enable IPv6 ACL based mirroring";
          leaf acl-name {
            type xr:Cisco-ios-xr-string {
              length "1..128" {
                description
                  "IPv6 ACL name";
              }
            }
            description
              "IPV6 ACL name";
          }
          leaf merge-group {
            type uint32 {
              range "1..65535" {
                description
                  "Group number to add ACL to";
              }
            }
            description
              "Group multiple ACLs into a group";
          }
          leaf priority {
            type uint32 {
              range "1..65535" {
                description
                  "Lower number takes greater priority over other ACLs";
              }
            }
            must "../merge-group";
            description
              "Determines which acl takes priority over another in the group (will take lowest priority by default)";
          }
        }
        container acl-mpls {
          description
            "Enable MPLS ACL based mirroring";
          leaf acl-name {
            type xr:Cisco-ios-xr-string {
              length "1..128" {
                description
                  "MPLS ACL name";
              }
            }
            description
              "MPLS ACL name";
          }
          leaf merge-group {
            type uint32 {
              range "1..65535" {
                description
                  "Group number to add ACL to";
              }
            }
            description
              "Group multiple ACLs into a group";
          }
          leaf priority {
            type uint32 {
              range "1..65535" {
                description
                  "Lower number takes greater priority over other ACLs";
              }
            }
            must "../merge-group";
            description
              "Determines which acl takes priority over another in the group (will take lowest priority by default)";
          }
        }
        container mirror {
          description
            "Set the mirroring properties of this interface";
          leaf first {
            type uint32 {
              range "1..10000" {
                description
                  "Specify the number of bytes to mirror";
              }
            }
            description
              "Enable mirroring on the first portion of a packet";
          }
          leaf interval {
            type enumeration {
              enum "512" {
                value 1;
                description
                  "Mirror 1 in every 512 packets";
              }
              enum "1K" {
                value 2;
                description
                  "Mirror 1 in every 1024 packets";
              }
              enum "2K" {
                value 3;
                description
                  "Mirror 1 in every 2048 packets";
              }
              enum "4K" {
                value 4;
                description
                  "Mirror 1 in every 4096 packets";
              }
              enum "8K" {
                value 5;
                description
                  "Mirror 1 in every 8192 packets";
              }
              enum "16K" {
                value 6;
                description
                  "Mirror 1 in every 16384 packets";
              }
              enum "2" {
                value 7;
                description
                  "Mirror 1 in every 2 packets";
              }
              enum "4" {
                value 8;
                description
                  "Mirror 1 in every 4 packets";
              }
              enum "8" {
                value 9;
                description
                  "Mirror 1 in every 8 packets";
              }
              enum "16" {
                value 10;
                description
                  "Mirror 1 in every 16 packets";
              }
              enum "32" {
                value 11;
                description
                  "Mirror 1 in every 32 packets";
              }
              enum "64" {
                value 12;
                description
                  "Mirror 1 in every 64 packets";
              }
              enum "128" {
                value 13;
                description
                  "Mirror 1 in every 128 packets";
              }
              enum "256" {
                value 14;
                description
                  "Mirror 1 in every 256 packets";
              }
            }
            description
              "Enable mirroring of every Nth packet";
          }
        }
      }
    }
    container monitor-session-deprecated {
      description
        "Monitor-session deprecated configuration commands";
      container ethernet {
        presence "Indicates a ethernet node is configured.";
        description
          "Replicate Ethernet traffic";
        leaf session-name {
          type span-session-name;
          mandatory true;
          description
            "Session Name";
        }
        container direction {
          description
            "Specify the direction of traffic to replicate";
          container rx-only {
            must "not(../tx-only)";
            presence "Indicates a rx-only node is configured.";
            description
              "Replicate only received (ingress) traffic";
          }
          container tx-only {
            must "not(../rx-only)";
            presence "Indicates a tx-only node is configured.";
            description
              "Replicate only transmitted (egress) traffic";
          }
        }
        container acl {
          presence "Indicates a acl node is configured.";
          description
            "Enable acl based mirroring";
          leaf acl-name {
            type xr:Cisco-ios-xr-string {
              length "1..128" {
                description
                  "ACL name";
              }
            }
            description
              "ACL name";
          }
        }
        leaf acl-ipv4 {
          type xr:Cisco-ios-xr-string {
            length "1..128" {
              description
                "IPv4 ACL name";
            }
          }
          description
            "Enable IPv4 ACL based mirroring";
        }
        leaf acl-ipv6 {
          type xr:Cisco-ios-xr-string {
            length "1..128" {
              description
                "IPv6 ACL name";
            }
          }
          description
            "Enable IPv6 ACL based mirroring";
        }
        container mirror {
          description
            "Set the mirroring properties of this interface";
          leaf first {
            type uint32 {
              range "1..10000" {
                description
                  "Specify the number of bytes to mirror";
              }
            }
            description
              "Enable mirroring on the first portion of a packet";
          }
          leaf interval {
            type enumeration {
              enum "512" {
                value 1;
                description
                  "Mirror 1 in every 512 packets";
              }
              enum "1K" {
                value 2;
                description
                  "Mirror 1 in every 1024 packets";
              }
              enum "2K" {
                value 3;
                description
                  "Mirror 1 in every 2048 packets";
              }
              enum "4K" {
                value 4;
                description
                  "Mirror 1 in every 4096 packets";
              }
              enum "8K" {
                value 5;
                description
                  "Mirror 1 in every 8192 packets";
              }
              enum "16K" {
                value 6;
                description
                  "Mirror 1 in every 16384 packets";
              }
            }
            description
              "Enable mirroring of every Nth packet";
          }
        }
        container port-level {
          presence "Indicates a port-level node is configured.";
          description
            "Replicate traffic on all interfaces of a main interface";
        }
      }
      container ipv4 {
        presence "Indicates a ipv4 node is configured.";
        description
          "Replicate IPv4 traffic";
        leaf session-name {
          type span-session-name;
          mandatory true;
          description
            "Session Name";
        }
        container direction {
          description
            "Specify the direction of traffic to replicate";
          container rx-only {
            must "not(../tx-only)";
            presence "Indicates a rx-only node is configured.";
            description
              "Replicate only received (ingress) traffic";
          }
          container tx-only {
            must "not(../rx-only)";
            presence "Indicates a tx-only node is configured.";
            description
              "Replicate only transmitted (egress) traffic";
          }
        }
        container acl {
          presence "Indicates a acl node is configured.";
          description
            "Enable acl based mirroring";
          leaf acl-name {
            type xr:Cisco-ios-xr-string {
              length "1..128" {
                description
                  "ACL name";
              }
            }
            description
              "ACL name";
          }
        }
        leaf acl-ipv4 {
          type xr:Cisco-ios-xr-string {
            length "1..128" {
              description
                "IPv4 ACL name";
            }
          }
          description
            "Enable IPv4 ACL based mirroring";
        }
        leaf acl-ipv6 {
          type xr:Cisco-ios-xr-string {
            length "1..128" {
              description
                "IPv6 ACL name";
            }
          }
          description
            "Enable IPv6 ACL based mirroring";
        }
        container mirror {
          description
            "Set the mirroring properties of this interface";
          leaf first {
            type uint32 {
              range "1..10000" {
                description
                  "Specify the number of bytes to mirror";
              }
            }
            description
              "Enable mirroring on the first portion of a packet";
          }
          leaf interval {
            type enumeration {
              enum "512" {
                value 1;
                description
                  "Mirror 1 in every 512 packets";
              }
              enum "1K" {
                value 2;
                description
                  "Mirror 1 in every 1024 packets";
              }
              enum "2K" {
                value 3;
                description
                  "Mirror 1 in every 2048 packets";
              }
              enum "4K" {
                value 4;
                description
                  "Mirror 1 in every 4096 packets";
              }
              enum "8K" {
                value 5;
                description
                  "Mirror 1 in every 8192 packets";
              }
              enum "16K" {
                value 6;
                description
                  "Mirror 1 in every 16384 packets";
              }
            }
            description
              "Enable mirroring of every Nth packet";
          }
        }
        container port-level {
          presence "Indicates a port-level node is configured.";
          description
            "Replicate traffic on all interfaces of a main interface";
        }
      }
      container ipv6 {
        presence "Indicates a ipv6 node is configured.";
        description
          "Replicate IPv6 traffic";
        leaf session-name {
          type span-session-name;
          mandatory true;
          description
            "Session Name";
        }
        container direction {
          description
            "Specify the direction of traffic to replicate";
          container rx-only {
            must "not(../tx-only)";
            presence "Indicates a rx-only node is configured.";
            description
              "Replicate only received (ingress) traffic";
          }
          container tx-only {
            must "not(../rx-only)";
            presence "Indicates a tx-only node is configured.";
            description
              "Replicate only transmitted (egress) traffic";
          }
        }
        container acl {
          presence "Indicates a acl node is configured.";
          description
            "Enable acl based mirroring";
          leaf acl-name {
            type xr:Cisco-ios-xr-string {
              length "1..128" {
                description
                  "ACL name";
              }
            }
            description
              "ACL name";
          }
        }
        leaf acl-ipv4 {
          type xr:Cisco-ios-xr-string {
            length "1..128" {
              description
                "IPv4 ACL name";
            }
          }
          description
            "Enable IPv4 ACL based mirroring";
        }
        leaf acl-ipv6 {
          type xr:Cisco-ios-xr-string {
            length "1..128" {
              description
                "IPv6 ACL name";
            }
          }
          description
            "Enable IPv6 ACL based mirroring";
        }
        container mirror {
          description
            "Set the mirroring properties of this interface";
          leaf first {
            type uint32 {
              range "1..10000" {
                description
                  "Specify the number of bytes to mirror";
              }
            }
            description
              "Enable mirroring on the first portion of a packet";
          }
          leaf interval {
            type enumeration {
              enum "512" {
                value 1;
                description
                  "Mirror 1 in every 512 packets";
              }
              enum "1K" {
                value 2;
                description
                  "Mirror 1 in every 1024 packets";
              }
              enum "2K" {
                value 3;
                description
                  "Mirror 1 in every 2048 packets";
              }
              enum "4K" {
                value 4;
                description
                  "Mirror 1 in every 4096 packets";
              }
              enum "8K" {
                value 5;
                description
                  "Mirror 1 in every 8192 packets";
              }
              enum "16K" {
                value 6;
                description
                  "Mirror 1 in every 16384 packets";
              }
            }
            description
              "Enable mirroring of every Nth packet";
          }
        }
        container port-level {
          presence "Indicates a port-level node is configured.";
          description
            "Replicate traffic on all interfaces of a main interface";
        }
      }
      container mpls-ipv4 {
        presence "Indicates a mpls-ipv4 node is configured.";
        description
          "Replicate MPLS-IPv4 traffic";
        leaf session-name {
          type span-session-name;
          mandatory true;
          description
            "Session Name";
        }
        container direction {
          description
            "Specify the direction of traffic to replicate";
          container rx-only {
            must "not(../tx-only)";
            presence "Indicates a rx-only node is configured.";
            description
              "Replicate only received (ingress) traffic";
          }
          container tx-only {
            must "not(../rx-only)";
            presence "Indicates a tx-only node is configured.";
            description
              "Replicate only transmitted (egress) traffic";
          }
        }
        container acl {
          presence "Indicates a acl node is configured.";
          description
            "Enable acl based mirroring";
          leaf acl-name {
            type xr:Cisco-ios-xr-string {
              length "1..128" {
                description
                  "ACL name";
              }
            }
            description
              "ACL name";
          }
        }
        leaf acl-ipv4 {
          type xr:Cisco-ios-xr-string {
            length "1..128" {
              description
                "IPv4 ACL name";
            }
          }
          description
            "Enable IPv4 ACL based mirroring";
        }
        leaf acl-ipv6 {
          type xr:Cisco-ios-xr-string {
            length "1..128" {
              description
                "IPv6 ACL name";
            }
          }
          description
            "Enable IPv6 ACL based mirroring";
        }
        container mirror {
          description
            "Set the mirroring properties of this interface";
          leaf first {
            type uint32 {
              range "1..10000" {
                description
                  "Specify the number of bytes to mirror";
              }
            }
            description
              "Enable mirroring on the first portion of a packet";
          }
          leaf interval {
            type enumeration {
              enum "512" {
                value 1;
                description
                  "Mirror 1 in every 512 packets";
              }
              enum "1K" {
                value 2;
                description
                  "Mirror 1 in every 1024 packets";
              }
              enum "2K" {
                value 3;
                description
                  "Mirror 1 in every 2048 packets";
              }
              enum "4K" {
                value 4;
                description
                  "Mirror 1 in every 4096 packets";
              }
              enum "8K" {
                value 5;
                description
                  "Mirror 1 in every 8192 packets";
              }
              enum "16K" {
                value 6;
                description
                  "Mirror 1 in every 16384 packets";
              }
            }
            description
              "Enable mirroring of every Nth packet";
          }
        }
        container port-level {
          presence "Indicates a port-level node is configured.";
          description
            "Replicate traffic on all interfaces of a main interface";
        }
      }
      container mpls-ipv6 {
        presence "Indicates a mpls-ipv6 node is configured.";
        description
          "Replicate MPLS-IPv6 traffic";
        leaf session-name {
          type span-session-name;
          mandatory true;
          description
            "Session Name";
        }
        container direction {
          description
            "Specify the direction of traffic to replicate";
          container rx-only {
            must "not(../tx-only)";
            presence "Indicates a rx-only node is configured.";
            description
              "Replicate only received (ingress) traffic";
          }
          container tx-only {
            must "not(../rx-only)";
            presence "Indicates a tx-only node is configured.";
            description
              "Replicate only transmitted (egress) traffic";
          }
        }
        container acl {
          presence "Indicates a acl node is configured.";
          description
            "Enable acl based mirroring";
          leaf acl-name {
            type xr:Cisco-ios-xr-string {
              length "1..128" {
                description
                  "ACL name";
              }
            }
            description
              "ACL name";
          }
        }
        leaf acl-ipv4 {
          type xr:Cisco-ios-xr-string {
            length "1..128" {
              description
                "IPv4 ACL name";
            }
          }
          description
            "Enable IPv4 ACL based mirroring";
        }
        leaf acl-ipv6 {
          type xr:Cisco-ios-xr-string {
            length "1..128" {
              description
                "IPv6 ACL name";
            }
          }
          description
            "Enable IPv6 ACL based mirroring";
        }
        container mirror {
          description
            "Set the mirroring properties of this interface";
          leaf first {
            type uint32 {
              range "1..10000" {
                description
                  "Specify the number of bytes to mirror";
              }
            }
            description
              "Enable mirroring on the first portion of a packet";
          }
          leaf interval {
            type enumeration {
              enum "512" {
                value 1;
                description
                  "Mirror 1 in every 512 packets";
              }
              enum "1K" {
                value 2;
                description
                  "Mirror 1 in every 1024 packets";
              }
              enum "2K" {
                value 3;
                description
                  "Mirror 1 in every 2048 packets";
              }
              enum "4K" {
                value 4;
                description
                  "Mirror 1 in every 4096 packets";
              }
              enum "8K" {
                value 5;
                description
                  "Mirror 1 in every 8192 packets";
              }
              enum "16K" {
                value 6;
                description
                  "Mirror 1 in every 16384 packets";
              }
            }
            description
              "Enable mirroring of every Nth packet";
          }
        }
        container port-level {
          presence "Indicates a port-level node is configured.";
          description
            "Replicate traffic on all interfaces of a main interface";
        }
      }
    }
  }

  grouping L2TRANS-BODY {
    description
      "Grouping for l2transport";
    container monitor-sessions {
      description
        "Monitor-session configuration commands";
      list monitor-session {
        must "ethernet or ipv4 or ipv6 or mpls-ipv4 or mpls-ipv6";
        key "session-name";
        description
          "Monitor-session configuration commands";
        leaf session-name {
          type span-session-name;
          description
            "Monitor-session configuration commands";
        }
        container ethernet {
          must "not(../ipv4 or ../ipv6 or ../mpls-ipv4 or ../mpls-ipv6)";
          presence "Indicates a ethernet node is configured.";
          description
            "Replicate Ethernet traffic";
        }
        container ipv4 {
          must "not(../ethernet or ../ipv6 or ../mpls-ipv4 or ../mpls-ipv6)";
          presence "Indicates a ipv4 node is configured.";
          description
            "Replicate IPv4 traffic";
        }
        container ipv6 {
          must "not(../ipv4 or ../ethernet or ../mpls-ipv4 or ../mpls-ipv6)";
          presence "Indicates a ipv6 node is configured.";
          description
            "Replicate IPv6 traffic";
        }
        container mpls-ipv4 {
          must "not(../ipv4 or ../ipv6 or ../ethernet or ../mpls-ipv6)";
          presence "Indicates a mpls-ipv4 node is configured.";
          description
            "Replicate MPLS-IPv4 traffic";
        }
        container mpls-ipv6 {
          must "not(../ipv4 or ../ipv6 or ../mpls-ipv4 or ../ethernet)";
          presence "Indicates a mpls-ipv6 node is configured.";
          description
            "Replicate MPLS-IPv6 traffic";
        }
        container direction {
          description
            "Specify the direction of traffic to replicate";
          container rx-only {
            must "not(../tx-only)";
            presence "Indicates a rx-only node is configured.";
            description
              "Replicate only received (ingress) traffic";
          }
          container tx-only {
            must "not(../rx-only)";
            presence "Indicates a tx-only node is configured.";
            description
              "Replicate only transmitted (egress) traffic";
          }
        }
        container port-level {
          presence "Indicates a port-level node is configured.";
          description
            "Replicate traffic on all interfaces of a main interface";
        }
        container acl {
          presence "Indicates a acl node is configured.";
          description
            "Enable acl based mirroring";
          leaf acl-name {
            type xr:Cisco-ios-xr-string {
              length "1..128" {
                description
                  "ACL name";
              }
            }
            description
              "ACL name";
          }
          leaf merge-group {
            type uint32 {
              range "1..65535" {
                description
                  "Group number to add ACL to";
              }
            }
            description
              "Group multiple ACLs into a group";
          }
          leaf priority {
            type uint32 {
              range "1..65535" {
                description
                  "Lower number takes greater priority over other ACLs";
              }
            }
            must "../merge-group";
            description
              "Determines which acl takes priority over another in the group (will take lowest priority by default)";
          }
        }
        container acl-ipv4 {
          description
            "Enable IPv4 ACL based mirroring";
          leaf acl-name {
            type xr:Cisco-ios-xr-string {
              length "1..128" {
                description
                  "IPv4 ACL name";
              }
            }
            description
              "IPV4 ACL name";
          }
          leaf merge-group {
            type uint32 {
              range "1..65535" {
                description
                  "Group number to add ACL to";
              }
            }
            description
              "Group multiple ACLs into a group";
          }
          leaf priority {
            type uint32 {
              range "1..65535" {
                description
                  "Lower number takes greater priority over other ACLs";
              }
            }
            must "../merge-group";
            description
              "Determines which acl takes priority over another in the group (will take lowest priority by default)";
          }
        }
        container acl-ipv6 {
          description
            "Enable IPv6 ACL based mirroring";
          leaf acl-name {
            type xr:Cisco-ios-xr-string {
              length "1..128" {
                description
                  "IPv6 ACL name";
              }
            }
            description
              "IPV6 ACL name";
          }
          leaf merge-group {
            type uint32 {
              range "1..65535" {
                description
                  "Group number to add ACL to";
              }
            }
            description
              "Group multiple ACLs into a group";
          }
          leaf priority {
            type uint32 {
              range "1..65535" {
                description
                  "Lower number takes greater priority over other ACLs";
              }
            }
            must "../merge-group";
            description
              "Determines which acl takes priority over another in the group (will take lowest priority by default)";
          }
        }
        container mirror {
          description
            "Set the mirroring properties of this interface";
          leaf first {
            type uint32 {
              range "1..10000" {
                description
                  "Specify the number of bytes to mirror";
              }
            }
            description
              "Enable mirroring on the first portion of a packet";
          }
          leaf interval {
            type enumeration {
              enum "512" {
                value 1;
                description
                  "Mirror 1 in every 512 packets";
              }
              enum "1K" {
                value 2;
                description
                  "Mirror 1 in every 1024 packets";
              }
              enum "2K" {
                value 3;
                description
                  "Mirror 1 in every 2048 packets";
              }
              enum "4K" {
                value 4;
                description
                  "Mirror 1 in every 4096 packets";
              }
              enum "8K" {
                value 5;
                description
                  "Mirror 1 in every 8192 packets";
              }
              enum "16K" {
                value 6;
                description
                  "Mirror 1 in every 16384 packets";
              }
            }
            description
              "Enable mirroring of every Nth packet";
          }
        }
      }
    }
    container monitor-session-deprecated {
      description
        "Monitor-session deprecated configuration commands";
      container ethernet {
        presence "Indicates a ethernet node is configured.";
        description
          "Replicate Ethernet traffic";
        leaf session-name {
          type span-session-name;
          mandatory true;
          description
            "Session Name";
        }
        container direction {
          description
            "Specify the direction of traffic to replicate";
          container rx-only {
            must "not(../tx-only)";
            presence "Indicates a rx-only node is configured.";
            description
              "Replicate only received (ingress) traffic";
          }
          container tx-only {
            must "not(../rx-only)";
            presence "Indicates a tx-only node is configured.";
            description
              "Replicate only transmitted (egress) traffic";
          }
        }
        container acl {
          presence "Indicates a acl node is configured.";
          description
            "Enable acl based mirroring";
          leaf acl-name {
            type xr:Cisco-ios-xr-string {
              length "1..128" {
                description
                  "ACL name";
              }
            }
            description
              "ACL name";
          }
        }
        leaf acl-ipv4 {
          type xr:Cisco-ios-xr-string {
            length "1..128" {
              description
                "IPv4 ACL name";
            }
          }
          description
            "Enable IPv4 ACL based mirroring";
        }
        leaf acl-ipv6 {
          type xr:Cisco-ios-xr-string {
            length "1..128" {
              description
                "IPv6 ACL name";
            }
          }
          description
            "Enable IPv6 ACL based mirroring";
        }
        container mirror {
          description
            "Set the mirroring properties of this interface";
          leaf first {
            type uint32 {
              range "1..10000" {
                description
                  "Specify the number of bytes to mirror";
              }
            }
            description
              "Enable mirroring on the first portion of a packet";
          }
          leaf interval {
            type enumeration {
              enum "512" {
                value 1;
                description
                  "Mirror 1 in every 512 packets";
              }
              enum "1K" {
                value 2;
                description
                  "Mirror 1 in every 1024 packets";
              }
              enum "2K" {
                value 3;
                description
                  "Mirror 1 in every 2048 packets";
              }
              enum "4K" {
                value 4;
                description
                  "Mirror 1 in every 4096 packets";
              }
              enum "8K" {
                value 5;
                description
                  "Mirror 1 in every 8192 packets";
              }
              enum "16K" {
                value 6;
                description
                  "Mirror 1 in every 16384 packets";
              }
            }
            description
              "Enable mirroring of every Nth packet";
          }
        }
        container port-level {
          presence "Indicates a port-level node is configured.";
          description
            "Replicate traffic on all interfaces of a main interface";
        }
      }
    }
  }

  augment "/a1:interfaces/a1:interface" {
    description
      "This augment extends active nodes configuration";
    uses IF-BODY;
  }
  augment "/a1:interfaces/a1:interface-preconfigure" {
    description
      "This augment extends preconfigured nodes configuration";
    uses IF-BODY;
  }
  augment "/a1:interfaces/a1:interface/a2:l2transport" {
    description
      "This augment extends active nodes configuration";
    uses L2TRANS-BODY;
  }
  augment "/a1:interfaces/a1:interface-preconfigure/a2:l2transport" {
    description
      "This augment extends preconfigured nodes configuration";
    uses L2TRANS-BODY;
  }
  container monitor-sessions {
    description
      "Monitor-session configuration commands";
    list monitor-session {
      key "session-name";
      description
        "Session Name";
      leaf session-name {
        type span-session-name;
        description
          "Session Name";
      }
      leaf traffic-type {
        type enumeration {
          enum "ethernet" {
            value 0;
            description
              "Replicate Ethernet traffic";
          }
          enum "ipv4" {
            value 1;
            description
              "Replicate IPv4 traffic";
          }
          enum "ipv6" {
            value 2;
            description
              "Replicate IPv6 traffic";
          }
          enum "mpls-ipv4" {
            value 3;
            description
              "Replicate MPLS-IPv4 traffic";
          }
          enum "mpls-ipv6" {
            value 4;
            description
              "Replicate MPLS-IPv6 traffic";
          }
        }
        mandatory true;
        description
          "Type of traffic to replicate";
      }
      container destination {
        description
          "Specify the destination that traffic should be replicated to";
        leaf interface {
          when
            "../../traffic-type = 'ethernet' or ../../traffic-type = 'mpls-ipv4'
             or ../../traffic-type = 'mpls-ipv6'";
          type xr:Interface-name;
          must
            "not(../pseudowire or ../next-hop/ipv4-address
             or ../next-hop/ipv6-address or ../file or ../udp or ../sflow
             or ../application)";
          description
            "Specify a destination interface";
        }
        leaf erspan-session-id {
          when "../interface" {
            description
              "ERSPAN session ID must be used with a GRE tunnel interface";
          }
          type uint32 {
            range "1..65535" {
              description
                "ERSPAN session ID value";
            }
          }
          description
            "Specify the ERSPAN session ID";
        }
        leaf rate-limit {
          type uint32 {
            range "1..4294967295" {
              description
                "Maximum mirroring rate";
            }
          }
          must "../rate-limit-units";
          description
            "Specify the maximum mirroring rate";
        }
        leaf rate-limit-units {
          type enumeration {
            enum "pps" {
              value 1;
              description
                "Maximum mirror rate is in packets per second";
            }
            enum "kbps" {
              value 2;
              description
                "Maximum mirror rate is in kbytes per second";
            }
          }
          must "../rate-limit";
          description
            "Specify the units for the maximum mirror rate";
        }
        container pseudowire {
          when "../../traffic-type = 'ethernet'";
          must
            "not(../interface or ../next-hop/ipv4-address
             or ../next-hop/ipv6-address or ../file or ../udp or ../sflow
             or ../application)";
          presence "Indicates a pseudowire node is configured.";
          description
            "Specify a pseudowire";
        }
        container next-hop {
          description
            "Specify a destination next-hop IP address";
          leaf ipv4-address {
            when
              "../../../traffic-type = 'ethernet'
               or ../../../traffic-type = 'ipv4'";
            type inet:ipv4-address-no-zone;
            must
              "not(../../interface or ../../pseudowire
               or ../../file or ../../udp or ../../sflow
               or ../../application)";
            description
              "Specify the destination next-hop IPv4 address";
          }
          leaf ipv6-address {
            when
              "../../../traffic-type = 'ethernet'
               or ../../../traffic-type = 'ipv6'";
            type inet:ipv6-address-no-zone;
            must
              "not(../../interface or ../../pseudowire
               or ../../file or ../../udp or ../../sflow
               or ../../application)";
            description
              "Specify an IPv6 address";
          }
          leaf vrf {
            type string {
              length "1..32" {
                description
                  "VRF name";
              }
            }
            must "../ipv4-address or ../ipv6-address";
            description
              "Specify the vrf name";
          }
        }
        container udp {
          must
            "not(../interface or ../pseudowire or ../next-hop/ipv4-address
               or ../next-hop/ipv6-address or ../file or ../sflow
               or ../application)
               and (ipv4 or ipv6)";
          presence "Indicates a udp node is configured.";
          description
            "Specify a UDP destination";
          leaf ipv4 {
            type inet:ipv4-address-no-zone;
            must "not(../ipv6) and ../ipv4-source-ip";
            description
              "Specify an IPv4 address";
          }
          leaf ipv6 {
            type inet:ipv6-address-no-zone;
            must "not(../ipv4) and ../ipv6-source-ip";
            description
              "Specify an IPv6 address";
          }
          leaf port {
            type uint32 {
              range "0..65535" {
                description
                  "Specify the destination port number";
              }
            }
            mandatory true;
            description
              "Specify the destination port number";
          }
          leaf ipv4-source-ip {
            type inet:ipv4-address-no-zone;
            must "../ipv4";
            description
              "Specify the source IPv4 address";
          }
          leaf ipv6-source-ip {
            type inet:ipv6-address-no-zone;
            must "../ipv6";
            description
              "Specify the source IPv6 address";
          }
          leaf source-port {
            type uint32 {
              range "0..65535" {
                description
                  "Specify the source port number";
              }
            }
            mandatory true;
            description
              "Specify the source port";
          }
          leaf vrf {
            type xr:Cisco-ios-xr-string {
              length "1..32" {
                description
                  "VRF name";
              }
            }
            description
              "Specify the vrf name";
          }
        }
        container file {
          must
            "not(../interface or ../next-hop/ipv4-address
             or ../next-hop/ipv6-address or ../pseudowire
             or ../udp or ../sflow or ../application)";
          presence "Indicates a file node is configured.";
          description
            "Specify destination as a file";
          leaf size {
            type uint32 {
              range "1..16777216" {
                description
                  "Specify size of buffer in kilobytes";
              }
            }
            description
              "Specify the packet buffer size";
          }
          container buffer-type {
            description
              "Specify the buffer type";
            container linear {
              presence "Indicates a linear node is configured.";
              description
                "Specify a linear buffer";
            }
          }
          container format {
            description
              "Specify the file output file format";
            container pcapng {
              presence "Indicates a pcapng node is configured.";
              description
                "Specify pcapng format";
            }
          }
          leaf filter {
            type string {
              length "1..800" {
                description
                  "pcap filter expression";
              }
            }
            description
              "Specify a pcap filter to apply";
          }
          container always-on {
            presence "Indicates the session is always-on.";
            description
              "Start packet capture immediately if configured";
            leaf periodic-write {
              type uint32 {
                range "1..4294967295" {
                  description
                    "Period in seconds";
                }
              }
              description
                "Configure the period in seconds at which the packet buffer is written to a file";
            }
            leaf capacity {
              type uint32 {
                range "1..4294967295" {
                  description
                    "Number of KB, MB or GB used to maintain periodic capture files";
                }
              }
              must "../periodic-write";
              description
                "The maximum amount of memory on disk used to maintain periodic capture files for this session";
            }
            container kb {
              must "not(../mb or ../gb)";
              presence "Indicates a kb node is configured.";
              description
                "Specify the capacity in KB";
            }
            container mb {
              must "not(../kb or ../gb)";
              presence "Indicates a mb node is configured.";
              description
                "Specify the capacity in MB";
            }
            container gb {
              must "not(../kb or ../mb)";
              presence "Indicates a gb node is configured.";
              description
                "Specify the capacity in GB";
            }
          }
        }
        container sflow {
          must
            "not(../interface or ../next-hop/ipv4-address
             or ../next-hop/ipv6-address or ../pseudowire
             or ../udp or ../file or ../application)";
          presence "Indicates a sflow node is configured.";
          description
            "Specify sflow destination with an exporter-map";
          leaf exporter-map-name {
            type string {
              length "1..32" {
                description
                  "Specify the exporter-map-name";
              }
            }
            description
              "Specify the exporter-map-name";
          }
        }
        container application {
          must
            "not(../interface or ../next-hop/ipv4-address
             or ../next-hop/ipv6-address or ../pseudowire
             or ../udp or ../file or ../sflow)";
          presence "Indicates an application node is configured.";
          description
            "Specify an application destination";
        }
      }
      container rx {
        description
          "Specify the destination that rx traffic should be replicated to";
        leaf interface {
          when
            "../../traffic-type = 'ethernet' or ../../traffic-type = 'mpls-ipv4'
             or ../../traffic-type = 'mpls-ipv6'";
          type xr:Interface-name;
          must
            "not(../pseudowire or ../next-hop/ipv4-address
             or ../next-hop/ipv6-address or ../sflow or ../application)";
          description
            "Specify a destination interface";
        }
        leaf erspan-session-id {
          when "../interface" {
            description
              "ERSPAN session ID must be used with a GRE tunnel interface";
          }
          type uint32 {
            range "1..65535" {
              description
                "ERSPAN session ID value";
            }
          }
          description
            "Specify the ERSPAN session ID";
        }
        leaf rate-limit {
          type uint32 {
            range "1..4294967295" {
              description
                "Maximum mirroring rate";
            }
          }
          must "../rate-limit-units";
          description
            "Specify the maximum mirroring rate";
        }
        leaf rate-limit-units {
          type enumeration {
            enum "pps" {
              value 1;
              description
                "Maximum mirror rate is in packets per second";
            }
            enum "kbps" {
              value 2;
              description
                "Maximum mirror rate is in kbytes per second";
            }
          }
          must "../rate-limit";
          description
            "Specify the units for the maximum mirror rate";
        }
        container pseudowire {
          when "../../traffic-type = 'ethernet'";
          must
            "not(../interface or ../next-hop/ipv4-address
             or ../next-hop/ipv6-address or ../sflow or ../application)";
          presence "Indicates a pseudowire node is configured.";
          description
            "Specify a pseudowire";
        }
        container next-hop {
          description
            "Specify a destination next-hop IP address";
          leaf ipv4-address {
            when
              "../../../traffic-type = 'ethernet'
               or ../../../traffic-type = 'ipv4'";
            type inet:ipv4-address-no-zone;
            must
              "not(../../interface or ../../pseudowire or ../../sflow
                                 or ../../application)";
            description
              "Specify the destination next-hop IPv4 address";
          }
          leaf ipv6-address {
            when
              "../../../traffic-type = 'ethernet'
               or ../../../traffic-type = 'ipv6'";
            type inet:ipv6-address-no-zone;
            must
              "not(../../interface or ../../pseudowire
               or ../../udp or ../../sflow or ../../application)";
            description
              "Specify an IPv6 address";
          }
          leaf vrf {
            type string {
              length "1..32" {
                description
                  "VRF name";
              }
            }
            must "../ipv4-address or ../ipv6-address";
            description
              "Specify the vrf name";
          }
        }
        container udp {
          must
            "not(../interface or ../pseudowire or ../next-hop/ipv4-address
               or ../next-hop/ipv6-address or ../sflow or ../application)
               and (ipv4 or ipv6)";
          presence "Indicates a udp node is configured.";
          description
            "Specify a UDP destination";
          leaf ipv4 {
            type inet:ipv4-address-no-zone;
            must "not(../ipv6) and ../ipv4-source-ip";
            description
              "Specify an IPv4 address";
          }
          leaf ipv6 {
            type inet:ipv6-address-no-zone;
            must "not(../ipv4) and ../ipv6-source-ip";
            description
              "Specify an IPv6 address";
          }
          leaf port {
            type uint32 {
              range "0..65535" {
                description
                  "Specify the destination port number";
              }
            }
            mandatory true;
            description
              "Specify the destination port number";
          }
          leaf ipv4-source-ip {
            type inet:ipv4-address-no-zone;
            must "../ipv4";
            description
              "Specify the source IPv4 address";
          }
          leaf ipv6-source-ip {
            type inet:ipv6-address-no-zone;
            must "../ipv6";
            description
              "Specify the source IPv6 address";
          }
          leaf source-port {
            type uint32 {
              range "0..65535" {
                description
                  "Specify the source port number";
              }
            }
            mandatory true;
            description
              "Specify the source port";
          }
          leaf vrf {
            type xr:Cisco-ios-xr-string {
              length "1..32" {
                description
                  "VRF name";
              }
            }
            description
              "Specify the vrf name";
          }
        }
        container sflow {
          must
            "not(../interface or ../next-hop/ipv4-address
             or ../next-hop/ipv6-address or ../pseudowire
             or ../udp or ../application)";
          presence "Indicates a sflow node is configured.";
          description
            "Specify sflow destination with an exporter-map";
          leaf exporter-map-name {
            type string {
              length "1..32" {
                description
                  "Specify the exporter-map-name";
              }
            }
            description
              "Specify the exporter-map-name";
          }
        }
        container application {
          must
            "not(../interface or ../next-hop/ipv4-address
             or ../next-hop/ipv6-address or ../pseudowire
             or ../udp or ../sflow)";
          presence "Indicates an application node is configured.";
          description
            "Specify an application destination";
        }
      }
      container tx {
        description
          "Specify the destination that tx traffic should be replicated to";
        leaf interface {
          when
            "../../traffic-type = 'ethernet' or ../../traffic-type = 'mpls-ipv4'
             or ../../traffic-type = 'mpls-ipv6'";
          type xr:Interface-name;
          must
            "not(../pseudowire or ../next-hop/ipv4-address
             or ../next-hop/ipv6-address or ../sflow or ../application)";
          description
            "Specify a destination interface";
        }
        leaf erspan-session-id {
          when "../interface" {
            description
              "ERSPAN session ID must be used with a GRE tunnel interface";
          }
          type uint32 {
            range "1..65535" {
              description
                "ERSPAN session ID value";
            }
          }
          description
            "Specify the ERSPAN session ID";
        }
        leaf rate-limit {
          type uint32 {
            range "1..4294967295" {
              description
                "Maximum mirroring rate";
            }
          }
          must "../rate-limit-units";
          description
            "Specify the maximum mirroring rate";
        }
        leaf rate-limit-units {
          type enumeration {
            enum "pps" {
              value 1;
              description
                "Maximum mirror rate is in packets per second";
            }
            enum "kbps" {
              value 2;
              description
                "Maximum mirror rate is in kbytes per second";
            }
          }
          must "../rate-limit";
          description
            "Specify the units for the maximum mirror rate";
        }
        container pseudowire {
          when "../../traffic-type = 'ethernet'";
          must
            "not(../interface or ../next-hop/ipv4-address
             or ../next-hop/ipv6-address or ../sflow or ../application)";
          presence "Indicates a pseudowire node is configured.";
          description
            "Specify a pseudowire";
        }
        container next-hop {
          description
            "Specify a destination next-hop IP address";
          leaf ipv4-address {
            when
              "../../../traffic-type = 'ethernet'
               or ../../../traffic-type = 'ipv4'";
            type inet:ipv4-address-no-zone;
            must
              "not(../../interface or ../../pseudowire or ../../sflow
                                 or ../../application)";
            description
              "Specify the destination next-hop IPv4 address";
          }
          leaf ipv6-address {
            when
              "../../../traffic-type = 'ethernet'
               or ../../../traffic-type = 'ipv6'";
            type inet:ipv6-address-no-zone;
            must
              "not(../../interface or ../../pseudowire
               or ../../udp or ../../sflow or ../../application)";
            description
              "Specify an IPv6 address";
          }
          leaf vrf {
            type string {
              length "1..32" {
                description
                  "VRF name";
              }
            }
            must "../ipv4-address or ../ipv6-address";
            description
              "Specify the vrf name";
          }
        }
        container udp {
          must
            "not(../interface or ../pseudowire or ../next-hop/ipv4-address
               or ../next-hop/ipv6-address or ../sflow or ../application)
               and (ipv4 or ipv6)";
          presence "Indicates a udp node is configured.";
          description
            "Specify a UDP destination";
          leaf ipv4 {
            type inet:ipv4-address-no-zone;
            must "not(../ipv6) and ../ipv4-source-ip";
            description
              "Specify an IPv4 address";
          }
          leaf ipv6 {
            type inet:ipv6-address-no-zone;
            must "not(../ipv4) and ../ipv6-source-ip";
            description
              "Specify an IPv6 address";
          }
          leaf port {
            type uint32 {
              range "0..65535" {
                description
                  "Specify the destination port number";
              }
            }
            mandatory true;
            description
              "Specify the destination port number";
          }
          leaf ipv4-source-ip {
            type inet:ipv4-address-no-zone;
            must "../ipv4";
            description
              "Specify the source IPv4 address";
          }
          leaf ipv6-source-ip {
            type inet:ipv6-address-no-zone;
            must "../ipv6";
            description
              "Specify the source IPv6 address";
          }
          leaf source-port {
            type uint32 {
              range "0..65535" {
                description
                  "Specify the source port number";
              }
            }
            mandatory true;
            description
              "Specify the source port";
          }
          leaf vrf {
            type xr:Cisco-ios-xr-string {
              length "1..32" {
                description
                  "VRF name";
              }
            }
            description
              "Specify the vrf name";
          }
        }
        container sflow {
          must
            "not(../interface or ../next-hop/ipv4-address
             or ../next-hop/ipv6-address or ../pseudowire
             or ../udp or ../application)";
          presence "Indicates a sflow node is configured.";
          description
            "Specify sflow destination with an exporter-map";
          leaf exporter-map-name {
            type string {
              length "1..32" {
                description
                  "Specify the exporter-map-name";
              }
            }
            description
              "Specify the exporter-map-name";
          }
        }
        container application {
          must
            "not(../interface or ../next-hop/ipv4-address
             or ../next-hop/ipv6-address or ../pseudowire
             or ../udp or ../sflow)";
          presence "Indicates an application node is configured.";
          description
            "Specify an application destination";
        }
      }
      leaf inject-interface {
        type xr:Interface-name;
        description
          "Specify the attachment interface into which traffic may be injected from the SPAN session's destination";
      }
      container cloud-span {
        presence "Indicates a cloud-span node is configured.";
        description
          "Configure CloudSPAN on this session";
      }
      leaf discard-class {
        type uint32 {
          range "0..2" {
            description
              "Discard class value";
          }
        }
        description
          "Specify the discard class value to be set on all traffic mirrored to the destination";
      }
      leaf traffic-class {
        type uint32 {
          range "0..7" {
            description
              "Traffic class value";
          }
        }
        description
          "Specify the traffic class value to be set on all traffic mirrored to the destination";
      }
      container mirror {
        description
          "Set the mirroring properties of this session";
        leaf first {
          type uint32 {
            range "1..10000" {
              description
                "Specify the number of bytes to mirror";
            }
          }
          description
            "Enable mirroring on the first portion of a packet";
        }
        leaf interval {
          type enumeration {
            enum "512" {
              value 1;
              description
                "Mirror 1 in every 512 packets";
            }
            enum "1K" {
              value 2;
              description
                "Mirror 1 in every 1024 packets";
            }
            enum "2K" {
              value 3;
              description
                "Mirror 1 in every 2048 packets";
            }
            enum "4K" {
              value 4;
              description
                "Mirror 1 in every 4096 packets";
            }
            enum "8K" {
              value 5;
              description
                "Mirror 1 in every 8192 packets";
            }
            enum "16K" {
              value 6;
              description
                "Mirror 1 in every 16384 packets";
            }
            enum "2" {
              value 7;
              description
                "Mirror 1 in every 2 packets";
            }
            enum "4" {
              value 8;
              description
                "Mirror 1 in every 4 packets";
            }
            enum "8" {
              value 9;
              description
                "Mirror 1 in every 8 packets";
            }
            enum "16" {
              value 10;
              description
                "Mirror 1 in every 16 packets";
            }
            enum "32" {
              value 11;
              description
                "Mirror 1 in every 32 packets";
            }
            enum "64" {
              value 12;
              description
                "Mirror 1 in every 64 packets";
            }
            enum "128" {
              value 13;
              description
                "Mirror 1 in every 128 packets";
            }
            enum "256" {
              value 14;
              description
                "Mirror 1 in every 256 packets";
            }
          }
          description
            "Enable mirroring of every Nth packet for this session";
        }
      }
      container drops {
        presence "Indicates a drop node is configured.";
        description
          "Mirror all dropped packets";
        container packet-processing {
          presence "Indicates a packet-processing node is configured.";
          description
            "Mirror packet-processing dropped packets only";
        }
        container traffic-management {
          presence "Indicates a traffic-management node is configured.";
          description
            "Mirror traffic-management dropped packets only";
        }
        container rx {
          must "not(../tx)";
          presence "Indicates a rx node is configured.";
          description
            "Mirror dropped packets in the Rx direction only";
        }
        container tx {
          must "not(../rx)";
          presence "Indicates a tx node is configured.";
          description
            "Mirror dropped packets in the Tx direction only";
        }
        leaf filter {
          type string {
            length "1..800" {
              description
                "pcap filter expression";
            }
          }
          description
            "Specify a pcap filter to apply";
        }
        container unique-punt {
          presence "Indicates a unique-punt node is configured.";
          description
            "Only mirror the first packet for a given drop reason";
        }
        container unique-port {
          presence "Indicates a unique-port node is configured.";
          description
            "Only mirror the first packet for a given port";
        }
      }
      container protocol-capture {
        presence "Indicates a protocol-capture node is configured.";
        description
          "Mirror punted packets";
        container rx {
          must "not(../tx)";
          presence "Indicates a rx node is configured.";
          description
            "Mirror Rx protocol-captured packets";
        }
        container tx {
          must "not(../rx)";
          presence "Indicates a tx node is configured.";
          description
            "Mirror Tx protocol-captured packets";
        }
        leaf filter {
          type string {
            length "1..800" {
              description
                "pcap filter expression";
            }
          }
          description
            "Specify a pcap filter to apply";
        }
      }
    }
    leaf router-id {
      type uint32 {
        range "1..255" {
          description
            "Router ID value";
        }
      }
      description
        "Specify the router ID";
    }
    leaf local-capture-capacity {
      type uint32 {
        range "1..4294967295" {
          description
            "Number of KB, MB or GB used to maintain periodic capture files";
        }
      }
      description
        "The maximum amount of memory on disk used to maintain periodic capture files for all sessions";
    }
    container kb {
      must "not(../mb or ../gb)";
      presence "Indicates a kb node is configured.";
      description
        "Specify the capacity in KB";
    }
    container mb {
      must "not(../kb or ../gb)";
      presence "Indicates a mb node is configured.";
      description
        "Specify the capacity in MB";
    }
    container gb {
      must "not(../kb or ../mb)";
      presence "Indicates a gb node is configured.";
      description
        "Specify the capacity in GB";
    }
    container default-capture-disable {
      presence "Indicates a default-capture-disable node is configured.";
      description
        "Do not create the default session on startup";
    }
    leaf mirror-interval {
      type enumeration {
        enum "512" {
          value 1;
          description
            "Mirror 1 in every 512 packets";
        }
        enum "1K" {
          value 2;
          description
            "Mirror 1 in every 1024 packets";
        }
        enum "2K" {
          value 3;
          description
            "Mirror 1 in every 2048 packets";
        }
        enum "4K" {
          value 4;
          description
            "Mirror 1 in every 4096 packets";
        }
        enum "8K" {
          value 5;
          description
            "Mirror 1 in every 8192 packets";
        }
        enum "16K" {
          value 6;
          description
            "Mirror 1 in every 16384 packets";
        }
        enum "2" {
          value 7;
          description
            "Mirror 1 in every 2 packets";
        }
        enum "4" {
          value 8;
          description
            "Mirror 1 in every 4 packets";
        }
        enum "8" {
          value 9;
          description
            "Mirror 1 in every 8 packets";
        }
        enum "16" {
          value 10;
          description
            "Mirror 1 in every 16 packets";
        }
        enum "32" {
          value 11;
          description
            "Mirror 1 in every 32 packets";
        }
        enum "64" {
          value 12;
          description
            "Mirror 1 in every 64 packets";
        }
        enum "128" {
          value 13;
          description
            "Mirror 1 in every 128 packets";
        }
        enum "256" {
          value 14;
          description
            "Mirror 1 in every 256 packets";
        }
      }
      description
        "Enable mirroring of every Nth packet on ALL sessions";
    }
  }
}
