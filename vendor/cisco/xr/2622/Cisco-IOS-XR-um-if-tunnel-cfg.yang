module Cisco-IOS-XR-um-if-tunnel-cfg {
  namespace "http://cisco.com/ns/yang/Cisco-IOS-XR-um-if-tunnel-cfg";
  prefix um-if-tunnel-cfg;

  import Cisco-IOS-XR-types {
    prefix xr;
  }
  import ietf-inet-types {
    prefix inet;
  }
  import Cisco-IOS-XR-um-interface-cfg {
    prefix a1;
  }
  import tailf-common {
    prefix tailf;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR if-tunnel package configuration.
     
     This YANG module augments the
     modules with configuration data.
     
     Copyright (c) 2019-2025 by Cisco Systems, Inc., and/or its affiliates.
     All rights reserved.";

  revision 2025-12-09 {
    description
      "Added gue mode and port containers
       2025-01-31
         ACL name max length changed from 64 to 128
       2024-11-07
         Added support for tunnel ipsec policy feature
       2023-09-29
         Added leaf for new tunnel lite mode
       2022-08-24
         Added containers for tunnel destination object-group
       2022-07-11
         Added missing description statement to nodes
       2022-03-09
         Added containers ipsec & container protection
       Also updated the must statements under container mode
       2022-03-02
         Added containers direct";
    semver:module-version "2.1.0";
  }
  revision 2021-01-21 {
    description
      "Added containers under tunnel";
    semver:module-version "2.0.0";
  }
  revision 2019-06-10 {
    description
      "Initial version";
    semver:module-version "1.0.1";
  }

  feature is_tunnel_ip_ipsec_supported {
    description
      "is tunnel ip ipsec supported";
  }

  feature is_tunnel_ipv6_any_mode_supported {
    description
      "is tunnel ipv6 any mode supported";
  }

  feature is_tunnel_src_direct_supported {
    description
      "is tunnel src direct supported";
  }

  feature is_tunnel_mode_decap_supported {
    description
      "is tunnel mode decap supported";
  }

  feature is_tunnel_dst_addr_grp_supported {
    description
      "Flag indicating that tunnel destination address group is supported";
  }

  feature is_tunnel_gre_supported {
    description
      "is tunnel gre supported";
  }

  feature is_tunnel_gre_lite_supported {
    description
      "is tunnel gre lite supported";
  }

  feature is_tunnel_gre_ipv6_trans_supported {
    description
      "is tunnel gre ipv6 trans supported";
  }

  feature is_mgre_through_cli_supported {
    description
      "is mgre through cli supported";
  }

  feature is_mgre_tunnel_ipv4_trans_supported {
    description
      "is mgre tunnel ipv4 trans supported";
  }

  feature is_mgre_tunnel_ipv6_trans_supported {
    description
      "is mgre tunnel ipv6 trans supported";
  }

  feature is_tunnel_ipv4_trans_supported {
    description
      "is tunnel ipv4 trans supported";
  }

  feature is_tunnel_ipv6_trans_supported {
    description
      "is tunnel ipv6 trans supported";
  }

  feature is_tunnel_ip_dfbit_copy_supported {
    description
      "is tunnel ip dfbit copy supported";
  }

  feature is_tunnel_gre_key_ignore_supported {
    description
      "is tunnel gre key ignore supported";
  }

  feature is_tunnel_gre_key_entropy_supported {
    description
      "is tunnel gre key entropy supported";
  }

  feature is_tunnel_gre_key_supported {
    description
      "is tunnel gre key supported";
  }

  feature is_tunnel_gue_supported {
    description
      "is tunnel gue mode supported";
  }

  feature is_tunnel_ip_transport_vrf_supported {
    description
      "is tunnel ip transport vrf supported";
  }

  grouping GROUP-TUNNEL {
    description
      "Grouping for tunnel";
    container tunnel {
      when "../a1:interface-name[starts-with(text(),'tunnel-ip')]" {
        tailf:dependency "../a1:interface-name";
      }
      description
        "Configure GRE/IP tunnel parameters";
      container source {
        description
          "Configure source of tunnel";
        leaf interface-name {
          type xr:Interface-name;
          must
            "not(../ipv4-address or ../ipv6-address
             or ../direct)";
          description
            "Name of tunnel source interface";
        }
        leaf ipv4-address {
          type inet:ipv4-address-no-zone;
          must
            "not(../interface-name or ../ipv6-address
             or ../direct)";
          description
            "IPV4 address of the tunnel source";
        }
        leaf ipv6-address {
          type inet:ipv6-address-no-zone;
          must "not(../interface-name or ../ipv4-address)";
          description
            "IPV6 address of the tunnel source";
        }
        container direct {
          if-feature "is_tunnel_src_direct_supported";
          must
            "not(../interface-name or ../ipv4-address
             or ../ipv6-address)";
          presence "Indicates a direct node is configured.";
          description
            "Local interface addresses";
        }
      }
      container destination {
        description
          "Configure destination of tunnel";
        leaf prefix-list {
          type xr:Cisco-ios-xr-string {
            length "1..128";
          }
          must "../ipv4-address or ../ipv6-address";
          description
            "Prefix-list to validate destination's resolving prefix";
        }
        leaf ipv4-address {
          type inet:ipv4-address-no-zone;
          must "not(../ipv6-address)";
          description
            "IPV4 address of the tunnel destination";
        }
        leaf length {
          type inet:ipv4-address-no-zone;
          must "../ipv4-address";
          description
            "IPv4 prefix length of the tunnel destination";
        }
        leaf ipv6-address {
          type inet:ipv6-address-no-zone;
          must "not(../ipv4-address)";
          description
            "IPV6 address of the tunnel destination";
        }
        container object-group {
          if-feature "is_tunnel_dst_addr_grp_supported";
          description
            "Object group of the tunnel destination";
          leaf ipv4 {
            type xr:Cisco-ios-xr-string {
              length "1..64" {
                description
                  "IPv4 tunnel destination object group name";
              }
            }
            must "not(../ipv6)";
            description
              "IPv4 object groups";
          }
          leaf ipv6 {
            type xr:Cisco-ios-xr-string {
              length "1..64" {
                description
                  "IPv6 tunnel destination object group name";
              }
            }
            must "not(../ipv4)";
            description
              "IPv6 object groups";
          }
        }
      }
      container bfd {
        description
          "Configure bfd for tunnel";
        container destination {
          description
            "Configure bfd for tunnel";
          leaf ipv4-address {
            type inet:ipv4-address-no-zone;
            must "not(../ipv6-address)";
            description
              "IPV4 address of the BFD destination";
          }
          leaf ipv6-address {
            type inet:ipv6-address-no-zone;
            must "not(../ipv4-address)";
            description
              "IPV6 address of the tunnel destination";
          }
        }
        leaf period {
          type uint32 {
            range "1..32767" {
              description
                "Enter period in seconds";
            }
          }
          description
            "Keepalive period in seconds (default 10 seconds)";
        }
        leaf retry {
          type uint32 {
            range "1..255" {
              description
                "Enter retry range 1-255";
            }
          }
          description
            "Number of retries for Keepalive (default 3)";
        }
        leaf minimum-interval {
          type uint32 {
            range "150..30000" {
              description
                "hello interval in milli-seconds";
            }
          }
          description
            "Hello interval";
        }
        leaf multiplier {
          type uint32 {
            range "3..50" {
              description
                "Detect multiplier";
            }
          }
          description
            "Detect multiplier";
        }
      }
      container mode {
        description
          "Tunnel encapsulation method (default: gre ipv4)";
        container gre {
          if-feature "is_tunnel_gre_supported";
          description
            "IP over GRE encapsulation";
          container multipoint {
            if-feature "is_mgre_through_cli_supported";
            description
              "multipoint GRE over IPv4/IPv6 encapsulation";
            container ipv4 {
              if-feature "is_mgre_tunnel_ipv4_trans_supported";
              must
                "not(../ipv6 or ../../ipv4 or ../../ipv6 or
                     ../../../ipv4 or ../../../ipv6)";
              presence "Indicates a ipv4 node is configured.";
              description
                "multipoint GRE over IPv4 encapsulation";
            }
            container ipv6 {
              if-feature "is_mgre_tunnel_ipv6_trans_supported";
              must
                "not(../ipv4 or ../../ipv4 or ../../ipv6 or
                     ../../../ipv4 or ../../../ipv6)";
              presence "Indicates a ipv6 node is configured.";
              description
                "multipoint GRE over IPv6 encapsulation";
            }
          }
          container ipv4 {
            must
              "not(../ipv6 or ../multipoint/ipv4 or ../multipoint/ipv6 or
                   ../../ipv4 or ../../ipv6)";
            presence "Indicates a ipv4 node is configured.";
            description
              "GRE over IPv4 encapsulation";
          }
          container ipv6 {
            if-feature "is_tunnel_gre_ipv6_trans_supported";
            must
              "not(../ipv4 or ../multipoint/ipv4 or ../multipoint/ipv6 or
                   ../../ipv4 or ../../ipv6)";
            presence "Indicates a ipv6 node is configured.";
            description
              "GRE over IPv6 encapsulation";
          }
        }
        container ipsec {
          if-feature "is_tunnel_ip_ipsec_supported";
          description
            "IPSec tunnel encapsulation";
          container ipv4 {
            must
              "not(../../ipv6 or ../../ipv4 or ../../gre/ipv4 or ../../gre/ipv6 or
                   ../../gre/multipoint/ipv4 or ../../gre/multipoint/ipv6)";
            presence "Indicates a ipv4 node is configured.";
            description
              "Over IPv4";
          }
        }
        container ipv4 {
          if-feature "is_tunnel_ipv4_trans_supported";
          must
            "not(../ipv6 or ../ipsec/ipv4 or ../gre/ipv4 or ../gre/ipv6 or
                 ../gre/multipoint/ipv4 or ../gre/multipoint/ipv6)";
          presence "Indicates a ipv4 node is configured.";
          description
            "Generic packet tunneling over IPv4 encapsulation";
        }
        container ipv6 {
          if-feature "is_tunnel_ipv6_trans_supported";
          must
            "not(../ipv4 or ../ipsec/ipv4 or ../gre/ipv4 or ../gre/ipv6 or
                 ../gre/multipoint/ipv4 or ../gre/multipoint/ipv6)";
          presence "Indicates a ipv6 node is configured.";
          description
            "Generic packet tunneling over IPv6 encapsulation";
        }
        leaf tunnel-lite-mode {
          if-feature "is_tunnel_gre_lite_supported";
          type enumeration {
            enum "lite" {
              value 3;
              description
                "lite mode allows higher tunnel scale with reduced feature set";
            }
          }
          must
            "(../gre/ipv4) and not(../gre/multipoint/ipv4 or
             ../gre/multipoint/ipv6 or ../ipv4 or ../ipv6 or
             ../gre/ipv6 or ../ipsec/ipv4)";
          description
            "configure this node";
        }
        leaf encapsulation-mode {
          if-feature "is_tunnel_mode_decap_supported";
          type enumeration {
            enum "decap" {
              value 1;
              description
                "Decap-only tunnel";
            }
            enum "encap" {
              value 2;
              description
                "Encap-only tunnel";
            }
          }
          must
            "(../ipv4 or ../ipv6 or ../gre/ipv4 or ../gre/ipv6) and
             not(../gre/multipoint/ipv4 or ../gre/multipoint/ipv6 or ../ipsec/ipv4)";
          description
            "configure this node";
        }
        container gue-v1 {
          if-feature "is_tunnel_gue_supported";
          description
            "Generic UDP Encapsulation over IP";
          container ipv4 {
            must
              "not(../../ipv6 or ../../ipv4 or ../../gre/ipv4 or ../../gre/ipv6 or
                   ../../gre/multipoint/ipv4 or ../../gre/multipoint/ipv6)";
            presence "Indicates a gue-v1 ipv4 node is configured.";
            description
              "GUE-v1 over IPv4 encapsulation";
          }
          container ipv6 {
            must
              "not(../../ipv6 or ../../ipv4 or ../../gre/ipv4 or ../../gre/ipv6 or
                   ../../gre/multipoint/ipv4 or ../../gre/multipoint/ipv6)";
            presence "Indicates a gue-v1 ipv6 node is configured.";
            description
              "GUE-v1 over IPv6 encapsulation";
          }
        }
      }
      leaf tos {
        type uint32 {
          range "0..255" {
            description
              "Enter TOS bits as decimal, hex (0x) or octal (0) value";
          }
        }
        description
          "Configure Type of Service bits for this tunnel";
      }
      container ttl {
        description
          "Configure the time-to-live for packets sent over this tunnel";
        container disable {
          must "not(../ttl-value)";
          presence "Indicates a disable node is configured.";
          description
            "Disable decrement of TTL";
        }
        leaf ttl-value {
          type uint32 {
            range "1..255" {
              description
                "Enter the TTL value";
            }
          }
          must "not(../disable)";
          description
            "Enter the TTL value";
        }
      }
      container dfbit {
        description
          "Modify Do not Fragment Bit";
        container disable {
          must "not(../copy)";
          presence "Indicates a disable node is configured.";
          description
            "Disable DF bit (i.e. allow fragmentation)";
        }
        container copy {
          if-feature "is_tunnel_ip_dfbit_copy_supported";
          must "not(../disable)";
          presence "Indicates a copy node is configured.";
          description
            "Copy DF bit from inner payload";
        }
      }
      container key-ignore {
        if-feature "is_tunnel_gre_key_ignore_supported";
        presence "Indicates a key-ignore node is configured.";
        description
          "GRE key field processing configuration";
      }
      container key {
        if-feature "is_tunnel_gre_key_entropy_supported";
        description
          "Configure the key value for packets sent over this tunnel";
        container entropy {
          if-feature "is_tunnel_gre_key_entropy_supported";
          must "not(../key-value)";
          presence "Indicates a entropy node is configured.";
          description
            "Key contains entropy hash";
        }
        leaf key-value {
          if-feature "is_tunnel_gre_key_supported";
          type uint32 {
            range "0..4294967295" {
              description
                "Enter the Key value";
            }
          }
          must "not(../entropy)";
          description
            "Enter the Key value";
        }
      }
      leaf vrf {
        if-feature "is_tunnel_ip_transport_vrf_supported";
        type xr:Cisco-ios-xr-string {
          length "1..32" {
            description
              "vrf table name";
          }
        }
        description
          "set tunnel vrf membership";
      }
      container protection {
        if-feature "is_tunnel_ip_ipsec_supported";
        description
          "set tunnel protection";
        container ipsec {
          description
            "set tunnel ipsec";
          leaf profile {
            type xr:Cisco-ios-xr-string {
              length "1..32" {
                description
                  "IPSec profile name - maximum 32 characters";
              }
            }
            description
              "set tunnel ipsec profile";
          }
          container policy {
            description
              "set policy name";
            leaf ipv4 {
              type xr:Cisco-ios-xr-string {
                length "1..128" {
                  description
                    "IPSec policy name - maximum 128 characters";
                }
              }
              must "../single-sa";
              description
                "set policy for ipv4";
            }
            container single-sa {
              must "../ipv4";
              presence "Indicates a single-sa node is configured.";
              description
                "single SA";
            }
          }
        }
      }
      container port {
        if-feature "is_tunnel_gue_supported";
        description
          "Configure GUE port parameters";
        leaf source {
          type uint32 {
            range "1..65535" {
              description
                "Enter source port number (1-65535)";
            }
          }
          description
            "Configure source port for GUE tunnel";
        }
        leaf destination {
          type uint32 {
            range "1..65535" {
              description
                "Enter destination port number (1-65535)";
            }
          }
          description
            "Configure destination port for GUE tunnel";
        }
      }
    }
    container keepalive {
      presence "Indicates a keepalive node is configured.";
      description
        "Enable keepalive packets on this tunnel";
      leaf keepalive-period {
        type uint32 {
          range "1..32767" {
            description
              "Keepalive period in seconds (default 10 seconds)";
          }
        }
        description
          "Keepalive period in seconds (default 10 seconds)";
      }
      leaf retries {
        type uint32 {
          range "1..255" {
            description
              "Number of retries (default 3)";
          }
        }
        must "../keepalive-period";
        description
          "Number of retries (default 3)";
      }
    }
  }

  augment "/a1:interfaces/a1:interface" {
    description
      "This augment extends active nodes configuration";
    uses GROUP-TUNNEL;
  }
  augment "/a1:interfaces/a1:interface-preconfigure" {
    description
      "This augment extends preconfigured nodes
       configuration";
    uses GROUP-TUNNEL;
  }
}
