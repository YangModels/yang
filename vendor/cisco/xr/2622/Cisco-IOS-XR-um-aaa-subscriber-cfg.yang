module Cisco-IOS-XR-um-aaa-subscriber-cfg {
  namespace "http://cisco.com/ns/yang/Cisco-IOS-XR-um-aaa-subscriber-cfg";
  prefix um-aaa-subscriber-cfg;

  import Cisco-IOS-XR-types {
    prefix xr;
  }
  import Cisco-IOS-XR-um-interface-cfg {
    prefix a1;
  }
  import Cisco-IOS-XR-um-subscriber-cfg {
    prefix a2;
  }
  import Cisco-IOS-XR-um-aaa-cfg {
    prefix a3;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR aaa-subscriber package configuration.
     
     This YANG module augments the
     modules with configuration data.
     
     Copyright (c) 2021-2025 by Cisco Systems, Inc., and/or its affiliates.
     All rights reserved.";

  revision 2023-06-08 {
    description
      "service policy type control node
       2023-03-09
         Added missing coa-nack cli node
       2022-09-28
         Added missing trace and history nodes
       2022-08-01
         Added missing node dyn-tmpl-sess-acct
       2022-07-11
         Added missing description statement to nodes";
    semver:module-version "1.1.0";
  }
  revision 2021-03-09 {
    description
      "Initial release";
    semver:module-version "1.0.0";
  }

  grouping IF-BODY {
    description
      "Grouping for interface";
    container aaa {
      description
        "AAA configuration";
      container radius {
        description
          "AAA radius configuration";
        container attribute {
          description
            "AAA radius attribute";
          leaf nas-port-type {
            type union {
              type uint32 {
                range "0..44" {
                  description
                    "Nas Port Type value";
                }
              }
              type enumeration {
                enum "Async" {
                  value 0;
                  description
                    "Async(0)";
                }
                enum "Sync" {
                  value 1;
                  description
                    "Sync(1)";
                }
                enum "ISDN" {
                  value 2;
                  description
                    "ISDN(2)";
                }
                enum "ISDN-Async-V120" {
                  value 3;
                  description
                    "ISDN-Async-V120(3)";
                }
                enum "ISDN-Async-V110" {
                  value 4;
                  description
                    "ISDN-Async-V110(4)";
                }
                enum "Virtual" {
                  value 5;
                  description
                    "Virtual(5)";
                }
                enum "ISDN-Async-PIAFS" {
                  value 6;
                  description
                    "ISDN-Async-PIAFS(6)";
                }
                enum "HDLC-CLEAR-CHANNEL" {
                  value 7;
                  description
                    "HDLC-Clear-Channel(7)";
                }
                enum "X25" {
                  value 8;
                  description
                    "X25(8)";
                }
                enum "X75" {
                  value 9;
                  description
                    "X75(9)";
                }
                enum "G3FAX" {
                  value 10;
                  description
                    "G.3 Fax(10)";
                }
                enum "SDSL-SYM-SL" {
                  value 11;
                  description
                    "SDSL -Symmetric DSL(11)";
                }
                enum "ADSL-CAP" {
                  value 12;
                  description
                    "ADSL-CAP - Asymmetric DSL(12)";
                }
                enum "ADSL-DMT" {
                  value 13;
                  description
                    "ADSL DMT(13)";
                }
                enum "IDSL" {
                  value 14;
                  description
                    "IDSL - ISDN Digital Subscriber Line(14)";
                }
                enum "Ethernet" {
                  value 15;
                  description
                    "Ethernet(15)";
                }
                enum "XDSL" {
                  value 16;
                  description
                    "Digital Subscriber Line(16)";
                }
                enum "CABLE" {
                  value 17;
                  description
                    "CABLE(17)";
                }
                enum "WIRELESS-OTHER" {
                  value 18;
                  description
                    "Wireless-Other(18)";
                }
                enum "WIRELESS-IEEE-802-11" {
                  value 19;
                  description
                    "Wireless - - IEEE 802.11(19)";
                }
                enum "TOKEN-RING" {
                  value 20;
                  description
                    "Token-Ring(20)";
                }
                enum "FDDI" {
                  value 21;
                  description
                    "FDDI(21)";
                }
                enum "WIRELESS-CDMA" {
                  value 22;
                  description
                    "Wireless - CDMA2000 (22)";
                }
                enum "WIRELESS-UMTS" {
                  value 23;
                  description
                    "Wireless - UMTS(23)";
                }
                enum "WIRELESS-1X-EV" {
                  value 24;
                  description
                    "Wireless - 1X-EV (24)";
                }
                enum "IAPP" {
                  value 25;
                  description
                    "IAPP(25)";
                }
                enum "FTTP" {
                  value 26;
                  description
                    "FTTP(26)";
                }
                enum "WIRELESS-IEEE-802-16" {
                  value 27;
                  description
                    "Wireless - IEEE 802.16 (27)";
                }
                enum "WIRELESS-IEEE-802-20" {
                  value 28;
                  description
                    "Wireless - IEEE 802.20 (28)";
                }
                enum "WIRELESS-IEEE-802-22" {
                  value 29;
                  description
                    "Wireless - IEEE 802.22 (29)";
                }
                enum "PPPoA" {
                  value 30;
                  description
                    "PPPoA(30)";
                }
                enum "PPPoEoA" {
                  value 31;
                  description
                    "PPPoEoA(31)";
                }
                enum "PPPoEoE" {
                  value 32;
                  description
                    "PPPoEoE(32)";
                }
                enum "PPPoEoVLAN" {
                  value 33;
                  description
                    "PPPoEoVLAN(33)";
                }
                enum "PPPoEoQinQ" {
                  value 34;
                  description
                    "PPPoEoQinQ(34)";
                }
                enum "Virtual-PPPoEoE" {
                  value 35;
                  description
                    "Virtual-PPPoEoE(35)";
                }
                enum "Virtual-PPPoEoVLAN" {
                  value 36;
                  description
                    "Virtual-PPPoEoVLAN(36)";
                }
                enum "Virtual-PPPoEoQinaQ" {
                  value 37;
                  description
                    "Virtual-PPPoEoQinQ(37)";
                }
                enum "IPSEC" {
                  value 38;
                  description
                    "IPSEC(38)";
                }
                enum "IPOEOE" {
                  value 39;
                  description
                    "IPOEOE(39)";
                }
                enum "IPOEOVLAN" {
                  value 40;
                  description
                    "IPOEOVLAN(40)";
                }
                enum "IPOEOQINQ" {
                  value 41;
                  description
                    "IPOEOQINQ(41)";
                }
                enum "VIRTUAL-IPOEOE" {
                  value 42;
                  description
                    "VIRTUAL-IPOEOE(42)";
                }
                enum "VIRTUAL-IPOEOVLAN" {
                  value 43;
                  description
                    "VIRTUAL-IPOEOVLAN(43)";
                }
                enum "VIRTUAL-IPOEOQINQ" {
                  value 44;
                  description
                    "VIRTUAL-IPOEOQINQ(44)";
                }
              }
            }
            description
              "AAA nas-port-type attribute";
          }
          leaf nas-identifier {
            type xr:Cisco-ios-xr-string {
              length "1..800" {
                description
                  "Enter a string";
              }
            }
            description
              "AAA nas-identifier attribute";
          }
        }
      }
    }
    container service-policy {
      description
        "Configure a service policy";
      container type {
        description
          "service policy type";
        container control {
          description
            "control policy";
          container subscribers {
            description
              "subscriber policy";
            list subscriber {
              key "subscriber-name";
              description
                "subscriber policy";
              leaf subscriber-name {
                type xr:Cisco-ios-xr-string {
                  length "1..800" {
                    description
                      "Policy name";
                  }
                }
                description
                  "subscriber policy";
              }
            }
          }
        }
      }
    }
  }

  augment "/a1:interfaces/a1:interface" {
    description
      "This augment extends active nodes configuration";
    uses IF-BODY;
  }
  augment "/a1:interfaces/a1:interface-preconfigure" {
    description
      "This augment extends preconfigured nodes
       configuration";
    uses IF-BODY;
  }
  augment "/a2:subscriber" {
    description
      "This augment extends subscriber nodes configuration";
    container manager {
      description
        "iEdge Subscriber Management";
      container accounting {
        description
          "Subscriber manager accounting";
        container send-stop {
          description
            "Generate accounting STOP record";
          container setup-failure {
            description
              "On subscriber session setup failure";
            container aaa {
              description
                "AAA subscriber accounting feature configuration";
              container list {
                description
                  "Accounting method list";
                container default {
                  must "not(../method-list-name)";
                  presence "Indicates a default node is configured.";
                  description
                    "default method list";
                }
                leaf method-list-name {
                  type xr:Cisco-ios-xr-string {
                    length "2..256" {
                      description
                        "Preconfigured method list name";
                    }
                  }
                  description
                    "Preconfigured method list name";
                }
              }
            }
          }
        }
        container interim {
          description
            "interim accounting related";
          leaf variation {
            type uint32 {
              range "0..50" {
                description
                  "maximum percentage variation (maximum absolute variation is 15 minutes)";
              }
            }
            description
              "variation of first session or service interim record from configured timeout";
          }
        }
        container history-storage {
          description
            "acct stop, interim history record storage in file";
          container enable {
            presence "Indicates a enable node is configured.";
            description
              "enable acct hist file storage";
          }
        }
        container stop-storage {
          presence "Indicates a stop-storage node is configured.";
          description
            "accounting STOP record storage in harddisk";
          container records {
            description
              "number of acct STOP records storage in harddisk";
            list record {
              key "record-id storage-time-id";
              description
                "number of acct STOP records storage in harddisk";
              leaf record-id {
                type uint32 {
                  range "64000..256000" {
                    description
                      "range of acct STOP records storage in harddisk, default 256000";
                  }
                }
                description
                  "number of acct STOP records storage in harddisk";
              }
              leaf storage-time-id {
                type uint32 {
                  range "1..24" {
                    description
                      "range of time interval in hours, default 24 hours";
                  }
                }
                description
                  "max life time of record in harddisk";
              }
            }
          }
        }
        container dyn-tmpl-sess-acct {
          description
            "allow dynamic template in session accounting";
          container enable {
            presence "Indicates a enable node is configured.";
            description
              "enable dynamic template in session accounting";
          }
        }
      }
      container trace {
        description
          "Subscriber manager trace ";
        container level {
          description
            "Subscriber manager trace level ";
          container locations {
            description
              "Select location";
            list location {
              key "location-name";
              description
                "Select location";
              leaf location-name {
                type xr:Node-id;
                description
                  "Select location";
              }
              container disable {
                presence "Indicates a disable node is configured.";
                description
                  "Disable tracing for subscriber manager";
              }
              container statistics-only {
                presence "Indicates a statistics-only node is configured.";
                description
                  "Keep only message tracing statistics for subscriber manager";
              }
              container critical {
                presence "Indicates a critical node is configured.";
                description
                  "Trace error tracing for subscriber manager";
              }
              container high {
                presence "Indicates a high node is configured.";
                description
                  "Trace high level logic for subscriber manager";
              }
              container medium {
                presence "Indicates a medium node is configured.";
                description
                  "Trace attributes plus high level logic for subscriber manager";
              }
              container low {
                presence "Indicates a low node is configured.";
                description
                  "Trace more detail messages for subscriber manager";
              }
              container verbose {
                presence "Indicates a verbose node is configured.";
                description
                  "Trace verbose messages for subscriber manager";
              }
              container all {
                presence "Indicates a all node is configured.";
                description
                  "Trace EDM functionality for subscriber manager";
              }
            }
          }
        }
      }
      container history {
        description
          "Subscriber manager history";
        container locations {
          description
            "Select location";
          list location {
            must "disable";
            key "location-name";
            description
              "Select location";
            leaf location-name {
              type xr:Node-id;
              description
                "Select location";
            }
            container disable {
              presence "Indicates a disable node is configured.";
              description
                "Disable history for subscriber manager";
            }
          }
        }
      }
      container srg {
        description
          "SRG specific config";
        container sync-acct-session-id {
          presence "Indicates a sync-acct-session-id node is configured.";
          description
            "sync account session id from primary to subordinate";
        }
        container acct-start-time {
          presence "Indicates a acct-start-time node is configured.";
          description
            "acct start time ref to srg role change Subordinate->Primary";
        }
      }
      container coa-nack {
        description
          "CoA nack specific config";
        container disc-subscriber {
          presence "Indicates a disc-subscriber node is configured.";
          description
            "disconnect subscriber";
        }
      }
    }
    container session {
      description
        "iEdge Subscriber Management session";
      leaf limit {
        type uint32 {
          range "1..200000" {
            description
              "Number of sessions";
          }
        }
        description
          "Configure subscriber session limits";
      }
    }
    container featurette {
      description
        "Enable Featurette";
      container identity-change {
        presence "Indicates a identity-change node is configured.";
        description
          "enable identity change processing";
      }
      container dhcp-renew-author {
        presence "Indicates a dhcp-renew-author node is configured.";
        description
          "enable dhcp renew authentication";
      }
      container ipoe-dhcp-client-reboot {
        presence "Indicates a ipoe-dhcp-client-reboot node is configured.";
        description
          "enable dual stack session tear down on client reboot";
      }
    }
  }
  augment "/a3:aaa" {
    description
      "This augment extends aaa nodes configuration";
    container attribute {
      description
        "AAA attribute";
      container format {
        description
          "AAA attribute format";
        container identifiers {
          description
            "identifier name";
          list identifier {
            key "identifier-name";
            description
              "identifier name";
            leaf identifier-name {
              type xr:Cisco-ios-xr-string {
                length "1..32" {
                  description
                    "identifier name";
                }
              }
              description
                "identifier name";
            }
            container mac-address {
              presence "Indicates a mac-address node is configured.";
              description
                "Mac-address";
              container plus {
                description
                  "Use additional identifiers";
                container circuit-id {
                  must "not(../remote-id)";
                  presence "Indicates a circuit-id node is configured.";
                  description
                    "Circuit ID";
                  container plus {
                    description
                      "Use additional identifiers";
                    container remote-id {
                      must "not(../../separator)";
                      presence "Indicates a remote-id node is configured.";
                      description
                        "Remote ID";
                      leaf separator {
                        type xr:Cisco-ios-xr-string {
                          length "1" {
                            description
                              "separator to be used between keys, default is :";
                          }
                        }
                        description
                          "separator to be used between keys";
                      }
                    }
                  }
                  leaf separator {
                    type xr:Cisco-ios-xr-string {
                      length "1" {
                        description
                          "separator to be used between keys, default is :";
                      }
                    }
                    must "not(../plus/remote-id)";
                    description
                      "separator to be used between keys";
                  }
                }
                container remote-id {
                  must "not(../circuit-id)";
                  presence "Indicates a remote-id node is configured.";
                  description
                    "Remote ID";
                  container plus {
                    description
                      "Use additional identifiers";
                    container circuit-id {
                      must "not(../../separator)";
                      presence "Indicates a remote-id node is configured.";
                      description
                        "Remote ID";
                      leaf separator {
                        type xr:Cisco-ios-xr-string {
                          length "1" {
                            description
                              "separator to be used between keys, default is :";
                          }
                        }
                        description
                          "separator to be used between keys";
                      }
                    }
                  }
                  leaf separator {
                    type xr:Cisco-ios-xr-string {
                      length "1" {
                        description
                          "separator to be used between keys, default is :";
                      }
                    }
                    must "not(../plus/circuit-id)";
                    description
                      "separator to be used between keys";
                  }
                }
              }
              leaf separator {
                type xr:Cisco-ios-xr-string {
                  length "1" {
                    description
                      "separator to be used between keys, default is :";
                  }
                }
                must "not(../plus/circuit-id or ../plus/remote-id)";
                description
                  "separator to be used between keys";
              }
            }
            container circuit-id {
              presence "Indicates a circuit-id node is configured.";
              description
                "Circuit ID";
              container plus {
                description
                  "Use additional identifiers";
                container mac-address {
                  must "not(../remote-id)";
                  presence "Indicates a mac-address node is configured.";
                  description
                    "Mac-address";
                  container plus {
                    description
                      "Use additional identifiers";
                    container remote-id {
                      must "not(../../separator)";
                      presence "Indicates a remote-id node is configured.";
                      description
                        "Remote ID";
                      leaf separator {
                        type xr:Cisco-ios-xr-string {
                          length "1" {
                            description
                              "separator to be used between keys, default is :";
                          }
                        }
                        description
                          "separator to be used between keys";
                      }
                    }
                  }
                  leaf separator {
                    type xr:Cisco-ios-xr-string {
                      length "1" {
                        description
                          "separator to be used between keys, default is :";
                      }
                    }
                    must "not(../plus/remote-id)";
                    description
                      "separator to be used between keys";
                  }
                }
                container remote-id {
                  must "not(../mac-address)";
                  presence "Indicates a remote-id node is configured.";
                  description
                    "Remote ID";
                  container plus {
                    description
                      "Use additional identifiers";
                    container circuit-id {
                      must "not(../../separator)";
                      presence "Indicates a remote-id node is configured.";
                      description
                        "Remote ID";
                      leaf separator {
                        type xr:Cisco-ios-xr-string {
                          length "1" {
                            description
                              "separator to be used between keys, default is :";
                          }
                        }
                        description
                          "separator to be used between keys";
                      }
                    }
                  }
                  leaf separator {
                    type xr:Cisco-ios-xr-string {
                      length "1" {
                        description
                          "separator to be used between keys, default is :";
                      }
                    }
                    must "not(../plus/circuit-id)";
                    description
                      "separator to be used between keys";
                  }
                }
              }
              leaf separator {
                type xr:Cisco-ios-xr-string {
                  length "1" {
                    description
                      "separator to be used between keys, default is :";
                  }
                }
                must "not(../plus/mac-address or ../plus/remote-id)";
                description
                  "separator to be used between keys";
              }
            }
            container remote-id {
              presence "Indicates a remote-id node is configured.";
              description
                "Remote ID";
              container plus {
                description
                  "Use additional identifiers";
                container mac-address {
                  must "not(../circuit-id)";
                  presence "Indicates a mac-address node is configured.";
                  description
                    "Mac-address";
                  container plus {
                    description
                      "Use additional identifiers";
                    container circuit-id {
                      must "not(../../separator)";
                      presence "Indicates a remote-id node is configured.";
                      description
                        "Circuit ID";
                      leaf separator {
                        type xr:Cisco-ios-xr-string {
                          length "1" {
                            description
                              "separator to be used between keys, default is :";
                          }
                        }
                        description
                          "separator to be used between keys";
                      }
                    }
                  }
                  leaf separator {
                    type xr:Cisco-ios-xr-string {
                      length "1" {
                        description
                          "separator to be used between keys, default is :";
                      }
                    }
                    must "not(../plus/circuit-id)";
                    description
                      "separator to be used between keys";
                  }
                }
                container circuit-id {
                  must "not(../mac-address)";
                  presence "Indicates a remote-id node is configured.";
                  description
                    "Circuit ID";
                  container plus {
                    description
                      "Use additional identifiers";
                    container mac-address {
                      must "not(../../separator)";
                      presence "Indicates a mac-address node is configured.";
                      description
                        "Circuit ID";
                      leaf separator {
                        type xr:Cisco-ios-xr-string {
                          length "1" {
                            description
                              "separator to be used between keys, default is :";
                          }
                        }
                        description
                          "separator to be used between keys";
                      }
                    }
                  }
                  leaf separator {
                    type xr:Cisco-ios-xr-string {
                      length "1" {
                        description
                          "separator to be used between keys, default is :";
                      }
                    }
                    must "not(../plus/mac-address)";
                    description
                      "separator to be used between keys";
                  }
                }
              }
              leaf separator {
                type xr:Cisco-ios-xr-string {
                  length "1" {
                    description
                      "separator to be used between keys, default is :";
                  }
                }
                must "not(../plus/mac-address or ../plus/circuit-id)";
                description
                  "separator to be used between keys";
              }
            }
            container format-string {
              presence "Indicates a format-string node is configured.";
              description
                "extended format";
              leaf length {
                type uint32 {
                  range "1..253" {
                    description
                      "length of the formatted string";
                  }
                }
                mandatory true;
                description
                  "length of the formatted string";
              }
              leaf format-string {
                type string {
                  length "1..800" {
                    description
                      "format string (conversion specifier) enclosed in double quotes";
                  }
                  pattern "[\"].*.[\"]";
                }
                mandatory true;
                description
                  "format string (conversion specifier) enclosed in double quotes";
              }
              leaf attribute-1 {
                type union {
                  type string {
                    pattern "circuit-id-tag" {
                      description
                        "Circuit-Id Tag";
                    }
                  }
                  type string {
                    pattern "dhcpv6-interface-id" {
                      description
                        "DHCPv6 Interface-Id";
                    }
                  }
                  type string {
                    pattern "remote-id-tag" {
                      description
                        "Remote-Id Tag";
                    }
                  }
                  type string {
                    pattern "service-name" {
                      description
                        "The name of the service";
                    }
                  }
                  type string {
                    pattern "client-mac-address" {
                      description
                        "MAC address of client";
                    }
                  }
                  type string {
                    pattern "client-mac-address-raw" {
                      description
                        "MAC address of client in raw format";
                    }
                  }
                  type string {
                    pattern "client-mac-address-ietf" {
                      description
                        "MAC address of client in ietf format";
                    }
                  }
                  type string {
                    pattern "client-mac-address-custom1" {
                      description
                        "MAC address of client in AA.BB.CC.DD.EE.FF format";
                    }
                  }
                  type string {
                    pattern "client-mac-address-custom2" {
                      description
                        "MAC address of client in AA:BB:CC:DD:EE:FF format";
                    }
                  }
                  type string {
                    pattern "dhcp-vendor-class" {
                      description
                        "DHCP vendor class name";
                    }
                  }
                  type string {
                    pattern "username" {
                      description
                        "The name of the user";
                    }
                  }
                  type string {
                    pattern "physical-slot" {
                      description
                        "Physical slot needed to form NAS Port";
                    }
                  }
                  type string {
                    pattern "physical-subslot" {
                      description
                        "Physical subslot needed to form NAS Port";
                    }
                  }
                  type string {
                    pattern "physical-adapter" {
                      description
                        "Physical adapter needed to form NAS Port";
                    }
                  }
                  type string {
                    pattern "physical-chassis" {
                      description
                        "Physical chassis needed to form NAS Port";
                    }
                  }
                  type string {
                    pattern "physical-port" {
                      description
                        "Physical port needed to form NAS Port";
                    }
                  }
                  type string {
                    pattern "inner-vlan-id" {
                      description
                        "Inner VLAN ID needed to form NAS Port";
                    }
                  }
                  type string {
                    pattern "outer-vlan-id" {
                      description
                        "Outer VLAN ID needed to form NAS Port";
                    }
                  }
                  type string {
                    pattern "port-type" {
                      description
                        "Interface/Port type";
                    }
                  }
                  type string {
                    pattern "pppoe-session-id" {
                      description
                        "PPPOE Session Id";
                    }
                  }
                  type string {
                    pattern "addr" {
                      description
                        "Source IP address of subscriber";
                    }
                  }
                  type string {
                    pattern "or" {
                      description
                        "OR between two attributes";
                    }
                  }
                  type string {
                    pattern "dhcp-client-id" {
                      description
                        "DHCP Client Identifier";
                    }
                  }
                  type string {
                    pattern "dhcp-client-id-spl" {
                      description
                        "DHCP Client Id special string";
                    }
                  }
                  type string {
                    pattern "dhcpv4-client-id-spl" {
                      description
                        "DHCPv4 Client Id special string";
                    }
                  }
                  type string {
                    pattern "dhcp-user-class" {
                      description
                        "DHCP User Class";
                    }
                  }
                  type string {
                    pattern "srg-group-id" {
                      description
                        "SRG Group ID";
                    }
                  }
                  type string {
                    pattern "dhcpv4-vendor-class" {
                      description
                        "DHCPv4 Vendor classs name";
                    }
                  }
                  type string {
                    pattern "dhcpv6-vendor-class-string" {
                      description
                        "DHCPv6 Vendor classs data string printable";
                    }
                  }
                  type string {
                    pattern "dhcpv6-client-id-enterprise-identifier" {
                      description
                        "DHCPv6 client id enterprise identifier";
                    }
                  }
                }
                description
                  "Format attribute 1";
              }
              leaf attribute-2 {
                type union {
                  type string {
                    pattern "circuit-id-tag" {
                      description
                        "Circuit-Id Tag";
                    }
                  }
                  type string {
                    pattern "dhcpv6-interface-id" {
                      description
                        "DHCPv6 Interface-Id";
                    }
                  }
                  type string {
                    pattern "remote-id-tag" {
                      description
                        "Remote-Id Tag";
                    }
                  }
                  type string {
                    pattern "service-name" {
                      description
                        "The name of the service";
                    }
                  }
                  type string {
                    pattern "client-mac-address" {
                      description
                        "MAC address of client";
                    }
                  }
                  type string {
                    pattern "client-mac-address-raw" {
                      description
                        "MAC address of client in raw format";
                    }
                  }
                  type string {
                    pattern "client-mac-address-ietf" {
                      description
                        "MAC address of client in ietf format";
                    }
                  }
                  type string {
                    pattern "client-mac-address-custom1" {
                      description
                        "MAC address of client in AA.BB.CC.DD.EE.FF format";
                    }
                  }
                  type string {
                    pattern "client-mac-address-custom2" {
                      description
                        "MAC address of client in AA:BB:CC:DD:EE:FF format";
                    }
                  }
                  type string {
                    pattern "dhcp-vendor-class" {
                      description
                        "DHCP vendor class name";
                    }
                  }
                  type string {
                    pattern "username" {
                      description
                        "The name of the user";
                    }
                  }
                  type string {
                    pattern "physical-slot" {
                      description
                        "Physical slot needed to form NAS Port";
                    }
                  }
                  type string {
                    pattern "physical-subslot" {
                      description
                        "Physical subslot needed to form NAS Port";
                    }
                  }
                  type string {
                    pattern "physical-adapter" {
                      description
                        "Physical adapter needed to form NAS Port";
                    }
                  }
                  type string {
                    pattern "physical-chassis" {
                      description
                        "Physical chassis needed to form NAS Port";
                    }
                  }
                  type string {
                    pattern "physical-port" {
                      description
                        "Physical port needed to form NAS Port";
                    }
                  }
                  type string {
                    pattern "inner-vlan-id" {
                      description
                        "Inner VLAN ID needed to form NAS Port";
                    }
                  }
                  type string {
                    pattern "outer-vlan-id" {
                      description
                        "Outer VLAN ID needed to form NAS Port";
                    }
                  }
                  type string {
                    pattern "port-type" {
                      description
                        "Interface/Port type";
                    }
                  }
                  type string {
                    pattern "pppoe-session-id" {
                      description
                        "PPPOE Session Id";
                    }
                  }
                  type string {
                    pattern "addr" {
                      description
                        "Source IP address of subscriber";
                    }
                  }
                  type string {
                    pattern "or" {
                      description
                        "OR between two attributes";
                    }
                  }
                  type string {
                    pattern "dhcp-client-id" {
                      description
                        "DHCP Client Identifier";
                    }
                  }
                  type string {
                    pattern "dhcp-client-id-spl" {
                      description
                        "DHCP Client Id special string";
                    }
                  }
                  type string {
                    pattern "dhcpv4-client-id-spl" {
                      description
                        "DHCPv4 Client Id special string";
                    }
                  }
                  type string {
                    pattern "dhcp-user-class" {
                      description
                        "DHCP User Class";
                    }
                  }
                  type string {
                    pattern "srg-group-id" {
                      description
                        "SRG Group ID";
                    }
                  }
                  type string {
                    pattern "dhcpv4-vendor-class" {
                      description
                        "DHCPv4 Vendor classs name";
                    }
                  }
                  type string {
                    pattern "dhcpv6-vendor-class-string" {
                      description
                        "DHCPv6 Vendor classs data string printable";
                    }
                  }
                  type string {
                    pattern "dhcpv6-client-id-enterprise-identifier" {
                      description
                        "DHCPv6 client id enterprise identifier";
                    }
                  }
                }
                must "../attribute-1";
                description
                  "Format attribute 2";
              }
              leaf attribute-3 {
                type union {
                  type string {
                    pattern "circuit-id-tag" {
                      description
                        "Circuit-Id Tag";
                    }
                  }
                  type string {
                    pattern "dhcpv6-interface-id" {
                      description
                        "DHCPv6 Interface-Id";
                    }
                  }
                  type string {
                    pattern "remote-id-tag" {
                      description
                        "Remote-Id Tag";
                    }
                  }
                  type string {
                    pattern "service-name" {
                      description
                        "The name of the service";
                    }
                  }
                  type string {
                    pattern "client-mac-address" {
                      description
                        "MAC address of client";
                    }
                  }
                  type string {
                    pattern "client-mac-address-raw" {
                      description
                        "MAC address of client in raw format";
                    }
                  }
                  type string {
                    pattern "client-mac-address-ietf" {
                      description
                        "MAC address of client in ietf format";
                    }
                  }
                  type string {
                    pattern "client-mac-address-custom1" {
                      description
                        "MAC address of client in AA.BB.CC.DD.EE.FF format";
                    }
                  }
                  type string {
                    pattern "client-mac-address-custom2" {
                      description
                        "MAC address of client in AA:BB:CC:DD:EE:FF format";
                    }
                  }
                  type string {
                    pattern "dhcp-vendor-class" {
                      description
                        "DHCP vendor class name";
                    }
                  }
                  type string {
                    pattern "username" {
                      description
                        "The name of the user";
                    }
                  }
                  type string {
                    pattern "physical-slot" {
                      description
                        "Physical slot needed to form NAS Port";
                    }
                  }
                  type string {
                    pattern "physical-subslot" {
                      description
                        "Physical subslot needed to form NAS Port";
                    }
                  }
                  type string {
                    pattern "physical-adapter" {
                      description
                        "Physical adapter needed to form NAS Port";
                    }
                  }
                  type string {
                    pattern "physical-chassis" {
                      description
                        "Physical chassis needed to form NAS Port";
                    }
                  }
                  type string {
                    pattern "physical-port" {
                      description
                        "Physical port needed to form NAS Port";
                    }
                  }
                  type string {
                    pattern "inner-vlan-id" {
                      description
                        "Inner VLAN ID needed to form NAS Port";
                    }
                  }
                  type string {
                    pattern "outer-vlan-id" {
                      description
                        "Outer VLAN ID needed to form NAS Port";
                    }
                  }
                  type string {
                    pattern "port-type" {
                      description
                        "Interface/Port type";
                    }
                  }
                  type string {
                    pattern "pppoe-session-id" {
                      description
                        "PPPOE Session Id";
                    }
                  }
                  type string {
                    pattern "addr" {
                      description
                        "Source IP address of subscriber";
                    }
                  }
                  type string {
                    pattern "or" {
                      description
                        "OR between two attributes";
                    }
                  }
                  type string {
                    pattern "dhcp-client-id" {
                      description
                        "DHCP Client Identifier";
                    }
                  }
                  type string {
                    pattern "dhcp-client-id-spl" {
                      description
                        "DHCP Client Id special string";
                    }
                  }
                  type string {
                    pattern "dhcpv4-client-id-spl" {
                      description
                        "DHCPv4 Client Id special string";
                    }
                  }
                  type string {
                    pattern "dhcp-user-class" {
                      description
                        "DHCP User Class";
                    }
                  }
                  type string {
                    pattern "srg-group-id" {
                      description
                        "SRG Group ID";
                    }
                  }
                  type string {
                    pattern "dhcpv4-vendor-class" {
                      description
                        "DHCPv4 Vendor classs name";
                    }
                  }
                  type string {
                    pattern "dhcpv6-vendor-class-string" {
                      description
                        "DHCPv6 Vendor classs data string printable";
                    }
                  }
                  type string {
                    pattern "dhcpv6-client-id-enterprise-identifier" {
                      description
                        "DHCPv6 client id enterprise identifier";
                    }
                  }
                }
                must "../attribute-2";
                description
                  "Format attribute 3";
              }
              leaf attribute-4 {
                type union {
                  type string {
                    pattern "circuit-id-tag" {
                      description
                        "Circuit-Id Tag";
                    }
                  }
                  type string {
                    pattern "dhcpv6-interface-id" {
                      description
                        "DHCPv6 Interface-Id";
                    }
                  }
                  type string {
                    pattern "remote-id-tag" {
                      description
                        "Remote-Id Tag";
                    }
                  }
                  type string {
                    pattern "service-name" {
                      description
                        "The name of the service";
                    }
                  }
                  type string {
                    pattern "client-mac-address" {
                      description
                        "MAC address of client";
                    }
                  }
                  type string {
                    pattern "client-mac-address-raw" {
                      description
                        "MAC address of client in raw format";
                    }
                  }
                  type string {
                    pattern "client-mac-address-ietf" {
                      description
                        "MAC address of client in ietf format";
                    }
                  }
                  type string {
                    pattern "client-mac-address-custom1" {
                      description
                        "MAC address of client in AA.BB.CC.DD.EE.FF format";
                    }
                  }
                  type string {
                    pattern "client-mac-address-custom2" {
                      description
                        "MAC address of client in AA:BB:CC:DD:EE:FF format";
                    }
                  }
                  type string {
                    pattern "dhcp-vendor-class" {
                      description
                        "DHCP vendor class name";
                    }
                  }
                  type string {
                    pattern "username" {
                      description
                        "The name of the user";
                    }
                  }
                  type string {
                    pattern "physical-slot" {
                      description
                        "Physical slot needed to form NAS Port";
                    }
                  }
                  type string {
                    pattern "physical-subslot" {
                      description
                        "Physical subslot needed to form NAS Port";
                    }
                  }
                  type string {
                    pattern "physical-adapter" {
                      description
                        "Physical adapter needed to form NAS Port";
                    }
                  }
                  type string {
                    pattern "physical-chassis" {
                      description
                        "Physical chassis needed to form NAS Port";
                    }
                  }
                  type string {
                    pattern "physical-port" {
                      description
                        "Physical port needed to form NAS Port";
                    }
                  }
                  type string {
                    pattern "inner-vlan-id" {
                      description
                        "Inner VLAN ID needed to form NAS Port";
                    }
                  }
                  type string {
                    pattern "outer-vlan-id" {
                      description
                        "Outer VLAN ID needed to form NAS Port";
                    }
                  }
                  type string {
                    pattern "port-type" {
                      description
                        "Interface/Port type";
                    }
                  }
                  type string {
                    pattern "pppoe-session-id" {
                      description
                        "PPPOE Session Id";
                    }
                  }
                  type string {
                    pattern "addr" {
                      description
                        "Source IP address of subscriber";
                    }
                  }
                  type string {
                    pattern "or" {
                      description
                        "OR between two attributes";
                    }
                  }
                  type string {
                    pattern "dhcp-client-id" {
                      description
                        "DHCP Client Identifier";
                    }
                  }
                  type string {
                    pattern "dhcp-client-id-spl" {
                      description
                        "DHCP Client Id special string";
                    }
                  }
                  type string {
                    pattern "dhcpv4-client-id-spl" {
                      description
                        "DHCPv4 Client Id special string";
                    }
                  }
                  type string {
                    pattern "dhcp-user-class" {
                      description
                        "DHCP User Class";
                    }
                  }
                  type string {
                    pattern "srg-group-id" {
                      description
                        "SRG Group ID";
                    }
                  }
                  type string {
                    pattern "dhcpv4-vendor-class" {
                      description
                        "DHCPv4 Vendor classs name";
                    }
                  }
                  type string {
                    pattern "dhcpv6-vendor-class-string" {
                      description
                        "DHCPv6 Vendor classs data string printable";
                    }
                  }
                  type string {
                    pattern "dhcpv6-client-id-enterprise-identifier" {
                      description
                        "DHCPv6 client id enterprise identifier";
                    }
                  }
                }
                must "../attribute-3";
                description
                  "Format attribute 4";
              }
              leaf attribute-5 {
                type union {
                  type string {
                    pattern "circuit-id-tag" {
                      description
                        "Circuit-Id Tag";
                    }
                  }
                  type string {
                    pattern "dhcpv6-interface-id" {
                      description
                        "DHCPv6 Interface-Id";
                    }
                  }
                  type string {
                    pattern "remote-id-tag" {
                      description
                        "Remote-Id Tag";
                    }
                  }
                  type string {
                    pattern "service-name" {
                      description
                        "The name of the service";
                    }
                  }
                  type string {
                    pattern "client-mac-address" {
                      description
                        "MAC address of client";
                    }
                  }
                  type string {
                    pattern "client-mac-address-raw" {
                      description
                        "MAC address of client in raw format";
                    }
                  }
                  type string {
                    pattern "client-mac-address-ietf" {
                      description
                        "MAC address of client in ietf format";
                    }
                  }
                  type string {
                    pattern "client-mac-address-custom1" {
                      description
                        "MAC address of client in AA.BB.CC.DD.EE.FF format";
                    }
                  }
                  type string {
                    pattern "client-mac-address-custom2" {
                      description
                        "MAC address of client in AA:BB:CC:DD:EE:FF format";
                    }
                  }
                  type string {
                    pattern "dhcp-vendor-class" {
                      description
                        "DHCP vendor class name";
                    }
                  }
                  type string {
                    pattern "username" {
                      description
                        "The name of the user";
                    }
                  }
                  type string {
                    pattern "physical-slot" {
                      description
                        "Physical slot needed to form NAS Port";
                    }
                  }
                  type string {
                    pattern "physical-subslot" {
                      description
                        "Physical subslot needed to form NAS Port";
                    }
                  }
                  type string {
                    pattern "physical-adapter" {
                      description
                        "Physical adapter needed to form NAS Port";
                    }
                  }
                  type string {
                    pattern "physical-chassis" {
                      description
                        "Physical chassis needed to form NAS Port";
                    }
                  }
                  type string {
                    pattern "physical-port" {
                      description
                        "Physical port needed to form NAS Port";
                    }
                  }
                  type string {
                    pattern "inner-vlan-id" {
                      description
                        "Inner VLAN ID needed to form NAS Port";
                    }
                  }
                  type string {
                    pattern "outer-vlan-id" {
                      description
                        "Outer VLAN ID needed to form NAS Port";
                    }
                  }
                  type string {
                    pattern "port-type" {
                      description
                        "Interface/Port type";
                    }
                  }
                  type string {
                    pattern "pppoe-session-id" {
                      description
                        "PPPOE Session Id";
                    }
                  }
                  type string {
                    pattern "addr" {
                      description
                        "Source IP address of subscriber";
                    }
                  }
                  type string {
                    pattern "or" {
                      description
                        "OR between two attributes";
                    }
                  }
                  type string {
                    pattern "dhcp-client-id" {
                      description
                        "DHCP Client Identifier";
                    }
                  }
                  type string {
                    pattern "dhcp-client-id-spl" {
                      description
                        "DHCP Client Id special string";
                    }
                  }
                  type string {
                    pattern "dhcpv4-client-id-spl" {
                      description
                        "DHCPv4 Client Id special string";
                    }
                  }
                  type string {
                    pattern "dhcp-user-class" {
                      description
                        "DHCP User Class";
                    }
                  }
                  type string {
                    pattern "srg-group-id" {
                      description
                        "SRG Group ID";
                    }
                  }
                  type string {
                    pattern "dhcpv4-vendor-class" {
                      description
                        "DHCPv4 Vendor classs name";
                    }
                  }
                  type string {
                    pattern "dhcpv6-vendor-class-string" {
                      description
                        "DHCPv6 Vendor classs data string printable";
                    }
                  }
                  type string {
                    pattern "dhcpv6-client-id-enterprise-identifier" {
                      description
                        "DHCPv6 client id enterprise identifier";
                    }
                  }
                }
                must "../attribute-4";
                description
                  "Format attribute 5";
              }
              leaf attribute-6 {
                type union {
                  type string {
                    pattern "circuit-id-tag" {
                      description
                        "Circuit-Id Tag";
                    }
                  }
                  type string {
                    pattern "dhcpv6-interface-id" {
                      description
                        "DHCPv6 Interface-Id";
                    }
                  }
                  type string {
                    pattern "remote-id-tag" {
                      description
                        "Remote-Id Tag";
                    }
                  }
                  type string {
                    pattern "service-name" {
                      description
                        "The name of the service";
                    }
                  }
                  type string {
                    pattern "client-mac-address" {
                      description
                        "MAC address of client";
                    }
                  }
                  type string {
                    pattern "client-mac-address-raw" {
                      description
                        "MAC address of client in raw format";
                    }
                  }
                  type string {
                    pattern "client-mac-address-ietf" {
                      description
                        "MAC address of client in ietf format";
                    }
                  }
                  type string {
                    pattern "client-mac-address-custom1" {
                      description
                        "MAC address of client in AA.BB.CC.DD.EE.FF format";
                    }
                  }
                  type string {
                    pattern "client-mac-address-custom2" {
                      description
                        "MAC address of client in AA:BB:CC:DD:EE:FF format";
                    }
                  }
                  type string {
                    pattern "dhcp-vendor-class" {
                      description
                        "DHCP vendor class name";
                    }
                  }
                  type string {
                    pattern "username" {
                      description
                        "The name of the user";
                    }
                  }
                  type string {
                    pattern "physical-slot" {
                      description
                        "Physical slot needed to form NAS Port";
                    }
                  }
                  type string {
                    pattern "physical-subslot" {
                      description
                        "Physical subslot needed to form NAS Port";
                    }
                  }
                  type string {
                    pattern "physical-adapter" {
                      description
                        "Physical adapter needed to form NAS Port";
                    }
                  }
                  type string {
                    pattern "physical-chassis" {
                      description
                        "Physical chassis needed to form NAS Port";
                    }
                  }
                  type string {
                    pattern "physical-port" {
                      description
                        "Physical port needed to form NAS Port";
                    }
                  }
                  type string {
                    pattern "inner-vlan-id" {
                      description
                        "Inner VLAN ID needed to form NAS Port";
                    }
                  }
                  type string {
                    pattern "outer-vlan-id" {
                      description
                        "Outer VLAN ID needed to form NAS Port";
                    }
                  }
                  type string {
                    pattern "port-type" {
                      description
                        "Interface/Port type";
                    }
                  }
                  type string {
                    pattern "pppoe-session-id" {
                      description
                        "PPPOE Session Id";
                    }
                  }
                  type string {
                    pattern "addr" {
                      description
                        "Source IP address of subscriber";
                    }
                  }
                  type string {
                    pattern "or" {
                      description
                        "OR between two attributes";
                    }
                  }
                  type string {
                    pattern "dhcp-client-id" {
                      description
                        "DHCP Client Identifier";
                    }
                  }
                  type string {
                    pattern "dhcp-client-id-spl" {
                      description
                        "DHCP Client Id special string";
                    }
                  }
                  type string {
                    pattern "dhcpv4-client-id-spl" {
                      description
                        "DHCPv4 Client Id special string";
                    }
                  }
                  type string {
                    pattern "dhcp-user-class" {
                      description
                        "DHCP User Class";
                    }
                  }
                  type string {
                    pattern "srg-group-id" {
                      description
                        "SRG Group ID";
                    }
                  }
                  type string {
                    pattern "dhcpv4-vendor-class" {
                      description
                        "DHCPv4 Vendor classs name";
                    }
                  }
                  type string {
                    pattern "dhcpv6-vendor-class-string" {
                      description
                        "DHCPv6 Vendor classs data string printable";
                    }
                  }
                  type string {
                    pattern "dhcpv6-client-id-enterprise-identifier" {
                      description
                        "DHCPv6 client id enterprise identifier";
                    }
                  }
                }
                must "../attribute-5";
                description
                  "Format attribute 6";
              }
              leaf attribute-7 {
                type union {
                  type string {
                    pattern "circuit-id-tag" {
                      description
                        "Circuit-Id Tag";
                    }
                  }
                  type string {
                    pattern "dhcpv6-interface-id" {
                      description
                        "DHCPv6 Interface-Id";
                    }
                  }
                  type string {
                    pattern "remote-id-tag" {
                      description
                        "Remote-Id Tag";
                    }
                  }
                  type string {
                    pattern "service-name" {
                      description
                        "The name of the service";
                    }
                  }
                  type string {
                    pattern "client-mac-address" {
                      description
                        "MAC address of client";
                    }
                  }
                  type string {
                    pattern "client-mac-address-raw" {
                      description
                        "MAC address of client in raw format";
                    }
                  }
                  type string {
                    pattern "client-mac-address-ietf" {
                      description
                        "MAC address of client in ietf format";
                    }
                  }
                  type string {
                    pattern "client-mac-address-custom1" {
                      description
                        "MAC address of client in AA.BB.CC.DD.EE.FF format";
                    }
                  }
                  type string {
                    pattern "client-mac-address-custom2" {
                      description
                        "MAC address of client in AA:BB:CC:DD:EE:FF format";
                    }
                  }
                  type string {
                    pattern "dhcp-vendor-class" {
                      description
                        "DHCP vendor class name";
                    }
                  }
                  type string {
                    pattern "username" {
                      description
                        "The name of the user";
                    }
                  }
                  type string {
                    pattern "physical-slot" {
                      description
                        "Physical slot needed to form NAS Port";
                    }
                  }
                  type string {
                    pattern "physical-subslot" {
                      description
                        "Physical subslot needed to form NAS Port";
                    }
                  }
                  type string {
                    pattern "physical-adapter" {
                      description
                        "Physical adapter needed to form NAS Port";
                    }
                  }
                  type string {
                    pattern "physical-chassis" {
                      description
                        "Physical chassis needed to form NAS Port";
                    }
                  }
                  type string {
                    pattern "physical-port" {
                      description
                        "Physical port needed to form NAS Port";
                    }
                  }
                  type string {
                    pattern "inner-vlan-id" {
                      description
                        "Inner VLAN ID needed to form NAS Port";
                    }
                  }
                  type string {
                    pattern "outer-vlan-id" {
                      description
                        "Outer VLAN ID needed to form NAS Port";
                    }
                  }
                  type string {
                    pattern "port-type" {
                      description
                        "Interface/Port type";
                    }
                  }
                  type string {
                    pattern "pppoe-session-id" {
                      description
                        "PPPOE Session Id";
                    }
                  }
                  type string {
                    pattern "addr" {
                      description
                        "Source IP address of subscriber";
                    }
                  }
                  type string {
                    pattern "or" {
                      description
                        "OR between two attributes";
                    }
                  }
                  type string {
                    pattern "dhcp-client-id" {
                      description
                        "DHCP Client Identifier";
                    }
                  }
                  type string {
                    pattern "dhcp-client-id-spl" {
                      description
                        "DHCP Client Id special string";
                    }
                  }
                  type string {
                    pattern "dhcpv4-client-id-spl" {
                      description
                        "DHCPv4 Client Id special string";
                    }
                  }
                  type string {
                    pattern "dhcp-user-class" {
                      description
                        "DHCP User Class";
                    }
                  }
                  type string {
                    pattern "srg-group-id" {
                      description
                        "SRG Group ID";
                    }
                  }
                  type string {
                    pattern "dhcpv4-vendor-class" {
                      description
                        "DHCPv4 Vendor classs name";
                    }
                  }
                  type string {
                    pattern "dhcpv6-vendor-class-string" {
                      description
                        "DHCPv6 Vendor classs data string printable";
                    }
                  }
                  type string {
                    pattern "dhcpv6-client-id-enterprise-identifier" {
                      description
                        "DHCPv6 client id enterprise identifier";
                    }
                  }
                }
                must "../attribute-6";
                description
                  "Format attribute 7";
              }
              leaf attribute-8 {
                type union {
                  type string {
                    pattern "circuit-id-tag" {
                      description
                        "Circuit-Id Tag";
                    }
                  }
                  type string {
                    pattern "dhcpv6-interface-id" {
                      description
                        "DHCPv6 Interface-Id";
                    }
                  }
                  type string {
                    pattern "remote-id-tag" {
                      description
                        "Remote-Id Tag";
                    }
                  }
                  type string {
                    pattern "service-name" {
                      description
                        "The name of the service";
                    }
                  }
                  type string {
                    pattern "client-mac-address" {
                      description
                        "MAC address of client";
                    }
                  }
                  type string {
                    pattern "client-mac-address-raw" {
                      description
                        "MAC address of client in raw format";
                    }
                  }
                  type string {
                    pattern "client-mac-address-ietf" {
                      description
                        "MAC address of client in ietf format";
                    }
                  }
                  type string {
                    pattern "client-mac-address-custom1" {
                      description
                        "MAC address of client in AA.BB.CC.DD.EE.FF format";
                    }
                  }
                  type string {
                    pattern "client-mac-address-custom2" {
                      description
                        "MAC address of client in AA:BB:CC:DD:EE:FF format";
                    }
                  }
                  type string {
                    pattern "dhcp-vendor-class" {
                      description
                        "DHCP vendor class name";
                    }
                  }
                  type string {
                    pattern "username" {
                      description
                        "The name of the user";
                    }
                  }
                  type string {
                    pattern "physical-slot" {
                      description
                        "Physical slot needed to form NAS Port";
                    }
                  }
                  type string {
                    pattern "physical-subslot" {
                      description
                        "Physical subslot needed to form NAS Port";
                    }
                  }
                  type string {
                    pattern "physical-adapter" {
                      description
                        "Physical adapter needed to form NAS Port";
                    }
                  }
                  type string {
                    pattern "physical-chassis" {
                      description
                        "Physical chassis needed to form NAS Port";
                    }
                  }
                  type string {
                    pattern "physical-port" {
                      description
                        "Physical port needed to form NAS Port";
                    }
                  }
                  type string {
                    pattern "inner-vlan-id" {
                      description
                        "Inner VLAN ID needed to form NAS Port";
                    }
                  }
                  type string {
                    pattern "outer-vlan-id" {
                      description
                        "Outer VLAN ID needed to form NAS Port";
                    }
                  }
                  type string {
                    pattern "port-type" {
                      description
                        "Interface/Port type";
                    }
                  }
                  type string {
                    pattern "pppoe-session-id" {
                      description
                        "PPPOE Session Id";
                    }
                  }
                  type string {
                    pattern "addr" {
                      description
                        "Source IP address of subscriber";
                    }
                  }
                  type string {
                    pattern "or" {
                      description
                        "OR between two attributes";
                    }
                  }
                  type string {
                    pattern "dhcp-client-id" {
                      description
                        "DHCP Client Identifier";
                    }
                  }
                  type string {
                    pattern "dhcp-client-id-spl" {
                      description
                        "DHCP Client Id special string";
                    }
                  }
                  type string {
                    pattern "dhcpv4-client-id-spl" {
                      description
                        "DHCPv4 Client Id special string";
                    }
                  }
                  type string {
                    pattern "dhcp-user-class" {
                      description
                        "DHCP User Class";
                    }
                  }
                  type string {
                    pattern "srg-group-id" {
                      description
                        "SRG Group ID";
                    }
                  }
                  type string {
                    pattern "dhcpv4-vendor-class" {
                      description
                        "DHCPv4 Vendor classs name";
                    }
                  }
                  type string {
                    pattern "dhcpv6-vendor-class-string" {
                      description
                        "DHCPv6 Vendor classs data string printable";
                    }
                  }
                  type string {
                    pattern "dhcpv6-client-id-enterprise-identifier" {
                      description
                        "DHCPv6 client id enterprise identifier";
                    }
                  }
                }
                must "../attribute-7";
                description
                  "Format attribute 8";
              }
            }
            container username-strip {
              description
                "User name formatting";
              container prefix-delimiter {
                must "not(../suffix-delimiter)";
                presence "Indicates a prefix-delimiter node is configured.";
                description
                  "prefix-delimiter";
                leaf delimiter {
                  type xr:Cisco-ios-xr-string {
                    length "1" {
                      description
                        "prefix-delimiter";
                    }
                  }
                  mandatory true;
                  description
                    "prefix-delimiter";
                }
                leaf suffix-delimiter {
                  type xr:Cisco-ios-xr-string {
                    length "1" {
                      description
                        "suffix-delimiter";
                    }
                  }
                  description
                    "suffix-delimiter";
                }
              }
              container suffix-delimiter {
                must "not(../prefix-delimiter)";
                presence "Indicates a suffix-delimiter node is configured.";
                description
                  "suffix-delimiter";
                leaf delimiter {
                  type xr:Cisco-ios-xr-string {
                    length "1" {
                      description
                        "suffix-delimiter";
                    }
                  }
                  mandatory true;
                  description
                    "suffix-delimiter";
                }
                leaf prefix-delimiter {
                  type xr:Cisco-ios-xr-string {
                    length "1" {
                      description
                        "prefix-delimiter";
                    }
                  }
                  description
                    "prefix-delimiter";
                }
              }
            }
          }
        }
      }
    }
    container radius {
      description
        "AAA radius attribute configuration";
      container attribute {
        description
          "AAA radius attribute";
        container nas-port-id {
          description
            "AAA nas-port-id attribute";
          leaf format {
            type xr:Cisco-ios-xr-string {
              length "1..32" {
                description
                  "nas-port-id attribute format name";
              }
            }
            description
              "AAA nas-port-id attribute format";
          }
          container types {
            description
              "AAA nas-port attribute format";
            list type {
              key "type-id";
              description
                "AAA nas-port attribute format";
              leaf type-id {
                type uint32 {
                  range "0..44" {
                    description
                      "Nas-Port-Type value to apply format name on";
                  }
                }
                description
                  "AAA nas-port attribute format";
              }
            }
          }
        }
        container nas-port {
          description
            "AAA nas-port-id attribute";
          container format {
            description
              "AAA nas-port attribute format";
            leaf e {
              type xr:Cisco-ios-xr-string {
                length "1..32" {
                  description
                    "A 32 character string representing the format to be used";
                }
              }
              description
                "format type";
            }
            container types {
              description
                "AAA nas-port attribute format";
              list type {
                key "type-id";
                description
                  "AAA nas-port attribute format";
                leaf type-id {
                  type uint32 {
                    range "0..44" {
                      description
                        "Nas-Port-Type value to apply format string on";
                    }
                  }
                  description
                    "AAA nas-port attribute format";
                }
              }
            }
          }
        }
        container calling-station-id {
          description
            "AAA calling station id attribute";
          leaf format {
            type xr:Cisco-ios-xr-string {
              length "1..32" {
                description
                  "calling-station-id attribute format name";
              }
            }
            description
              "AAA calling-station-id attribute format";
          }
          container types {
            description
              "AAA nas-port attribute format";
            list type {
              key "type-id";
              description
                "AAA nas-port attribute format";
              leaf type-id {
                type uint32 {
                  range "0..44" {
                    description
                      "Nas-Port-Type value to apply format name on";
                  }
                }
                description
                  "AAA nas-port attribute format";
              }
              leaf format {
                type xr:Cisco-ios-xr-string {
                  length "1..32" {
                    description
                      "calling-station-id attribute format name";
                  }
                }
                mandatory true;
                description
                  "AAA calling-station-id attribute format";
              }
            }
          }
        }
        container called-station-id {
          description
            "AAA called station id attribute";
          leaf format {
            type xr:Cisco-ios-xr-string {
              length "1..32" {
                description
                  "called-station-id attribute format name";
              }
            }
            description
              "AAA called-station-id attribute format";
          }
          container types {
            description
              "AAA nas-port attribute format";
            list type {
              key "type-id";
              description
                "AAA nas-port attribute format";
              leaf type-id {
                type uint32 {
                  range "0..44" {
                    description
                      "Nas-Port-Type value to apply format name on";
                  }
                }
                description
                  "AAA nas-port attribute format";
              }
            }
          }
        }
        container nas-identifier {
          description
            "AAA nas-identifier attribute";
          leaf format {
            type xr:Cisco-ios-xr-string {
              length "1..32" {
                description
                  "nas-identifier attribute format name";
              }
            }
            description
              "AAA nas-identifier attribute format";
          }
        }
      }
    }
    container service-accounting {
      description
        "Set accounting parameters for Service";
      container extended {
        must "not(../brief)";
        must "not(../brief)";
        presence "Indicates a extended node is configured.";
        description
          "Send extended service accounting records (default)";
      }
      container brief {
        must "not(../extended)";
        must "not(../extended)";
        presence "Indicates a brief node is configured.";
        description
          "Send brief service accounting records";
      }
    }
  }
  augment "/a3:aaa/a3:accounting" {
    description
      "This augment extends aaa accounting nodes configuration";
    container subscriber {
      description
        "Set accounting lists for Subscriber";
      container default {
        presence "Indicates a default node is configured.";
        description
          "Default list name for AAA accounting";
        container broadcast {
          presence "Indicates a broadcast node is configured.";
          description
            "Set broadcast accounting for Subscriber";
        }
        container groups {
          description
            "Use Server-group";
          container group1 {
            description
              "Use Server-group";
            leaf all-hosts {
              type enumeration {
                enum "radius" {
                  value 3;
                  description
                    "Use list of all RADIUS hosts";
                }
                enum "diameter" {
                  value 15;
                  description
                    "Use list of all DIAMETER peers";
                }
              }
              must "not(../server-group)";
              description
                "configure this node";
            }
            leaf server-group {
              type xr:Cisco-ios-xr-string {
                length "1..1024" {
                  description
                    "server-group name";
                }
              }
              must "not(../all-hosts)";
              description
                "server-group name";
            }
          }
          container group2 {
            description
              "Use Server-group";
            leaf all-hosts {
              type enumeration {
                enum "radius" {
                  value 3;
                  description
                    "Use list of all RADIUS hosts";
                }
                enum "diameter" {
                  value 15;
                  description
                    "Use list of all DIAMETER peers";
                }
              }
              must
                "not(../server-group) and
                 (../../group1/all-hosts or ../../group1/server-group)";
              description
                "configure this node";
            }
            leaf server-group {
              type xr:Cisco-ios-xr-string {
                length "1..1024" {
                  description
                    "server-group name";
                }
              }
              must
                "not(../all-hosts) and
                 (../../group1/all-hosts or ../../group1/server-group)";
              description
                "server-group name";
            }
          }
          container group3 {
            description
              "Use Server-group";
            leaf all-hosts {
              type enumeration {
                enum "radius" {
                  value 3;
                  description
                    "Use list of all RADIUS hosts";
                }
                enum "diameter" {
                  value 15;
                  description
                    "Use list of all DIAMETER peers";
                }
              }
              must
                "not(../server-group) and
                 (../../group2/all-hosts or ../../group2/server-group)";
              description
                "configure this node";
            }
            leaf server-group {
              type xr:Cisco-ios-xr-string {
                length "1..1024" {
                  description
                    "server-group name";
                }
              }
              must
                "not(../all-hosts) and
                 (../../group2/all-hosts or ../../group2/server-group)";
              description
                "server-group name";
            }
          }
          container group4 {
            description
              "Use Server-group";
            leaf all-hosts {
              type enumeration {
                enum "radius" {
                  value 3;
                  description
                    "Use list of all RADIUS hosts";
                }
                enum "diameter" {
                  value 15;
                  description
                    "Use list of all DIAMETER peers";
                }
              }
              must
                "not(../server-group) and
                 (../../group3/all-hosts or ../../group3/server-group)";
              description
                "configure this node";
            }
            leaf server-group {
              type xr:Cisco-ios-xr-string {
                length "1..1024" {
                  description
                    "server-group name";
                }
              }
              must
                "not(../all-hosts) and
                 (../../group3/all-hosts or ../../group3/server-group)";
              description
                "server-group name";
            }
          }
        }
      }
      container accounting-lists {
        description
          "List name for AAA accounting";
        list accounting-list {
          key "list-name";
          description
            "List name for AAA accounting";
          leaf list-name {
            type xr:Cisco-ios-xr-string {
              length "1..800" {
                description
                  "List name for AAA accounting";
              }
            }
            description
              "List name for AAA accounting";
          }
          container broadcast {
            presence "Indicates a broadcast node is configured.";
            description
              "Set broadcast accounting for Subscriber";
          }
          container groups {
            description
              "Use Server-group";
            container group1 {
              description
                "Use Server-group";
              leaf all-hosts {
                type enumeration {
                  enum "radius" {
                    value 3;
                    description
                      "Use list of all RADIUS hosts";
                  }
                  enum "diameter" {
                    value 15;
                    description
                      "Use list of all DIAMETER peers";
                  }
                }
                must "not(../server-group)";
                description
                  "configure this node";
              }
              leaf server-group {
                type xr:Cisco-ios-xr-string {
                  length "1..1024" {
                    description
                      "server-group name";
                  }
                }
                must "not(../all-hosts)";
                description
                  "server-group name";
              }
            }
            container group2 {
              description
                "Use Server-group";
              leaf all-hosts {
                type enumeration {
                  enum "radius" {
                    value 3;
                    description
                      "Use list of all RADIUS hosts";
                  }
                  enum "diameter" {
                    value 15;
                    description
                      "Use list of all DIAMETER peers";
                  }
                }
                must
                  "not(../server-group) and
                   (../../group1/all-hosts or ../../group1/server-group)";
                description
                  "configure this node";
              }
              leaf server-group {
                type xr:Cisco-ios-xr-string {
                  length "1..1024" {
                    description
                      "server-group name";
                  }
                }
                must
                  "not(../all-hosts) and
                   (../../group1/all-hosts or ../../group1/server-group)";
                description
                  "server-group name";
              }
            }
            container group3 {
              description
                "Use Server-group";
              leaf all-hosts {
                type enumeration {
                  enum "radius" {
                    value 3;
                    description
                      "Use list of all RADIUS hosts";
                  }
                  enum "diameter" {
                    value 15;
                    description
                      "Use list of all DIAMETER peers";
                  }
                }
                must
                  "not(../server-group) and
                   (../../group2/all-hosts or ../../group2/server-group)";
                description
                  "configure this node";
              }
              leaf server-group {
                type xr:Cisco-ios-xr-string {
                  length "1..1024" {
                    description
                      "server-group name";
                  }
                }
                must
                  "not(../all-hosts) and
                   (../../group2/all-hosts or ../../group2/server-group)";
                description
                  "server-group name";
              }
            }
            container group4 {
              description
                "Use Server-group";
              leaf all-hosts {
                type enumeration {
                  enum "radius" {
                    value 3;
                    description
                      "Use list of all RADIUS hosts";
                  }
                  enum "diameter" {
                    value 15;
                    description
                      "Use list of all DIAMETER peers";
                  }
                }
                must
                  "not(../server-group) and
                   (../../group3/all-hosts or ../../group3/server-group)";
                description
                  "configure this node";
              }
              leaf server-group {
                type xr:Cisco-ios-xr-string {
                  length "1..1024" {
                    description
                      "server-group name";
                  }
                }
                must
                  "not(../all-hosts) and
                   (../../group3/all-hosts or ../../group3/server-group)";
                description
                  "server-group name";
              }
            }
          }
        }
      }
    }
    container service {
      description
        "Set accounting lists for Service";
      container default {
        presence "Indicates a default node is configured.";
        description
          "Default list name for AAA accounting";
        container broadcast {
          presence "Indicates a broadcast node is configured.";
          description
            "Set broadcast accounting for Subscriber";
        }
        container groups {
          description
            "Use Server-group";
          container group1 {
            description
              "Use Server-group";
            leaf all-hosts {
              type enumeration {
                enum "radius" {
                  value 3;
                  description
                    "Use list of all RADIUS hosts";
                }
                enum "diameter" {
                  value 15;
                  description
                    "Use list of all DIAMETER peers";
                }
              }
              must "not(../server-group)";
              description
                "configure this node";
            }
            leaf server-group {
              type xr:Cisco-ios-xr-string {
                length "1..1024" {
                  description
                    "server-group name";
                }
              }
              must "not(../all-hosts)";
              description
                "server-group name";
            }
          }
          container group2 {
            description
              "Use Server-group";
            leaf all-hosts {
              type enumeration {
                enum "radius" {
                  value 3;
                  description
                    "Use list of all RADIUS hosts";
                }
                enum "diameter" {
                  value 15;
                  description
                    "Use list of all DIAMETER peers";
                }
              }
              must
                "not(../server-group) and
                 (../../group1/all-hosts or ../../group1/server-group)";
              description
                "configure this node";
            }
            leaf server-group {
              type xr:Cisco-ios-xr-string {
                length "1..1024" {
                  description
                    "server-group name";
                }
              }
              must
                "not(../all-hosts) and
                 (../../group1/all-hosts or ../../group1/server-group)";
              description
                "server-group name";
            }
          }
          container group3 {
            description
              "Use Server-group";
            leaf all-hosts {
              type enumeration {
                enum "radius" {
                  value 3;
                  description
                    "Use list of all RADIUS hosts";
                }
                enum "diameter" {
                  value 15;
                  description
                    "Use list of all DIAMETER peers";
                }
              }
              must
                "not(../server-group) and
                 (../../group2/all-hosts or ../../group2/server-group)";
              description
                "configure this node";
            }
            leaf server-group {
              type xr:Cisco-ios-xr-string {
                length "1..1024" {
                  description
                    "server-group name";
                }
              }
              must
                "not(../all-hosts) and
                 (../../group2/all-hosts or ../../group2/server-group)";
              description
                "server-group name";
            }
          }
          container group4 {
            description
              "Use Server-group";
            leaf all-hosts {
              type enumeration {
                enum "radius" {
                  value 3;
                  description
                    "Use list of all RADIUS hosts";
                }
                enum "diameter" {
                  value 15;
                  description
                    "Use list of all DIAMETER peers";
                }
              }
              must
                "not(../server-group) and
                 (../../group3/all-hosts or ../../group3/server-group)";
              description
                "configure this node";
            }
            leaf server-group {
              type xr:Cisco-ios-xr-string {
                length "1..1024" {
                  description
                    "server-group name";
                }
              }
              must
                "not(../all-hosts) and
                 (../../group3/all-hosts or ../../group3/server-group)";
              description
                "server-group name";
            }
          }
        }
      }
      container accounting-lists {
        description
          "List name for AAA accounting";
        list accounting-list {
          key "list-name";
          description
            "List name for AAA accounting";
          leaf list-name {
            type xr:Cisco-ios-xr-string {
              length "1..800" {
                description
                  "List name for AAA accounting";
              }
            }
            description
              "List name for AAA accounting";
          }
          container broadcast {
            presence "Indicates a broadcast node is configured.";
            description
              "Set broadcast accounting for Subscriber";
          }
          container groups {
            description
              "Use Server-group";
            container group1 {
              description
                "Use Server-group";
              leaf all-hosts {
                type enumeration {
                  enum "radius" {
                    value 3;
                    description
                      "Use list of all RADIUS hosts";
                  }
                  enum "diameter" {
                    value 15;
                    description
                      "Use list of all DIAMETER peers";
                  }
                }
                must "not(../server-group)";
                description
                  "configure this node";
              }
              leaf server-group {
                type xr:Cisco-ios-xr-string {
                  length "1..1024" {
                    description
                      "server-group name";
                  }
                }
                must "not(../all-hosts)";
                description
                  "server-group name";
              }
            }
            container group2 {
              description
                "Use Server-group";
              leaf all-hosts {
                type enumeration {
                  enum "radius" {
                    value 3;
                    description
                      "Use list of all RADIUS hosts";
                  }
                  enum "diameter" {
                    value 15;
                    description
                      "Use list of all DIAMETER peers";
                  }
                }
                must
                  "not(../server-group) and
                   (../../group1/all-hosts or ../../group1/server-group)";
                description
                  "configure this node";
              }
              leaf server-group {
                type xr:Cisco-ios-xr-string {
                  length "1..1024" {
                    description
                      "server-group name";
                  }
                }
                must
                  "not(../all-hosts) and
                   (../../group1/all-hosts or ../../group1/server-group)";
                description
                  "server-group name";
              }
            }
            container group3 {
              description
                "Use Server-group";
              leaf all-hosts {
                type enumeration {
                  enum "radius" {
                    value 3;
                    description
                      "Use list of all RADIUS hosts";
                  }
                  enum "diameter" {
                    value 15;
                    description
                      "Use list of all DIAMETER peers";
                  }
                }
                must
                  "not(../server-group) and
                   (../../group2/all-hosts or ../../group2/server-group)";
                description
                  "configure this node";
              }
              leaf server-group {
                type xr:Cisco-ios-xr-string {
                  length "1..1024" {
                    description
                      "server-group name";
                  }
                }
                must
                  "not(../all-hosts) and
                   (../../group2/all-hosts or ../../group2/server-group)";
                description
                  "server-group name";
              }
            }
            container group4 {
              description
                "Use Server-group";
              leaf all-hosts {
                type enumeration {
                  enum "radius" {
                    value 3;
                    description
                      "Use list of all RADIUS hosts";
                  }
                  enum "diameter" {
                    value 15;
                    description
                      "Use list of all DIAMETER peers";
                  }
                }
                must
                  "not(../server-group) and
                   (../../group3/all-hosts or ../../group3/server-group)";
                description
                  "configure this node";
              }
              leaf server-group {
                type xr:Cisco-ios-xr-string {
                  length "1..1024" {
                    description
                      "server-group name";
                  }
                }
                must
                  "not(../all-hosts) and
                   (../../group3/all-hosts or ../../group3/server-group)";
                description
                  "server-group name";
              }
            }
          }
        }
      }
    }
  }
  augment "/a3:aaa/a3:authorization" {
    description
      "This augment extends aaa authorization nodes configuration";
    container subscriber {
      description
        "Set authorization lists for Subscriber";
      container default {
        description
          "Default list name for AAA authorization";
        container groups {
          description
            "Use Server-group";
          container group1 {
            description
              "Use Server-group";
            leaf all-hosts {
              type enumeration {
                enum "radius" {
                  value 3;
                  description
                    "Use list of all RADIUS hosts";
                }
                enum "diameter" {
                  value 15;
                  description
                    "Use list of all DIAMETER peers";
                }
              }
              must "not(../server-group)";
              description
                "configure this node";
            }
            leaf server-group {
              type xr:Cisco-ios-xr-string {
                length "1..1024" {
                  description
                    "server-group name";
                }
              }
              must "not(../all-hosts)";
              description
                "server-group name";
            }
          }
          container group2 {
            description
              "Use Server-group";
            leaf all-hosts {
              type enumeration {
                enum "radius" {
                  value 3;
                  description
                    "Use list of all RADIUS hosts";
                }
                enum "diameter" {
                  value 15;
                  description
                    "Use list of all DIAMETER peers";
                }
              }
              must
                "not(../server-group) and
                 (../../group1/all-hosts or ../../group1/server-group)";
              description
                "configure this node";
            }
            leaf server-group {
              type xr:Cisco-ios-xr-string {
                length "1..1024" {
                  description
                    "server-group name";
                }
              }
              must
                "not(../all-hosts) and
                 (../../group1/all-hosts or ../../group1/server-group)";
              description
                "server-group name";
            }
          }
          container group3 {
            description
              "Use Server-group";
            leaf all-hosts {
              type enumeration {
                enum "radius" {
                  value 3;
                  description
                    "Use list of all RADIUS hosts";
                }
                enum "diameter" {
                  value 15;
                  description
                    "Use list of all DIAMETER peers";
                }
              }
              must
                "not(../server-group) and
                 (../../group2/all-hosts or ../../group2/server-group)";
              description
                "configure this node";
            }
            leaf server-group {
              type xr:Cisco-ios-xr-string {
                length "1..1024" {
                  description
                    "server-group name";
                }
              }
              must
                "not(../all-hosts) and
                 (../../group2/all-hosts or ../../group2/server-group)";
              description
                "server-group name";
            }
          }
          container group4 {
            description
              "Use Server-group";
            leaf all-hosts {
              type enumeration {
                enum "radius" {
                  value 3;
                  description
                    "Use list of all RADIUS hosts";
                }
                enum "diameter" {
                  value 15;
                  description
                    "Use list of all DIAMETER peers";
                }
              }
              must
                "not(../server-group) and
                 (../../group3/all-hosts or ../../group3/server-group)";
              description
                "configure this node";
            }
            leaf server-group {
              type xr:Cisco-ios-xr-string {
                length "1..1024" {
                  description
                    "server-group name";
                }
              }
              must
                "not(../all-hosts) and
                 (../../group3/all-hosts or ../../group3/server-group)";
              description
                "server-group name";
            }
          }
        }
      }
      container authorization-lists {
        description
          "List name for AAA authorization";
        list authorization-list {
          key "list-name";
          description
            "List name for AAA authorization";
          leaf list-name {
            type xr:Cisco-ios-xr-string {
              length "1..800" {
                description
                  "List name for AAA authorization";
              }
            }
            description
              "List name for AAA authorization";
          }
          container groups {
            description
              "Use Server-group";
            container group1 {
              description
                "Use Server-group";
              leaf all-hosts {
                type enumeration {
                  enum "radius" {
                    value 3;
                    description
                      "Use list of all RADIUS hosts";
                  }
                  enum "diameter" {
                    value 15;
                    description
                      "Use list of all DIAMETER peers";
                  }
                }
                must "not(../server-group)";
                description
                  "configure this node";
              }
              leaf server-group {
                type xr:Cisco-ios-xr-string {
                  length "1..1024" {
                    description
                      "server-group name";
                  }
                }
                must "not(../all-hosts)";
                description
                  "server-group name";
              }
            }
            container group2 {
              description
                "Use Server-group";
              leaf all-hosts {
                type enumeration {
                  enum "radius" {
                    value 3;
                    description
                      "Use list of all RADIUS hosts";
                  }
                  enum "diameter" {
                    value 15;
                    description
                      "Use list of all DIAMETER peers";
                  }
                }
                must
                  "not(../server-group) and
                   (../../group1/all-hosts or ../../group1/server-group)";
                description
                  "configure this node";
              }
              leaf server-group {
                type xr:Cisco-ios-xr-string {
                  length "1..1024" {
                    description
                      "server-group name";
                  }
                }
                must
                  "not(../all-hosts) and
                   (../../group1/all-hosts or ../../group1/server-group)";
                description
                  "server-group name";
              }
            }
            container group3 {
              description
                "Use Server-group";
              leaf all-hosts {
                type enumeration {
                  enum "radius" {
                    value 3;
                    description
                      "Use list of all RADIUS hosts";
                  }
                  enum "diameter" {
                    value 15;
                    description
                      "Use list of all DIAMETER peers";
                  }
                }
                must
                  "not(../server-group) and
                   (../../group2/all-hosts or ../../group2/server-group)";
                description
                  "configure this node";
              }
              leaf server-group {
                type xr:Cisco-ios-xr-string {
                  length "1..1024" {
                    description
                      "server-group name";
                  }
                }
                must
                  "not(../all-hosts) and
                   (../../group2/all-hosts or ../../group2/server-group)";
                description
                  "server-group name";
              }
            }
            container group4 {
              description
                "Use Server-group";
              leaf all-hosts {
                type enumeration {
                  enum "radius" {
                    value 3;
                    description
                      "Use list of all RADIUS hosts";
                  }
                  enum "diameter" {
                    value 15;
                    description
                      "Use list of all DIAMETER peers";
                  }
                }
                must
                  "not(../server-group) and
                   (../../group3/all-hosts or ../../group3/server-group)";
                description
                  "configure this node";
              }
              leaf server-group {
                type xr:Cisco-ios-xr-string {
                  length "1..1024" {
                    description
                      "server-group name";
                  }
                }
                must
                  "not(../all-hosts) and
                   (../../group3/all-hosts or ../../group3/server-group)";
                description
                  "server-group name";
              }
            }
          }
        }
      }
    }
    container policy-if {
      description
        "Set authorization lists for policy interface";
      container default {
        description
          "Default list name for AAA authorization";
        container groups {
          description
            "Use Server-group";
          container group1 {
            description
              "Use Server-group";
            leaf all-hosts {
              type enumeration {
                enum "diameter" {
                  value 15;
                  description
                    "Use list of all DIAMETER peers";
                }
              }
              must "not(../server-group)";
              description
                "configure this node";
            }
            leaf server-group {
              type xr:Cisco-ios-xr-string {
                length "1..1024" {
                  description
                    "server-group name";
                }
              }
              must "not(../all-hosts)";
              description
                "server-group name";
            }
          }
          container group2 {
            description
              "Use Server-group";
            leaf all-hosts {
              type enumeration {
                enum "diameter" {
                  value 15;
                  description
                    "Use list of all DIAMETER peers";
                }
              }
              must
                "not(../server-group) and
                 (../../group1/all-hosts or ../../group1/server-group)";
              description
                "configure this node";
            }
            leaf server-group {
              type xr:Cisco-ios-xr-string {
                length "1..1024" {
                  description
                    "server-group name";
                }
              }
              must
                "not(../all-hosts) and
                 (../../group1/all-hosts or ../../group1/server-group)";
              description
                "server-group name";
            }
          }
          container group3 {
            description
              "Use Server-group";
            leaf all-hosts {
              type enumeration {
                enum "diameter" {
                  value 15;
                  description
                    "Use list of all DIAMETER peers";
                }
              }
              must
                "not(../server-group) and
                 (../../group2/all-hosts or ../../group2/server-group)";
              description
                "configure this node";
            }
            leaf server-group {
              type xr:Cisco-ios-xr-string {
                length "1..1024" {
                  description
                    "server-group name";
                }
              }
              must
                "not(../all-hosts) and
                 (../../group2/all-hosts or ../../group2/server-group)";
              description
                "server-group name";
            }
          }
          container group4 {
            description
              "Use Server-group";
            leaf all-hosts {
              type enumeration {
                enum "diameter" {
                  value 15;
                  description
                    "Use list of all DIAMETER peers";
                }
              }
              must
                "not(../server-group) and
                 (../../group3/all-hosts or ../../group3/server-group)";
              description
                "configure this node";
            }
            leaf server-group {
              type xr:Cisco-ios-xr-string {
                length "1..1024" {
                  description
                    "server-group name";
                }
              }
              must
                "not(../all-hosts) and
                 (../../group3/all-hosts or ../../group3/server-group)";
              description
                "server-group name";
            }
          }
        }
      }
      container authorization-lists {
        description
          "List name for AAA authorization";
        list authorization-list {
          key "list-name";
          description
            "List name for AAA authorization";
          leaf list-name {
            type xr:Cisco-ios-xr-string {
              length "1..800" {
                description
                  "List name for AAA authorization";
              }
            }
            description
              "List name for AAA authorization";
          }
          container groups {
            description
              "Use Server-group";
            container group1 {
              description
                "Use Server-group";
              leaf all-hosts {
                type enumeration {
                  enum "diameter" {
                    value 15;
                    description
                      "Use list of all DIAMETER peers";
                  }
                }
                must "not(../server-group)";
                description
                  "configure this node";
              }
              leaf server-group {
                type xr:Cisco-ios-xr-string {
                  length "1..1024" {
                    description
                      "server-group name";
                  }
                }
                must "not(../all-hosts)";
                description
                  "server-group name";
              }
            }
            container group2 {
              description
                "Use Server-group";
              leaf all-hosts {
                type enumeration {
                  enum "diameter" {
                    value 15;
                    description
                      "Use list of all DIAMETER peers";
                  }
                }
                must
                  "not(../server-group) and
                   (../../group1/all-hosts or ../../group1/server-group)";
                description
                  "configure this node";
              }
              leaf server-group {
                type xr:Cisco-ios-xr-string {
                  length "1..1024" {
                    description
                      "server-group name";
                  }
                }
                must
                  "not(../all-hosts) and
                   (../../group1/all-hosts or ../../group1/server-group)";
                description
                  "server-group name";
              }
            }
            container group3 {
              description
                "Use Server-group";
              leaf all-hosts {
                type enumeration {
                  enum "diameter" {
                    value 15;
                    description
                      "Use list of all DIAMETER peers";
                  }
                }
                must
                  "not(../server-group) and
                   (../../group2/all-hosts or ../../group2/server-group)";
                description
                  "configure this node";
              }
              leaf server-group {
                type xr:Cisco-ios-xr-string {
                  length "1..1024" {
                    description
                      "server-group name";
                  }
                }
                must
                  "not(../all-hosts) and
                   (../../group2/all-hosts or ../../group2/server-group)";
                description
                  "server-group name";
              }
            }
            container group4 {
              description
                "Use Server-group";
              leaf all-hosts {
                type enumeration {
                  enum "diameter" {
                    value 15;
                    description
                      "Use list of all DIAMETER peers";
                  }
                }
                must
                  "not(../server-group) and
                   (../../group3/all-hosts or ../../group3/server-group)";
                description
                  "configure this node";
              }
              leaf server-group {
                type xr:Cisco-ios-xr-string {
                  length "1..1024" {
                    description
                      "server-group name";
                  }
                }
                must
                  "not(../all-hosts) and
                   (../../group3/all-hosts or ../../group3/server-group)";
                description
                  "server-group name";
              }
            }
          }
        }
      }
    }
    container prepaid {
      description
        "Set authorization lists for prepaid";
      container default {
        description
          "Default list name for AAA authorization";
        container groups {
          description
            "Use Server-group";
          container group1 {
            description
              "Use Server-group";
            leaf all-hosts {
              type enumeration {
                enum "diameter" {
                  value 15;
                  description
                    "Use list of all DIAMETER peers";
                }
              }
              must "not(../server-group)";
              description
                "configure this node";
            }
            leaf server-group {
              type xr:Cisco-ios-xr-string {
                length "1..1024" {
                  description
                    "server-group name";
                }
              }
              must "not(../all-hosts)";
              description
                "server-group name";
            }
          }
          container group2 {
            description
              "Use Server-group";
            leaf all-hosts {
              type enumeration {
                enum "diameter" {
                  value 15;
                  description
                    "Use list of all DIAMETER peers";
                }
              }
              must
                "not(../server-group) and
                 (../../group1/all-hosts or ../../group1/server-group)";
              description
                "configure this node";
            }
            leaf server-group {
              type xr:Cisco-ios-xr-string {
                length "1..1024" {
                  description
                    "server-group name";
                }
              }
              must
                "not(../all-hosts) and
                 (../../group1/all-hosts or ../../group1/server-group)";
              description
                "server-group name";
            }
          }
          container group3 {
            description
              "Use Server-group";
            leaf all-hosts {
              type enumeration {
                enum "diameter" {
                  value 15;
                  description
                    "Use list of all DIAMETER peers";
                }
              }
              must
                "not(../server-group) and
                 (../../group2/all-hosts or ../../group2/server-group)";
              description
                "configure this node";
            }
            leaf server-group {
              type xr:Cisco-ios-xr-string {
                length "1..1024" {
                  description
                    "server-group name";
                }
              }
              must
                "not(../all-hosts) and
                 (../../group2/all-hosts or ../../group2/server-group)";
              description
                "server-group name";
            }
          }
          container group4 {
            description
              "Use Server-group";
            leaf all-hosts {
              type enumeration {
                enum "diameter" {
                  value 15;
                  description
                    "Use list of all DIAMETER peers";
                }
              }
              must
                "not(../server-group) and
                 (../../group3/all-hosts or ../../group3/server-group)";
              description
                "configure this node";
            }
            leaf server-group {
              type xr:Cisco-ios-xr-string {
                length "1..1024" {
                  description
                    "server-group name";
                }
              }
              must
                "not(../all-hosts) and
                 (../../group3/all-hosts or ../../group3/server-group)";
              description
                "server-group name";
            }
          }
        }
      }
      container authorization-lists {
        description
          "List name for AAA authorization";
        list authorization-list {
          key "list-name";
          description
            "List name for AAA authorization";
          leaf list-name {
            type xr:Cisco-ios-xr-string {
              length "1..800" {
                description
                  "List name for AAA authorization";
              }
            }
            description
              "List name for AAA authorization";
          }
          container groups {
            description
              "Use Server-group";
            container group1 {
              description
                "Use Server-group";
              leaf all-hosts {
                type enumeration {
                  enum "diameter" {
                    value 15;
                    description
                      "Use list of all DIAMETER peers";
                  }
                }
                must "not(../server-group)";
                description
                  "configure this node";
              }
              leaf server-group {
                type xr:Cisco-ios-xr-string {
                  length "1..1024" {
                    description
                      "server-group name";
                  }
                }
                must "not(../all-hosts)";
                description
                  "server-group name";
              }
            }
            container group2 {
              description
                "Use Server-group";
              leaf all-hosts {
                type enumeration {
                  enum "diameter" {
                    value 15;
                    description
                      "Use list of all DIAMETER peers";
                  }
                }
                must
                  "not(../server-group) and
                   (../../group1/all-hosts or ../../group1/server-group)";
                description
                  "configure this node";
              }
              leaf server-group {
                type xr:Cisco-ios-xr-string {
                  length "1..1024" {
                    description
                      "server-group name";
                  }
                }
                must
                  "not(../all-hosts) and
                   (../../group1/all-hosts or ../../group1/server-group)";
                description
                  "server-group name";
              }
            }
            container group3 {
              description
                "Use Server-group";
              leaf all-hosts {
                type enumeration {
                  enum "diameter" {
                    value 15;
                    description
                      "Use list of all DIAMETER peers";
                  }
                }
                must
                  "not(../server-group) and
                   (../../group2/all-hosts or ../../group2/server-group)";
                description
                  "configure this node";
              }
              leaf server-group {
                type xr:Cisco-ios-xr-string {
                  length "1..1024" {
                    description
                      "server-group name";
                  }
                }
                must
                  "not(../all-hosts) and
                   (../../group2/all-hosts or ../../group2/server-group)";
                description
                  "server-group name";
              }
            }
            container group4 {
              description
                "Use Server-group";
              leaf all-hosts {
                type enumeration {
                  enum "diameter" {
                    value 15;
                    description
                      "Use list of all DIAMETER peers";
                  }
                }
                must
                  "not(../server-group) and
                   (../../group3/all-hosts or ../../group3/server-group)";
                description
                  "configure this node";
              }
              leaf server-group {
                type xr:Cisco-ios-xr-string {
                  length "1..1024" {
                    description
                      "server-group name";
                  }
                }
                must
                  "not(../all-hosts) and
                   (../../group3/all-hosts or ../../group3/server-group)";
                description
                  "server-group name";
              }
            }
          }
        }
      }
    }
  }
  augment "/a3:aaa/a3:authentication" {
    description
      "This augment extends aaa authentication nodes configuration";
    container subscriber {
      description
        "Set authentication lists for Subscriber";
      container default {
        description
          "Default list name for AAA authentication";
        container groups {
          description
            "Use Server-group";
          container group1 {
            description
              "Use Server-group";
            leaf all-hosts {
              type enumeration {
                enum "radius" {
                  value 3;
                  description
                    "Use list of all RADIUS hosts";
                }
                enum "diameter" {
                  value 15;
                  description
                    "Use list of all DIAMETER peers";
                }
              }
              must "not(../server-group)";
              description
                "configure this node";
            }
            leaf server-group {
              type xr:Cisco-ios-xr-string {
                length "1..1024" {
                  description
                    "server-group name";
                }
              }
              must "not(../all-hosts)";
              description
                "server-group name";
            }
          }
          container group2 {
            description
              "Use Server-group";
            leaf all-hosts {
              type enumeration {
                enum "radius" {
                  value 3;
                  description
                    "Use list of all RADIUS hosts";
                }
                enum "diameter" {
                  value 15;
                  description
                    "Use list of all DIAMETER peers";
                }
              }
              must
                "not(../server-group) and
                 (../../group1/all-hosts or ../../group1/server-group)";
              description
                "configure this node";
            }
            leaf server-group {
              type xr:Cisco-ios-xr-string {
                length "1..1024" {
                  description
                    "server-group name";
                }
              }
              must
                "not(../all-hosts) and
                 (../../group1/all-hosts or ../../group1/server-group)";
              description
                "server-group name";
            }
          }
          container group3 {
            description
              "Use Server-group";
            leaf all-hosts {
              type enumeration {
                enum "radius" {
                  value 3;
                  description
                    "Use list of all RADIUS hosts";
                }
                enum "diameter" {
                  value 15;
                  description
                    "Use list of all DIAMETER peers";
                }
              }
              must
                "not(../server-group) and
                 (../../group2/all-hosts or ../../group2/server-group)";
              description
                "configure this node";
            }
            leaf server-group {
              type xr:Cisco-ios-xr-string {
                length "1..1024" {
                  description
                    "server-group name";
                }
              }
              must
                "not(../all-hosts) and
                 (../../group2/all-hosts or ../../group2/server-group)";
              description
                "server-group name";
            }
          }
          container group4 {
            description
              "Use Server-group";
            leaf all-hosts {
              type enumeration {
                enum "radius" {
                  value 3;
                  description
                    "Use list of all RADIUS hosts";
                }
                enum "diameter" {
                  value 15;
                  description
                    "Use list of all DIAMETER peers";
                }
              }
              must
                "not(../server-group) and
                 (../../group3/all-hosts or ../../group3/server-group)";
              description
                "configure this node";
            }
            leaf server-group {
              type xr:Cisco-ios-xr-string {
                length "1..1024" {
                  description
                    "server-group name";
                }
              }
              must
                "not(../all-hosts) and
                 (../../group3/all-hosts or ../../group3/server-group)";
              description
                "server-group name";
            }
          }
        }
      }
      container authentication-lists {
        description
          "List name for AAA authentication";
        list authentication-list {
          key "list-name";
          description
            "List name for AAA authentication";
          leaf list-name {
            type xr:Cisco-ios-xr-string {
              length "1..800" {
                description
                  "List name for AAA authentication";
              }
            }
            description
              "List name for AAA authentication";
          }
          container groups {
            description
              "Use Server-group";
            container group1 {
              description
                "Use Server-group";
              leaf all-hosts {
                type enumeration {
                  enum "radius" {
                    value 3;
                    description
                      "Use list of all RADIUS hosts";
                  }
                  enum "diameter" {
                    value 15;
                    description
                      "Use list of all DIAMETER peers";
                  }
                }
                must "not(../server-group)";
                description
                  "configure this node";
              }
              leaf server-group {
                type xr:Cisco-ios-xr-string {
                  length "1..1024" {
                    description
                      "server-group name";
                  }
                }
                must "not(../all-hosts)";
                description
                  "server-group name";
              }
            }
            container group2 {
              description
                "Use Server-group";
              leaf all-hosts {
                type enumeration {
                  enum "radius" {
                    value 3;
                    description
                      "Use list of all RADIUS hosts";
                  }
                  enum "diameter" {
                    value 15;
                    description
                      "Use list of all DIAMETER peers";
                  }
                }
                must
                  "not(../server-group) and
                   (../../group1/all-hosts or ../../group1/server-group)";
                description
                  "configure this node";
              }
              leaf server-group {
                type xr:Cisco-ios-xr-string {
                  length "1..1024" {
                    description
                      "server-group name";
                  }
                }
                must
                  "not(../all-hosts) and
                   (../../group1/all-hosts or ../../group1/server-group)";
                description
                  "server-group name";
              }
            }
            container group3 {
              description
                "Use Server-group";
              leaf all-hosts {
                type enumeration {
                  enum "radius" {
                    value 3;
                    description
                      "Use list of all RADIUS hosts";
                  }
                  enum "diameter" {
                    value 15;
                    description
                      "Use list of all DIAMETER peers";
                  }
                }
                must
                  "not(../server-group) and
                   (../../group2/all-hosts or ../../group2/server-group)";
                description
                  "configure this node";
              }
              leaf server-group {
                type xr:Cisco-ios-xr-string {
                  length "1..1024" {
                    description
                      "server-group name";
                  }
                }
                must
                  "not(../all-hosts) and
                   (../../group2/all-hosts or ../../group2/server-group)";
                description
                  "server-group name";
              }
            }
            container group4 {
              description
                "Use Server-group";
              leaf all-hosts {
                type enumeration {
                  enum "radius" {
                    value 3;
                    description
                      "Use list of all RADIUS hosts";
                  }
                  enum "diameter" {
                    value 15;
                    description
                      "Use list of all DIAMETER peers";
                  }
                }
                must
                  "not(../server-group) and
                   (../../group3/all-hosts or ../../group3/server-group)";
                description
                  "configure this node";
              }
              leaf server-group {
                type xr:Cisco-ios-xr-string {
                  length "1..1024" {
                    description
                      "server-group name";
                  }
                }
                must
                  "not(../all-hosts) and
                   (../../group3/all-hosts or ../../group3/server-group)";
                description
                  "server-group name";
              }
            }
          }
        }
      }
    }
  }
}
