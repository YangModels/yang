module Cisco-IOS-XR-um-lldp-cfg {
  namespace "http://cisco.com/ns/yang/Cisco-IOS-XR-um-lldp-cfg";
  prefix um-lldp-cfg;

  import tailf-common {
    prefix tailf;
  }
  import Cisco-IOS-XR-um-interface-cfg {
    prefix interface-cfg;
  }
  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco lldp package configuration.
     This YANG module augments interface and other modules configuration data.
     Copyright (c) 2024 by Cisco Systems, Inc.
     All rights reserved.";

  revision 2024-11-20 {
    description
      "Modified maximum length of global LLDP string parameters
       2024-08-21
         Added interface-only node
       2024-03-19
         Updating model for um2 changes
       2022-12-07
         Added tagged and subinterfaces-tagged nodes
       2022-11-25
         Corrected chassis-id-type values and order item numbers
       2022-09-16
         Added chassis-id and system-description nodes
       2022-07-11
         Added missing description statement to nodes";
    semver:module-version "2.0.0";
  }
  revision 2020-03-23 {
    description
      "Initial release";
    semver:module-version "1.0.0";
  }

  grouping GROUP-INTERFACES-INTERFACE-LLDP-BODY {
    description
      "Grouping for interfaces";
    container lldp {
      when "../interface-cfg:interface-name[starts-with(text(),'Ethernet')] or ../interface-cfg:interface-name[starts-with(text(),'FastEthernet')] or ../interface-cfg:interface-name[starts-with(text(),'GigabitEthernet')] or ../interface-cfg:interface-name[starts-with(text(),'TenGigE')] or ../interface-cfg:interface-name[starts-with(text(),'TwentyFiveGigE')] or ../interface-cfg:interface-name[starts-with(text(),'FortyGigE')] or ../interface-cfg:interface-name[starts-with(text(),'FiftyGigE')] or ../interface-cfg:interface-name[starts-with(text(),'HundredGigE')] or ../interface-cfg:interface-name[starts-with(text(),'TwoHundredGigE')] or ../interface-cfg:interface-name[starts-with(text(),'FourHundredGigE')] or ../interface-cfg:interface-name[starts-with(text(),'EightHundredGigE')] or ../interface-cfg:interface-name[starts-with(text(),'CPRIoE')] or ../interface-cfg:interface-name[starts-with(text(),'Bundle-Ether')] or ../interface-cfg:interface-name[starts-with(text(),'MgmtEth')]" {
        tailf:dependency "../interface-cfg:interface-name";
      }
      presence "LLDP interface configuration commands";
      description
        "LLDP interface configuration commands";
      container receive {
        description
          "Disable LLDP RX on an interface";
        leaf disable {
          type empty;
          description
            "Disable LLDP RX on an interface";
        }
      }
      leaf enable {
        type empty;
        description
          "Enable LLDP TX and RX on an interface";
      }
      container transmit {
        description
          "Disable LLDP TX on an interface";
        leaf disable {
          type empty;
          description
            "Disable LLDP TX on an interface";
        }
      }
      leaf tagged {
        type empty;
        description
          "Enable VLAN tagging on LLDP PDU on this interface";
      }
      container destination {
        description
          "Configure LLDP Destination MAC on the interface";
        container mac-address {
          presence "Destination MAC address on the interface";
          description
            "Destination MAC address on the interface";
          leaf ieee-bridge {
            type enumeration {
              enum "ieee-nearest-bridge" {
                value 14;
                description
                  "Default LLDP Destination MAC address, 01:80:C2:00:00:0E";
              }
              enum "ieee-nearest-non-tmpr-bridge" {
                value 3;
                description
                  "IEEE Non-TMPR Bridge MAC address, 01:80:C2:00:00:03";
              }
            }
            description
              "Bridge Mac address";
          }
        }
      }
    }
  }

  augment "/interface-cfg:interfaces/interface-cfg:interface" {
    description
      "This augment extends the configuration data of Cisco-IOS-XR-um-interface-cfg";
    uses GROUP-INTERFACES-INTERFACE-LLDP-BODY;
  }
  augment "/interface-cfg:interfaces/interface-cfg:interface-preconfigure" {
    description
      "This augment extends the configuration data of Cisco-IOS-XR-um-interface-cfg";
    uses GROUP-INTERFACES-INTERFACE-LLDP-BODY;
  }
  container lldp {
    presence "Enable LLDP, or configure global LLDP subcommands";
    description
      "Enable LLDP, or configure global LLDP subcommands";
    leaf holdtime {
      type uint32 {
        range "0..65535" {
          description
            "Length of time (in sec) that receiver must keep this packet";
        }
      }
      description
        "Specify the holdtime (in sec) to be sent in packets";
    }
    leaf interface-only {
      type empty;
      description
        "Enable LLDP only based on interface LLDP configuration. No Global enable";
    }
    container subinterfaces {
      description
        "Configure LLDP over Sub-interfaces";
      leaf enable {
        type empty;
        description
          "Enable LLDP over Sub-interfaces as well";
      }
    }
    container management {
      description
        "Configure LLDP over Management interface";
      leaf enable {
        type empty;
        description
          "Enable LLDP over Management interface as well";
      }
    }
    leaf reinit {
      type uint32 {
        range "2..5" {
          description
            "Delay (in sec) for LLDP initialization on any interface";
        }
      }
      description
        "Delay (in sec) for LLDP initialization on any interface";
    }
    leaf system-name {
      type xr:Cisco-ios-xr-string {
        length "1..255" {
          description
            "LLDP system name string";
        }
      }
      description
        "LLDP system name to advertise";
    }
    leaf system-description {
      type xr:Cisco-ios-xr-string {
        length "1..255" {
          description
            "LLDP system description string";
        }
      }
      description
        "LLDP system description to advertise";
    }
    leaf chassis-id {
      type xr:Cisco-ios-xr-string {
        length "1..255" {
          description
            "LLDP chassis id string";
        }
      }
      description
        "LLDP chassis ID to advertise";
    }
    leaf chassis-id-type {
      type enumeration {
        enum "chassis-component" {
          value 0;
          description
            "Value of entPhysicalAlias object defined in IETF RFC 2737";
        }
        enum "interface-alias" {
          value 1;
          description
            "Value of ifAlias object defined in IETF RFC 2863";
        }
        enum "port-component" {
          value 2;
          description
            "Value of entPhysicalAlias object defined in IETF RFC 2737";
        }
        enum "mac-address" {
          value 3;
          description
            "Value of a unicast source address";
        }
        enum "network-address" {
          value 4;
          description
            "Network address associated with a particular chassis";
        }
        enum "interface-name" {
          value 5;
          description
            "Value of ifName object defined in IETF RFC 2863";
        }
        enum "local" {
          value 6;
          description
            "Chassis identifier based on a locally defined value";
        }
      }
      description
        "LLDP chassis ID type to advertise";
    }
    container priorityaddr {
      description
        "Configure Priority to advertise Management interface address first";
      leaf enable {
        type empty;
        description
          "Enable LLDP to use Management interface address first(if configured)";
      }
    }
    leaf timer {
      type uint32 {
        range "5..65534" {
          description
            "Rate at which LLDP packets are sent (in sec)";
        }
      }
      description
        "Specify the rate at which LLDP packets are sent (in sec)";
    }
    leaf subinterfaces-tagged {
      type empty;
      description
        "Enable VLAN tagging for LLDP PDU over Sub-interfaces";
    }
    container extended-show-width {
      description
        "Configure Extended Show LLDP Neighbor Width";
      leaf enable {
        type empty;
        description
          "Enable Extended Show LLDP Neighbor Width";
      }
    }
    container tlv-select {
      presence "Selection of LLDP TLVs to disable";
      description
        "Selection of LLDP TLVs to disable";
      container system-name {
        description
          "System Name TLV";
        leaf disable {
          type empty;
          description
            "disable System Name TLV";
        }
      }
      container management-address {
        description
          "Management Address TLV";
        leaf disable {
          type empty;
          description
            "disable Management Address TLV";
        }
      }
      container system-capabilities {
        description
          "System Capabilities TLV";
        leaf disable {
          type empty;
          description
            "disable System Capabilities TLV";
        }
      }
      container port-description {
        description
          "Port Description TLV";
        leaf disable {
          type empty;
          description
            "disable Port Description TLV";
        }
      }
      container system-description {
        description
          "System Description TLV";
        leaf disable {
          type empty;
          description
            "disable System Description TLV";
        }
      }
    }
  }
}
