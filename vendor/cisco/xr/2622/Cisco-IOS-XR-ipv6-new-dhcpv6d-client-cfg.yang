module Cisco-IOS-XR-ipv6-new-dhcpv6d-client-cfg {
  namespace "http://cisco.com/ns/yang/Cisco-IOS-XR-ipv6-new-dhcpv6d-client-cfg";
  prefix ipv6-new-dhcpv6d-client-cfg;

  import cisco-semver {
    prefix semver;
  }
  import Cisco-IOS-XR-ifmgr-cfg {
    prefix a1;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ipv6-new-dhcpv6d-client package configuration.
     
     This YANG module augments the
       Cisco-IOS-XR-ifmgr-cfg
     module with configuration data.
     
     Copyright (c) 2013-2020 by Cisco Systems, Inc.
     All rights reserved.";

  revision 2020-09-17 {
    description
      "Added prefix-len option for dhcpv6 client";
    semver:module-version "1.1.0";
  }
  revision 2020-02-18 {
    description
      "Modified DHCPv6 client timers range.";
    semver:module-version "1.0.0";
  }
  revision 2019-11-16 {
    description
      "Added Support for DHCPv6 Client.";
  }
  revision 2019-04-05 {
    description
      "Establish semantic version baseline.";
  }
  revision 2015-11-09 {
    description
      "IOS XR 6.0 revision.";
  }

  typedef Duid {
    type enumeration {
      enum "duid-ll" {
        value 3;
        description
          "Link Local Address";
      }
    }
    description
      "Duid";
  }

  augment "/a1:interface-configurations/a1:interface-configuration" {
    description
      "This augment extends the configuration data of
       'Cisco-IOS-XR-ifmgr-cfg'";
    container ipv6-dhcp-client-options {
      description
        "Interface IPv6 dhcp-address-client-options
         configuration";
      container options {
        description
          "DHCPv6 Options";
        leaf dns-option {
          type string;
          description
            "Domain Name Server Option";
        }
        leaf user-class-id-option {
          type string;
          description
            "User Class ID String";
        }
        leaf vendor-id-option {
          type string;
          description
            "Vendor ID Option String";
        }
        leaf domain-list-option {
          type string;
          description
            "Domain List Option";
        }
      }
      container duidses {
        description
          "DUID Types";
        leaf-list duids {
          type Duid;
          max-elements "1";
          description
            "DUID Type";
        }
      }
      container timers {
        description
          "DHCPv6 Client Timers";
        leaf req-time-out {
          type uint32 {
            range "1..4";
          }
          description
            "Initial request timeout";
        }
        leaf release-time-out {
          type uint32 {
            range "1..3";
          }
          description
            "Initial release timeout value";
        }
        leaf sol-max-rt {
          type uint32 {
            range "10..3600";
          }
          description
            "Maximum solicit retransmission value";
        }
        leaf req-max-rt {
          type uint32 {
            range "10..30";
          }
          description
            "Maximum request timeout value";
        }
        leaf sol-time-out {
          type uint32 {
            range "1..4";
          }
          description
            "Initial solicit timeout";
        }
        leaf sol-max-delay {
          type uint32 {
            range "1..4";
          }
          description
            "Max delay of first solicit";
        }
      }
      leaf enable {
        type empty;
        description
          "Enabled";
      }
      leaf rapid-commit {
        type string;
        description
          "Rapid-Commit";
      }
      leaf prefix-length {
        type uint32 {
          range "64..127";
        }
        description
          "Prefix Length";
      }
    }
  }
}
