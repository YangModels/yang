//*************  DO-NOT EDIT  **************
//*********** Auto-generated file ********** 

 module cisco-xr-openconfig-system-fpd-ext-deviations {

  namespace "http://cisco.com/ns/yang/cisco-xr-openconfig-system-fpd-ext-deviations";

  prefix  "oc-sysfpdextdevs";

  import Cisco-IOS-XR-openconfig-system-fpd-ext { prefix oc-fpd-ext; }
  import openconfig-system { prefix oc-sys; }

  import cisco-semver { prefix "semver"; }

  organization "Cisco Systems, Inc.";

  contact
    "Cisco Systems, Inc.
     Customer Service

     Postal: 170 West Tasman Drive
     San Jose, CA 95134

     Tel: +1 800 553-NETS

     E-mail: cs-yang@cisco.com";

  description
    "This module contains a set of deviations for 

     Cisco-IOS-XR-openconfig-system-fpd-ext.yang@2024-05-10 

     on Cisco IOS-XR devices.

     Copyright (c) 2024 by Cisco Systems, Inc.
     All rights reserved.";

  revision "2024-05-29" {
    description
      "Initial revision applicable to IOS-XR 24.4.1";
    semver:module-version "1.0.0";
  }


  deviation /oc-sys:system/oc-fpd-ext:cisco/oc-fpd-ext:fpd/oc-fpd-ext:config/oc-fpd-ext:enable-auto-upgrade {
    deviate delete {
      default true;
    }
  }

  deviation /oc-sys:system/oc-fpd-ext:cisco/oc-fpd-ext:fpd/oc-fpd-ext:state/oc-fpd-ext:enable-auto-upgrade {
    deviate delete {
      default true;
    }
  }

}
//total deviations:2
