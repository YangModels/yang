module Cisco-IOS-XR-aaa-locald-cfg {
  namespace "http://cisco.com/ns/yang/Cisco-IOS-XR-aaa-locald-cfg";
  prefix aaa-locald-cfg;

  import Cisco-IOS-XR-types {
    prefix xr;
  }
  import cisco-semver {
    prefix semver;
  }
  import Cisco-IOS-XR-aaa-lib-cfg {
    prefix a1;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR aaa-locald package configuration.
     
     This YANG module augments the
       Cisco-IOS-XR-aaa-lib-cfg
     module with configuration data.
     
     Copyright (c) 2013-2025 by Cisco Systems, Inc.
     All rights reserved.";

  revision 2025-08-05 {
    description
      "Added max length as 800 for usergroup and taskgroup description.
       2024-04-14
         Added aaa logging accounting disable config.
       2024-04-06
         Removed type7 password and type5 secret options
       2024-03-27
         Corrected the version in deprecation warnings.
       2024-01-22
         Added warnings for secret type-5 deprecation.
       2023-10-16
         Added config knob to map username with spiffe-id
       2022-11-28
         Added config knob to display username after failure login attempts
       2022-07-11
         Added config support for certificate based authentication for TACACS+ users
       2021-11-02
         Added restrict-consecutive-character in password policy";
    semver:module-version "3.0.0";
  }
  revision 2019-11-24 {
    description
      "Added cli for enabling/disabling admin accounting via XR.";
    semver:module-version "2.0.0";
  }
  revision 2019-04-05 {
    description
      "Establish semantic version baseline.";
    semver:module-version "1.0.0";
  }
  revision 2018-06-04 {
    description
      "Added Yang support for aaa password-policy.";
  }
  revision 2018-04-30 {
    description
      "Added model support for aaa shell-type, directory.";
  }
  revision 2017-09-07 {
    description
      "Fixed type translation error.";
  }
  revision 2017-03-11 {
    description
      "Added model support for aaa password-policy.";
  }
  revision 2015-11-09 {
    description
      "IOS XR 6.0 revision.";
  }

  typedef Aaa-pass-policy-lockout-seconds {
    type uint32 {
      range "0..59";
    }
    description
      "Aaa pass policy lockout seconds";
  }

  typedef Aaa-pass-policy-authen-attempts {
    type uint32 {
      range "1..24";
    }
    description
      "Aaa pass policy authen attempts";
  }

  typedef Aaa-pass-policy-days {
    type uint32 {
      range "0..30";
    }
    description
      "Aaa pass policy days";
  }

  typedef Aaa-pass-policy-restrict-consecutive-qwerty-keyboard-characters {
    type uint32 {
      range "2..10";
    }
    description
      "Aaa pass policy restrict consecutive qwerty
       keyboard characters";
  }

  typedef Aaa-locald-task-id {
    type string;
    description
      "Aaa locald task id";
  }

  typedef Aaa-pass-policy-restrict-old-count {
    type uint32 {
      range "0..10";
    }
    description
      "Aaa pass policy restrict old count";
  }

  typedef Aaa-pass-policy-years {
    type uint32 {
      range "0..99";
    }
    description
      "Aaa pass policy years";
  }

  typedef Aaa-pass-policy-hours {
    type uint32 {
      range "0..23";
    }
    description
      "Aaa pass policy hours";
  }

  typedef Aaa-pass-policy-months {
    type uint32 {
      range "0..11";
    }
    description
      "Aaa pass policy months";
  }

  typedef Aaa-password {
    type enumeration {
      enum "type5" {
        value 5;
        description
          "Type 5 password";
      }
      enum "type8" {
        value 8;
        description
          "Type 8 password";
      }
      enum "type9" {
        value 9;
        description
          "Type 9 password";
      }
      enum "type10" {
        value 10;
        description
          "Type 10 password";
      }
    }
    description
      "Aaa password";
  }

  typedef Aaa-pass-policy-lockout-days {
    type uint32 {
      range "0..255";
    }
    description
      "Aaa pass policy lockout days";
  }

  typedef Aaa-pass-policy-seconds {
    type uint32 {
      range "30..59";
    }
    description
      "Aaa pass policy seconds";
  }

  typedef Aaa-pass-policy-restrict-consecutive-english-alphabet {
    type uint32 {
      range "2..26";
    }
    description
      "Aaa pass policy restrict consecutive english
       alphabet";
  }

  typedef Aaa-pass-policy-length {
    type uint32 {
      range "2..253";
    }
    description
      "Aaa pass policy length";
  }

  typedef Aaa-locald-task-class {
    type enumeration {
      enum "read" {
        value 0;
        description
          "Permits read operation for a Task ID";
      }
      enum "write" {
        value 1;
        description
          "Permits write operation for a Task ID";
      }
      enum "execute" {
        value 2;
        description
          "Permits execute operation for a Task ID";
      }
      enum "debug" {
        value 3;
        description
          "Permits debug operation for a Task ID";
      }
    }
    description
      "Aaa locald task class";
  }

  typedef Aaa-pass-policy-char-repeat-length {
    type uint32 {
      range "2..5";
    }
    description
      "Aaa pass policy char repeat length";
  }

  typedef Aaa-login-history {
    type uint32 {
      range "0..1";
    }
    description
      "Aaa login history";
  }

  typedef Aaa-pass-policy-case-length {
    type uint32 {
      range "0..253";
    }
    description
      "Aaa pass policy case length";
  }

  typedef Aaa-pass-policy-minutes {
    type uint32 {
      range "0..59";
    }
    description
      "Aaa pass policy minutes";
  }

  augment "/a1:aaa" {
    description
      "This augment extends the configuration data of
       'Cisco-IOS-XR-aaa-lib-cfg'";
    container password-policies {
      description
        "Configure password-policy";
      list password-policy {
        key "name";
        description
          "Password Policy name";
        container lifetime {
          description
            "Liftime of the password";
          leaf years {
            type Aaa-pass-policy-years;
            description
              "Number of years";
          }
          leaf months {
            type Aaa-pass-policy-months;
            description
              "Number of months";
          }
          leaf hours {
            type Aaa-pass-policy-hours;
            units "hour";
            description
              "Number of hours";
          }
          leaf minutes {
            type Aaa-pass-policy-minutes;
            units "minute";
            description
              "Number of minutes";
          }
          leaf seconds {
            type Aaa-pass-policy-seconds;
            units "second";
            description
              "Number of seconds";
          }
          leaf days {
            type Aaa-pass-policy-days;
            units "day";
            description
              "Number of days";
          }
        }
        container lockout-time {
          description
            "Lockout time for the maximum authentication
             failures";
          leaf hours {
            type Aaa-pass-policy-hours;
            units "hour";
            description
              "Number of hours";
          }
          leaf minutes {
            type Aaa-pass-policy-minutes;
            units "minute";
            description
              "Number of minutes";
          }
          leaf seconds {
            type Aaa-pass-policy-lockout-seconds;
            units "second";
            description
              "Number of seconds";
          }
          leaf days {
            type Aaa-pass-policy-lockout-days;
            units "day";
            description
              "Number of days";
          }
        }
        container restrict-old-time {
          description
            "Time limit for old password to be considered
             for new password check";
          leaf years {
            type Aaa-pass-policy-years;
            description
              "Number of years";
          }
          leaf months {
            type Aaa-pass-policy-months;
            description
              "Number of months";
          }
          leaf days {
            type Aaa-pass-policy-days;
            units "day";
            description
              "Number of days";
          }
        }
        container warninterval {
          description
            "Warninterval of the password";
          leaf years {
            type Aaa-pass-policy-years;
            description
              "Number of years";
          }
          leaf months {
            type Aaa-pass-policy-months;
            description
              "Number of months";
          }
          leaf hours {
            type Aaa-pass-policy-hours;
            units "hour";
            description
              "Number of hours";
          }
          leaf minutes {
            type Aaa-pass-policy-minutes;
            units "minute";
            description
              "Number of minutes";
          }
          leaf seconds {
            type Aaa-pass-policy-seconds;
            units "second";
            description
              "Number of seconds";
          }
          leaf days {
            type Aaa-pass-policy-days;
            units "day";
            description
              "Number of days";
          }
        }
        container restrict-consecutive-characters {
          description
            "Restrict consecutive letters and decimal
             numbers from English alphabet and qwerty
             keyboard";
          container qwerty-keyboard {
            presence "Indicates a qwerty-keyboard node is configured.";
            description
              "Restrict consecutive alphanumeric chracters
               from qwerty keyboard, e.g. qwer";
            leaf characters {
              type Aaa-pass-policy-restrict-consecutive-qwerty-keyboard-characters;
              mandatory true;
              description
                "Number of consecutivealphanumeric characters
                 from qwerty keyboard that are not allowed";
            }
            leaf cyclic-wrap {
              type empty;
              description
                "Restrict alphanumeric characters on qwerty
                 keyboardfrom cyclic wrapping, e.g. opqw";
            }
          }
          container english-alphabet {
            presence "Indicates a english-alphabet node is configured.";
            description
              "Restrict consecutive letters from English
               alphabet, e.g. abcd";
            leaf characters {
              type Aaa-pass-policy-restrict-consecutive-english-alphabet;
              mandatory true;
              description
                "Number of consecutive Englishletters that
                 are not allowed";
            }
            leaf cyclic-wrap {
              type empty;
              description
                "Restrict English letters from cyclic
                 wrapping, e.g. yzab ";
            }
          }
        }
        leaf restrict-password-advanced {
          type empty;
          description
            "Imposes advanced constraints on new password";
        }
        leaf lower-case {
          type Aaa-pass-policy-case-length;
          description
            "Number of lower-case characters";
        }
        leaf restrict-password-reverse {
          type empty;
          description
            "Restrict usage of reversed old password as new
             password";
        }
        leaf upper-case {
          type Aaa-pass-policy-case-length;
          description
            "Number of upper-case characters";
        }
        leaf max-length {
          type Aaa-pass-policy-length;
          description
            "Maximum length of the password";
        }
        leaf restrict-old-count {
          type Aaa-pass-policy-restrict-old-count;
          description
            "Number of old passwords to be considered for
             new password check";
        }
        leaf restrict-username-reverse {
          type empty;
          description
            "Restrict usage of reversed username as
             passwordRestrict associated username to be
             used as password";
        }
        leaf min-char-change {
          type Aaa-pass-policy-case-length;
          description
            "Number of characters change required between
             old and new passwords";
        }
        leaf special-char {
          type Aaa-pass-policy-case-length;
          description
            "Number of special characters";
        }
        leaf numeric {
          type Aaa-pass-policy-case-length;
          description
            "Number of numeric characters";
        }
        leaf restrict-username {
          type empty;
          description
            "Restrict associated username to be used as
             password";
        }
        leaf max-char-repetition {
          type Aaa-pass-policy-char-repeat-length;
          description
            "Number of times a character can repeat
             consecutively in new password";
        }
        leaf min-length {
          type Aaa-pass-policy-length;
          description
            "Minimum length of the password";
        }
        leaf authen-max-attempts {
          type Aaa-pass-policy-authen-attempts;
          description
            "Number of maximum authentication attempts";
        }
        leaf name {
          type xr:Cisco-ios-xr-string {
            length "1..252";
          }
          description
            "Password Policy name";
        }
      }
    }
  }
  augment "/a1:aaa" {
    description
      "This augment extends the configuration data of
       'Cisco-IOS-XR-aaa-lib-cfg'";
    container server-groups {
      description
        "AAA group definitions";
    }
  }
  augment "/a1:aaa" {
    description
      "This augment extends the configuration data of
       'Cisco-IOS-XR-aaa-lib-cfg'";
    container logging-table {
      description
        "Logging AAA messages";
      container account-logging {
        description
          "Logging AAA accounting messages";
        container disable-services {
          description
            "Disable logging (syslog) for accounting
             messages.";
          leaf acctz {
            type boolean;
            description
              "Disable logging for acctz messages.";
          }
          leaf netconf {
            type boolean;
            description
              "Disable logging for netconf messages.";
          }
          leaf cli {
            type boolean;
            description
              "Disable logging for CLI messages.";
          }
        }
      }
    }
  }
  augment "/a1:aaa" {
    description
      "This augment extends the configuration data of
       'Cisco-IOS-XR-aaa-lib-cfg'";
    leaf default-taskgroup {
      type string;
      description
        "This class is used for setting the default
         taskgroup to be used for remote server
         authentication";
    }
  }
  augment "/a1:aaa" {
    description
      "This augment extends the configuration data of
       'Cisco-IOS-XR-aaa-lib-cfg'";
    leaf admin-accounting {
      type string;
      description
        "This class is used to enable/disable
         admin-accounting";
    }
  }
  augment "/a1:aaa" {
    description
      "This augment extends the configuration data of
       'Cisco-IOS-XR-aaa-lib-cfg'";
    container usernames {
      description
        "Configure local usernames";
      list username {
        key "ordering-index name";
        description
          "Local username";
        container secret {
          description
            "Specify the secret for the user";
          leaf type {
            type Aaa-password;
            description
              "Password type";
          }
          leaf secret5 {
            type xr:Md5-password;
            description
              "Not Supported";
          }
          leaf secret8 {
            when "../type = 'type8'" {
              description
                "../Type = Type8";
            }
            type xr:Type8-password;
            description
              "Type 8 password";
          }
          leaf secret9 {
            when "../type = 'type9'" {
              description
                "../Type = Type9";
            }
            type xr:Type9-password;
            description
              "Type 9 password";
          }
          leaf secret10 {
            when "../type = 'type10'" {
              description
                "../Type = Type10";
            }
            type xr:Type10-password;
            description
              "Type 10 password";
          }
        }
        container usergroup-under-usernames {
          description
            "Specify the usergroup to which this user
             belongs";
          list usergroup-under-username {
            key "name";
            description
              "Name of the usergroup";
            leaf name {
              type xr:Cisco-ios-xr-string;
              description
                "Name of the usergroup";
            }
          }
        }
        leaf login-history {
          type Aaa-login-history;
          description
            "To display previous login details after login
             is successful.";
        }
        leaf password {
          type xr:Type10-password;
          description
            "Specify the password for the user";
        }
        leaf directory {
          type string {
            length "1..512";
          }
          description
            "Specify the directory for the user";
        }
        leaf shell-type {
          type string {
            length "1..32";
          }
          description
            "Specify the shell-type for the user";
        }
        leaf policy {
          type xr:Cisco-ios-xr-string {
            length "1..252";
          }
          description
            "Mention Secret policy for the user";
        }
        leaf ordering-index {
          type uint32;
          description
            "This is used to sort the users in the order of
             precedence";
        }
        leaf name {
          type string;
          description
            "Username";
        }
      }
    }
  }
  augment "/a1:aaa" {
    description
      "This augment extends the configuration data of
       'Cisco-IOS-XR-aaa-lib-cfg'";
    container taskgroups {
      description
        "Specify a taskgroup to inherit from";
      list taskgroup {
        key "name";
        description
          "Taskgroup name";
        container taskgroup-under-taskgroups {
          description
            "Specify a taskgroup to inherit from";
          list taskgroup-under-taskgroup {
            key "name";
            description
              "Name of the task group to include";
            leaf name {
              type xr:Cisco-ios-xr-string;
              description
                "Name of the task group to include";
            }
          }
        }
        container tasks {
          description
            "Specify task IDs to be part of this group";
          list task {
            key "type task-id";
            description
              "Task ID to be included";
            leaf type {
              type Aaa-locald-task-class;
              description
                "This specifies the operation permitted for
                 this task eg: read/write/execute/debug";
            }
            leaf task-id {
              type Aaa-locald-task-id;
              description
                "Task ID to which permission is to be granted
                 (please use class AllTasks to get a list of
                 valid task IDs)";
            }
          }
        }
        leaf description {
          type string {
            length "1..800";
          }
          description
            "Description for the task group";
        }
        leaf name {
          type string;
          description
            "Taskgroup name";
        }
      }
    }
  }
  augment "/a1:aaa" {
    description
      "This augment extends the configuration data of
       'Cisco-IOS-XR-aaa-lib-cfg'";
    container usergroups {
      description
        "Specify a Usergroup to inherit from";
      list usergroup {
        key "name";
        description
          "Usergroup name";
        container taskgroup-under-usergroups {
          description
            "Task group associated with this group";
          list taskgroup-under-usergroup {
            key "name";
            description
              "Name of the task group";
            leaf name {
              type xr:Cisco-ios-xr-string;
              description
                "Name of the task group";
            }
          }
        }
        container usergroup-under-usergroups {
          description
            "User group to be inherited by this group";
          list usergroup-under-usergroup {
            key "name";
            description
              "Name of the user group";
            leaf name {
              type xr:Cisco-ios-xr-string;
              description
                "Name of the user group";
            }
          }
        }
        leaf description {
          type string {
            length "1..800";
          }
          description
            "Description for the user group";
        }
        leaf name {
          type string;
          description
            "Usergroup name";
        }
      }
    }
  }
  augment "/a1:aaa" {
    description
      "This augment extends the configuration data of
       'Cisco-IOS-XR-aaa-lib-cfg'";
    leaf display-login-failed-users {
      type empty;
      description
        "Display username in syslog after failure login
         attempt.";
    }
  }
  augment "/a1:aaa" {
    description
      "This augment extends the configuration data of
       'Cisco-IOS-XR-aaa-lib-cfg'";
    container spiffe-users {
      description
        "AAA username map-to SPIFFE ID";
      list spiffe-user {
        key "username spiffe-id";
        description
          "Username to be mapped with spiffe Id";
        leaf username {
          type string;
          description
            "Configure username to map with SPIFFE ID";
        }
        leaf spiffe-id {
          type string;
          description
            "Configured SPIFFE Id";
        }
      }
    }
  }
  augment "/a1:aaa" {
    description
      "This augment extends the configuration data of
       'Cisco-IOS-XR-aaa-lib-cfg'";
    leaf enable-certificate-authentication {
      type empty;
      description
        "Enable certificate based authentication for
         TACACS+ users. Mandates exec authorization with
         TACACS+";
    }
  }
}
