module Cisco-IOS-XR-um-ncs1k-hw-module-ptp-cfg {
  namespace "http://cisco.com/ns/yang/Cisco-IOS-XR-um-ncs1k-hw-module-ptp-cfg";
  prefix um-ncs1k-hw-module-ptp-cfg;

  import Cisco-IOS-XR-types {
    prefix xr;
  }
  import Cisco-IOS-XR-um-location-cfg {
    prefix location;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ncs1k-hw-module-ptp package configuration.
     
     This YANG module augments the
     modules with configuration data.
     
     Copyright (c) 2025 by Cisco Systems, Inc.
     All rights reserved.";

  revision 2025-04-19 {
    description
      "Initial release";
    semver:module-version "1.0.0";
  }

  grouping LOCATION-BODY {
    description
      "Grouping for location body";
    container hw-module {
      description
        "Configure h/w module";
      container ptps {
        description
          "PTP port ";
        list ptp {
          key "ptp-id";
          description
            "PTP port ";
          leaf ptp-id {
            type uint32 {
              range "0..1" {
                description
                  "Enter PTP port number 0 / 1";
              }
            }
            description
              "PTP port ";
          }
          container port-mode {
            description
              "Port mode configuration";
            container udc {
              description
                "Convert PTP port to UDC";
              container attach {
                description
                  "Attach OSC port of LC";
                leaf interface {
                  type xr:Interface-name {
                    pattern "GigabitEthernet.*";
                  }
                  description
                    "Fully qualified node location specification";
                }
              }
            }
          }
        }
      }
    }
  }

  augment "/location:locations/location:location" {
    description
      "Augmenting location for hw-module";
    uses LOCATION-BODY;
  }
  augment "/location:locations/location:preconfigured-location" {
    description
      "Augmenting location for hw-module";
    uses LOCATION-BODY;
  }
}
