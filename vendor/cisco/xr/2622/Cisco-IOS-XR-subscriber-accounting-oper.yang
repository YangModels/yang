module Cisco-IOS-XR-subscriber-accounting-oper {
  namespace "http://cisco.com/ns/yang/Cisco-IOS-XR-subscriber-accounting-oper";
  prefix subscriber-accounting-oper;

  import Cisco-IOS-XR-types {
    prefix xr;
  }
  import cisco-semver {
    prefix semver;
  }
  include Cisco-IOS-XR-subscriber-accounting-oper-sub1 {
    revision-date 2026-08-23;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR subscriber-accounting package operational data.
     
     This module contains definitions
     for the following management objects:
       subscriber-accounting: Subscriber accounting operational data
     
     Copyright (c) 2013-2026 by Cisco Systems, Inc.
     All rights reserved.";

  revision 2026-08-23 {
    description
      "Added customer-visible SRG subscriber consistency and SADB query failure counters.
       2025-03-25
         Updated timestamp data type from unit32 to unit64
       2024-05-19
         Added accounting flag for service and session feature
       2023-12-04
         Added support for feature accounting config status per subscriber interface in srg summary.
       2022-03-16
         Added support for srg group id and transient role per access interface in srg summary.";
    semver:module-version "2.1.0";
  }
  revision 2021-02-10 {
    description
      "New cli added to list accouting statistics for all subscribers";
    semver:module-version "2.0.0";
  }
  revision 2019-12-16 {
    description
      "Fixed for service acct stats i.e leaf nodes are deleted for session accounting stats from service acct stats bag and maintained unique stats for session and service accounting.";
    semver:module-version "2.0.0";
  }
  revision 2019-04-05 {
    description
      "Establish semantic version baseline.";
    semver:module-version "1.0.1";
  }
  revision 2018-10-30 {
    description
      "Fixed for CSCvm83576.";
  }
  revision 2017-09-07 {
    description
      "Fixed type translation error.";
  }
  revision 2015-11-09 {
    description
      "IOS XR 6.0 revision.";
  }

  container subscriber-accounting {
    config false;
    description
      "Subscriber accounting operational data";
    container nodes {
      description
        "Subscriber accounting operational data for a
         particular location";
      list node {
        key "node-id";
        description
          "Location. For example, 0/1/CPU0";
        container subscriber-accounting-session-features {
          description
            "Subscriber accounting session feature data";
          list subscriber-accounting-session-feature {
            key "sub-label";
            description
              "Display accounting session features by unique
               subscriber label";
            leaf sub-label {
              type uint32;
              description
                "Unique subscriber label";
            }
            uses ACCT-MA-SESSION-FEATURES;
          }
        }
        container subscriber-accounting-summary {
          description
            "Display subscriber accounting summary data";
          uses ACCT-MA-FEATURE-SUMMARY;
        }
        container subscriber-accounting-flow-features {
          description
            "Subscriber accounting flow feature data";
          list subscriber-accounting-flow-feature {
            key "class-label";
            description
              "Display accounting flow features by unique
               subscriber label";
            leaf class-label {
              type uint32;
              description
                "Unique subscriber class label";
            }
            uses ACCT-MA-FLOW-FEATURES;
          }
        }
        container subscriber-accounting-srg-features {
          description
            "Subscriber accounting SRG feature data";
          list subscriber-accounting-srg-feature {
            key "interface-name";
            description
              "Display accounting SRG features by unique
               access interface-name";
            leaf interface-name {
              type xr:Interface-name;
              description
                "Interface name";
            }
            uses ACCT-MA-SRG-STATS;
          }
        }
        leaf node-id {
          type xr:Node-id;
          description
            "The node id to filter on. For example,
             0/1/CPU0";
        }
      }
    }
  }
}
