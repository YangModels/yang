module Cisco-IOS-XR-lns-ea-oper {
  namespace "http://cisco.com/ns/yang/Cisco-IOS-XR-lns-ea-oper";
  prefix lns-ea-oper;

  import Cisco-IOS-XR-types {
    prefix xr;
  }
  import cisco-semver {
    prefix semver;
  }
  include Cisco-IOS-XR-lns-ea-oper-sub1 {
    revision-date 2019-04-05;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR lns-ea package operational data.
     
     This module contains definitions
     for the following management objects:
       lns-ea: LNS Ea data
     
     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  container lns-ea {
    config false;
    description
      "LNS Ea data";
    container nodes {
      description
        "LNS_EA list of nodes";
      list node {
        key "node-name";
        description
          "LNS-EA operational data for a particular node";
        container interface-ids {
          description
            "LNS interface info";
          list interface-id {
            key "interface-name";
            description
              "LNS interface info";
            leaf interface-name {
              type xr:Interface-name;
              description
                "Interface Name";
            }
            uses LNS-EA-INTERFACE-INFO;
          }
        }
        container parent-interface-ids {
          description
            "LNS parent interface info";
          list parent-interface-id {
            key "parent-interface-name";
            description
              "LNS parent interface info";
            leaf parent-interface-name {
              type xr:Interface-name;
              description
                "Interface Name";
            }
            uses LNS-EA-PARENT-INTERFACE-INFO;
          }
        }
        leaf node-name {
          type xr:Node-id;
          description
            "Node name";
        }
      }
    }
  }
}
