module Cisco-IOS-XR-igp-topodb-v3-oper {
  namespace "http://cisco.com/ns/yang/Cisco-IOS-XR-igp-topodb-v3-oper";
  prefix igp-topodb-v3-oper;

  import Cisco-IOS-XR-types {
    prefix xr;
  }
  import cisco-semver {
    prefix semver;
  }
  include Cisco-IOS-XR-igp-topodb-v3-oper-sub1 {
    revision-date 2025-08-21;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR igp-topodb-v3 package operational data.
     
     This module contains definitions
     for the following management objects:
       topo-db-v3: Open Topology Database v3 library operational data
     
     Copyright (c) 2013-2025 by Cisco Systems, Inc.
     All rights reserved.";

  revision 2025-08-21 {
    description
      "Adding ospfv3 support";
    semver:module-version "1.0.0";
  }
  revision 2019-04-05 {
    description
      "Establish semantic version baseline.";
  }
  revision 2015-11-09 {
    description
      "IOS XR 6.0 revision.";
  }

  container topo-db-v3 {
    config false;
    description
      "Open Topology Database v3 library operational
       data";
    container topo-db-process-v3s {
      description
        "Table for each process using topology library";
      list topo-db-process-v3 {
        key "process-name";
        description
          "Operational data for a particular process";
        container topology-v3-prefixes {
          description
            "Container for Topology prefix information";
          list topology-v3-prefix {
            key "topo-vrf-name";
            description
              "Topology prefix information";
            leaf topo-vrf-name {
              type xr:Cisco-ios-xr-string;
              description
                "VRF Name";
            }
            uses OTLIB-V3-SHOW-INSTANCE;
          }
        }
        container topology-v3s {
          description
            "Container for Topology information";
          list topology-v3 {
            key "topo-vrf-name";
            description
              "Topology information";
            leaf topo-vrf-name {
              type xr:Cisco-ios-xr-string;
              description
                "VRF Name";
            }
            uses OTLIB-V3-SHOW-INSTANCE;
          }
        }
        container topology-v3-summaries {
          description
            "Container for Topology summary information";
          list topology-v3-summary {
            key "topo-vrf-name";
            description
              "Topology summary information";
            leaf topo-vrf-name {
              type xr:Cisco-ios-xr-string;
              description
                "VRF Name";
            }
            uses OTLIB-V3-SHOW-INST-SUMMARY;
          }
        }
        leaf process-name {
          type xr:Cisco-ios-xr-string;
          description
            "Process name";
        }
      }
    }
  }
}
