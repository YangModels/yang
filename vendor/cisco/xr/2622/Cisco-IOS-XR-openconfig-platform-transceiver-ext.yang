module Cisco-IOS-XR-openconfig-platform-transceiver-ext {
  namespace "http://cisco.com/ns/yang/Cisco-IOS-XR-openconfig-platform-transceiver-ext";
  prefix oc-opt-trans-ext;

  import ietf-yang-types {
    prefix yang;
  }
  import openconfig-platform {
    prefix oc-platform;
  }
  import openconfig-platform-transceiver {
    prefix oc-transceiver;
  }
  import openconfig-platform-types {
    prefix oc-platform-types;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module is an extension of optical transceiver model
      and contains the definition of extended parameters for Physical
      Channels in order to add the support of per lane FEC configuration and Performance monitoring.
     
      This module contains definitions for the following management objects:
      FEC Parameters
     
      Copyright (c) 2023-2024 by Cisco Systems, Inc.
      All rights reserved.";

  revision 2023-01-30 {
    description
      "Initial version of oc transceiver extended model";
    reference "0.1.0";
  }

  grouping transceiver-physical-channel-ext-info {
    description
      "FEC parameters for physical channel";
    leaf fec-mode {
      type identityref {
        base oc-platform-types:FEC_MODE_TYPE;
      }
      description
        "The FEC mode indicates the mode of operation for the
                transceiver's physical channel's FEC. This defines typical operational modes
                and does not aim to specify more granular FEC capabilities.";
    }
    leaf fec-uncorrectable-words {
      type yang:counter64;
      description
        "The number of words that were uncorrectable by the FEC";
    }
    leaf fec-corrected-words {
      type yang:counter64;
      description
        "The number of words that were corrected by the FEC";
    }
  }

  augment "/oc-platform:components/oc-platform:component/oc-transceiver:transceiver/oc-transceiver:physical-channels/oc-transceiver:channel" {
    description
      "This augment extends the operational data of
       'oc-transceiver:physical-channel-top'";
    container extended {
      description
        "Enclosing container for the state fec parameters for extended model";
      container state {
        config false;
        description
          "Extended Operational parameters";
        leaf index {
          type uint16 {
            range "0..max";
          }
          description
            "Index of the physical channnel or lane within a physical
                 \t\tclient port";
        }
        uses transceiver-physical-channel-ext-info;
      }
    }
  }
}
