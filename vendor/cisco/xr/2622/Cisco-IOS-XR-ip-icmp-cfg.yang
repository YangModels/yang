module Cisco-IOS-XR-ip-icmp-cfg {
  namespace "http://cisco.com/ns/yang/Cisco-IOS-XR-ip-icmp-cfg";
  prefix ip-icmp-cfg;

  import ietf-inet-types {
    prefix inet;
  }
  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ip-icmp package configuration.
     
     This module contains definitions
     for the following management objects:
       icmp: IP ICMP configuration data
     
     Copyright (c) 2013-2026 by Cisco Systems, Inc.
     All rights reserved.";

  revision 2026-06-22 {
    description
      "Added traceroute-filter schema and restricted VRF leaf length to 32 characters.";
    semver:module-version "2.1.0";
  }
  revision 2020-08-10 {
    description
      "IOS XR 7.3.1 revision.";
    semver:module-version "2.0.0";
  }
  revision 2019-04-05 {
    description
      "Establish semantic version baseline.";
    semver:module-version "1.0.0";
  }
  revision 2017-06-08 {
    description
      "IOS XR 6.3.1 revision.";
  }
  revision 2015-11-09 {
    description
      "IOS XR 6.0 revision.";
  }

  typedef Source-policy {
    type enumeration {
      enum "vrf" {
        value 1;
        description
          "Set Source Selection Policy to vrf";
      }
      enum "rfc" {
        value 2;
        description
          "Set Source Selection Policy to rfc";
      }
    }
    description
      "Source policy";
  }

  grouping SOURCE {
    description
      "Common node of ipv4, ipv6";
    container source {
      description
        "IP ICMP Source Address Selection Policy";
      leaf source-address-policy {
        type Source-policy;
        description
          "Configure Source Address Policy";
      }
    }
  }

  grouping TRACEROUTE-FILTER-ENTRY {
    description
      "Common node of traceroute-filter-ipv4udp,
       traceroute-filter-ipv4tcp,
       traceroute-filter-ipv6udp,
       traceroute-filter-ipv6tcp";
    list traceroute-filter-entry {
      key "filter-id";
      description
        "Traceroute filter entry";
      leaf filter-id {
        type uint32 {
          range "1..256";
        }
        description
          "Unique ID for the policy config";
      }
      leaf filter-id-value {
        type uint32 {
          range "1..256";
        }
        mandatory true;
        description
          "Unique ID for the policy config";
      }
      leaf protocol {
        type string {
          length "1..15";
        }
        mandatory true;
        description
          "Traceroute protocol";
      }
      leaf vrf-name {
        type xr:Cisco-ios-xr-string {
          length "1..32";
        }
        mandatory true;
        description
          "VRF name";
      }
      leaf source-address {
        type string;
        mandatory true;
        description
          "Source address for traceroute";
      }
      leaf destination-address {
        type string;
        mandatory true;
        description
          "Destination address for traceroute";
      }
      leaf source-port-start {
        type inet:port-number;
        mandatory true;
        description
          "Source port start of range";
      }
      leaf source-port-end {
        type inet:port-number;
        mandatory true;
        description
          "Source port end of range";
      }
      leaf destination-port-start {
        type uint32 {
          range "33435..33535";
        }
        mandatory true;
        description
          "Destination port start of range";
      }
      leaf destination-port-end {
        type uint32 {
          range "33435..33535";
        }
        mandatory true;
        description
          "Destination port end of range";
      }
    }
  }

  container icmp {
    description
      "IP ICMP configuration data";
    container ipv6 {
      description
        "IP Protocol Type";
      uses SOURCE;
    }
    container traceroute-filter {
      description
        "Traceroute filter configuration";
      container traceroute-filter-ipv4 {
        description
          "IPv4 traceroute filter configuration";
        container traceroute-filter-ipv4udp {
          description
            "IPv4 UDP traceroute filter configuration";
          uses TRACEROUTE-FILTER-ENTRY;
        }
        container traceroute-filter-ipv4tcp {
          description
            "IPv4 TCP traceroute filter configuration";
          uses TRACEROUTE-FILTER-ENTRY;
        }
      }
      container traceroute-filter-ipv6 {
        description
          "IPv6 traceroute filter configuration";
        container traceroute-filter-ipv6udp {
          description
            "IPv6 UDP traceroute filter configuration";
          uses TRACEROUTE-FILTER-ENTRY;
        }
        container traceroute-filter-ipv6tcp {
          description
            "IPv6 TCP traceroute filter configuration";
          uses TRACEROUTE-FILTER-ENTRY;
        }
      }
    }
    container ipv4 {
      description
        "IP Protocol Type";
      container rate-limit {
        description
          "Set ratelimit of ICMP packets";
        container unreachable {
          description
            "Set unreachable ICMP packets ratelimit";
          leaf rate {
            type uint32 {
              range "0..4294967295";
            }
            description
              "Rate Limit of Unreachable ICMP packets";
          }
          leaf fragmentation {
            type uint32 {
              range "0..4294967295";
            }
            description
              "Rate Limit of Unreachable DF packets";
          }
        }
      }
      uses SOURCE;
    }
  }
}
