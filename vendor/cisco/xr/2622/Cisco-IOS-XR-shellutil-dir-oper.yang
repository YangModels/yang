module Cisco-IOS-XR-shellutil-dir-oper {
  namespace "http://cisco.com/ns/yang/Cisco-IOS-XR-shellutil-dir-oper";
  prefix shellutil-dir-oper;

  import Cisco-IOS-XR-types {
    prefix xr;
  }
  import cisco-semver {
    prefix semver;
  }
  include Cisco-IOS-XR-shellutil-dir-oper-sub1 {
    revision-date 2026-05-29;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR shellutil-dir package operational data.
     
     This module contains definitions
     for the following management objects:
       dir: List of directories
     
     Copyright (c) 2013-2026 by Cisco Systems, Inc.
     All rights reserved.";

  revision 2026-05-29 {
    description
      "Aligned shellutil dir operational schema task-name with filesystem CLI task.";
    semver:module-version "1.0.0";
  }
  revision 2020-10-14 {
    description
      "Initial version.";
    semver:module-version "1.0.0";
  }
  revision 2019-04-05 {
    description
      "Establish semantic version baseline.";
  }
  revision 2015-11-09 {
    description
      "IOS XR 6.0 revision.";
  }

  container dir {
    config false;
    description
      "List of directories";
    container nodes {
      description
        "List of nodes";
      list node {
        key "node-name";
        description
          "Node ID";
        container dir-paths {
          description
            "Directory info";
          list dir-path {
            key "name";
            description
              "Directory path";
            leaf name {
              type string;
              description
                "PATH";
            }
            uses SHELLUTIL-DIR;
          }
        }
        container dir-path-recs {
          description
            "Directory info with recusive option";
          list dir-path-rec {
            key "name";
            description
              "Directory path with recursive option";
            leaf name {
              type string;
              description
                "PATHREC";
            }
            uses SHELLUTIL-DIR;
          }
        }
        leaf node-name {
          type xr:Node-id;
          description
            "Node name";
        }
      }
    }
  }
}
