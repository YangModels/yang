module Cisco-IOS-XR-um-environment-cfg {
  namespace "http://cisco.com/ns/yang/Cisco-IOS-XR-um-environment-cfg";
  prefix um-environment-cfg;

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR environment package configuration.
     
     This YANG module augments the
     modules with configuration data.
     
     Copyright (c) 2020-2025 by Cisco Systems, Inc., and/or its affiliates.
     All rights reserved.";

  revision 2026-07-22 {
    description
      "Added control sensor alarm disable support.";
    semver:module-version "1.2.0";
  }
  revision 2022-02-22 {
    description
      "Added alarm-contact support";
    semver:module-version "1.1.0";
  }
  revision 2020-12-14 {
    description
      "Initial release";
    semver:module-version "1.0.0";
  }

  feature altitude {
    description
      "altitude";
  }

  feature alarm-contact {
    description
      "alarm-contact supported";
  }

  container environment {
    description
      "Global environment configuration commands";
    leaf altitude {
      if-feature "altitude";
      type uint32 {
        range "0..4000" {
          description
            "meters";
        }
      }
      description
        "Altitude of the chassis in meters";
    }
    container air-filter {
      description
        "chassis air-filter status";
      container replaced {
        description
          "air-filter replaced date";
        leaf date {
          type xr:Cisco-ios-xr-string {
            length "1..800" {
              description
                "CCYY-MM-DD format";
            }
          }
          description
            "";
        }
      }
    }
    leaf min-fan-speed {
      type uint32 {
        range "0..100" {
          description
            "pwm";
        }
      }
      description
        "Min default fan speed in PWM (the speed cannot go lower, but can go higher based on environmental conditions)";
    }
    container chassis-door-alarm {
      description
        "Control chassis door alarm";
      container enable {
        presence "Indicates a enable node is configured.";
        description
          "Enable chassis door alarm";
      }
    }
    container control-sensor-alarm {
      description
        "Control_Sensor alarm configuration";
      container disable {
        presence "Indicates a disable node is configured.";
        description
          "Disable Control_Sensor alarms and related actions";
      }
    }
    container alarm-contact {
      if-feature "alarm-contact";
      description
        "Control the alarm-contact behavior";
      container alarm-contact-numbers {
        description
          "alarm-contact number";
        list alarm-contact-number {
          key "alarm-contact-number-id";
          description
            "alarm-contact number";
          leaf alarm-contact-number-id {
            type uint32 {
              range "1..256" {
                description
                  "alarm-contact number";
              }
            }
            description
              "alarm-contact number";
          }
          container severity {
            description
              "The severity of the alarm minor|major|critical";
            container minor {
              must "not(../major or ../critical)";
              presence "Indicates a minor node is configured.";
              description
                "Alarm type minor";
            }
            container major {
              must "not(../minor or ../critical)";
              presence "Indicates a major node is configured.";
              description
                "Alarm type major";
            }
            container critical {
              must "not(../minor or ../major)";
              presence "Indicates a critical node is configured.";
              description
                "Alarm type critical";
            }
          }
          leaf description {
            type string {
              length "1..40" {
                description
                  "Alarm Description (max 40 characters)";
              }
            }
            description
              "The description of the alarm";
          }
          container trigger {
            description
              "Whether to trigger on open or closed contact. open|closed";
            container open {
              must "not(../closed)";
              presence "Indicates a open node is configured.";
              description
                "Trigger on contact open";
            }
            container closed {
              must "not(../open)";
              presence "Indicates a closed node is configured.";
              description
                "Trigger on contact closed";
            }
          }
        }
      }
      container all {
        presence "Indicates a all node is configured.";
        description
          "set options for all pins";
        container severity {
          description
            "The severity of the alarm minor|major|critical";
          container minor {
            must "not(../major or ../critical)";
            presence "Indicates a minor node is configured.";
            description
              "Alarm type minor";
          }
          container major {
            must "not(../minor or ../critical)";
            presence "Indicates a major node is configured.";
            description
              "Alarm type major";
          }
          container critical {
            must "not(../minor or ../major)";
            presence "Indicates a critical node is configured.";
            description
              "Alarm type critical";
          }
        }
        leaf description {
          type string {
            length "1..40" {
              description
                "Alarm Description (max 40 characters)";
            }
          }
          description
            "The description of the alarm";
        }
        container trigger {
          description
            "Whether to trigger on open or closed contact. open|closed";
          container open {
            must "not(../closed)";
            presence "Indicates a open node is configured.";
            description
              "Trigger on contact open";
          }
          container closed {
            must "not(../open)";
            presence "Indicates a closed node is configured.";
            description
              "Trigger on contact closed";
          }
        }
      }
    }
  }
}
