module Cisco-IOS-XR-odugrpmp-cfg {
  namespace "http://cisco.com/ns/yang/Cisco-IOS-XR-odugrpmp-cfg";
  prefix odugrpmp-cfg;

  import cisco-semver {
    prefix semver;
  }
  import Cisco-IOS-XR-ifmgr-cfg {
    prefix a1;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR odugrpmp package configuration.
     
     This YANG module augments the
       Cisco-IOS-XR-ifmgr-cfg
     module with configuration data.
     
     Copyright (c) 2013-2023 by Cisco Systems, Inc.
     All rights reserved.";

  revision 2023-06-09 {
    description
      "Support added to configure protection attributes Wait-to-Restore and Hold-off-timer.";
    semver:module-version "1.0.0";
  }
  revision 2019-04-05 {
    description
      "Establish semantic version baseline.";
  }
  revision 2015-11-09 {
    description
      "IOS XR 6.0 revision.";
  }

  typedef Odu-grp-mp-signal {
    type enumeration {
      enum "ethernet" {
        value 1;
        description
          "ETHERNET Port Mode Type";
      }
      enum "sonet" {
        value 2;
        description
          "SONET Port Mode Type";
      }
      enum "fc" {
        value 3;
        description
          "FC Port Mode Type";
      }
      enum "otn" {
        value 4;
        description
          "OTN Port Mode Type";
      }
      enum "sdh" {
        value 5;
        description
          "SDH Port Mode Type";
      }
    }
    description
      "Odu grp mp signal";
  }

  typedef Odu-grp-mp-odu {
    type enumeration {
      enum "odu1" {
        value 1;
        description
          "add odu1";
      }
      enum "odu2" {
        value 2;
        description
          "add odu2";
      }
      enum "odu3" {
        value 3;
        description
          "add odu3";
      }
      enum "odu4" {
        value 4;
        description
          "add odu4";
      }
      enum "odu0" {
        value 10;
        description
          "add odu0";
      }
      enum "odu2e" {
        value 11;
        description
          "add odu2e";
      }
      enum "odu-flex" {
        value 22;
        description
          "add odu-flex";
      }
      enum "odu1e" {
        value 23;
        description
          "add odu1e";
      }
      enum "odu1f" {
        value 24;
        description
          "add odu1f";
      }
      enum "odu2f" {
        value 25;
        description
          "add odu2f";
      }
      enum "odu3e1" {
        value 26;
        description
          "add odu3e1";
      }
      enum "odu3e2" {
        value 27;
        description
          "add odu3e2";
      }
      enum "oduc2" {
        value 38;
        description
          "add oduc2";
      }
      enum "oduc4" {
        value 40;
        description
          "add oduc4";
      }
      enum "oduc1" {
        value 41;
        description
          "add oduc1";
      }
      enum "oduc3" {
        value 42;
        description
          "add oduc3";
      }
    }
    description
      "Odu grp mp odu";
  }

  typedef Odu-grp-mp-protection-mode {
    type enumeration {
      enum "nonrevertive" {
        value 0;
        description
          "Non Revertive Protection Mode Type";
      }
      enum "revertive" {
        value 1;
        description
          "Revertive Protection Mode Type";
      }
    }
    description
      "Odu grp mp protection mode";
  }

  augment "/a1:interface-configurations/a1:interface-configuration" {
    description
      "This augment extends the configuration data of
       'Cisco-IOS-XR-ifmgr-cfg'";
    list odu-group-mp {
      key "signal-value odu-type num-trib-slot-odu";
      description
        "Configures the protection switch on an ODU group
         controller pertaining to the management plane";
      container protection-attributes {
        description
          "Configuration of Protection Attributes for Odu
           Group MP Controller";
        container protection-mode {
          description
            "Types of Protection Mode";
          container wait-to-restore-time {
            presence "Contains mandatory nodes that used to set default values";
            description
              "Configure wait-to-restore timer";
            leaf protection-mode-type {
              type Odu-grp-mp-protection-mode;
              description
                "Protection Mode Type";
            }
            leaf timer-value {
              when "../protection-mode-type = 'revertive'" {
                description
                  "../ProtectionModeType = REVERTIVE";
              }
              type uint32 {
                range "300..720";
              }
              mandatory true;
              description
                "Value for range of wait-to-restore timer in
                 sec (Default 300 second)";
            }
          }
        }
        container timers {
          description
            "Protection Timers";
          leaf hold-off-time {
            type uint32 {
              range "100..10000";
            }
            description
              "Value for range of hold-off timer (Default 0)
               .Give timer in multiple of 100";
          }
        }
      }
      leaf signal-value {
        type Odu-grp-mp-signal;
        description
          "Client type";
      }
      leaf odu-type {
        type Odu-grp-mp-odu;
        description
          "ODU Type";
      }
      leaf num-trib-slot-odu {
        type uint32;
        description
          "Number of Tributary Slots for Odu,must be set
           to 0 if OduType is not ODU-FLEX";
      }
    }
  }
}
