module Cisco-IOS-XR-pwrmgmt-cfg {
  namespace "http://cisco.com/ns/yang/Cisco-IOS-XR-pwrmgmt-cfg";
  prefix pwrmgmt-cfg;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR pwrmgmt package configuration.
     
     This module contains definitions
     for the following management objects:
       power-management: EnvMon Power Management Config Data
     
     Copyright (c) 2013-2025 by Cisco Systems, Inc.
     All rights reserved.";

  revision 2025-01-16 {
    description
      "IOS XR 25.2.1 revision. Added config support for utilization threshold for the resource power.
       2023-10-24
         IOS XR 24.1.1 revision. Feed redundancy failure protection across all power modules.
       2023-05-23
         IOS XR 7.11.1 revision. Max power capacity configuration to limit power capacity usage.";
    semver:module-version "2.1.0";
  }
  revision 2020-04-14 {
    description
      "IOS XR 7.0.14 revision. Moved action-disable to be valid only for SF-D platforms.";
    semver:module-version "2.0.0";
  }
  revision 2019-04-05 {
    description
      "Establish semantic version baseline.";
    semver:module-version "1.0.0";
  }
  revision 2015-11-09 {
    description
      "IOS XR 6.0 revision.";
  }

  typedef Power-red-feed-mode-enum {
    type enumeration {
      enum "single-fault" {
        value 1;
        description
          "Single Fault";
      }
      enum "dual-fault" {
        value 2;
        description
          "Dual Fault";
      }
    }
    description
      "Power red feed mode enum";
  }

  container power-management {
    description
      "EnvMon Power Management Config Data";
    container pwr-threshold-locations {
      description
        "percent threshold for resource utilization for
         oc";
      list pwr-threshold-location {
        key "location-string";
        description
          "Location for power threshold upper/clear values";
        leaf used-threshold-upper-clear {
          type uint32 {
            range "1..100";
          }
          units "percentage";
          default "40";
          description
            "percent of used power to go below for flag to
             be cleared";
        }
        leaf used-threshold-upper {
          type uint32 {
            range "0..99";
          }
          units "percentage";
          default "50";
          description
            "percent of used power on crossing which flag
             is set";
        }
        leaf location-string {
          type string;
          description
            "Location for power threshold upper/clear
             values";
        }
      }
    }
    leaf max-pwr-capacity {
      type uint32;
      description
        "Configured Max Power Capacity";
    }
    leaf extended-temp {
      type boolean;
      description
        "Config for setting power budget for extended
         temp mode";
    }
    leaf single-feed-mode {
      type boolean;
      description
        "Config for suppressing alarms for missing feed
         supplies";
    }
    leaf red-num-pems {
      type uint32;
      description
        "Number of the redundant PEMS";
    }
    leaf red-feed-mode {
      type Power-red-feed-mode-enum;
      description
        "Power feed redundancy mode. can be single/dual
         fault";
    }
  }
}
