module Cisco-IOS-XR-tpmsvcs-oper {
  namespace "http://cisco.com/ns/yang/Cisco-IOS-XR-tpmsvcs-oper";
  prefix tpmsvcs-oper;

  import Cisco-IOS-XR-types {
    prefix xr;
  }
  import cisco-semver {
    prefix semver;
  }
  include Cisco-IOS-XR-tpmsvcs-oper-sub1 {
    revision-date 2025-02-20;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR tpmsvcs package operational data.
     
     This module contains definitions
     for the following management objects:
       tpm: TPM services operational data
     
     Copyright (c) 2013-2025 by Cisco Systems, Inc.
     All rights reserved.";

  revision 2025-02-20 {
    description
      "Show device info for tpm";
    semver:module-version "1.0.0";
  }
  revision 2019-04-05 {
    description
      "Establish semantic version baseline.";
  }
  revision 2015-11-09 {
    description
      "IOS XR 6.0 revision.";
  }

  container tpm {
    config false;
    description
      "TPM services operational data";
    container nodes {
      description
        "Per Node TPM Services operation data";
      list node {
        key "node";
        description
          "Node Location for TPM services operational data";
        container all {
          description
            "TPM services all information";
          uses TAMSVCS-INFO-ALL;
        }
        container device-info {
          description
            "TPM services device information";
          uses TAMSVCS-DEVICE-INFO;
        }
        container ha-sudi-certs {
          description
            "TPM services HA Sudi Certificates";
          uses TAMSVCS-HA-SUDI-CERTS;
        }
        leaf node {
          type xr:Node-id;
          description
            "Node location";
        }
      }
    }
  }
}
