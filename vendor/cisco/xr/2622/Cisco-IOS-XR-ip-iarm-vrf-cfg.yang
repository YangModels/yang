module Cisco-IOS-XR-ip-iarm-vrf-cfg {
  namespace "http://cisco.com/ns/yang/Cisco-IOS-XR-ip-iarm-vrf-cfg";
  prefix ip-iarm-vrf-cfg;

  import Cisco-IOS-XR-types {
    prefix xr;
  }
  import cisco-semver {
    prefix semver;
  }
  import Cisco-IOS-XR-infra-rsi-cfg {
    prefix a1;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ip-iarm-vrf package configuration.
     
     This YANG module augments the
       Cisco-IOS-XR-infra-rsi-cfg
     module with configuration data.
     
     Copyright (c) 2013-2019 by Cisco Systems, Inc.
     All rights reserved.";

  revision 2019-04-05 {
    description
      "Establish semantic version baseline.";
    semver:module-version "1.0.1";
  }
  revision 2015-11-09 {
    description
      "IOS XR 6.0 revision.";
  }

  grouping INTERFACE {
    description
      "Common node of ipv4, ipv6";
    leaf interface {
      type xr:Interface-name;
      description
        "Default multicast host interface name";
    }
  }

  augment "/a1:vrfs/a1:vrf" {
    description
      "This augment extends the configuration data of
       'Cisco-IOS-XR-infra-rsi-cfg'";
    container multicast-host {
      description
        "Multicast host stack configuration";
      container ipv4 {
        description
          "IPv4 configuration";
        uses INTERFACE;
      }
      container ipv6 {
        description
          "IPv6 configuration";
        uses INTERFACE;
      }
    }
  }
}
