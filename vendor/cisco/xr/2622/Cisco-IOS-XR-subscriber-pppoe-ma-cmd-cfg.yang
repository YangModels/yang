module Cisco-IOS-XR-subscriber-pppoe-ma-cmd-cfg {
  namespace "http://cisco.com/ns/yang/Cisco-IOS-XR-subscriber-pppoe-ma-cmd-cfg";
  prefix subscriber-pppoe-ma-cmd-cfg;

  import cisco-semver {
    prefix semver;
  }
  import Cisco-IOS-XR-ifmgr-cfg {
    prefix a1;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR subscriber-pppoe-ma-cmd package configuration.
     
     This YANG module augments the
       Cisco-IOS-XR-ifmgr-cfg
     module with configuration data.
     
     Copyright (c) 2013-2019 by Cisco Systems, Inc.
     All rights reserved.";

  revision 2019-04-05 {
    description
      "Establish semantic version baseline.";
    semver:module-version "1.0.1";
  }
  revision 2015-11-09 {
    description
      "IOS XR 6.0 revision.";
  }

  augment "/a1:interface-configurations/a1:interface-configuration" {
    description
      "This augment extends the configuration data of
       'Cisco-IOS-XR-ifmgr-cfg'";
    container pppoe {
      description
        "Interface PPPoE configuration data";
      container enable-bba-group {
        presence "Indicates a enable-bba-group node is configured.";
        description
          "Use this BBA-Group to enable PPPoE on this
           interface";
        leaf enable {
          type boolean;
          mandatory true;
          description
            "Enable PPPoE on this interface";
        }
        leaf bba-group-name {
          type string;
          description
            "Name of the BBA-Group";
        }
      }
    }
  }
}
