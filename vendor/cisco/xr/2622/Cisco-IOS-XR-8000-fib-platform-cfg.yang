module Cisco-IOS-XR-8000-fib-platform-cfg {
  namespace "http://cisco.com/ns/yang/Cisco-IOS-XR-8000-fib-platform-cfg";
  prefix xr-8000-fib-platform-cfg;

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR 8000-fib-platform package configuration.
     
     This module contains definitions
     for the following management objects:
       cef: Establish CEF configuration
     
     Copyright (c) 2013-2026 by Cisco Systems, Inc.
     All rights reserved.";

  revision 2026-02-14 {
    description
      "Added cli to control exclusion/inclusion of NVGRE payload fields in hash computation for load balancing
       2025-04-30
         Added options with kobs related to hash seed, hash rotate, extended-entropy for load balancing
       2025-02-04
         Adjust usage info for npu hash rotate from 0-431 to 0-143 for load balancing
       2025-01-10
         Updated usage info for npu hash rotate for load balancing
       2024-11-27
         Added extended range for npu hash rotate for load balancing
       2024-07-21
         Added MPLS non-ip load balancing behavior config
       2024-05-09
         Added npu hash rotate for load balancing
       2024-02-08
         Added platforms container in schema for load-balancing
       2022-06-23
         Added schema for Load balancing user-data configuration
       2022-03-01
         Updated max rotate value of hash rotate to 35";
    semver:module-version "2.0.0";
  }
  revision 2019-04-05 {
    description
      "Establish semantic version baseline.";
    semver:module-version "1.0.0";
  }
  revision 2015-11-09 {
    description
      "IOS XR 6.0 revision.";
  }

  typedef V4-udp {
    type uint32 {
      range "0..35";
    }
    description
      "V4 udp";
  }

  typedef V6-tcp {
    type uint32 {
      range "0..3";
    }
    description
      "V6 tcp";
  }

  typedef V6-udp {
    type uint32 {
      range "0..15";
    }
    description
      "V6 udp";
  }

  typedef Size4 {
    type uint32 {
      range "1..4";
    }
    description
      "Size4";
  }

  typedef V4-tcp {
    type uint32 {
      range "0..23";
    }
    description
      "V4 tcp";
  }

  typedef V4 {
    type uint32 {
      range "0..43";
    }
    description
      "V4";
  }

  typedef V6 {
    type uint32 {
      range "0..23";
    }
    description
      "V6";
  }

  container cef {
    description
      "Establish CEF configuration";
    container platform {
      description
        "Specify platform Load balancing parameters";
      container load-balance {
        description
          "Specify Load balancing algorithm";
        container hash {
          description
            "Specify Hash adjust";
          leaf rotate {
            type uint32 {
              range "1..215";
            }
            description
              "Default value is 0. Count range 1-35. For
               Q200 count range 1-215";
          }
        }
        container fields {
          description
            "additional fields considered for hashing";
          container userdata {
            description
              "specify the offset and size of additional
               packet data to be included in hashing";
            container ipv6-udps {
              description
                "additional data for ipv6 udp packet";
              list ipv6-udp {
                key "location-string";
                description
                  "none";
                container ipv6-udp-hash {
                  description
                    "offset and size for ipv6 udp header";
                  leaf offset {
                    type V6-udp;
                    description
                      "zero-based offset from the end of ipv6
                       udp header";
                  }
                  leaf size {
                    type Size4;
                    units "byte";
                    description
                      "number of bytes considered in hashing";
                  }
                }
                leaf location-string {
                  type xr:Cisco-ios-xr-string;
                  description
                    "ingress card location";
                }
              }
            }
            container ipv4-nontcpudps {
              description
                "additional data for ipv4 non-tcp-udp packet";
              list ipv4-nontcpudp {
                key "location-string";
                description
                  "none";
                container ipv4-hash {
                  description
                    "offset and size for ipv4 nontcpudp header";
                  leaf offset {
                    type V4;
                    description
                      "zero-based offset from the end of ipv4
                       header";
                  }
                  leaf size {
                    type Size4;
                    units "byte";
                    description
                      "number of bytes considered in hashing";
                  }
                }
                leaf location-string {
                  type xr:Cisco-ios-xr-string;
                  description
                    "ingress card location";
                }
              }
            }
            container ipv6-tcps {
              description
                "additional data for ipv6 tcp packet";
              list ipv6-tcp {
                key "location-string";
                description
                  "none";
                container ipv6-tcp-hash {
                  description
                    "offset and size for ipv6 tcp header";
                  leaf offset {
                    type V6-tcp;
                    description
                      "zero-based offset from the end of ipv6
                       tcp header";
                  }
                  leaf size {
                    type Size4;
                    units "byte";
                    description
                      "number of bytes considered in hashing";
                  }
                }
                leaf location-string {
                  type xr:Cisco-ios-xr-string;
                  description
                    "ingress card location";
                }
              }
            }
            container ipv4-udps {
              description
                "additional data for ipv4 udp packet";
              list ipv4-udp {
                key "location-string";
                description
                  "none";
                container ipv4-udp-hash {
                  description
                    "offset and size for ipv4 udp header";
                  leaf offset {
                    type V4-udp;
                    description
                      "zero-based offset from the end of ipv4
                       udp header";
                  }
                  leaf size {
                    type Size4;
                    units "byte";
                    description
                      "number of bytes considered in hashing";
                  }
                }
                leaf location-string {
                  type xr:Cisco-ios-xr-string;
                  description
                    "ingress card location";
                }
              }
            }
            container ipv6-nontcpudps {
              description
                "additional data for ipv6 non-tcp-udp packet";
              list ipv6-nontcpudp {
                key "location-string";
                description
                  "none";
                container ipv6-hash {
                  description
                    "offset and size for ipv6 nontcpudp header";
                  leaf offset {
                    type V6;
                    description
                      "zero-based offset from the end of ipv6
                       header";
                  }
                  leaf size {
                    type Size4;
                    units "byte";
                    description
                      "number of bytes considered in hashing";
                  }
                }
                leaf location-string {
                  type xr:Cisco-ios-xr-string;
                  description
                    "ingress card location";
                }
              }
            }
            container ipv4-tcps {
              description
                "additional data for ipv4 tcp packet";
              list ipv4-tcp {
                key "location-string";
                description
                  "none";
                container ipv4-tcp-hash {
                  description
                    "offset and size for ipv4 tcp header";
                  leaf offset {
                    type V4-tcp;
                    description
                      "zero-based offset from the end of ipv4
                       tcp header";
                  }
                  leaf size {
                    type Size4;
                    units "byte";
                    description
                      "number of bytes considered in hashing";
                  }
                }
                leaf location-string {
                  type xr:Cisco-ios-xr-string;
                  description
                    "ingress card location";
                }
              }
            }
          }
        }
        container instances {
          description
            "Specify Hash adjust per npu";
          list instance {
            key "npu-instance";
            description
              "none";
            leaf npu-instance {
              type uint32;
              description
                "Npu instance to which hash rotate has to be
                 applied";
            }
            list hash-location {
              key "location-string";
              description
                "none";
              leaf npu-spa-seed {
                type uint32 {
                  range "0..65535";
                }
                description
                  "Configure SPA seed value in Hex (0x<value>)";
              }
              leaf npu-ecmp-seed {
                type uint32 {
                  range "0..65535";
                }
                description
                  "Configure ECMP seed value in Hex
                   (0x<value>)";
              }
              leaf npu-rotate {
                type uint32 {
                  range "1..215";
                }
                description
                  "Default value is 0. Count range 1-35. For
                   Q200 count range 1-215";
              }
              leaf location-string {
                type xr:Cisco-ios-xr-string;
                description
                  "ingress card location";
              }
            }
          }
        }
        leaf extended-entropy-auto-global {
          type empty;
          description
            "Q200 only. Automatically select packet header
             fields per router";
        }
        leaf extended-entropy-auto-instance {
          type empty;
          description
            "Q200 only. Automatically select packet header
             fields per NPU instance";
        }
        leaf spa-seed {
          type uint32 {
            range "0..65535";
          }
          description
            "Configure SPA seed value in Hex (0x<value>)";
        }
        leaf auto-instance {
          type empty;
          description
            "automatically generated hash profile per NPU
             instance";
        }
        leaf auto-global {
          type empty;
          description
            "automatically generated hash profile per
             chassis";
        }
        leaf user-extended-entropy {
          type uint32 {
            range "0..255";
          }
          description
            "Q200 only. Specify index of extended entropy
             profile used for hashing(<value>) 0-255";
        }
        leaf ecmp-seed {
          type uint32 {
            range "0..65535";
          }
          description
            "Configure ECMP seed value in Hex (0x<value>)";
        }
      }
    }
    container platform-load-balance {
      description
        "Specify platform Load balancing parameters";
      leaf nvgre-payload-exclude {
        type empty;
        description
          "Exclude NVGRE payload from hash calculation
           (overlay hashing disabled)";
      }
      leaf mpls-hash-non-ip-lbl-only {
        type empty;
        description
          "MPLS label stack and non-IP payload hash method
           to use labels only";
      }
    }
  }
}
