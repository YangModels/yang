submodule Cisco-IOS-XR-cosm-oper-sub1 {
  belongs-to Cisco-IOS-XR-cosm-oper {
    prefix Cisco-IOS-XR-cosm-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR cosm package operational data.
     
     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  grouping COSM-MANAGER-STATUS {
    description
      "COSM Manager status information";
    leaf state {
      type string;
      description
        "Internal state of COSM Manager";
    }
    leaf app-state {
      type string;
      description
        "Application state from AppMgr";
    }
    leaf container-state {
      type string;
      description
        "Container state from AppMgr";
    }
    leaf container-status {
      type string;
      description
        "Container status";
    }
    leaf last-error {
      type string;
      description
        "Last error from AppMgr";
    }
    leaf version {
      type string;
      description
        "COSM Version";
    }
    leaf ha-role {
      type string;
      description
        "HA Role";
    }
  }
}
