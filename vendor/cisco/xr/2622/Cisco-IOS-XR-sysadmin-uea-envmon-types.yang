module Cisco-IOS-XR-sysadmin-uea-envmon-types {
  namespace "http://www.cisco.com/ns/Cisco-IOS-XR-sysadmin-uea-envmon-types";
  prefix envmon-types;

  import tailf-common {
    prefix tailf;
  }
  import Cisco-IOS-XR-sysadmin-types {
    prefix calvados;
  }

  revision 2025-12-16 {
    description
      "Add alternative fan table CLI.";
  }
  revision 2022-08-05 {
    description
      "Add gen2 common low power CLI.";
  }
  revision 2017-11-27 {
    description
      "Add graceful shutdown disable CLI.";
  }
  revision 2017-05-01 {
    description
      "Namespace change to comply with Cisco guidelines on namespace";
  }

  typedef num_pm {
    type uint32 {
      range "0..5";
    }
  }

  grouping fan-speed-group {
    leaf raise-fan-speed {
      type uint32 {
        range "0..100";
      }
      config false;
      tailf:cli-drop-node-name;
    }
  }

  grouping fan-ctrl-optics-group {
    leaf fan-ctrl-optics {
      type uint32 {
        range "0..1";
      }
      config false;
      tailf:cli-drop-node-name;
    }
  }

  grouping vin-uv-shut-group {
    leaf graceful-shutdown {
      type uint32 {
        range "0..1";
      }
      config false;
      tailf:cli-drop-node-name;
    }
  }

  grouping gen2-common-lowpower-group {
    leaf gen2-common-lowpower {
      type uint32 {
        range "0..1";
      }
      config false;
      tailf:cli-drop-node-name;
    }
  }

  grouping alt-fan-table-group {
    container alt-fan-table {
      tailf:info "Switch to alternative fan table to reduce noise (NCS 560 Stelvio with specific IMs only)";
      tailf:cli-sequence-commands;
      tailf:cli-compact-syntax;
      container enable {
        tailf:info "Enable alternative fan table. See release notes for applicable chassis configurations.";
        container rack_loc {
          tailf:cli-drop-node-name;
          leaf all {
            type empty;
            tailf:cli-drop-node-name;
          }
          list location {
            key "rackId";
            tailf:info "rack-id";
            tailf:cli-optional-in-sequence;
            leaf rackId {
              type calvados:rack-id;
            }
          }
        }
      }
    }
  }
  tailf:id "http://www.cisco.com/panini/calvados/envmon/types";
}
