module Cisco-IOS-XR-ipv4-msdp-cfg {
  namespace "http://cisco.com/ns/yang/Cisco-IOS-XR-ipv4-msdp-cfg";
  prefix ipv4-msdp-cfg;

  import ietf-inet-types {
    prefix inet;
  }
  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ipv4-msdp package configuration.
     
     This module contains definitions
     for the following management objects:
       msdp: MSDP Configuration
     
     Copyright (c) 2013-2024 by Cisco Systems, Inc.
     All rights reserved.";

  revision 2024-07-23 {
    description
      "Increasing acl name length to 128 chars";
    semver:module-version "2.1.0";
  }
  revision 2019-10-31 {
    description
      "Added mandatory nodes.";
    semver:module-version "2.0.0";
  }
  revision 2019-04-05 {
    description
      "Establish semantic version baseline.";
    semver:module-version "1.0.0";
  }
  revision 2017-10-15 {
    description
      "Removed presence statement generated from internal CLI data.";
  }
  revision 2015-11-09 {
    description
      "IOS XR 6.0 revision.";
  }

  typedef Msdp-filter-type-vrf {
    type enumeration {
      enum "incoming" {
        value 1;
        description
          "Incoming Mode";
      }
      enum "outgoing" {
        value 2;
        description
          "Outgoing Mode";
      }
    }
    description
      "Msdp filter type vrf";
  }

  typedef Msdp-list-type-vrf {
    type enumeration {
      enum "list" {
        value 3;
        description
          "List";
      }
      enum "rp-list" {
        value 4;
        description
          "RPList";
      }
    }
    description
      "Msdp list type vrf";
  }

  grouping TTL-THRESHOLD {
    description
      "Common node of default-context, vrf, peer";
    leaf ttl-threshold {
      type uint32 {
        range "1..255";
      }
      description
        "Configure TTL Threshold for MSDP Peer";
    }
  }

  grouping ORIGINATOR-ID {
    description
      "Common node of default-context, vrf";
    leaf originator-id {
      type xr:Interface-name;
      description
        "Configure interface name used as originator ID";
    }
  }

  grouping PEER-TABLE {
    description
      "Common node of default-context, vrf";
    container peers {
      description
        "Entering Peer Configuration";
      list peer {
        key "peer-address";
        description
          "Peer address";
        container remote-as {
          presence "Indicates a remote-as node is configured.";
          description
            "Configure the remote AS of this peer";
          leaf as-xx {
            type uint32 {
              range "0..65535";
            }
            mandatory true;
            description
              "First half of ASN in asdot format or 0 in
               asplain";
          }
          leaf as-yy {
            type uint32 {
              range "0..4294967295";
            }
            mandatory true;
            description
              "Second half of ASN in asdot format or
               complete ASN in asplain";
          }
        }
        leaf shutdown {
          type empty;
          description
            "MSDP Peer Shutdown";
        }
        leaf description {
          type string {
            length "1..80";
          }
          description
            "Up to 80 characters describing this peer";
        }
        leaf enable {
          type empty;
          description
            "Enabling Peer Configuration";
        }
        leaf max-sa {
          type uint32 {
            range "1..75000";
          }
          description
            "Maximum SA accepted from this peer";
        }
        leaf nsr-down {
          type empty;
          description
            "Disable NSR for the peer";
        }
        leaf peer-password {
          type xr:Proprietary-password;
          description
            "Configuration of password of peer";
        }
        leaf mesh-group {
          type xr:Cisco-ios-xr-string {
            length "1..32";
          }
          description
            "Configure an MSDP mesh-group";
        }
        leaf peer-address {
          type inet:ipv4-address-no-zone;
          description
            "Peer address";
        }
        uses TTL-THRESHOLD;
        uses KEEP-ALIVE;
        uses CONNECT-SOURCE;
        uses SA-FILTER-TABLE;
      }
    }
  }

  grouping MAX-PEER-SA {
    description
      "Common node of default-context, vrf";
    leaf max-peer-sa {
      type uint32 {
        range "1..75000";
      }
      description
        "Configure inheritable MAX SA state for peers";
    }
  }

  grouping KEEP-ALIVE {
    description
      "Common node of default-context, vrf, peer";
    container keep-alive {
      presence "Indicates a keep-alive node is configured.";
      description
        "MSDP keep alive period";
      leaf keep-alive-period {
        type uint32 {
          range "1..60";
        }
        units "second";
        mandatory true;
        description
          "Keep alive period in seconds";
      }
      leaf peer-timeout-period {
        type uint32 {
          range "1..75";
        }
        units "second";
        mandatory true;
        description
          "Peer timeout period in seconds";
      }
    }
  }

  grouping CONNECT-SOURCE {
    description
      "Common node of default-context, vrf, peer";
    leaf connect-source {
      type xr:Interface-name;
      description
        "Configure interface name used for MSDP
         connection";
    }
  }

  grouping DEFAULT-PEER {
    description
      "Common node of default-context, vrf";
    leaf default-peer {
      type inet:ipv4-address-no-zone;
      description
        "Configure default peers for the box";
    }
  }

  grouping MAX-SA {
    description
      "Common node of default-context, vrf";
    leaf max-sa {
      type uint32 {
        range "1..75000";
      }
      description
        "Configure context's MAX SA state for the router";
    }
  }

  grouping SA-FILTER-TABLE {
    description
      "Common node of default-context, vrf, peer";
    container sa-filters {
      description
        "Filter SA messages from peer";
      list sa-filter {
        key "list filter-type";
        description
          "SA-Filter incoming/outgoing list or RPlist";
        leaf list {
          type Msdp-list-type-vrf;
          description
            "Src List/RP List";
        }
        leaf filter-type {
          type Msdp-filter-type-vrf;
          description
            "Incoming/Outgoing ACL";
        }
        leaf access-list-name {
          type xr:Cisco-ios-xr-string {
            length "1..128";
          }
          mandatory true;
          description
            "Access list name";
        }
      }
    }
  }

  grouping CACHE-STATE {
    description
      "Common node of default-context, vrf";
    container cache-state {
      description
        "Configure this systems SA cache access-lists";
      leaf sa-holdtime {
        type uint32 {
          range "150..3600";
        }
        units "second";
        default "150";
        description
          "SA State Holdtime period";
      }
      leaf list {
        type xr:Cisco-ios-xr-string {
          length "1..128";
        }
        description
          "Access list name";
      }
      leaf rp-list {
        type xr:Cisco-ios-xr-string {
          length "1..128";
        }
        description
          "Access-list for originating RP";
      }
    }
  }

  container msdp {
    description
      "MSDP Configuration";
    container vrfs {
      description
        "VRF Table";
      list vrf {
        key "vrf-name";
        description
          "VRF Name";
        leaf vrf-name {
          type xr:Cisco-ios-xr-string {
            length "1..32";
          }
          description
            "VRF name";
        }
        uses TTL-THRESHOLD;
        uses MAX-PEER-SA;
        uses DEFAULT-PEER;
        uses ORIGINATOR-ID;
        uses MAX-SA;
        uses CACHE-STATE;
        uses KEEP-ALIVE;
        uses PEER-TABLE;
        uses CONNECT-SOURCE;
        uses SA-FILTER-TABLE;
      }
    }
    container default-context {
      description
        "Default Context";
      uses TTL-THRESHOLD;
      uses MAX-PEER-SA;
      uses DEFAULT-PEER;
      uses ORIGINATOR-ID;
      uses MAX-SA;
      uses CACHE-STATE;
      uses KEEP-ALIVE;
      uses PEER-TABLE;
      uses CONNECT-SOURCE;
      uses SA-FILTER-TABLE;
    }
    leaf global-max-sa {
      type uint32 {
        range "1..75000";
      }
      description
        "Configure the global MAX SA state for the router";
    }
    leaf nsr-delay {
      type uint32 {
        range "5..90";
      }
      units "second";
      description
        "NSR-Ready delay period for MSDP Peer";
    }
  }
}
