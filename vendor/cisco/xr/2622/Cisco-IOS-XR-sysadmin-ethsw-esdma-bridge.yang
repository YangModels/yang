module Cisco-IOS-XR-sysadmin-ethsw-esdma-bridge {
  namespace "http://www.cisco.com/ns/yang/Cisco-IOS-XR-sysadmin-ethsw-esdma-bridge";
  prefix esdma_bridge;

  import Cisco-IOS-XR-sysadmin-ethsw-esdma-types {
    prefix esdma_types;
  }
  import cisco-semver {
    prefix semver;
  }

  organization
    "Cisco Systems Inc.";
  contact
    "Cisco Systems, Inc.
     Customer Service
     
     Postal: 170 West Tasman Drive
     San Jose, CA 95134
     
     Tel: +1 800 553-NETS
     
     E-mail: cs-yang@cisco.com";
  description
    "This module contains the YANG definitions
     for the Cisco IOS-XR SysAdmin
     'show controller switch bridge' commands.
     
     Copyright (c) 2011-2020 by Cisco Systems, Inc.
     All rights reserved.";

  revision 2019-04-15 {
    description
      "Establish semantic version baseline.";
    semver:module-version "1.0.0";
  }
  revision 2017-05-01 {
    description
      "Namespace change to comply with Cisco guidelines on namespace";
  }
  revision 2016-07-06 {
    description
      "Initial revision with content extracted from esdma_cli.yang.";
  }

  grouping switch-bridge-group {
    container bridge {
      container statistics {
        list location {
          key "rack card switch-id";
          leaf rack {
            type esdma_types:esdma-rack-num-enum;
          }
          leaf card {
            type esdma_types:esdma-cpu;
            description
              "Card";
          }
          leaf switch-id {
            type esdma_types:esdma-switch-type-enum;
            description
              "Switch type";
          }
          list ingress-set-id {
            key "ingress-set";
            leaf ingress-set {
              type uint32;
            }
            leaf ingress-set-name {
              type string;
            }
            leaf ingress-frames {
              type uint64;
            }
            leaf ingress-vlan-discards {
              type uint64;
            }
            leaf ingress-security-discards {
              type uint64;
            }
            leaf ingress-other-discards {
              type uint64;
            }
          }
          list egress-set-id {
            key "egress-set";
            leaf egress-set {
              type uint32;
            }
            leaf egress-set-name {
              type string;
            }
            leaf egress-ucast-frames {
              type uint64;
            }
            leaf egress-mcast-frames {
              type uint64;
            }
            leaf egress-bcast-frames {
              type uint64;
            }
            leaf egress-discarded-frames {
              type uint64;
            }
            leaf egress-txq-congestion {
              type uint64;
            }
            leaf egress-ctrl-packets {
              type uint64;
            }
            leaf egress-other-drops {
              type uint64;
            }
          }
        }
      }
    }
  }
}
