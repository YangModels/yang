module Cisco-IOS-XR-um-cinetd-cfg {
  namespace "http://cisco.com/ns/yang/Cisco-IOS-XR-um-cinetd-cfg";
  prefix um-cinetd-cfg;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR cinetd package configuration.
     
     This YANG module augments the
     modules with configuration data.
     
     Copyright (c) 2020-2025 by Cisco Systems, Inc., and/or its affiliates.
     All rights reserved.";

  revision 2020-03-27 {
    description
      "Initial release";
    semver:module-version "1.0.0";
  }

  container cinetd {
    description
      "Global Cisco inetd configuration commands";
    leaf rate-limit {
      type uint32 {
        range "1..100" {
          description
            "Number of service requests accepted per second (default 1)";
        }
      }
      description
        "Cisco inetd rate-limit of service requests";
    }
  }
}
