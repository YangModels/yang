module Cisco-IOS-XR-um-appmgr-cfg {
  namespace "http://cisco.com/ns/yang/Cisco-IOS-XR-um-appmgr-cfg";
  prefix um-appmgr-cfg;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR appmgr package configuration.
     
     This YANG module augments the
     modules with configuration data.
     
     Copyright (c) 2025 by Cisco Systems, Inc., and/or its affiliates.
     All rights reserved.";

  revision 2026-06-04 {
    description
      "Restrict docker vrf leaf to valid XR VRF identifier pattern
       2025-11-04
         Adding support of docker sensitive host paths access config
       2025-08-25
         Adding support of docker vrf config
       2025-08-04
         Adding support of docker socket-access config
       2025-05-18
         Adding support of monitor-session config
       2024-11-04
         Added new config cli for configuring appmgr resources
       2021-11-19
         Updated the string length, added string constraint for svault";
    semver:module-version "2.0.0";
  }
  revision 2021-06-23 {
    description
      "Initial release";
    semver:module-version "1.0.0";
  }

  container appmgr {
    description
      "appmgr configuration";
    container applications {
      description
        "Per application configuration";
      list application {
        key "application-name";
        description
          "Per application configuration";
        leaf application-name {
          type string {
            length "1..255" {
              description
                "Application name";
            }
            pattern "[a-zA-Z0-9][a-zA-Z0-9_.-]+";
          }
          description
            "Per application configuration";
        }
        container activate {
          description
            "Activate - Install and run an application";
          leaf type {
            type enumeration {
              enum "docker" {
                value 1;
                description
                  "Docker application";
              }
            }
            mandatory true;
            description
              "Type of app to configure";
          }
          leaf source-name {
            type string {
              length "1..255" {
                description
                  "Source name";
              }
              pattern "[a-zA-Z0-9][a-zA-Z0-9_:.-]+";
            }
            mandatory true;
            description
              "Source name";
          }
          leaf monitor-session {
            type string {
              length "1..10" {
                description
                  "monitor-session name";
              }
              pattern "[a-zA-Z_][a-zA-Z_0-9:.-]*";
            }
            description
              "monitor-session name";
          }
          leaf svault {
            type string {
              length "1..255" {
                description
                  "secure vault profile name";
              }
              pattern "[a-zA-Z_][a-zA-Z_0-9:.-]*";
            }
            description
              "secure vault profile name";
          }
          leaf docker-run-opts {
            type string {
              length "1..1024" {
                description
                  "run options (enclosed in double quotes)";
              }
            }
            description
              "Docker run 'options' argument - multiple options can be specified";
          }
          leaf docker-run-cmd {
            type string {
              length "1..1024" {
                description
                  "command (enclosed in double quotes)";
              }
            }
            description
              "Docker run 'command' argument - command to be executed in container";
          }
        }
      }
    }
    container process-scripts {
      description
        "Process script configuration";
      list process-script {
        must "executable or run-args or restart";
        key "process-script-name";
        description
          "Process script configuration";
        leaf process-script-name {
          type string {
            length "1..255" {
              description
                "Process script name";
            }
            pattern "[a-zA-Z0-9][a-zA-Z0-9_.-]+";
          }
          description
            "Process script configuration";
        }
        leaf executable {
          type string {
            length "1..255" {
              description
                "Relative path of the executable";
            }
            pattern "[a-zA-Z0-9][a-zA-Z0-9_./-]+";
          }
          description
            "Executable filename";
        }
        leaf run-args {
          type string {
            length "1..800" {
              description
                "Arguments string";
            }
          }
          description
            "Run arguments";
        }
        leaf restart {
          type enumeration {
            enum "never" {
              value 1;
              description
                "Never restart automatically";
            }
            enum "on-failure" {
              value 2;
              description
                "Restart on failure automatically";
            }
            enum "always" {
              value 3;
              description
                "Always restart automatically";
            }
            enum "unless-stopped" {
              value 4;
              description
                "Restart automatically unless stopped";
            }
            enum "unless-errored" {
              value 5;
              description
                "Restart automatically unless errored";
            }
          }
          description
            "Restart policy for the application";
        }
        leaf max-retries {
          when "../restart = 'on-failure'";
          type uint32 {
            range "1..10" {
              description
                "Max restart retries";
            }
          }
          description
            "Maximum retry attempts; always restarted by default";
        }
        leaf username {
          type string {
            length "2..253" {
              description
                "Name of a configured user";
            }
          }
          description
            "User to execute the process-script under";
        }
        container autorun {
          presence "Indicates a autorun node is configured.";
          description
            "Auto-run activation of the process script";
        }
      }
    }
    container resources {
      description
        "configure appmgr resources";
      container containers {
        description
          "configure appmgr resources containers";
        container limit {
          description
            "configure appmgr resource containers limit";
          leaf memory {
            type uint32 {
              range "1..25" {
                description
                  "In Percentage";
              }
            }
            description
              "set memory limit for appmgr";
          }
          leaf cpu {
            type uint32 {
              range "25..75" {
                description
                  "In Percentage";
              }
            }
            description
              "set cpu limit for appmgr";
          }
        }
      }
    }
    container docker {
      description
        "Docker configuration";
      container vrf {
        presence "Indicates a vrf node is configured.";
        description
          "Docker vrf configuration";
      }
      leaf vrf-name {
        type string {
          length "1..64" {
            description
              "VRF name";
          }
          pattern "[a-zA-Z0-9][a-zA-Z0-9_.-]+";
        }
        description
          "VRF name";
      }
      container allow-sensitive-paths {
        presence "Indicates a allow-sensitive-paths node is configured.";
        description
          "Configure appmgr docker sensitive host paths access to TP containers";
      }
    }
  }
}
