module Cisco-IOS-XR-iedge4710-cfg {
  namespace "http://cisco.com/ns/yang/Cisco-IOS-XR-iedge4710-cfg";
  prefix iedge4710-cfg;

  import Cisco-IOS-XR-types {
    prefix xr;
  }
  import cisco-semver {
    prefix semver;
  }
  import Cisco-IOS-XR-ifmgr-cfg {
    prefix a1;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR iedge4710 package configuration.
     
     This module contains definitions
     for the following management objects:
       subscriber-manager: iEdge subscriber manager configuration
       subscriber-featurette: iEdge subscriber featurette
         configuration
       iedge-license-manager: Session License Manager Configuration
       sub-manager: iEdge subscriber manager configuration
     
     This YANG module augments the
       Cisco-IOS-XR-ifmgr-cfg
     module with configuration data.
     
     Copyright (c) 2013-2025 by Cisco Systems, Inc.
     All rights reserved.";

  revision 2025-09-14 {
    description
      "Initial revision.";
    semver:module-version "1.2.0";
  }
  revision 2020-10-14 {
    description
      "added srg acct start time.";
    semver:module-version "1.1.0";
  }
  revision 2019-04-05 {
    description
      "Establish semantic version baseline.";
    semver:module-version "1.0.1";
  }
  revision 2017-09-07 {
    description
      "Fixed type translation error.";
  }
  revision 2015-11-09 {
    description
      "IOS XR 6.0 revision.";
  }

  augment "/a1:interface-configurations/a1:interface-configuration" {
    description
      "This augment extends the configuration data of
       'Cisco-IOS-XR-ifmgr-cfg'";
    container service-policies {
      description
        "Interface control subscriber policy
         configuration";
      list service-policy {
        key "service-policy-name";
        description
          "Service policy to be applied to access
           interface  for subscribers";
        leaf service-policy-name {
          type string {
            length "1..63";
          }
          description
            "Name of policy-map";
        }
      }
    }
  }
  container subscriber-manager {
    description
      "iEdge subscriber manager configuration";
    container accounting {
      description
        "iEdge accounting feature";
      container send-stop {
        description
          "Accounting send stop feature";
        container setup-failure {
          description
            "Setup failure feature";
          leaf method-list-name {
            type string;
            description
              "AAA List name either default or preconfigured";
          }
        }
      }
      container dyn-tmpl-sess-acct {
        description
          "dynamic template in session accounting configs";
        leaf enable {
          type boolean;
          default "false";
          description
            "allow dynamic template in session accounting";
        }
      }
      container interim {
        description
          "interim accounting related";
        container variation {
          description
            "variation of first session or service interim
             record from configured timeout";
          leaf maximum-percentage-variation {
            type uint32 {
              range "0..50";
            }
            units "percentage";
            description
              "maximum percentage variation (maximum
               absolute variation is 15 minutes)";
          }
        }
      }
    }
    container coa-nack {
      description
        "Coa Nack specific config";
      leaf disc-subscriber {
        type empty;
        description
          "if CoA Nack disconnect subscriber";
      }
    }
    container srg {
      description
        "SRG specific config";
      leaf account-start-time {
        type empty;
        description
          "acct start time ref to srg role change slave to
           master";
      }
      leaf sync-account-session-id {
        type empty;
        description
          "sync account session id from master to slave";
      }
    }
    container clear-session-stats-failure {
      description
        "Clear session stats failure config";
      leaf disable-subscriber-disconnect {
        type empty;
        description
          "Disable subscriber disconnect, if clear session
           stats failed";
      }
    }
  }
  container subscriber-featurette {
    description
      "iEdge subscriber featurette configuration";
    list featurette-name {
      key "featurette";
      description
        "enable featurette processing";
      leaf enable {
        type uint32;
        description
          "instance of featurette";
      }
      leaf featurette {
        type xr:Cisco-ios-xr-string;
        description
          "subscriber feature";
      }
    }
  }
  container iedge-license-manager {
    description
      "Session License Manager Configuration";
    leaf session-limit {
      type uint32 {
        range "1..200000";
      }
      description
        "Session limit configured on linecard";
    }
  }
  container sub-manager {
    description
      "iEdge subscriber manager configuration";
    list location {
      key "location1";
      description
        "Select location";
      container trace {
        description
          "Subscriber manager trace";
        leaf trace-level {
          type uint32;
          description
            "Subscriber manager trace level";
        }
      }
      leaf history {
        type empty;
        description
          "Disable history for subscriber manager";
      }
      leaf location1 {
        type xr:Cisco-ios-xr-string;
        description
          "Specify location";
      }
    }
  }
}
