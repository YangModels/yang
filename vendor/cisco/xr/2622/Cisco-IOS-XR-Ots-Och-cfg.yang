module Cisco-IOS-XR-Ots-Och-cfg {
  namespace "http://cisco.com/ns/yang/Cisco-IOS-XR-Ots-Och-cfg";
  prefix ots-och-cfg;

  import Cisco-IOS-XR-types {
    prefix xr;
  }
  import cisco-semver {
    prefix semver;
  }
  import Cisco-IOS-XR-ifmgr-cfg {
    prefix a1;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR Ots-Och package configuration.
     
     This YANG module augments the
       Cisco-IOS-XR-ifmgr-cfg
     module with configuration data.
     
     Copyright (c) 2013-2025 by Cisco Systems, Inc.
     All rights reserved.";

  revision 2025-12-10 {
    description
      "expected-power thresholds and max psd offset parameters added";
    semver:module-version "1.0.0";
  }
  revision 2025-09-08 {
    description
      "Attenuation unit changed to db from dBm of egress-ase-attn, egress-channel-attn, ingress-channel-attn";
  }
  revision 2025-03-28 {
    description
      "Added support for egress-ase-attn, egress-channel-attn & ingress-channel-attn for Ots-Och Controller";
  }
  revision 2021-03-16 {
    description
      "Channel Attenuation Parameter added for Ots-Och Controller";
  }
  revision 2020-07-09 {
    description
      "New Cfg Model Added for Ots-Och Controller";
  }
  revision 2019-04-05 {
    description
      "Establish semantic version baseline.";
  }
  revision 2015-11-09 {
    description
      "IOS XR 6.0 revision.";
  }

  augment "/a1:interface-configurations/a1:interface-configuration" {
    description
      "This augment extends the configuration data of
       'Cisco-IOS-XR-ifmgr-cfg'";
    container ots-och {
      description
        "Ots-Och controller configuration";
      leaf channel-attenuation {
        type uint32 {
          range "0..250";
        }
        description
          "Select Channel Attenuation(in units of 0.1dB)";
      }
      leaf ots-och-max-psd-degraded-limit {
        type uint32 {
          range "1..60";
        }
        description
          "Configure OTS-OCH maximum PSD degraded limit
           threshold";
      }
      leaf ots-och-max-psd-violated-limit {
        type uint32 {
          range "1..60";
        }
        description
          "Configure OTS-OCH maximum PSD violated limit
           threshold";
      }
      leaf add-drop-channel {
        type xr:Interface-name;
        description
          "configures optical cross connect";
      }
      leaf ots-och-expected-power-degraded-low-offset {
        type int32 {
          range "-60..-1";
        }
        description
          "Configure OTS-OCH expected power degraded low
           offset threshold";
      }
      leaf ots-och-expected-power {
        type int32 {
          range "-190..210";
        }
        description
          "Expected power value in units of 0.1 dBm";
      }
      leaf ots-och-expected-power-violated-low-offset {
        type int32 {
          range "-60..-1";
        }
        description
          "Configure OTS-OCH expected power violated low
           offset threshold";
      }
      leaf ots-och-expected-power-violated-high-offset {
        type uint32 {
          range "1..60";
        }
        description
          "Configure OTS-OCH expected power violated high
           offset threshold";
      }
      leaf ots-och-expected-power-degraded-high-offset {
        type uint32 {
          range "1..60";
        }
        description
          "Configure OTS-OCH expected power degraded high
           offset threshold";
      }
      leaf ots-och-ingress-channel-attn {
        type int32 {
          range "0..250";
        }
        description
          "configure Ingress channel attenuation(in units
           of 0.1dB)";
      }
      leaf ots-och-egress-channel-attn {
        type int32 {
          range "0..250";
        }
        description
          "configure Egress channel attenuation(in units
           of 0.1dB)";
      }
      leaf ots-och-egress-ase-attn {
        type int32 {
          range "0..250";
        }
        description
          "configure Egress ASE attenuation(in units of 0
           .1dB)";
      }
    }
  }
}
