module Cisco-IOS-XR-tty-server-oper {
  namespace "http://cisco.com/ns/yang/Cisco-IOS-XR-tty-server-oper";
  prefix tty-server-oper;

  import Cisco-IOS-XR-types {
    prefix xr;
  }
  import cisco-semver {
    prefix semver;
  }
  import Cisco-IOS-XR-tty-management-datatypes {
    prefix dt1;
  }
  include Cisco-IOS-XR-tty-server-oper-sub5 {
    revision-date 2019-04-05;
  }
  include Cisco-IOS-XR-tty-server-oper-sub4 {
    revision-date 2019-04-05;
  }
  include Cisco-IOS-XR-tty-server-oper-sub3 {
    revision-date 2019-04-05;
  }
  include Cisco-IOS-XR-tty-server-oper-sub2 {
    revision-date 2019-04-05;
  }
  include Cisco-IOS-XR-tty-server-oper-sub1 {
    revision-date 2019-04-05;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR tty-server package operational data.
     
     This module contains definitions
     for the following management objects:
       tty: TTY Line Configuration
     
     Copyright (c) 2013-2019 by Cisco Systems, Inc.
     All rights reserved.";

  revision 2019-04-05 {
    description
      "Establish semantic version baseline.";
    semver:module-version "1.0.0";
  }
  revision 2019-02-25 {
    description
      "Fixed unconstrained data type issues";
  }
  revision 2017-09-07 {
    description
      "Fixed type translation error.";
  }
  revision 2015-07-30 {
    description
      "Descriptions updated.";
  }
  revision 2015-01-07 {
    description
      "IOS XR 5.3.1 revision.";
  }

  typedef Line-state {
    type enumeration {
      enum "none" {
        value 0;
        description
          "Line not connected";
      }
      enum "registered" {
        value 1;
        description
          "Line registered";
      }
      enum "in-use" {
        value 2;
        description
          "Line active and in use";
      }
    }
    description
      "Line state";
  }

  typedef Session-operation {
    type enumeration {
      enum "none" {
        value 0;
        description
          "No sessions on the line";
      }
      enum "setup" {
        value 1;
        description
          "Session getting set up";
      }
      enum "shell" {
        value 2;
        description
          "Session active with a shell";
      }
      enum "transitioning" {
        value 3;
        description
          "Session in transitioning phase";
      }
      enum "packet" {
        value 4;
        description
          "Session ready to receive packets";
      }
    }
    description
      "Session operation";
  }

  grouping STATE {
    description
      "Common node of console-line, vty-line,
       auxiliary-line";
    container state {
      description
        "Line state information";
      container template {
        description
          "Information related to template applied to the
           line";
        leaf name {
          type xr:Cisco-ios-xr-string {
            length "1..990";
          }
          description
            "Name of the template";
        }
      }
      container general {
        description
          "General information";
        leaf operation {
          type Session-operation;
          description
            "application running of on the tty line";
        }
        leaf general-state {
          type Line-state;
          description
            "State of the line";
        }
      }
    }
  }

  grouping GENERAL-STATISTICS {
    description
      "Common node of console-statistics, vty-statistics
       , auxiliary-statistics";
    container general-statistics {
      description
        "General statistics of line";
      uses TTY-GENERAL-STATS;
    }
  }

  grouping AAA {
    description
      "Common node of console-statistics, vty-statistics
       , auxiliary-statistics";
    container aaa {
      description
        "AAA related statistics";
      uses TTY-AAA-STATS;
    }
  }

  grouping RS232 {
    description
      "Common node of console-statistics,
       auxiliary-statistics";
    container rs232 {
      description
        "RS232 statistics of console line";
      uses TTY-RS232-STATS;
    }
  }

  grouping EXEC {
    description
      "Common node of console-statistics, vty-statistics
       , auxiliary-statistics";
    container exec {
      description
        "Exec related statistics";
      uses TTY-EXEC-PROP-STATS;
    }
  }

  grouping CONFIGURATION {
    description
      "Common node of console-line, vty-line,
       auxiliary-line";
    container configuration {
      description
        "Configuration information of the line";
      container connection-configuration {
        description
          "Conection configuration information";
        container transport-input {
          description
            "Protocols to use when connecting to the
             terminal server";
          leaf select {
            type dt1:Tty-transport-protocol-select;
            default "all";
            description
              "Choose transport protocols";
          }
          leaf protocol1 {
            when "../select = 'some'" {
              description
                "../Select = Some";
            }
            type dt1:Tty-transport-protocol;
            description
              "Transport protocol1";
          }
          leaf protocol2 {
            when "../select = 'some'" {
              description
                "../Select = Some";
            }
            type dt1:Tty-transport-protocol;
            description
              "Transport protocol2";
          }
          leaf none {
            type uint32 {
              range "0..4294967295";
            }
            description
              "Not used";
          }
        }
        leaf acl-out {
          type xr:Cisco-ios-xr-string {
            length "1..64";
          }
          description
            "ACL for outbound traffic";
        }
        leaf acl-in {
          type xr:Cisco-ios-xr-string {
            length "1..64";
          }
          description
            "ACL for inbound traffic";
        }
      }
    }
  }

  container tty {
    config false;
    description
      "TTY Line Configuration";
    container console-nodes {
      description
        "List of Nodes for console";
      list console-node {
        key "id";
        description
          "Console line configuration on a node";
        container console-line {
          description
            "Details about console line";
          container console-statistics {
            description
              "Statistics of the console line";
            uses RS232;
            uses GENERAL-STATISTICS;
            uses EXEC;
            uses AAA;
          }
          uses STATE;
          uses CONFIGURATION;
        }
        leaf id {
          type xr:Node-id;
          description
            "Node ID";
        }
      }
    }
    container vty-lines {
      description
        "List of VTY lines";
      list vty-line {
        key "line-number";
        description
          "VTY Line";
        container vty-statistics {
          description
            "Statistics of the VTY line";
          container connection {
            description
              "Connection related statistics";
            uses TTY-CONNECTION-STATS;
          }
          uses GENERAL-STATISTICS;
          uses EXEC;
          uses AAA;
        }
        leaf line-number {
          type uint32 {
            range "0..4294967295";
          }
          description
            "VTY Line number";
        }
        uses STATE;
        uses CONFIGURATION;
      }
    }
    container auxiliary-nodes {
      description
        "List of Nodes attached with an auxiliary line";
      list auxiliary-node {
        key "id";
        description
          "Line configuration on a node";
        container auxiliary-line {
          description
            "Details about auxiliary line";
          container auxiliary-statistics {
            description
              "Statistics of the auxiliary line";
            uses RS232;
            uses GENERAL-STATISTICS;
            uses EXEC;
            uses AAA;
          }
          uses STATE;
          uses CONFIGURATION;
        }
        leaf id {
          type xr:Node-id;
          description
            "Node ID";
        }
      }
    }
  }
}
