module Cisco-IOS-XR-optics-dac-cfg {
  namespace "http://cisco.com/ns/yang/Cisco-IOS-XR-optics-dac-cfg";
  prefix optics-dac-cfg;

  import cisco-semver {
    prefix semver;
  }
  import Cisco-IOS-XR-ifmgr-cfg {
    prefix a1;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR optics-dac package configuration.
     
     This YANG module augments the
       Cisco-IOS-XR-ifmgr-cfg
     module with configuration data.
     
     Copyright (c) 2013-2024 by Cisco Systems, Inc.
     All rights reserved.";

  revision 2024-01-31 {
    description
      "Added 8x25 BO Support.
       2024-01-10
         Added 40G port mode.
       2022-05-09
         Removed unused module.";
    semver:module-version "1.1.0";
  }
  revision 2021-02-16 {
    description
      "Schema added.";
    semver:module-version "1.0.0";
  }
  revision 2019-04-05 {
    description
      "Establish semantic version baseline.";
  }
  revision 2015-11-09 {
    description
      "IOS XR 6.0 revision.";
  }

  typedef Optics-dac-rate {
    type enumeration {
      enum "1:1" {
        value 0;
        description
          "DAC Rate 1:1 Sampling off";
      }
      enum "1:1.25" {
        value 1;
        description
          "DAC Rate 1:1.25";
      }
      enum "1:1.50" {
        value 2;
        description
          "DAC Rate 1:1.50";
      }
      enum "1:1.75" {
        value 3;
        description
          "DAC Rate 1:1.75";
      }
      enum "1:2" {
        value 4;
        description
          "DAC Rate 1:2";
      }
    }
    description
      "Optics dac rate";
  }

  augment "/a1:interface-configurations/a1:interface-configuration" {
    description
      "This augment extends the configuration data of
       'Cisco-IOS-XR-ifmgr-cfg'";
    leaf optics-dac-rate {
      type Optics-dac-rate;
      description
        "Configure optics sampling rate ";
    }
  }
}
