module Cisco-IOS-XR-rgmgr-oper {
  namespace "http://cisco.com/ns/yang/Cisco-IOS-XR-rgmgr-oper";
  prefix rgmgr-oper;

  import Cisco-IOS-XR-types {
    prefix xr;
  }
  import cisco-semver {
    prefix semver;
  }
  include Cisco-IOS-XR-rgmgr-oper-sub1 {
    revision-date 2021-12-01;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR rgmgr package operational data.
     
     This module contains definitions
     for the following management objects:
       redundancy-group-manager: Redundancy group manager operational
         data
     
     Copyright (c) 2013-2021 by Cisco Systems, Inc.
     All rights reserved.";

  revision 2021-12-01 {
    description
      "Increase in interface name length";
    semver:module-version "1.1.0";
  }
  revision 2019-04-05 {
    description
      "Establish semantic version baseline.";
    semver:module-version "1.0.1";
  }
  revision 2015-01-07 {
    description
      "IOS XR 5.3.1 revision.";
  }

  container redundancy-group-manager {
    config false;
    description
      "Redundancy group manager operational data";
    container controllers {
      description
        "Redundancy group manager data";
      list controller {
        key "controller-name";
        description
          "Display redundancy group by controller name";
        leaf controller-name {
          type xr:Interface-name;
          description
            "Controller name";
        }
        uses RGMGR-RED-GRP;
      }
    }
  }
}
