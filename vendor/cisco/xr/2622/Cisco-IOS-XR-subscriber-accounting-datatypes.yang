module Cisco-IOS-XR-subscriber-accounting-datatypes {
  namespace "http://cisco.com/ns/yang/Cisco-IOS-XR-subscriber-accounting-datatypes";
  prefix subscriber-accounting-datatypes;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of generally useful
     derived YANG data types.
     
     Copyright (c) 2013-2026 by Cisco Systems, Inc.
     All rights reserved.";

  revision 2026-06-22 {
    description
      "Renamed subscriber accounting datatypes module.";
    semver:module-version "1.0.0";
  }
  revision 2019-04-05 {
    description
      "Establish semantic version baseline.";
  }
  revision 2015-11-09 {
    description
      "IOS XR 6.0 revision.";
  }

  typedef Idle-timeout-direction {
    type string {
      pattern "(inbound)|(outbound)|(both)";
    }
    description
      "inbound: Inbound traffic while deriving idleness,
       outbound: Outbound traffic while deriving
       idleness, both: Both inbound and outbound traffic
       while deriving idleness";
  }
}
