submodule Cisco-IOS-XR-platform-oir-history-oper-sub1 {
  belongs-to Cisco-IOS-XR-platform-oir-history-oper {
    prefix Cisco-IOS-XR-platform-oir-history-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR platform-oir-history package operational data.
     
     Copyright (c) 2013-2020 by Cisco Systems, Inc.
     All rights reserved.";

  revision 2020-05-26 {
    description
      "IOS XR 7.0.14 revision.";
    semver:module-version "1.0.0";
  }
  revision 2019-04-05 {
    description
      "Establish semantic version baseline.";
  }
  revision 2015-11-09 {
    description
      "IOS XR 6.0 revision.";
  }

  grouping OIR-HISTORY-ENTRY {
    description
      "OIR History Entry";
    leaf time {
      type string;
      description
        "Time of OIR";
    }
    leaf micro-seconds {
      type uint64;
      units "microsecond";
      description
        "Time Stamp's Micro Seconds";
    }
    leaf event {
      type string;
      description
        "OIR event";
    }
    leaf pid {
      type string;
      description
        "PID of the card";
    }
    leaf serial-number {
      type string;
      description
        "Serial Number of the card";
    }
    leaf node-string {
      type string;
      description
        "Node String of the card";
    }
  }

  grouping OIR-HISTORY {
    description
      "OIR History List";
    list oir-history {
      description
        "OIR History List";
      uses OIR-HISTORY-ENTRY;
    }
  }
}
