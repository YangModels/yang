submodule Cisco-IOS-XR-infra-iccp-oper-sub1 {
  belongs-to Cisco-IOS-XR-infra-iccp-oper {
    prefix Cisco-IOS-XR-infra-iccp-oper;
  }

  import ietf-inet-types {
    prefix inet;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR infra-iccp package operational data.
     
     Copyright (c) 2013-2024 by Cisco Systems, Inc.
     All rights reserved.";

  revision 2024-04-18 {
    description
      "Created.";
    semver:module-version "1.0.0";
  }
  revision 2019-04-05 {
    description
      "Establish semantic version baseline.";
  }
  revision 2015-11-09 {
    description
      "IOS XR 6.0 revision.";
  }

  typedef Iccp-timer-state {
    type enumeration {
      enum "running" {
        description
          "Running";
      }
      enum "not-running" {
        description
          "Not Running";
      }
    }
    description
      "ICCP timer states";
  }

  typedef Iccp-application {
    type enumeration {
      enum "mlacp" {
        description
          "MLACP";
      }
      enum "igmp-snooping" {
        description
          "IGMP Snooping";
      }
      enum "ancp" {
        description
          "ANCP";
      }
      enum "pmlacp" {
        description
          "PMLACP";
      }
      enum "orbit" {
        description
          "Satellite ORBIT";
      }
      enum "sonet-aps" {
        description
          "Sonet APS";
      }
      enum "nve" {
        description
          "NVE";
      }
      enum "unknown" {
        description
          "Unknown";
      }
    }
    description
      "ICCP application type";
  }

  typedef Im-state-enum {
    type enumeration {
      enum "im-state-not-ready" {
        description
          "im state not ready";
      }
      enum "im-state-admin-down" {
        description
          "im state admin down";
      }
      enum "im-state-down" {
        description
          "im state down";
      }
      enum "im-state-up" {
        description
          "im state up";
      }
      enum "im-state-shutdown" {
        description
          "im state shutdown";
      }
      enum "im-state-err-disable" {
        description
          "im state err disable";
      }
      enum "im-state-down-immediate" {
        description
          "im state down immediate";
      }
      enum "im-state-down-immediate-admin" {
        description
          "im state down immediate admin";
      }
      enum "im-state-down-graceful" {
        description
          "im state down graceful";
      }
      enum "im-state-begin-shutdown" {
        description
          "im state begin shutdown";
      }
      enum "im-state-end-shutdown" {
        description
          "im state end shutdown";
      }
      enum "im-state-begin-error-disable" {
        description
          "im state begin error disable";
      }
      enum "im-state-end-error-disable" {
        description
          "im state end error disable";
      }
      enum "im-state-begin-down-graceful" {
        description
          "im state begin down graceful";
      }
      enum "im-state-reset" {
        description
          "im state reset";
      }
      enum "im-state-operational" {
        description
          "im state operational";
      }
      enum "im-state-not-operational" {
        description
          "im state not operational";
      }
      enum "im-state-unknown" {
        description
          "im state unknown";
      }
      enum "im-state-last" {
        description
          "im state last";
      }
    }
    description
      "Im state enum";
  }

  typedef Iccp-mgmt-route-watch-state {
    type enumeration {
      enum "route-watch-not-initialized" {
        description
          "Route Watch not yet Initiated";
      }
      enum "route-watch-down" {
        description
          "Route Watch in Down State";
      }
      enum "route-watch-up" {
        description
          "Route Watch in Up State";
      }
    }
    description
      "ICCP Route Watch states";
  }

  typedef Iccp-mgmt-member-iccp-state {
    type enumeration {
      enum "not-iccp-capable" {
        description
          "Member in Not Capable State";
      }
      enum "disconnected" {
        description
          "Member in Disconnected State";
      }
      enum "connecting" {
        description
          "Member in Connecting State";
      }
      enum "connected" {
        description
          "Member in Connected State";
      }
    }
    description
      "ICCP member states";
  }

  typedef Iccp-mgmt-member-ldp-state {
    type enumeration {
      enum "initializing" {
        description
          "Initializing";
      }
      enum "up" {
        description
          "Up";
      }
      enum "down" {
        description
          "Down";
      }
    }
    description
      "ICCP LDP member states";
  }

  grouping ICCP-MGMT-ISOLATION-RECOVERY-DELAY-TIMER-INFO {
    description
      "ICCP Isolation Recovery Delay Timer Information";
    leaf state {
      type Iccp-timer-state;
      description
        "Timer State";
    }
    leaf value {
      type uint32;
      units "second";
      description
        "Timer Value in Seconds";
    }
    leaf elapsed {
      type uint32;
      units "second";
      description
        "Elapsed Time in Seconds when Running";
    }
  }

  grouping ICCP-MGMT-APP-INFO {
    description
      "ICCP Application Information";
    leaf type {
      type Iccp-application;
      description
        "Application Type";
    }
  }

  grouping ICCP-MGMT-BBI-INFO {
    description
      "ICCP Backbone Interface Information";
    leaf interface-name {
      type string;
      description
        "Interface name";
    }
    leaf state {
      type Im-state-enum;
      description
        "Interface State";
    }
  }

  grouping ICCP-MGMT-MEMBER-INFO {
    description
      "ICCP Member Information";
    leaf address {
      type inet:ipv4-address;
      description
        "Address";
    }
    leaf ldp-state {
      type Iccp-mgmt-member-ldp-state;
      description
        "LDP State";
    }
    leaf iccp-state {
      type Iccp-mgmt-member-iccp-state;
      description
        "ICCP State";
    }
    leaf route-watch-state {
      type Iccp-mgmt-route-watch-state;
      description
        "Route Watch State";
    }
    leaf host-name {
      type string;
      description
        "Host name";
    }
  }

  grouping ICCP-MGMT-RG-INFO {
    description
      "ICCP Redundancy Group Information";
    container isolation-recovery-delay-timer {
      description
        "Isolation Recovery Delay Timer";
      uses ICCP-MGMT-ISOLATION-RECOVERY-DELAY-TIMER-INFO;
    }
    leaf group-id {
      type uint32;
      description
        "Redundancy Group ID";
    }
    list member {
      description
        "Member table";
      uses ICCP-MGMT-MEMBER-INFO;
    }
    list backbone-interface {
      description
        "Backbone Interface table";
      uses ICCP-MGMT-BBI-INFO;
    }
    list application {
      description
        "Application table";
      uses ICCP-MGMT-APP-INFO;
    }
  }
}
