module Cisco-IOS-XR-openconfig-interfaces-stats-ext {
  namespace "http://cisco.com/ns/yang/Cisco-IOS-XR-openconfig-interfaces-stats-ext";
  prefix oc-stats-ext;

  import openconfig-interfaces {
    prefix oc-if;
  }
  import openconfig-types {
    prefix oc-types;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module is an extension of openconfig interfaces model
      and contains the definition of last-read-time
     
      This module contains definitions for the following:
      last-read-time
     
      Copyright (c) 2023-2024 by Cisco Systems, Inc.
      All rights reserved.";

  revision 2024-02-26 {
    description
      "Added last-read-time in vendor container";
  }
  revision 2023-10-11 {
    description
      "Initial revision";
    reference "0.1.0";
  }

  grouping interface-stats-timestamp-info {
    description
      "Timestamp information for ocif stats";
    container cisco {
      description
        "Vendor specific operational data that are not yet available in OC
         model. This container contains Cisco IOS-XR specific stats
         counter data.";
      leaf last-read-time {
        type oc-types:timeticks64;
        description
          "Time when counters were last read by Primary collector
           from hardware (in msecs)";
      }
    }
  }

  augment "/oc-if:interfaces/oc-if:interface/oc-if:state/oc-if:counters" {
    description
      "Add timestamp info to interface stats";
    uses interface-stats-timestamp-info;
  }
  augment "/oc-if:interfaces/oc-if:interface/oc-if:subinterfaces/oc-if:subinterface/oc-if:state/oc-if:counters" {
    description
      "Add timestamp info to interface stats";
    uses interface-stats-timestamp-info;
  }
}
