submodule Cisco-IOS-XR-subscriber-accounting-oper-sub1 {
  belongs-to Cisco-IOS-XR-subscriber-accounting-oper {
    prefix Cisco-IOS-XR-subscriber-accounting-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR subscriber-accounting package operational data.
     
     Copyright (c) 2013-2026 by Cisco Systems, Inc.
     All rights reserved.";

  revision 2026-08-23 {
    description
      "Added customer-visible SRG subscriber consistency and SADB query failure counters.
       2025-03-25
         Updated timestamp data type from unit32 to unit64
       2024-05-19
         Added accounting flag for service and session feature
       2023-12-04
         Added support for feature accounting config status per subscriber interface in srg summary.
       2022-03-16
         Added support for srg group id and transient role per access interface in srg summary.";
    semver:module-version "2.1.0";
  }
  revision 2021-02-10 {
    description
      "New cli added to list accouting statistics for all subscribers";
    semver:module-version "2.0.0";
  }
  revision 2019-12-16 {
    description
      "Fixed for service acct stats i.e leaf nodes are deleted for session accounting stats from service acct stats bag and maintained unique stats for session and service accounting.";
    semver:module-version "2.0.0";
  }
  revision 2019-04-05 {
    description
      "Establish semantic version baseline.";
    semver:module-version "1.0.1";
  }
  revision 2018-10-30 {
    description
      "Fixed for CSCvm83576.";
  }
  revision 2017-09-07 {
    description
      "Fixed type translation error.";
  }
  revision 2015-11-09 {
    description
      "IOS XR 6.0 revision.";
  }

  grouping ACCT-MA-SRG-STATS-INFO-BAG-DATA {
    description
      "ACCT MA SRG STATS INFO BAG DATA";
    leaf interface-name {
      type string;
      description
        "Interface name";
    }
    leaf access-interface-handle {
      type uint32;
      description
        "Access Interface handle";
    }
    leaf srg-node-role {
      type uint32;
      description
        "SRG Role for given access interface";
    }
    leaf srg-master-eoms-pending-flag {
      type boolean;
      description
        "True/False,if SRG Master Node Sync is still
         pending";
    }
    leaf srg-diameter-up-flag {
      type boolean;
      description
        "True/False,SRG Node Diameter Notification flag";
    }
    leaf srg-role-upd-time {
      type uint32;
      description
        "SRG Role Update Notif time in DDD MMM DD HH:MM
         :SS YYYY format eg: Tue Apr 11 21:30:47 2011";
    }
    leaf diameter-up-ts {
      type uint32;
      description
        "Diameter UP Notif time in DDD MMM DD HH:MM:SS
         YYYY format eg: Tue Apr 11 21:30:47 2011";
    }
    leaf srg-transient-role {
      type uint32;
      description
        "SRG Transient Role for given access interface";
    }
    leaf srg-group-id {
      type uint32;
      description
        "SRG Group id ";
    }
    leaf subscriber-count {
      type uint32;
      description
        "Number of subscribers linked to the SRG parent
         interface";
    }
  }

  grouping ACCT-MA-SRG-STATS {
    description
      "ACCT MA SRG STATS";
    container srg-status-counters {
      description
        "Accounting's SRG Statistics Info Bag";
      uses ACCT-MA-SRG-STATS-INFO-BAG-DATA;
    }
  }

  grouping ACCT-MA-FLOW-FEAT-BAG-DATA {
    description
      "ACCT MA FLOW FEAT BAG DATA";
    leaf flow-accounting-enabled-flag {
      type boolean;
      description
        "True if flow accounting is enabled";
    }
    leaf scan-complete-flag {
      type boolean;
      description
        "Scan Complete is done";
    }
    leaf disc-pending-flag {
      type boolean;
      description
        "Disc Pending Flag";
    }
    leaf flow-idle-timeout-enabled-flag {
      type boolean;
      description
        "True if flow idle timeout is enabled";
    }
    leaf prepaid-enabled-flag {
      type boolean;
      description
        "True if prepaid is enabled";
    }
    leaf prepaid-reauth-timer-enabled {
      type boolean;
      description
        "Flag to specify if absolute timeout for ervice
         is enabled.";
    }
    leaf prepaid-idle-timeout-enabled {
      type boolean;
      description
        "Flag to specify if idle timeout for service is
         enabled";
    }
    leaf prepaid-final-unit {
      type boolean;
      description
        "Prepaid final unit indication flag";
    }
    leaf stats-pending-flag {
      type boolean;
      description
        "True if Prepaid Stats is Pending";
    }
    leaf srg-trans-in-progress {
      type boolean;
      description
        "True if SRG Transition Progress Status";
    }
    leaf prepaid-retry-cnt {
      type boolean;
      description
        "True if Prepaid Start Retry is set";
    }
    leaf prepaid-start-retry {
      type boolean;
      description
        "True if Prepaid Start Retry is set";
    }
    leaf prepaid-start-queued {
      type boolean;
      description
        "True if Prepaid Start Queue is set";
    }
    leaf prepaid-start-post-poned {
      type boolean;
      description
        "True if Prepaid Start Postpone is set";
    }
    leaf prepaid-zero-quota-arrived {
      type boolean;
      description
        "True if zero quota is arrived";
    }
    leaf unique-class-label {
      type uint32;
      description
        "Unique class label used to identify the flow";
    }
    leaf subscriber-label {
      type uint32;
      description
        "Subscriber label";
    }
    leaf interface-handle {
      type uint32;
      description
        "If Handle";
    }
    leaf flow-direction {
      type uint32;
      description
        "Direction of the flow. 0 = Ingress, 1 = Egress";
    }
    leaf transaction-id {
      type uint32;
      description
        "Transaction ID";
    }
    leaf service-id {
      type uint32;
      description
        "ServiceID";
    }
    leaf reporting-reason {
      type uint32;
      description
        "Reporting Reason";
    }
    leaf policy-map-name {
      type string {
        length "0..256";
      }
      description
        "Policy-Map name";
    }
    leaf class-map-name {
      type string {
        length "0..256";
      }
      description
        "ClassMap name";
    }
    leaf flow-acct-dyn-template-name {
      type string {
        length "0..256";
      }
      description
        "Flow accounting Dynamic Template name";
    }
    leaf flow-accounting-periodic-interval {
      type uint32;
      description
        "Flow accounting periodic interval";
    }
    leaf flow-idle-timeout-value {
      type uint32;
      units "second";
      description
        "Flow idle timeout value in seconds";
    }
    leaf prepaid-pending-event {
      type uint32;
      description
        "Prepaid Pending AAA Event";
    }
    leaf prepaid-start-req-status {
      type uint32;
      description
        "Prepaid Start Request status";
    }
    leaf prepaid-start-sent-timestamp {
      type uint64;
      units "second";
      description
        "Session Start sent time, Timestamp in seconds";
    }
    leaf prepaid-start-ac-kd-timestamp {
      type uint64;
      units "second";
      description
        "Session Accounting Start Response time,
         Timestamp in seconds";
    }
    leaf prepaid-stop-req-status {
      type uint32;
      description
        "Prepaid Stop Request status";
    }
    leaf prepaid-stop-sent-timestamp {
      type uint64;
      units "second";
      description
        "Session Accounting Stop Sent time, Timestamp in
         seconds";
    }
    leaf prepaid-time-quota {
      type uint32;
      units "second";
      description
        "Current prepaid time quota in seconds";
    }
    leaf prepaid-time-threshold {
      type uint32;
      units "second";
      description
        "Current prepaid time threshold in seconds";
    }
    leaf prepaid-total-time-quota {
      type uint32;
      description
        "Total accumulated prepaid time quota";
    }
    leaf prepaid-volume-threshold {
      type uint32;
      units "byte";
      description
        "Current prepaid volume threshold in bytes";
    }
    leaf prepaid-remaining-qt {
      type uint32;
      description
        "The time remaing for QT timer to fire.";
    }
    leaf prepaid-remaining-qat {
      type uint32;
      description
        "The time remaing for quota absolute timer to
         fire.";
    }
    leaf prepaid-remaining-qit {
      type uint32;
      description
        "The time remaing for quota holding timer to fire
         .";
    }
    leaf prepaid-remaining-qtt {
      type uint32;
      description
        "The time remaining for tariff timer to fire.";
    }
    leaf prepaid-remaining-wheel {
      type uint32;
      description
        "The time remaining for idle timer wheel to fire.";
    }
    leaf prepaid-tariff-time {
      type uint64;
      description
        "The absolute time at which the traffic switch
         will occur expressed in UNIX time";
    }
    leaf prepaid-idle-timeout-value {
      type uint32;
      units "second";
      description
        "Prepaid idle timeout value in seconds";
    }
    leaf prepaid-reauth-timeout-value {
      type uint32;
      description
        "The time at which the re-authorization will
         occur";
    }
    leaf prepaid-ccfh {
      type uint32;
      description
        "Prepaid CCFH flag";
    }
    leaf prepaid-result-code {
      type uint32;
      description
        "Prepaid authorization operation result code";
    }
    leaf prepaid-volumei-quota {
      type uint64;
      units "byte";
      description
        "Current prepaid input volume quota in bytes";
    }
    leaf prepaid-volumeo-quota {
      type uint64;
      units "byte";
      description
        "Current prepaid output volume quota in bytes";
    }
    leaf prepaid-volumeb-quota {
      type uint64;
      units "byte";
      description
        "Current prepaid total volume quota in bytes";
    }
    leaf prepaid-total-volumei-quota {
      type uint64;
      units "byte";
      description
        "Total accumulated input volume quota in bytes";
    }
    leaf prepaid-total-volumeo-quota {
      type uint64;
      units "byte";
      description
        "Total accumulated output volume quota in bytes";
    }
    leaf prepaid-total-volumeb-quota {
      type uint64;
      units "byte";
      description
        "Total accumulated total volume quota in bytes";
    }
    leaf prepaid-volume-usedi-quota {
      type uint64;
      units "byte";
      description
        "Accumulated input volume used quota in bytes";
    }
    leaf prepaid-volume-usedo-quota {
      type uint64;
      units "byte";
      description
        "Accumulated output volume used quota in bytes";
    }
    leaf prepaid-volume-refi-quota {
      type uint64;
      units "byte";
      description
        "Accumulated input volume reference quota in
         bytes";
    }
    leaf prepaid-volume-refo-quota {
      type uint64;
      units "byte";
      description
        "Accumulated output volume reference quota in
         bytes";
    }
    leaf prepaid-volume-refb-quota {
      type uint64;
      units "byte";
      description
        "Accumulated bi-directional volume reference
         quota in bytes";
    }
    leaf prepaid-volume-agg-refi-quota {
      type uint64;
      units "byte";
      description
        "Total Accumulated input volume reference quota
         in bytes";
    }
    leaf prepaid-volume-agg-refo-quota {
      type uint64;
      units "byte";
      description
        "Total Accumulated output volume reference quota
         in bytes";
    }
    leaf prepaid-volume-agg-refb-quota {
      type uint64;
      units "byte";
      description
        "Total Accumulated bi-directional volume
         reference quota in bytes";
    }
    leaf prepaid-volume-rem-refi-quota {
      type uint64;
      units "byte";
      description
        "Total Accumulated input volume reference quota
         in bytes";
    }
    leaf prepaid-volume-rem-refo-quota {
      type uint64;
      units "byte";
      description
        "Total Accumulated output volume reference quota
         in bytes";
    }
    leaf prepaid-volume-rem-refb-quota {
      type uint64;
      units "byte";
      description
        "Total Accumulated bi-directional volume
         reference quota in bytes";
    }
    leaf prepaid-volume-newi-quota {
      type uint64;
      units "byte";
      description
        "Newly arrvied input volume quota in bytes";
    }
    leaf prepaid-volume-newo-quota {
      type uint64;
      units "byte";
      description
        "Newly arrvied output volume quota in bytes";
    }
    leaf prepaid-volume-newb-quota {
      type uint64;
      units "byte";
      description
        "Newly arrvied bi-directional volume quota in
         bytes";
    }
    leaf prepaid-tariff-volumei-quota {
      type uint64;
      units "byte";
      description
        "Total accumulated prepaid pre-tarrif input
         volume quota in bytes";
    }
    leaf prepaid-tariff-volumeo-quota {
      type uint64;
      units "byte";
      description
        "Total accumulated prepaid pre-tarrif output
         volume quota in bytes";
    }
    leaf prepaid-tariff-volumeb-quota {
      type uint64;
      units "byte";
      description
        "Total accumulated prepaid pre-tarrif total
         volume quota in bytes";
    }
    leaf flow-accounting-method-list-name {
      type string {
        length "0..256";
      }
      description
        "Flow accounting method list name";
    }
    leaf prepaid-cfg {
      type string {
        length "0..256";
      }
      description
        "Prepaid Config";
    }
    leaf prepaid-time-state {
      type string {
        length "0..256";
      }
      description
        "Prepaid time state machine state";
    }
    leaf prepaid-volume-state {
      type string {
        length "0..256";
      }
      description
        "Prepaid volume state machine state";
    }
    leaf prepaid-charging-rule {
      type string {
        length "0..256";
      }
      description
        "Prepaid charging rule name string";
    }
  }

  grouping ACCT-MA-FLOW-FEATURES {
    description
      "ACCT MA FLOW FEATURES";
    container flow-feature-data {
      description
        "Accouting flow feature display data";
      uses ACCT-MA-FLOW-FEAT-BAG-DATA;
    }
  }

  grouping ACCT-MA-CTX-BAG-SUM-COUNTS {
    description
      "ACCT MA CTX BAG SUM COUNTS";
    leaf active-sessions {
      type uint32;
      description
        "Number of Active Sessions";
    }
    leaf disconnected-sessions {
      type uint32;
      description
        "Number of Disconnected Sessions";
    }
    leaf active-session-accounting-sessions {
      type uint32;
      description
        "Number of Active Sessions with Accounting";
    }
    leaf active-flows {
      type uint32;
      description
        "Number of Active Flows";
    }
    leaf quota-received {
      type uint32;
      description
        "Number of flows for which Quota is received";
    }
  }

  grouping ACCT-MA-SESS-TO-BAG-SUM-COUNTS {
    description
      "ACCT MA SESS TO BAG SUM COUNTS";
    leaf active-session-timers {
      type uint32;
      description
        "Number of Active Session Timers";
    }
    leaf expired-session-timers {
      type uint32;
      description
        "Number of Expired Session Timers";
    }
  }

  grouping ACCT-MA-IDLE-TO-BAG-SUM-COUNTS {
    description
      "ACCT MA IDLE TO BAG SUM COUNTS";
    leaf active-session-idle-timers {
      type uint32;
      description
        "Number of Sessions with Idle Timeout Feature";
    }
    leaf idle-sessions {
      type uint32;
      description
        "Number of Idle Sessions";
    }
    leaf transitions-to-idle {
      type uint32;
      description
        "Number of Sessions Transitions to Idle State";
    }
    leaf transitions-to-awake {
      type uint32;
      description
        "Number of Sessions Transitions to Awake State";
    }
    leaf active-flow-idle-timers {
      type uint32;
      description
        "Number of Active Flow Idle Timers";
    }
    leaf expired-flow-idle-timers {
      type uint32;
      description
        "Number of Flow Expired Idle Timers";
    }
    leaf active-prepaid-idle-timers {
      type uint32;
      description
        "Number of Active Prepaid Idle Timers";
    }
    leaf expired-prepaid-idle-timers {
      type uint32;
      description
        "Number of Expired Prepaid Idle Timers";
    }
  }

  grouping ACCT-MA-AAA-BAG-SUM-COUNTS {
    description
      "ACCT MA AAA BAG SUM COUNTS";
    leaf flow-start {
      type uint32;
      description
        "Number of Flow Start Requests Sent";
    }
    leaf flow-disconnect {
      type uint32;
      description
        "Number of Flow Disconnect Requests Sent";
    }
    leaf session-accounting-start {
      type uint32;
      description
        "Number of Session Accounting Start Requests Sent";
    }
    leaf session-accounting-stop {
      type uint32;
      description
        "Number of Session Accounting Stop Requests Sent";
    }
    leaf session-accounting-update {
      type uint32;
      description
        "Number of Session Accounting Update Requests
         Sent";
    }
    leaf service-accounting-start {
      type uint32;
      description
        "Number of Service Accounting Start Requests Sent";
    }
    leaf service-accounting-stop {
      type uint32;
      description
        "Number of Service Accounting Stop Requests Sent";
    }
    leaf service-accounting-update {
      type uint32;
      description
        "Number of Service Accounting Update Requests
         Sent";
    }
    leaf flow-accounting-start {
      type uint32;
      description
        "Number of Flow Accounting Start Requests Sent";
    }
    leaf flow-accounting-stop {
      type uint32;
      description
        "Number of Flow Accounting Stop Requests Sent";
    }
    leaf flow-accounting-update {
      type uint32;
      description
        "Number of Flow Accounting Update Requests Sent";
    }
    leaf accounting-callback {
      type uint32;
      description
        "Number of Accounting Callbacks Received";
    }
    leaf session-acct-trans-pending {
      type uint32;
      description
        "Number of Session Accounting transactions
         pending";
    }
    leaf session-acct-reqs-failed {
      type uint32;
      description
        "Number of Session Accounting requests that
         failed";
    }
    leaf session-acct-out-of-sync {
      type uint32;
      description
        "Number of Session Accounting sessions out of
         sync";
    }
    leaf session-idle-to-trans-pending {
      type uint32;
      description
        "Number of Session Idle Timeout transactions
         pending";
    }
    leaf session-idle-to-reqs-failed {
      type uint32;
      description
        "Number of Session Idle Timeout requests that
         failed";
    }
    leaf session-idle-to-out-of-sync {
      type uint32;
      description
        "Number of Session Idle Timeout sessions out of
         sync";
    }
    leaf service-acct-trans-pending {
      type uint32;
      description
        "Number of Service Accounting transactions
         pending";
    }
    leaf service-acct-reqs-failed {
      type uint32;
      description
        "Number of Service Accounting requests that
         failed";
    }
    leaf service-acct-out-of-sync {
      type uint32;
      description
        "Number of Service Accounting services out of
         sync";
    }
    leaf service-idle-to-trans-pending {
      type uint32;
      description
        "Number of Service Idle Timeout transactions
         pending";
    }
    leaf service-idle-to-reqs-failed {
      type uint32;
      description
        "Number of Service Idle Timeout requests that
         failed";
    }
    leaf service-idle-to-out-of-sync {
      type uint32;
      description
        "Number of Service Idle Timeout services out of
         sync";
    }
    leaf prepaid-start {
      type uint32;
      description
        "Number of Prepaid Start Requests Sent";
    }
    leaf prepaid-stop {
      type uint32;
      description
        "Number of Prepaid Stop Requests Sent";
    }
    leaf prepaid-accounting-start {
      type uint32;
      description
        "Number of Prepaid Accounting Start Requests Sent";
    }
    leaf prepaid-accounting-stop {
      type uint32;
      description
        "Number of Prepaid Accounting Stop Requests Sent";
    }
    leaf prepaid-volume-threshold-reached {
      type uint32;
      description
        "Number of Prepaid Volume Threshold Reached
         Requests Sent";
    }
    leaf prepaid-time-threshold-reached {
      type uint32;
      description
        "Number of Prepaid Time Threshold Reached
         Requests Sent";
    }
    leaf prepaid-quota-depleted {
      type uint32;
      description
        "Number of Prepaid Quota Depleted Requests Sent";
    }
    leaf prepaid-reauthorization {
      type uint32;
      description
        "Number of Prepaid Authorization Requests Sent";
    }
    leaf idle-timeout {
      type uint32;
      description
        "Number of Idle Timeout Events Sent";
    }
    leaf idle-timeout-response-callback {
      type uint32;
      description
        "Number of Idle Timeout Callbacks Received";
    }
    leaf owned-resource-start {
      type uint32;
      description
        "Number of Owned Resource Starts";
    }
    leaf srg-subscriber-mismatch-walks {
      type uint32;
      description
        "Number of SRG parent walks that found subscriber
         membership mismatch";
    }
    leaf srg-subscriber-local-only {
      type uint32;
      description
        "Number of subscriber observations present only
         in Accounting MA";
    }
    leaf srg-subscriber-sadb-only {
      type uint32;
      description
        "Number of subscriber observations present only
         in SADB";
    }
    leaf srg-subscriber-sadb-query-failures {
      type uint32;
      description
        "Number of failed SADB parent subscriber
         membership queries";
    }
  }

  grouping ACCT-MA-FEATURE-SUMMARY {
    description
      "ACCT MA FEATURE SUMMARY";
    container aaa-counters {
      description
        "Accounting feature AAA summary counters";
      uses ACCT-MA-AAA-BAG-SUM-COUNTS;
    }
    container idle-timeout-counters {
      description
        "Accounting feature idle timeout summary counters";
      uses ACCT-MA-IDLE-TO-BAG-SUM-COUNTS;
    }
    container session-timeout-counters {
      description
        "Accounting feature session timeout summary
         counters";
      uses ACCT-MA-SESS-TO-BAG-SUM-COUNTS;
    }
    container session-flow-counters {
      description
        "Accounting feature session context summary
         counters";
      uses ACCT-MA-CTX-BAG-SUM-COUNTS;
    }
  }

  grouping ACCT-MA-SERV-FEAT-BAG-DATA {
    description
      "ACCT MA SERV FEAT BAG DATA";
    leaf service-accounting-enabled-flag {
      type boolean;
      description
        "True if service accounting is enabled";
    }
    leaf service-accounting-service-id {
      type uint32;
      description
        "Service accounting service ID";
    }
    leaf service-accounting-method-list {
      type string {
        length "0..256";
      }
      description
        "Service accounting method list name";
    }
    leaf service-accounting-periodic-interval {
      type uint32;
      description
        "Service accounting periodic interval";
    }
    leaf session-accounting-aaa-trans-pending {
      type uint32;
      description
        "Number of Service Accounting AAA transactions
         pending for the service";
    }
    leaf service-accounting-start-sent {
      type uint32;
      description
        "Number of Service Accounting AAA request
         failures for the service";
    }
    leaf session-accounting-aaa-request-failed {
      type uint32;
      description
        "Number of Service Accounting AAA request
         failures for the service";
    }
    leaf service-accounting-start-ackd {
      type boolean;
      description
        "True if Service accounting started  for the
         service";
    }
    leaf service-accounting-start-sent-timestamp {
      type uint64;
      units "second";
      description
        "Service Accounting Start Sent, Timestamp in
         seconds";
    }
    leaf service-acct-start-ac-kd-timestamp {
      type uint64;
      units "second";
      description
        "Service Accounting Start Response, Timestamp in
         seconds";
    }
    leaf service-accounting-stop-sent-timestamp {
      type uint64;
      units "second";
      description
        "Service Accounting Stop Sent, Timestamp in
         seconds";
    }
    leaf service-feature-accounting-enabled-flag {
      type boolean;
      description
        "True if service feature accounting is enabled";
    }
    leaf service-accounting-flags {
      type uint32;
      description
        "Flags for Service Accounting";
    }
  }

  grouping ACCT-MA-SESS-FEAT-BAG-DATA {
    description
      "ACCT MA SESS FEAT BAG DATA";
    leaf unique-subscriber-label {
      type uint32;
      description
        "Unique subscriber label used to identify the
         session";
    }
    leaf interface-handle {
      type uint32;
      description
        "Handle of interface associated with the session";
    }
    leaf session-disconnected {
      type boolean;
      description
        "True if session is disconnected";
    }
    leaf session-accounting-enabled-flag {
      type boolean;
      description
        "True if session accounting is enabled";
    }
    leaf session-accounting-method-list {
      type string {
        length "0..256";
      }
      description
        "Session accounting method list name";
    }
    leaf session-accounting-periodic-interval {
      type uint32;
      description
        "Session accounting periodic interval";
    }
    leaf session-accounting-aaa-trans-pending {
      type uint32;
      description
        "Number of Session Accounting AAA transactions
         pending";
    }
    leaf session-accounting-start-sent {
      type uint32;
      description
        "True if session accounting started";
    }
    leaf session-accounting-aaa-request-failed {
      type uint32;
      description
        "Number of Session Accounting AAA request
         failures";
    }
    leaf session-accounting-start-ackd {
      type boolean;
      description
        "True if session accounting started";
    }
    leaf session-start-sent-timestamp {
      type uint32;
      description
        "Session Start sent time in DDD MMM DD HH:MM:SS
         YYYY format eg: Tue Apr 11 21:30:47 2011";
    }
    leaf session-acct-start-ac-kd-timestamp {
      type uint32;
      description
        "Session Accounting Start Response time in DDD
         MMM DD HH:MM:SS YYYY format eg: Tue Apr 11 21:30
         :47 2011";
    }
    leaf session-accounting-stop-sent-timestamp {
      type uint32;
      description
        "Session Accounting Stop Sent time in DDD MMM DD
         HH:MM:SS YYYY format eg: Tue Apr 11 21:30:47
         2011";
    }
    leaf session-idle-timeout-enabled-flag {
      type boolean;
      description
        "True if session idle timeout is enabled";
    }
    leaf idle-timeout-value {
      type uint32;
      units "second";
      description
        "Idle timeout value in seconds";
    }
    leaf idle-timeout-threshold {
      type uint32;
      units "minute";
      description
        "Idle timeout threshold in minutes per packets";
    }
    leaf idle-timeout-direction {
      type string {
        length "0..256";
      }
      description
        "Idle timeout direction";
    }
    leaf session-is-idle {
      type boolean;
      description
        "True if session is idle";
    }
    leaf session-stats-changed-time {
      type uint32;
      description
        "Last time session data was received";
    }
    leaf session-total-idle-time {
      type uint32;
      description
        "Total time session has been idle";
    }
    leaf session-to-idle-count {
      type uint32;
      description
        "Number of Session Idle AAA events";
    }
    leaf session-to-awake-count {
      type uint32;
      description
        "Number of Session Awake AAA events";
    }
    leaf session-idle-to-aaa-trans-pending {
      type uint32;
      description
        "Number of Session Idle AAA transactions pending";
    }
    leaf session-idle-to-aaa-request-failed {
      type uint32;
      description
        "Number of Session Idle AAA request failures";
    }
    leaf session-timeout-enabled-flag {
      type boolean;
      description
        "True if session timeout is enabled";
    }
    leaf session-timeout-value {
      type uint32;
      units "second";
      description
        "Session timeout value in seconds";
    }
    leaf session-timeout-time-remaining {
      type uint32;
      units "second";
      description
        "Number seconds remaining before session times
         out";
    }
    leaf session-accounting-flags {
      type uint32;
      description
        "Flags for Service Accounting";
    }
    list service-accounting-feature {
      description
        "List of service accounting features";
      uses ACCT-MA-SERV-FEAT-BAG-DATA;
    }
  }

  grouping ACCT-MA-SESSION-FEATURES {
    description
      "ACCT MA SESSION FEATURES";
    container session-feature-data {
      description
        "Accounting session feature display data";
      uses ACCT-MA-SESS-FEAT-BAG-DATA;
    }
  }
}
