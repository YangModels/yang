submodule Cisco-IOS-XR-terminal-device-oper-sub1 {
  belongs-to Cisco-IOS-XR-terminal-device-oper {
    prefix Cisco-IOS-XR-terminal-device-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR terminal-device package operational data.
     
     Copyright (c) 2013-2026 by Cisco Systems, Inc.
     All rights reserved.";

  revision 2026-04-16 {
    description
      "Added leaf logical-channel-assignment
       2025-12-16
         Extended frequency range in operational state to support C+S Band (up to 196.30 THz)
       2024-07-26
         Added Insight based telemetry
       2024-05-29
         Added support for gain offset CLI
       2023-03-23
         rate class support for 1200G added";
    semver:module-version "2.1.0";
  }
  revision 2020-05-20 {
    description
      "leaf fec, baut rate and oper-mode has been updated";
    semver:module-version "2.0.0";
  }
  revision 2019-04-05 {
    description
      "Establish semantic version baseline.";
    semver:module-version "1.1.0";
  }
  revision 2015-11-09 {
    description
      "IOS XR 6.0 revision.";
  }

  typedef Oc-mod-type-et {
    type enumeration {
      enum "mod-none" {
        value 0;
        description
          "Unknown Modulation";
      }
      enum "mod-bpsk" {
        value 1;
        description
          "BPSK Modulation";
      }
      enum "mod-qpsk" {
        value 2;
        description
          "QPSK Modulation";
      }
      enum "mod8qam" {
        value 3;
        description
          "8QAM Modulation";
      }
      enum "mod16qam" {
        value 4;
        description
          "16QAM Modulation";
      }
      enum "mod32qam" {
        value 5;
        description
          "32QAM Modulation";
      }
      enum "mod64qam" {
        value 6;
        description
          "64QAM Modulation";
      }
      enum "mod-eqpsk" {
        value 7;
        description
          "EQPSK Modulation";
      }
    }
    description
      "Oc mod type et";
  }

  typedef Fec {
    type enumeration {
      enum "fec-none" {
        value 0;
        description
          "Unknown FEC";
      }
      enum "fec-statndard" {
        value 1;
        description
          "Standard FEC";
      }
      enum "fec-otu1-i-7" {
        value 2;
        description
          "OTU 1 I 7";
      }
      enum "fec-otu1-i-4" {
        value 3;
        description
          "OTU 1 I 4";
      }
      enum "fec-swizzle" {
        value 4;
        description
          "FEC SWIZZLE";
      }
      enum "fec-hg20" {
        value 5;
        description
          "FEC HG20";
      }
      enum "fec-enhanced-hg7" {
        value 6;
        description
          "FEC ENHANCED HG7";
      }
      enum "fec-sd20" {
        value 7;
        description
          "FEC SD20";
      }
      enum "fec-sd7" {
        value 8;
        description
          "FEC SD7";
      }
      enum "fec-sd15" {
        value 9;
        description
          "FEC SD15";
      }
      enum "fec-sd27" {
        value 10;
        description
          "FEC SD27";
      }
      enum "fec-cfec" {
        value 11;
        description
          "FEC CFEC";
      }
      enum "fec-ofec" {
        value 12;
        description
          "FEC OFEC";
      }
    }
    description
      "Fec";
  }

  typedef Client-als {
    type enumeration {
      enum "none" {
        value 0;
        description
          "none";
      }
      enum "ethernet" {
        value 1;
        description
          "ethernet";
      }
      enum "laser-shutdown" {
        value 2;
        description
          "laser shutdown";
      }
    }
    description
      "Client als";
  }

  typedef Logical-protocol {
    type enumeration {
      enum "proto-type-unknown" {
        value 0;
        description
          "Unknown protocol framing";
      }
      enum "proto-type-ethernet" {
        value 1;
        description
          "Ethernet protocol framing";
      }
      enum "proto-type-otn" {
        value 2;
        description
          "OTN protocol framing";
      }
    }
    description
      "Logical protocol";
  }

  typedef Trib-protocol {
    type enumeration {
      enum "trib-proto-type-unknown" {
        value 0;
        description
          "Unknown protocol";
      }
      enum "trib-proto-type1ge" {
        value 1;
        description
          "1G Ethernet protocol";
      }
      enum "trib-proto-type-oc48" {
        value 2;
        description
          "OC48 protocol";
      }
      enum "trib-proto-type-stm16" {
        value 3;
        description
          "STM 16 protocol";
      }
      enum "trib-proto-type10gelan" {
        value 4;
        description
          "10G Ethernet LAN protocol";
      }
      enum "trib-proto-type10gewan" {
        value 5;
        description
          "10G Ethernet WAN protocol";
      }
      enum "trib-proto-type-oc192" {
        value 6;
        description
          "OC 192 (9.6GB) port protocol";
      }
      enum "trib-proto-type-stm64" {
        value 7;
        description
          "STM 64 protocol";
      }
      enum "trib-proto-type-otu2" {
        value 8;
        description
          "OTU 2 protocol";
      }
      enum "trib-proto-type-otu2e" {
        value 9;
        description
          "OTU 2e protocol";
      }
      enum "trib-proto-type-otu1e" {
        value 10;
        description
          "OTU 1e protocol";
      }
      enum "trib-proto-type-odu2" {
        value 11;
        description
          "ODU 2 protocol";
      }
      enum "trib-proto-type-odu2e" {
        value 12;
        description
          "ODU 2e protocol";
      }
      enum "trib-proto-type40ge" {
        value 13;
        description
          "40G Ethernet port protocol";
      }
      enum "trib-proto-type-oc768" {
        value 14;
        description
          "OC 768 protocol";
      }
      enum "trib-proto-type-stm256" {
        value 15;
        description
          "STM 256 protocol";
      }
      enum "trib-proto-type-otu3" {
        value 16;
        description
          "OTU 3 protocol";
      }
      enum "trib-proto-type-odu3" {
        value 17;
        description
          "ODU 3 protocol";
      }
      enum "trib-proto-type100ge" {
        value 18;
        description
          "100G Ethernet protocol";
      }
      enum "trib-proto-type100g-mlg" {
        value 19;
        description
          "100G MLG protocol";
      }
      enum "trib-proto-type-otu4" {
        value 20;
        description
          "OTU4 signal protocol (112G) for transporting
           100GE signal";
      }
      enum "trib-proto-type-otu-cn" {
        value 21;
        description
          "OTU Cn protocol";
      }
      enum "trib-proto-type-odu4" {
        value 22;
        description
          "ODU 4 protocol";
      }
      enum "trib-proto-type-odu-cn" {
        value 23;
        description
          "ODU Cn protocol";
      }
      enum "trib-proto-type-oduflexcbr" {
        value 24;
        description
          "ODU Flex CBR protocol";
      }
      enum "trib-proto-type-oduflexgfp" {
        value 25;
        description
          "ODU Flex GFP protocol";
      }
      enum "trib-proto-type400ge" {
        value 26;
        description
          "400G Ethernet protocol";
      }
      enum "trib-proto-type800ge" {
        value 27;
        description
          "800G Ethernet protocol";
      }
    }
    description
      "Trib protocol";
  }

  typedef Trib-rate-class {
    type enumeration {
      enum "trib-rate-unknown" {
        value 0;
        description
          "Unknown tributary signal rate";
      }
      enum "trib-rate1g" {
        value 1;
        description
          "1G tributary signal rate";
      }
      enum "trib-rate25g" {
        value 2;
        description
          "2.5G tributary signal rate";
      }
      enum "trib-rate10g" {
        value 3;
        description
          "10G tributary signal rate";
      }
      enum "trib-rate40g" {
        value 4;
        description
          "40G tributary signal rate";
      }
      enum "trib-rate100g" {
        value 5;
        description
          "100G tributary signal rate";
      }
      enum "trib-rate150g" {
        value 6;
        description
          "150G tributary signal rate";
      }
      enum "trib-rate200g" {
        value 7;
        description
          "200G tributary signal rate";
      }
      enum "trib-rate250g" {
        value 8;
        description
          "250G tributary signal rate";
      }
      enum "trib-rate300g" {
        value 9;
        description
          "300G tributary signal rate";
      }
      enum "trib-rate400g" {
        value 10;
        description
          "400G tributary signal rate";
      }
      enum "trib-rate500g" {
        value 11;
        description
          "500G tributary signal rate";
      }
      enum "trib-rate600g" {
        value 12;
        description
          "600G tributary signal rate";
      }
      enum "trib-rate700g" {
        value 13;
        description
          "700G tributary signal rate";
      }
      enum "trib-rate800g" {
        value 14;
        description
          "800G tributary signal rate";
      }
      enum "trib-rate900g" {
        value 15;
        description
          "900G tributary signal rate";
      }
      enum "trib-rate1000g" {
        value 16;
        description
          "1000G tributary signal rate";
      }
      enum "trib-rate1100g" {
        value 17;
        description
          "1100G tributary signal rate";
      }
      enum "trib-rate1200g" {
        value 18;
        description
          "1200G tributary signal rate";
      }
    }
    description
      "Trib rate class";
  }

  grouping OPERATIONAL-MODE-ATTRIBUTES {
    description
      "OPERATIONAL MODE ATTRIBUTES";
    leaf fec {
      type Fec;
      description
        "Fec";
    }
    leaf description {
      type string {
        length "0..128";
      }
      description
        "Description";
    }
    leaf vendor-id {
      type string {
        length "0..64";
      }
      description
        "VendorId";
    }
    leaf baud-rate {
      type string {
        length "0..128";
      }
      description
        "BaudRate";
    }
    leaf modulation {
      type Oc-mod-type-et;
      description
        "Modulation";
    }
    leaf dac-rate {
      type string;
      description
        "DacRate";
    }
  }

  grouping OPTICAL-CHANNEL-ATTRIBUTES {
    description
      "OPTICAL CHANNEL ATTRIBUTES";
    leaf name {
      type string {
        length "0..128";
      }
      description
        "Name";
    }
    leaf index {
      type uint32;
      description
        "Index";
    }
    leaf frequency {
      type uint64;
      description
        "Frequency";
    }
    leaf power {
      type uint64;
      description
        "Power";
    }
    leaf oper-mode {
      type uint16;
      description
        "OperMode";
    }
    leaf filter-roll-off-factor {
      type string {
        length "0..256";
      }
      description
        "FilterRollOffFactor";
    }
    leaf enh-colorless-mode {
      type uint32;
      description
        "EnhColorlessMode";
    }
    leaf enh-sop-tol-mode {
      type uint32;
      description
        "EnhSopTolMode";
    }
    leaf nleq-comp-mode {
      type uint32;
      description
        "NleqCompMode";
    }
    leaf cross-pol-gain-mode {
      type uint32;
      description
        "CrossPolGainMode";
    }
    leaf cross-pol-weight-mode {
      type uint32;
      description
        "CrossPolWeightMode";
    }
    leaf cpr-win-mode {
      type uint32;
      description
        "CprWinMode";
    }
    leaf cpr-ext-win-mode {
      type uint32;
      description
        "CprExtWinMode";
    }
    leaf cd-max {
      type int32;
      description
        "CDMax";
    }
    leaf cd-min {
      type int32;
      description
        "CDMin";
    }
    leaf cd-high-threshold {
      type int32;
      description
        "CDHighThreshold";
    }
    leaf cd-low-threshold {
      type int32;
      description
        "CDLowThreshold";
    }
    leaf rx-voa-fixed-ratio {
      type int32;
      description
        "RxVoaFixedRatio";
    }
    leaf rx-voa-target-power {
      type int32;
      description
        "RxVoaTargetPower";
    }
    leaf line-port {
      type string {
        length "0..128";
      }
      description
        "LinePort";
    }
    leaf rx-voa-gain-offset {
      type int32;
      description
        "RxVoaGainOffset";
    }
    leaf logical-channel-assignment {
      type uint32;
      description
        "LogicalChannelAssignment";
    }
  }

  grouping GRAPH-STRUCTURE-PATH {
    description
      "GRAPH STRUCTURE PATH";
    leaf path {
      type string {
        length "0..256";
      }
      description
        "Path";
    }
  }

  grouping ADJACENCY-LIST-PATH {
    description
      "ADJACENCY LIST PATH";
    leaf path {
      type string {
        length "0..256";
      }
      description
        "Path";
    }
  }

  grouping PARTIAL-CONFIG-STATUS {
    description
      "PARTIAL CONFIG STATUS";
    leaf partial-config {
      type uint8;
      description
        "PartialConfig";
    }
  }

  grouping SLICE-CONFIG-STATUS-ATTRIBUTES {
    description
      "SLICE CONFIG STATUS ATTRIBUTES";
    leaf slice {
      type uint8;
      description
        "Slice";
    }
    leaf prov-status {
      type string {
        length "0..32";
      }
      description
        "ProvStatus";
    }
    leaf present-config {
      type string {
        length "0..32";
      }
      description
        "PresentConfig";
    }
    leaf present-timestamp {
      type string {
        length "0..32";
      }
      description
        "PresentTimestamp";
    }
    leaf past-config {
      type string {
        length "0..32";
      }
      description
        "PastConfig";
    }
    leaf past-timestamp {
      type string {
        length "0..32";
      }
      description
        "PastTimestamp";
    }
    leaf err-str {
      type string {
        length "0..1024";
      }
      description
        "ErrStr";
    }
    leaf err-timestamp {
      type string {
        length "0..32";
      }
      description
        "ErrTimestamp";
    }
  }

  grouping LOGICAL-CHANNEL-ATTRIBUTES {
    description
      "LOGICAL CHANNEL ATTRIBUTES";
    leaf logical-channel-index {
      type uint32;
      description
        "LogicalChannelIndex";
    }
    leaf logical-channel-ifname {
      type string {
        length "0..128";
      }
      description
        "LogicalChannelIfname";
    }
    leaf type {
      type string {
        length "0..32";
      }
      description
        "Type";
    }
    leaf trib-rate-class {
      type Trib-rate-class;
      description
        "TribRateClass";
    }
    leaf trib-protocol {
      type Trib-protocol;
      description
        "TribProtocol";
    }
    leaf protocol-type {
      type Logical-protocol;
      description
        "ProtocolType";
    }
    leaf admin-state {
      type uint32;
      description
        "AdminState";
    }
    leaf loopback-mode {
      type uint32;
      description
        "LoopbackMode";
    }
    leaf ingress-client-port {
      type string {
        length "0..128";
      }
      description
        "IngressClientPort";
    }
    leaf ingress-physical-channel {
      type uint32;
      description
        "IngressPhysicalChannel";
    }
    leaf tti-transmit {
      type string {
        length "0..256";
      }
      description
        "TtiTransmit";
    }
    leaf tti-expected {
      type string {
        length "0..256";
      }
      description
        "TtiExpected";
    }
    leaf client-als {
      type Client-als;
      description
        "ClientAls";
    }
    leaf als-delay {
      type uint32;
      description
        "AlsDelay";
    }
  }

  grouping LOGICAL-CHANNEL-ASSIGNMENT {
    description
      "LOGICAL CHANNEL ASSIGNMENT";
    leaf index {
      type uint32;
      description
        "Index";
    }
    leaf name {
      type string {
        length "0..128";
      }
      description
        "Name";
    }
    leaf is-logical-link {
      type boolean;
      description
        "IsLogicalLink";
    }
    leaf logical-channel {
      type uint32;
      description
        "LogicalChannel";
    }
    leaf optical-channel {
      type string {
        length "0..128";
      }
      description
        "OpticalChannel";
    }
    leaf allocation {
      type uint32;
      description
        "Allocation";
    }
    leaf assignment-type {
      type uint32;
      description
        "AssignmentType";
    }
  }
}
