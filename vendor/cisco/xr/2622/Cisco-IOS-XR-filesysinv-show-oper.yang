module Cisco-IOS-XR-filesysinv-show-oper {
  namespace "http://cisco.com/ns/yang/Cisco-IOS-XR-filesysinv-show-oper";
  prefix filesysinv-show-oper;

  import Cisco-IOS-XR-types {
    prefix xr;
  }
  import cisco-semver {
    prefix semver;
  }
  include Cisco-IOS-XR-filesysinv-show-oper-sub1 {
    revision-date 2019-04-05;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR filesysinv-show package operational data.
     
     This module contains definitions
     for the following management objects:
       file-system-inventory: File System Snapshot operational data
     
     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  grouping SNAPSHOT-ID {
    description
      "Common node of xr, admin";
    list snapshot-id {
      key "snapshot-id";
      description
        "Snapshot date and time and number";
      container snapshot-info {
        description
          "Current file system inventory snapshot";
        uses FILESYS-INV-FILE-SYSTEM-SIGNED-SNAPSHOT;
      }
      leaf snapshot-id {
        type xr:Cisco-ios-xr-string;
        description
          "Snapshot id";
      }
    }
  }

  container file-system-inventory {
    config false;
    description
      "File System Snapshot operational data";
    container rack-slots {
      description
        "List of nodes (having admin only) with filesys
         inv operation data";
      list rack-slot {
        key "card-id";
        description
          "Card";
        container snapshot {
          description
            "File SystemInventory Snapshot";
          container on-demand-all {
            description
              "On Demand Snapshot for Root Directory";
            uses FILESYS-INV-FILE-SYSTEM-SIGNED-SNAPSHOT;
          }
          container current {
            description
              "Current File SystemInventory Snapshot";
            uses FILESYS-INV-FILE-SYSTEM-SIGNED-SNAPSHOT;
          }
          container snapshot-ids {
            description
              "File SystemInventory Snapshot";
            list snapshot-id {
              key "snapshot-id";
              description
                "Snapshot date and time and number";
              container snapshot-info {
                description
                  "Current file system inventory snapshot";
                uses FILESYS-INV-FILE-SYSTEM-SIGNED-SNAPSHOT;
              }
              leaf snapshot-id {
                type xr:Cisco-ios-xr-string;
                description
                  "Snapshot id";
              }
            }
          }
        }
        leaf card-id {
          type xr:Cisco-ios-xr-string;
          description
            "Card id";
        }
      }
    }
    container nodes {
      description
        "List of nodes with filesys inv operation data";
      list node {
        key "node-name";
        description
          "Node with filesys inv operational data";
        container snapshot {
          description
            "File SystemInventory Snapshot";
          container directory-sets {
            description
              "OnDemand Configured Snapshot. Only supported
               for Full Snapshot type";
            list directory-set {
              key "on-demand-dir-set";
              description
                "On Demand Snapshot for Configured Directory
                 Set";
              leaf on-demand-dir-set {
                type xr:Cisco-ios-xr-string;
                description
                  "Set id";
              }
              uses FILESYS-INV-FILE-SYSTEM-SIGNED-SNAPSHOT;
            }
          }
          container current {
            description
              "Current File SystemInventory Snapshot";
            container admin {
              description
                "Current File SystemInventory Snapshot";
              uses FILESYS-INV-FILE-SYSTEM-SIGNED-SNAPSHOT;
            }
            container xr {
              description
                "Current File SystemInventory Snapshot";
              uses FILESYS-INV-FILE-SYSTEM-SIGNED-SNAPSHOT;
            }
          }
          container all {
            description
              "List of all available File SystemInventory
               Snapshots";
            container admin {
              description
                "File SystemInventory Snapshot";
              uses SNAPSHOT-ID;
            }
            container xr {
              description
                "File SystemInventory Snapshot";
              uses SNAPSHOT-ID;
            }
          }
          container on-demand-all {
            description
              "On Demand Snapshot for Root Directory. Only
               supported for Full Snapshot type";
            container admin {
              description
                "On Demand Snapshot for Root Directory";
              uses FILESYS-INV-FILE-SYSTEM-SIGNED-SNAPSHOT;
            }
            container xr {
              description
                "On Demand Snapshot for Root Directory";
              uses FILESYS-INV-FILE-SYSTEM-SIGNED-SNAPSHOT;
            }
          }
        }
        leaf node-name {
          type xr:Node-id;
          description
            "Node name";
        }
      }
    }
  }
}
