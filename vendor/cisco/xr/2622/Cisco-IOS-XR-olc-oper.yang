module Cisco-IOS-XR-olc-oper {
  namespace "http://cisco.com/ns/yang/Cisco-IOS-XR-olc-oper";
  prefix olc-oper;

  import Cisco-IOS-XR-types {
    prefix xr;
  }
  import cisco-semver {
    prefix semver;
  }
  include Cisco-IOS-XR-olc-oper-sub1 {
    revision-date 2026-03-02;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR olc package operational data.
     
     This module contains definitions
     for the following management objects:
       olc: Optical Application oper data
     
     Copyright (c) 2013-2026 by Cisco Systems, Inc.
     All rights reserved.";

  revision 2026-03-02 {
    description
      "Fix for NCS1014 amplifier APC regulation measurement units";
    semver:module-version "1.0.0";
  }
  revision 2026-02-05 {
    description
      "Added last correction span loss in ampli apc CLI information";
  }
  revision 2025-12-05 {
    description
      "Added enum representation for osc state and span type and deprecated older fields in topology CLI";
  }
  revision 2025-10-20 {
    description
      "Added new oper data for OSC TX Regulation";
  }
  revision 2025-08-08 {
    description
      "Added Span Loss relative thresholds to the OLC baseline information";
  }
  revision 2025-08-04 {
    description
      "Add new parameters to alc baseline CLI to display optical parameters";
  }
  revision 2025-06-21 {
    description
      "Add new CLI to display the OLC baseline information";
  }
  revision 2025-04-21 {
    description
      "Add new CLI to display the line-System topology information";
  }
  revision 2025-03-07 {
    description
      "Add new show and activation for NCS1014 APC control loop applications";
  }
  revision 2025-01-13 {
    description
      "Revert previous change";
  }
  revision 2024-11-12 {
    description
      "Fix typos in enums";
  }
  revision 2024-11-09 {
    description
      "Bidirectional OTDR autoscan status support";
  }
  revision 2024-10-29 {
    description
      "Remove OTDR baseline from ALC baseline";
  }
  revision 2024-10-20 {
    description
      "Added new raman tuning bag for raman gain profile details";
  }
  revision 2024-07-22 {
    description
      "Add TIMEOUT status for ALC agent and manager";
  }
  revision 2024-06-28 {
    description
      "Add Timestamp bag to ALC baseline";
  }
  revision 2024-05-28 {
    description
      "1010-1014 CLI re-group for conditional install";
  }
  revision 2024-05-01 {
    description
      "ALC Span Loss baseline field additions";
  }
  revision 2024-03-22 {
    description
      "Fix unit in descrption for span loss bag";
  }
  revision 2024-03-20 {
    description
      "Link status bag field name changed";
  }
  revision 2024-02-28 {
    description
      "Link status osnr fields removal";
  }
  revision 2023-10-28 {
    description
      "ALC status and baseline CLI modifications.";
  }
  revision 2023-10-01 {
    description
      "Otdr autoscan status and reason fields modification.";
  }
  revision 2023-08-21 {
    description
      "ALC status and baseline CLI addition";
  }
  revision 2023-05-24 {
    description
      "Otdr autoscan CLI addition";
  }
  revision 2023-04-18 {
    description
      "Link-status CLI addition";
  }
  revision 2022-12-20 {
    description
      "Comments added for all the fields in bag";
  }
  revision 2022-10-10 {
    description
      "raman tune status details CLI addition";
  }
  revision 2022-10-06 {
    description
      "Enhanced APC domain CLI for partial topology support";
  }
  revision 2022-06-30 {
    description
      "C+L band status CLI addition";
  }
  revision 2022-06-03 {
    description
      "L Band Path Loss information.";
  }
  revision 2022-04-18 {
    description
      "Link tuner bag modification include PSD index.";
  }
  revision 2021-12-07 {
    description
      "Link tuner CLI modification.";
  }
  revision 2021-03-26 {
    description
      "Span-loss CLI modification.";
  }
  revision 2021-01-19 {
    description
      "APC oper CLI addition.";
  }
  revision 2020-11-05 {
    description
      "Initial Revision.";
  }
  revision 2019-04-05 {
    description
      "Establish semantic version baseline.";
  }
  revision 2015-11-09 {
    description
      "IOS XR 6.0 revision.";
  }

  typedef Apc-reg-info-dir {
    type enumeration {
      enum "tx" {
        value 0;
        description
          "TX Direction";
      }
      enum "rx" {
        value 1;
        description
          "RX Direction";
      }
    }
    description
      "Apc reg info dir";
  }

  container olc {
    config false;
    description
      "Optical Application oper data";
    container channel-apc-mols-table {
      description
        "Channel APC MOLS per controller status
         information";
      container channel-apc-reg-info-mols-ctrlr-tables {
        description
          "Channel APC regulation oper data for MOLS";
        list channel-apc-reg-info-mols-ctrlr-table {
          key "name";
          description
            "Channel APC per controller regulation for MOLS";
          leaf name {
            type xr:Interface-name;
            description
              "Controller RSIP";
          }
          uses OLC-CHANNEL-APC-MOLS-REG-INFO;
        }
      }
    }
    container alc-status-ctrlr-tables {
      description
        "ALC procedure Status per controller information";
      list alc-status-ctrlr-table {
        key "name";
        description
          "Controller ALC procedure Status information";
        leaf name {
          type xr:Interface-name;
          description
            "Controller RSIP";
        }
        uses OLC-CONTROLLER-ALC-STATUS;
      }
    }
    container raman-tuning-ctrlr-tables {
      description
        "Raman Tuning per controller status information";
      list raman-tuning-ctrlr-table {
        key "name";
        description
          "Controller Raman Tuning status oper data";
        leaf name {
          type xr:Interface-name;
          description
            "Controller RSIP";
        }
        uses OLC-RAMAN-STATUS;
      }
    }
    container baseline-ctrlr-tables {
      description
        "Span loss Baseline per controller information";
      list baseline-ctrlr-table {
        key "name";
        description
          "Controller span loss baseline info";
        leaf name {
          type xr:Interface-name;
          description
            "Controller RSIP";
        }
        uses OLC-MBLINE-INFO;
      }
    }
    container link-status-ctrlr-tables {
      description
        "Link Simulator Status per controller information";
      list link-status-ctrlr-table {
        key "name";
        description
          "Controller Link Tuner and Gain Estimator Status
           information";
        leaf name {
          type xr:Interface-name;
          description
            "Controller RSIP";
        }
        uses OLC-CONTROLLER-LINK-STATUS;
      }
    }
    container topology-ctrlr-tables {
      description
        "Topology controller data";
      list topology-ctrlr-table {
        key "name";
        description
          "Topology controller data";
        leaf name {
          type xr:Interface-name;
          description
            "Controller RSIP";
        }
        uses OLC-LINK-TOPO-B;
      }
    }
    container band-status-ctrlr-tables {
      description
        "Band Status per controller information";
      list band-status-ctrlr-table {
        key "name";
        description
          "Controller Band Status information";
        leaf name {
          type xr:Interface-name;
          description
            "Controller RSIP";
        }
        uses OLC-CONTROLLER-BAND-STATUS;
      }
    }
    container alc-local-table {
      description
        "ALC local agent per controller information";
      container alc-local-baseline-ctrlr-tables {
        description
          "ALC local agent baseline information";
        list alc-local-baseline-ctrlr-table {
          key "name";
          description
            "APC local agent per controller baseline
             information";
          leaf name {
            type xr:Interface-name;
            description
              "Controller RSIP";
          }
          uses OLC-ALC-BASELINE-INFO;
        }
      }
      container alc-local-status-ctrlr-tables {
        description
          "ALC local agent status information";
        list alc-local-status-ctrlr-table {
          key "name";
          description
            "APC local agent per controller status
             information";
          leaf name {
            type xr:Interface-name;
            description
              "Controller RSIP";
          }
          list alc-local-status-ctrlr-dir-table {
            key "direction";
            description
              "ALC local agent per controller per direction
               status information";
            leaf direction {
              type Apc-reg-info-dir;
              description
                "TX/RX direction for ALC Local Status info";
            }
            uses OLC-CONTROLLER-ALC-LOCAL-STATUS;
          }
        }
      }
    }
    container osc-regulation-table {
      description
        "OSC regulation per controller status information";
      container osc-reg-info-ctrlr-tables {
        description
          "OSC regulation oper data";
        list osc-reg-info-ctrlr-table {
          key "name";
          description
            "OSC per controller regulation information";
          leaf name {
            type xr:Interface-name;
            description
              "Controller RSIP";
          }
          uses OLC-OSC-MOLS-REG-INFO;
        }
      }
    }
    container apc-status-ctrlr-tables {
      description
        "APC per controller status information";
      list apc-status-ctrlr-table {
        key "name";
        description
          "Controller APC status oper data";
        leaf name {
          type xr:Interface-name;
          description
            "Controller RSIP";
        }
        uses OLC-APC-STATUS;
      }
    }
    container apc-local-table {
      description
        "APC local agent per controller status
         information";
      container apc-local-reg-info-ctrlr-tables {
        description
          "APC local agent regulation information";
        list apc-local-reg-info-ctrlr-table {
          key "name";
          description
            "Controller selection for APC local regulation
             info";
          leaf name {
            type xr:Interface-name;
            description
              "Controller RSIP";
          }
          list apc-local-reg-info-dir-table {
            key "direction";
            description
              "APC Local regulation oper data";
            leaf direction {
              type Apc-reg-info-dir;
              description
                "TX/RX direction for APC regulation info";
            }
            uses OLC-APC-AGENT-REG-INFO;
          }
        }
      }
      container apc-local-status-ctrlr-tables {
        description
          "APC local agent per controller status
           information";
        list apc-local-status-ctrlr-table {
          key "name";
          description
            "Controller APC local agent status oper data";
          leaf name {
            type xr:Interface-name;
            description
              "Controller RSIP";
          }
          uses OLC-APC-AGENT-STATUS;
        }
      }
      container apc-local-target-psd-profile-ctrlr-tables {
        description
          "APC local agent per controller target psd
           profile information";
        list apc-local-target-psd-profile-ctrlr-table {
          key "name";
          description
            "Controller APC local agent target psd profile
             oper data";
          leaf name {
            type xr:Interface-name;
            description
              "Controller RSIP";
          }
          uses OLC-APC-AGENT-TARGET-PSD-PROFILE;
        }
      }
    }
    container partnerband-loss-ctrlr-tables {
      description
        "Partnerband per controller information";
      list partnerband-loss-ctrlr-table {
        key "name";
        description
          "Controller Partnerband loss oper data in dB";
        leaf name {
          type xr:Interface-name;
          description
            "Controller RSIP";
        }
        uses OLC-CONTROLLER-PARTNERBAND;
      }
    }
    container gain-estimator-ctrlr-tables {
      description
        "Gain Estimator per controller status information";
      list gain-estimator-ctrlr-table {
        key "name";
        description
          "Controller Gain Estimator status oper data";
        leaf name {
          type xr:Interface-name;
          description
            "Controller RSIP";
        }
        uses OLC-GAIN-ESTIMATOR-STATUS;
      }
    }
    container otdr-ctrlr-tables {
      description
        "OTDR Automatic Scan per controller Status
         information";
      list otdr-ctrlr-table {
        key "name";
        description
          "OTDR Automatic Scan Status oper data";
        leaf name {
          type xr:Interface-name;
          description
            "Controller RSIP";
        }
        uses OLC-OTDR-STATUS;
      }
    }
    container ampli-apc-mols-table {
      description
        "Amplifier APC MOLS per controller status
         information";
      container ampli-apc-reg-info-mols-ctrlr-tables {
        description
          "Amplifier APC regulation oper data for MOLS";
        list ampli-apc-reg-info-mols-ctrlr-table {
          key "name";
          description
            "Amplifier APC per controller regulation for
             MOLS";
          leaf name {
            type xr:Interface-name;
            description
              "Controller RSIP";
          }
          uses OLC-AMPLI-APC-MOLS-REG-INFO;
        }
      }
    }
    container link-tuner-table {
      description
        "Link Tuner status information";
      container link-tuner-detail-ctrlr-tables {
        description
          "Link Tuner per controller status information in
           detail";
        list link-tuner-detail-ctrlr-table {
          key "name";
          description
            "Controller Link Tuner status oper data in
             detail";
          leaf name {
            type xr:Interface-name;
            description
              "Controller RSIP";
          }
          uses OLC-LINK-TUNER-STATUS-DETAIL;
        }
      }
      container link-tuner-brief-ctrlr-tables {
        description
          "Link Tuner per controller status information";
        list link-tuner-brief-ctrlr-table {
          key "name";
          description
            "Controller Link Tuner status oper data summary";
          leaf name {
            type xr:Interface-name;
            description
              "Controller RSIP";
          }
          uses OLC-LINK-TUNER-STATUS-SUMMARY;
        }
      }
    }
    container span-loss-ctrlr-tables {
      description
        "Span loss per controller information";
      list span-loss-ctrlr-table {
        key "name";
        description
          "Controller span loss oper data in dB";
        leaf name {
          type xr:Interface-name;
          description
            "Controller RSIP";
        }
        uses OLC-CONTROLLER-SPAN-LOSS;
      }
    }
  }
}
