submodule Cisco-IOS-XR-yiny-oper-sub1 {
  belongs-to Cisco-IOS-XR-yiny-oper {
    prefix Cisco-IOS-XR-yiny-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR yiny package operational data.
     
     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  typedef Out-of-sync-failure {
    type enumeration {
      enum "verify" {
        description
          "The item could not be verified.";
      }
      enum "apply" {
        description
          "The item could not be applied.";
      }
    }
    description
      "The failure resulting in an item not being
       present in the running config.";
  }

  typedef Out-of-sync-operation {
    type enumeration {
      enum "set" {
        description
          "The item was attempted to be set, but could not
           be. This means the item either does not exist
           in the running config, or it exists with a
           potentially wrong value.";
      }
      enum "delete" {
        description
          "The item was attempted to be deleted, but could
           not be. This means the item exists in the
           running config when it should not.";
      }
    }
    description
      "The operation attempted where an item was found
       to be out of sync.";
  }

  typedef Out-of-sync-activity {
    type enumeration {
      enum "commit" {
        description
          "The item failed to be applied during a regular
           commit.";
      }
      enum "resync" {
        description
          "The item failed to be verified or applied
           during a resync commit.";
      }
    }
    description
      "The activity where the out-of-sync condition was
       detected.";
  }

  typedef Path {
    type string;
    description
      "String type representing a path";
  }

  grouping YINY-OPER-BAG-OOS-ITEM {
    description
      "YINY OPER BAG OOS ITEM";
    leaf path {
      type Path;
      description
        "Path of the out-of-sync item";
    }
    leaf activity {
      type Out-of-sync-activity;
      description
        "Activity that caused the out-of-sync item";
    }
    leaf operation {
      type Out-of-sync-operation;
      description
        "Operation that caused the out-of-sync item";
    }
    leaf latest-failure-type {
      type Out-of-sync-failure;
      description
        "Latest failure type of the out-of-sync item";
    }
    leaf latest-error {
      type string;
      description
        "Latest error message";
    }
    leaf-list input-path {
      type Path;
      description
        "OC input paths from which the path was mapped";
    }
  }

  grouping YINY-OPER-BAG-OOS-ITEMS-BAG {
    description
      "YinY out-of-sync items information";
    list out-of-sync-item {
      key "path";
      description
        "List of out-of-sync items";
      uses YINY-OPER-BAG-OOS-ITEM;
    }
  }
}
