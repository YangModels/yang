module Cisco-IOS-XR-config-mda-cfg {
  namespace "http://cisco.com/ns/yang/Cisco-IOS-XR-config-mda-cfg";
  prefix config-mda-cfg;

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR config-mda package configuration.
     
     This module contains definitions
     for the following management objects:
       active-nodes: Per-node configuration for active nodes
       preconfigured-nodes: Per-node configuration for non-active
         nodes
     
     Copyright (c) 2013-2019 by Cisco Systems, Inc.
     All rights reserved.";

  revision 2019-04-05 {
    description
      "Establish semantic version baseline.";
    semver:module-version "1.0.1";
  }
  revision 2015-11-09 {
    description
      "IOS XR 6.0 revision.";
  }

  container active-nodes {
    description
      "Per-node configuration for active nodes";
    list active-node {
      key "node-name";
      description
        "The configuration for an active node";
      leaf node-name {
        type xr:Node-id;
        description
          "The identifier for this node";
      }
    }
  }
  container preconfigured-nodes {
    description
      "Per-node configuration for non-active nodes";
    list preconfigured-node {
      key "node-name";
      description
        "The configuration for a non-active node";
      leaf node-name {
        type xr:Node-id;
        description
          "The identifier for this node";
      }
    }
  }
}
