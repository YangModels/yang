submodule Cisco-IOS-XR-ikev2-oper-sub1 {
  belongs-to Cisco-IOS-XR-ikev2-oper {
    prefix Cisco-IOS-XR-ikev2-oper;
  }

  import ietf-inet-types {
    prefix inet;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR ikev2 package operational data.
     
     Copyright (c) 2013-2026 by Cisco Systems, Inc.
     All rights reserved.";

  revision 2026-01-06 {
    description
      "Added DPD interval and retry in SA details
       2025-03-12
         Fips mode added in summary
       2024-07-09
         New packet stats added
       2024-04-10
         Update identity enum
       2024-03-25
         FQDN domain identity Support
       2024-01-10
         FQDN identity Support
       2023-01-30
         PPK Support
       2021-10-22
         Vrf Support";
    semver:module-version "2.0.0";
  }
  revision 2019-09-27 {
    description
      "Certificate Authentication Support";
    semver:module-version "1.1.0";
  }
  revision 2019-04-05 {
    description
      "Establish semantic version baseline.";
    semver:module-version "1.0.1";
  }
  revision 2018-12-20 {
    description
      "Operational Yang Support";
  }
  revision 2015-11-09 {
    description
      "IOS XR 6.0 revision.";
  }

  typedef Ikev2-authentication-method {
    type enumeration {
      enum "ikev2-edm-auth-no-method" {
        value 0;
        description
          "No authentication method";
      }
      enum "ikev2-edm-auth-rsa-sig" {
        value 1;
        description
          "RSA authentication method";
      }
      enum "ikev2-edm-auth-pre-shared" {
        value 2;
        description
          "PSK authentication method";
      }
      enum "ikev2-edm-auth-dss-sig" {
        value 3;
        description
          "DSS SIG authentication method";
      }
      enum "ikev2-edm-auth-ecdsa-256-sig" {
        value 9;
        description
          "ECDSA 256 SIG authentication method";
      }
      enum "ikev2-edm-auth-ecdsa-384-sig" {
        value 10;
        description
          "ECDSA 384 SIG authentication method";
      }
      enum "ikev2-edm-auth-any-connect-eap" {
        value 254;
        description
          "ANYCONNECT EAP authentication method";
      }
      enum "ikev2-edm-auth-eap" {
        value 256;
        description
          "EAP authentication method";
      }
    }
    description
      "Ikev2 authentication method";
  }

  typedef Ikev2-identification {
    type enumeration {
      enum "id-none" {
        value 0;
        description
          "No Id configured";
      }
      enum "id-ipv4-addr" {
        value 1;
        description
          "Single four octet IPv4 address";
      }
      enum "id-fqdn" {
        value 2;
        description
          "Fully-qualified domain name string e.g. foo.bar
           .com";
      }
    }
    description
      "Ikev2 identification";
  }

  typedef String1 {
    type string;
    description
      "String1";
  }

  grouping IKEV2-IDENTITY-IPV4 {
    description
      "IKEv2 IPv4 identity";
    leaf address {
      type inet:ipv4-address;
      description
        "IPv4 address";
    }
    leaf mask {
      type inet:ipv4-address;
      description
        "IPv4 mask";
    }
  }

  grouping IKEV2-IDENTITY-DOMAIN {
    description
      "IKEv2 identity domain";
    leaf id {
      type string;
      description
        "domain identity string";
    }
    leaf domain {
      type boolean;
      description
        "is a domain name match";
    }
  }

  grouping IK-EV2-REMOTE-ID-INFO {
    description
      "IKEv2 identifier info";
    container fqdn {
      when "../identification-type = 'id-fqdn'" {
        description
          "../Identification_type = 'ID_FQDN'";
      }
      description
        "Fully-qualified domain name";
      uses IKEV2-IDENTITY-DOMAIN;
    }
    container ipv4 {
      when "../identification-type = 'id-ipv4-addr'" {
        description
          "../Identification_type = 'ID_IPV4_ADDR'";
      }
      description
        "IPv4 address and Mask";
      uses IKEV2-IDENTITY-IPV4;
    }
    leaf identification-type {
      type Ikev2-identification;
      description
        "Identification type";
    }
  }

  grouping IKEV2-EDM-PROFILE {
    description
      "IKEV2 EDM PROFILE";
    container local-id {
      description
        "Local identity";
      uses IK-EV2-REMOTE-ID-INFO;
    }
    leaf profile-name {
      type string;
      description
        "Name of the Profile";
    }
    leaf keyring-name {
      type string;
      description
        "Name of the keyring";
    }
    leaf fvrf-name {
      type string;
      description
        "Name of the Fvrf";
    }
    leaf match-any {
      type boolean;
      description
        "Match Any Criteria";
    }
    leaf lifetime-in-sec {
      type uint32;
      description
        "Lifetime";
    }
    leaf dpd-interval-in-sec {
      type uint32;
      description
        "DPD Interval";
    }
    leaf dpd-retry-in-sec {
      type uint32;
      description
        "DPD Retry";
    }
    leaf local-auth {
      type Ikev2-authentication-method;
      description
        "local authentication method";
    }
    leaf keyring-ppk {
      type string;
      description
        "Name of the PPK keyring";
    }
    leaf-list trustpoint {
      type String1;
      description
        "trustpoints";
    }
    leaf-list remote-auth {
      type Ikev2-authentication-method;
      description
        "remote authentication method";
    }
    list remote-id {
      description
        "List of remote identities";
      uses IK-EV2-REMOTE-ID-INFO;
    }
  }

  grouping IKEV2-EDM-PROPOSAL {
    description
      "IKEV2 EDM PROPOSAL";
    leaf proposal-name {
      type string;
      description
        "Name of the proposal";
    }
    leaf total-enc-alg {
      type uint32;
      description
        "Total encryption algo";
    }
    leaf total-hash-alg {
      type uint32;
      description
        "Total hash algo";
    }
    leaf total-prf-alg {
      type uint32;
      description
        "Total prf algo";
    }
    leaf total-group-alg {
      type uint32;
      description
        "Total group algo";
    }
    leaf status {
      type string;
      description
        "Status of roposal";
    }
    leaf-list encryption-alg {
      type String1;
      description
        "Encryption Algorithm";
    }
    leaf-list hash-alg {
      type String1;
      description
        "Integrity Algorithm";
    }
    leaf-list prf-alg {
      type String1;
      description
        "PRF Algorithm";
    }
    leaf-list group-alg {
      type String1;
      description
        "Group Algorithm";
    }
  }

  grouping IKEV2-EDM-POLICY {
    description
      "IKEV2 EDM POLICY";
    leaf policy-name {
      type string;
      description
        "Name of the policy";
    }
    leaf total-local-addr {
      type uint32;
      description
        "Total match local addr";
    }
    leaf total-proposal {
      type uint32;
      description
        "Total proposal";
    }
    leaf total-fvrf {
      type uint32;
      description
        "Fvrf count";
    }
    leaf-list addr {
      type inet:ipv4-address;
      description
        "Match address of peer";
    }
    leaf-list proposal {
      type String1;
      description
        "List of proposals";
    }
    leaf-list fvrf {
      type String1;
      description
        "List of Fvrf";
    }
  }

  grouping IKEV2-EDM-SUMMARY {
    description
      "IKEV2 EDM SUMMARY";
    leaf fips-mode {
      type string;
      description
        "Fips mode status";
    }
    leaf total-sa {
      type uint32;
      description
        "Total SA count";
    }
    leaf total-sa-active {
      type uint32;
      description
        "Total SA active count";
    }
    leaf total-sa-negotiating {
      type uint32;
      description
        "Total SA in-negotiation count";
    }
    leaf total-outgoing-sa {
      type uint32;
      description
        "Total Outgoing SA count";
    }
    leaf outgoing-sa-active {
      type uint32;
      description
        "Outgoing SA active count";
    }
    leaf outgoing-sa-negotiating {
      type uint32;
      description
        "Outgoing SA in-negotiation count";
    }
    leaf total-incoming-sa {
      type uint32;
      description
        "Total Incoming Sa count";
    }
    leaf incoming-sa-active {
      type uint32;
      description
        "Incoming SA active count";
    }
    leaf incoming-sa-negotiating {
      type uint32;
      description
        "Incoming SA in-negotiation count";
    }
    leaf ppk-total-sess-cnt {
      type uint32;
      description
        "PPK total session count";
    }
    leaf ppk-dynamic-sess-cnt {
      type uint32;
      description
        "PPK dynamic session count";
    }
    leaf ppk-manual-sess-cnt {
      type uint32;
      description
        "PPK manual session count";
    }
  }

  grouping IKEV2-EDM-SA-DB {
    description
      "IKEV2 EDM SA DB";
    list sa {
      description
        "SA list";
      uses IKEV2-EDM-SA;
    }
  }

  grouping IKEV2-MSG {
    description
      "IKEV2 MSG";
    leaf tx-req {
      type uint32;
      description
        "TX(REQ)";
    }
    leaf rx-res {
      type uint32;
      description
        "RX(RES)";
    }
    leaf tx-res {
      type uint32;
      description
        "TX(RES)";
    }
    leaf rx-req {
      type uint32;
      description
        "RX(REQ)";
    }
  }

  grouping IKEV2-EDM-STATS {
    description
      "IKEV2 EDM STATS";
    container ike-sa-init-cnt {
      description
        "IKE SA INIT COUNT";
      uses IKEV2-MSG;
    }
    container ike-auth-cnt {
      description
        "IKE AUTH COUNT";
      uses IKEV2-MSG;
    }
    container create-child-sa-cnt {
      description
        "Create Child SA Count";
      uses IKEV2-MSG;
    }
    container create-child-sa-ipsec-cnt {
      description
        "Create Child SA IPSEC Count";
      uses IKEV2-MSG;
    }
    container create-child-sa-ipsec-rekey-cnt {
      description
        "Create Child SA IPSEC Rekey Count";
      uses IKEV2-MSG;
    }
    container create-child-sa-ike-rekey-cnt {
      description
        "Create Child SA IKE Rekey Count";
      uses IKEV2-MSG;
    }
    container gsk-auth-cnt {
      description
        "GSK Auth Count";
      uses IKEV2-MSG;
    }
    container gsk-reg-cnt {
      description
        "GSK Reg Count";
      uses IKEV2-MSG;
    }
    container gsk-rekey-cnt {
      description
        "GSK Rekey Count";
      uses IKEV2-MSG;
    }
    container gsk-rekey-ack-cnt {
      description
        "GSK Rekey Ack Count";
      uses IKEV2-MSG;
    }
    container informational-cnt {
      description
        "Informational Count";
      uses IKEV2-MSG;
    }
    container unsupported-critical-cnt {
      description
        "Unsupported Critical Count";
      uses IKEV2-MSG;
    }
    container invalid-ike-spi-cnt {
      description
        "Invalid IKE SPI COUNT";
      uses IKEV2-MSG;
    }
    container invalid-major-version-ikev2-cnt {
      description
        "Invalid Major Version IKEv2 Count";
      uses IKEV2-MSG;
    }
    container invalid-syntax-cnt {
      description
        "Invalid Syntax Count";
      uses IKEV2-MSG;
    }
    container invalid-msg-id-ikev2-cnt {
      description
        "Invalid Message ID IKEv2 Count";
      uses IKEV2-MSG;
    }
    container invalid-spi-ikev2-cnt {
      description
        "Invalid SPI IKEv2 Count";
      uses IKEV2-MSG;
    }
    container no-proposal-chosen-ikev2-cnt {
      description
        "No Proposal Chosen IKEv2 Count";
      uses IKEV2-MSG;
    }
    container invalid-ke-pyld-cnt {
      description
        "Invalid KE Payload Count";
      uses IKEV2-MSG;
    }
    container auth-failed-cnt {
      description
        "Auth Failed Count";
      uses IKEV2-MSG;
    }
    container single-pair-required-cnt {
      description
        "Single Pair Required Count";
      uses IKEV2-MSG;
    }
    container no-additional-sas-cnt {
      description
        "No Additional SAs Count";
      uses IKEV2-MSG;
    }
    container internal-addr-failure-cnt {
      description
        "Internal Addr Failure Count";
      uses IKEV2-MSG;
    }
    container failed-cp-required-cnt {
      description
        "Failed CP Required Count";
      uses IKEV2-MSG;
    }
    container ts-unacceptable-cnt {
      description
        "TS Unacceptable Count";
      uses IKEV2-MSG;
    }
    container invalid-selectors-cnt {
      description
        "Invalid Selectors Count";
      uses IKEV2-MSG;
    }
    container initial-contact-ikev2-cnt {
      description
        "Initial Contact IKEv2 Count";
      uses IKEV2-MSG;
    }
    container set-window-size-cnt {
      description
        "Set Window Size Count";
      uses IKEV2-MSG;
    }
    container additional-ts-poss-cnt {
      description
        "Additional TS Poss Count";
      uses IKEV2-MSG;
    }
    container ipcomp-supported-cnt {
      description
        "IPCOMP Supported Cnt";
      uses IKEV2-MSG;
    }
    container nat-detection-src-cnt {
      description
        "Nat Detection Src Count";
      uses IKEV2-MSG;
    }
    container nat-detection-dst-cnt {
      description
        "Nat Detection Dst Count";
      uses IKEV2-MSG;
    }
    container cookie-cnt {
      description
        "Cookie Count";
      uses IKEV2-MSG;
    }
    container use-transport-mode-cnt {
      description
        "Use Transport Mode Count";
      uses IKEV2-MSG;
    }
    container http-cert-lookup-cnt {
      description
        "HTTP Cert Lookup Cnt";
      uses IKEV2-MSG;
    }
    container rekey-sa-cnt {
      description
        "Rekey SA Count";
      uses IKEV2-MSG;
    }
    container esp-tfc-padding-not-supported-cnt {
      description
        "ESP TFC Padding Not Supported Count";
      uses IKEV2-MSG;
    }
    container delete-reason-cnt {
      description
        "Delete Reason Count";
      uses IKEV2-MSG;
    }
    container custom-cnt {
      description
        "Custom Count";
      uses IKEV2-MSG;
    }
    container redirect-supported-cnt {
      description
        "Redirected Supported Count";
      uses IKEV2-MSG;
    }
    container redirect-cnt {
      description
        "Redirect Count";
      uses IKEV2-MSG;
    }
    container redirected-from-cnt {
      description
        "Redirected From Count";
      uses IKEV2-MSG;
    }
    container ikev2-dpd-cnt {
      description
        "IKEv2 DPD Count";
      uses IKEV2-MSG;
    }
    container cfg-request-cnt {
      description
        "Config Request Count";
      uses IKEV2-MSG;
    }
    container cfg-reply-cnt {
      description
        "Config Reply Count";
      uses IKEV2-MSG;
    }
    container cfg-set-cnt {
      description
        "Config Set Count";
      uses IKEV2-MSG;
    }
    container cfg-ack-cnt {
      description
        "Config Ack Count";
      uses IKEV2-MSG;
    }
    container nat-inside-cnt {
      description
        "Nat Inside Count";
      uses IKEV2-MSG;
    }
    container nat-outside-cnt {
      description
        "Nat Outside Count";
      uses IKEV2-MSG;
    }
    container no-nat-cnt {
      description
        "No Nat Count";
      uses IKEV2-MSG;
    }
    leaf tx-succ {
      type uint32;
      description
        "IKEv2 TX Success";
    }
    leaf rx-succ {
      type uint32;
      description
        "IKEv2 RX Success";
    }
    leaf tx-write-fail {
      type uint32;
      description
        "TX Write Fail";
    }
    leaf tx-send-fail {
      type uint32;
      description
        "TX Send Fail";
    }
    leaf tx-set-qos-fail {
      type uint32;
      description
        "TX Set Qos Fail";
    }
    leaf tx-pak-buf-fail {
      type uint32;
      description
        "TX Pak Buf Fail";
    }
    leaf tx-socket-not-conn {
      type uint32;
      description
        "Tx Socket Not Conn";
    }
    leaf tx-unknown-src-port {
      type uint32;
      description
        "Tx Unknown Src Port";
    }
    leaf rx-get-if-fail {
      type uint32;
      description
        "Rx Get IF Failed";
    }
    leaf rx-null-ifhndl {
      type uint32;
      description
        "Rx NULL IFHNDL";
    }
    leaf rx-get-ntwrk-offset {
      type uint32;
      description
        "Rx Get Network Offset";
    }
    leaf rx-read-ip-head {
      type uint32;
      description
        "Rx read Ip header";
    }
    leaf rx-get-transport-offset {
      type uint32;
      description
        "Rx Get transport offset";
    }
    leaf rx-read-upd-head {
      type uint32;
      description
        "Rx read udp head";
    }
    leaf rx-unexpected-marker {
      type uint32;
      description
        "Rx Unexpected marker";
    }
    leaf rx-get-vrf-id {
      type uint32;
      description
        "Rx get Vrf Id";
    }
    leaf rx-read-pyld {
      type uint32;
      description
        "Rx Read Pyld";
    }
    leaf rx-invalid-pkt-len {
      type uint32;
      description
        "Rx invalid packet length";
    }
    leaf ppk-id-mismatch-cnt {
      type uint32;
      description
        "PPK Id mismatch count";
    }
    leaf ppk-retrieve-fail-cnt {
      type uint32;
      description
        "PPK retrieve failure count";
    }
    leaf ppk-auth-fail-cnt {
      type uint32;
      description
        "PPK authentication failure count";
    }
  }

  grouping IKEV2-EDM-CHILD-SA {
    description
      "IKEV2 EDM CHILD SA";
    leaf local-selector {
      type string;
      description
        "Local Selector";
    }
    leaf remote-selector {
      type string;
      description
        "Remote Selector";
    }
    leaf esp-spi-in-out {
      type string;
      description
        "ESP SPI In Out";
    }
    leaf encr {
      type string;
      description
        "Encryption";
    }
    leaf keysize {
      type uint32;
      description
        "Keysize";
    }
    leaf hmac {
      type string;
      description
        "ESP HMAC";
    }
  }

  grouping IKEV2-EDM-SA {
    description
      "IKEV2 EDM SA";
    leaf tunnel-id {
      type uint32;
      description
        "Tunnel ID";
    }
    leaf local-addr-port {
      type string;
      description
        "Local Addr Port";
    }
    leaf remote-addr-port {
      type string;
      description
        "Remote Addr Port";
    }
    leaf fvrf {
      type string;
      description
        "Fvrf";
    }
    leaf state {
      type string;
      description
        "State";
    }
    leaf encr {
      type string;
      description
        "Encryption";
    }
    leaf keysize {
      type uint32;
      description
        "Keysize";
    }
    leaf prf {
      type string;
      description
        "PRF";
    }
    leaf hash {
      type string;
      description
        "Hash";
    }
    leaf dh-group {
      type uint32;
      description
        "DH Group";
    }
    leaf auth-sign {
      type string;
      description
        "Auth Sign";
    }
    leaf auth-verify {
      type string;
      description
        "Auth Verify";
    }
    leaf life-active {
      type string;
      description
        "Life-Active Time";
    }
    leaf session-id {
      type uint32;
      description
        "Session ID";
    }
    leaf status-desc {
      type string;
      description
        "Status Description";
    }
    leaf local-spi {
      type string;
      description
        "Local SPI";
    }
    leaf remote-spi {
      type string;
      description
        "Remote SPI";
    }
    leaf local-id {
      type string;
      description
        "Local ID";
    }
    leaf remote-id {
      type string;
      description
        "Remote ID";
    }
    leaf sa-initiator {
      type boolean;
      description
        "Sa Initiator";
    }
    leaf quantum-resistance {
      type string;
      description
        "Quantum Resistance";
    }
    leaf dpd-interval {
      type uint32;
      description
        "DPD Interval";
    }
    leaf dpd-retry {
      type uint32;
      description
        "DPD Retry";
    }
  }

  grouping IKEV2-EDM-SESSION {
    description
      "IKEV2 EDM SESSION";
    leaf session-id {
      type uint32;
      description
        "Session ID";
    }
    leaf session-status {
      type string;
      description
        "Session Status";
    }
    leaf ike-cnt {
      type uint32;
      description
        "IKE Count";
    }
    leaf child-cnt {
      type uint32;
      description
        "Child Count";
    }
    list sa {
      description
        "SA List";
      uses IKEV2-EDM-SA;
    }
    list child-sa {
      description
        "Child SA List";
      uses IKEV2-EDM-CHILD-SA;
    }
  }
}
