submodule Cisco-IOS-XR-tty-show-terminal-oper-sub1 {
  belongs-to Cisco-IOS-XR-tty-show-terminal-oper {
    prefix Cisco-IOS-XR-tty-show-terminal-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR tty-show-terminal package operational data.
     
     Copyright (c) 2013-2021 by Cisco Systems, Inc.
     All rights reserved.";

  revision 2021-08-27 {
    description
      "yang support for show terminal";
    semver:module-version "1.0.0";
  }
  revision 2019-04-05 {
    description
      "Establish semantic version baseline.";
  }
  revision 2015-11-09 {
    description
      "IOS XR 6.0 revision.";
  }

  typedef Parity {
    type enumeration {
      enum "empty" {
        value 0;
        description
          "Empty";
      }
      enum "even" {
        value 1;
        description
          "Even";
      }
      enum "odd" {
        value 2;
        description
          "Odd";
      }
      enum "space" {
        value 3;
        description
          "Space";
      }
      enum "mark" {
        value 4;
        description
          "Mark";
      }
      enum "no" {
        value 5;
        description
          "No";
      }
    }
    description
      "parity type";
  }

  grouping SHOWTERMINAL-ENTRY {
    description
      "Per Line Information";
    leaf line {
      type string;
      description
        "Line Number";
    }
    leaf location {
      type string;
      description
        "IP address of remote login host";
    }
    leaf type {
      type string;
      description
        "Type";
    }
    leaf length {
      type uint32;
      description
        "number of lines";
    }
    leaf width {
      type uint32;
      description
        "number of columns";
    }
    leaf speed {
      type uint32;
      description
        "Baud rate";
    }
    leaf parity {
      type Parity;
      description
        "parity";
    }
    leaf stop-bits {
      type uint32;
      description
        "stop bits";
    }
    leaf data-bits {
      type uint32;
      description
        "data bits";
    }
    leaf template {
      type string;
      description
        "line template";
    }
    leaf timestamp {
      type boolean;
      description
        "timestamp enabled or disabled";
    }
    leaf no-exec {
      type boolean;
      description
        "spawning exec disallowed";
    }
  }
}
