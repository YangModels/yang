module Cisco-IOS-XR-telemetry-oper {
  namespace "http://cisco.com/ns/yang/Cisco-IOS-XR-telemetry-oper";
  prefix xr-telemetry;

  import cisco-semver {
    prefix semver;
  }
  import ietf-inet-types {
    prefix inet;
  }
  import ietf-yang-types {
    prefix yang;
  }

  organization
    "Cisco Systems, Inc.";
  contact
    "Cisco Systems, Inc.
     Customer Service
     Postal: 170 West Tasman Drive
     San Jose, CA 95134
     Tel: +1 800 553-NETS
     E-mail: cs-yang@cisco.com";
  description
    "This module contains a collection of YANG definitions
     for Cisco IOS-XR telemetry subsystem on the network device
     operational data.
     
     Copyright (c) 2025-2026 by Cisco Systems, Inc., and/or its affiliates.
     All rights reserved.";

  revision 2026-03-10 {
    description
      "Remove heartbeat-always and missed-heartbeats leaves";
  }
  revision 2026-02-09 {
    description
      "Add YANG-Push CBOR encoding.";
    semver:module-version "1.1.0";
  }
  revision 2025-10-31 {
    description
      "Initial revision";
    semver:module-version "1.0.0";
  }

  typedef encoding-type {
    type enumeration {
      enum "GPB" {
        description
          "XR Telemetry GPB encoding format used for dial-in and dial-out interfaces.";
        reference
          "Cisco IOS XR Telemetry GPB Encoding:
             <https://github.com/ios-xr/model-driven-telemetry/blob/master/protos/24_4_2/telemetry.proto>
           Proto file of the YANG models:
             <https://github.com/ios-xr/model-driven-telemetry/blob/master/protos/24_4_2/>";
      }
      enum "SELF_DESCRIBING_GPB" {
        description
          "XR Telemetry Self-describing GPB encoding format used for dial-in and dial-out interfaces.";
        reference
          "Cisco IOS XR Telemetry Self-describing GPB Encoding:
             <https://github.com/ios-xr/model-driven-telemetry/blob/master/protos/24_4_2/telemetry.proto>";
      }
      enum "JSON" {
        description
          "XR Telemetry encoding used for dial-in and dial-out interfaces with a JSON
           representation of telemetry.proto schema.";
      }
      enum "YANG_PUSH_JSON" {
        description
          "YANG-Push JSON encoding format conforming to RFC-8641.";
      }
      enum "GNMI_PROTO" {
        description
          "gNMI protocol buffers encoding format conforming to the
           gNMI specification of openconfig where TypedValue are scalar.";
        reference
          "GNMI Specification:
            <https://www.openconfig.net/docs/gnmi/gnmi-specification/>
            <https://github.com/openconfig/gnmi/blob/master/proto/gnmi/gnmi.proto>";
      }
      enum "GNMI_JSON_IETF" {
        description
          "gNMI JSON encoding following IETF JSON encoding rules
           (RFC 7951) for YANG-modeled data representation.";
        reference
          "json-ietf-val in gnmi.proto follows RFC-7951:
            <https://www.openconfig.net/docs/gnmi/gnmi-specification/>
            <https://github.com/openconfig/gnmi/blob/master/proto/gnmi/gnmi.proto>";
      }
    }
    description
      "Telemetry YANG-modeled data encodings that determine how telemetry
       data is serialized for transmission to collectors.";
  }

  typedef transport-type {
    type enumeration {
      enum "gRPC" {
        description
          "gRPC transport providing reliable, bidirectional streaming
           over HTTP/2 with built-in flow control and TLS support.";
      }
      enum "TCP" {
        description
          "TCP transport providing reliable, connection-oriented
           delivery with ordered packets and error detection.";
      }
      enum "UDP" {
        description
          "UDP transport providing connectionless, best-effort
           delivery with minimal overhead for high-throughput scenarios.";
      }
    }
    description
      "Transport layer protocols used for delivering telemetry data
       from the network device to collectors.";
  }

  typedef subscription-state {
    type enumeration {
      enum "NOT_ACTIVE" {
        description
          "Subscription is not currently operational.";
      }
      enum "ACTIVE" {
        description
          "Subscription is fully operational and telemetry data can
           be streamed to destinations.";
      }
      enum "PAUSED" {
        description
          "Subscription is suspended, data collection instances are
           halted until resumed.";
      }
    }
    description
      "Current operational state of a telemetry subscription indicating
       whether data is being streamed to destinations.";
  }

  typedef destination-state {
    type enumeration {
      enum "NOT_ACTIVE" {
        description
          "Destination is set but not operational.";
      }
      enum "ACTIVE" {
        description
          "Device is actively sending telemetry data to the destination.";
      }
      enum "CONNECTING" {
        description
          "Destination is transitioning from not-active to active state,
           resuming normal telemetry data transmission.";
      }
    }
    description
      "Current operational state of a telemetry destination indicating
       the status of data transmission to that collector endpoint.";
  }

  typedef sensor-path-state {
    type enumeration {
      enum "RESOLVED" {
        description
          "Sensor path has been successfully mapped to internal data source(s).";
      }
      enum "UNRESOLVED" {
        description
          "Sensor path could not be mapped to any internal data source.";
      }
    }
    description
      "Resolution status indicating whether a sensor path has been
       successfully mapped to collectable internal data source(s).";
  }

  typedef sample-interval-state {
    type enumeration {
      enum "USER_SET" {
        description
          "IOS-XR implementation supports sample-interval to be specified for subscription
           TARGET_DEFINED in the gNMI subscribe request. If the target [device] determines
           a leaf is SAMPLE, and a sample-interval is specified, the device uses that sample-interval;
           otherwise, device determines one.";
      }
      enum "ADJUSTING" {
        description
          "For subscription TARGET_DEFINED with unspecified sample-interval, if the device
           determines leaf is SAMPLE, the sample-interval is being determined by the device.";
      }
      enum "FINALIZED" {
        description
          "For subscription TARGET_DEFINED with unspecified sample-interval, if the device
           determines leaf is SAMPLE, the sample-interval is finalized by the device.";
      }
    }
    description
      "For subscription TARGET_DEFINED, the target [device] determines whether a leaf
       is ON_CHANGE or SAMPLE (and for SAMPLE, the sample-interval). As an example,
       leaves representing state changes may use ON_CHANGE collection instances, while
       counter values may use SAMPLE collection instances.";
  }

  typedef path-state {
    type enumeration {
      enum "ACTIVE" {
        description
          "Sensor path is active and streaming data normally.";
      }
      enum "NOT_ACTIVE" {
        description
          "Data collection for this path has been paused.";
      }
      enum "ERROR" {
        description
          "Internal error occurred within the telemetry subsystem
           preventing data collection of this path.";
      }
    }
    description
      "Internal operational state of telemetry sensor paths within
       the collection instance, including error conditions and
       plugin-specific states that affect data collection capability.";
  }

  typedef collection-method {
    type enumeration {
      enum "GET" {
        description
          "Gets the information contained in a set of specific items from the
           internal data source.";
      }
      enum "DATALIST" {
        description
          "Retrieves a list of items and their data from the internal data source.";
      }
      enum "FIND_DATA" {
        description
          "Retrieves a list of matching items and the items' data from the internal
           data source based on filter criteria.";
      }
    }
    description
      "Methods used for telemetry data collection, determining how
       data is gathered from the internal data sources.";
  }

  typedef compression-algorithm {
    type enumeration {
      enum "GZIP" {
        description
          "GZIP compression algorithm applied to telemetry data.";
      }
    }
    description
      "Compression algorithms that can be applied to telemetry data
       before transmission to collectors.";
  }

  grouping destination-address-port {
    description
      "Destination IP address and port";
    leaf address {
      type inet:ip-address;
      description
        "Destination IP address";
    }
    leaf port {
      type inet:port-number;
      description
        "Destination port";
    }
  }

  grouping collection-time {
    description
      "Collection time statistics.";
    leaf min {
      type uint32;
      units "milliseconds";
      description
        "Minimum time taken to collect data from the internal data source.";
    }
    leaf avg {
      type uint32;
      units "milliseconds";
      description
        "Average time taken to collect data from the internal data source.";
    }
    leaf max {
      type uint32;
      units "milliseconds";
      description
        "Maximum time taken to collect data from the internal data source.";
    }
  }

  grouping count_error_count {
    description
      "Count and error count statistics.";
    leaf count {
      type yang:counter64;
      description
        "Total number of operations.";
    }
    leaf error-count {
      type yang:counter32;
      description
        "Total number of errors.";
    }
  }

  grouping sensor-path-common-attributes {
    description
      "Common attributes for sensor paths";
    leaf state {
      type sensor-path-state;
      description
        "Resolution status indicating whether a sensor path has been
         successfully mapped to collectable internal data source(s).";
    }
    leaf error {
      type string;
      description
        "Detailed error message describing why path resolution failed, empty if
         the path is successfully resolved. This field is for display purpose only.";
    }
    leaf filter-keys {
      type string;
      description
        "This indicates the include key filter(s) of the sensor path, if specified.
         The format is a semicolon-separated list of key=value pairs.";
    }
  }

  grouping sensor-group-common-attributes {
    description
      "Common attributes for sensor groups";
    leaf sample-interval {
      type uint32;
      units "milliseconds";
      description
        "Time interval between successive data collections for sample-based
         subscriptions, in milliseconds.";
    }
    leaf heartbeat-interval {
      type uint32;
      units "milliseconds";
      description
        "The value of the data item(s) is re-sent once per heartbeat interval
         regardless of whether the value has changed or not.";
    }
  }

  grouping collection-path-common-attributes {
    description
      "Common attributes for internal data collections.
       Warning: backwards incompatible changes can be made to this grouping.";
    leaf filter-keys {
      type string;
      description
        "This indicates the include key filter(s) of the internal path if any.
         The format is a semicolon-separated list of key=value pairs.";
    }
    leaf data-source {
      type string;
      description
        "Data source within the device that generates telemetry data
         for collection by the telemetry subsystem.";
    }
    leaf path-state {
      type path-state;
      description
        "Internal operational state of telemetry data source, including error
         condition states that affect data collection capability.";
    }
    leaf collection-method {
      type collection-method;
      description
        "Method in use for this internal data collection.";
    }
    leaf completed-collections {
      type yang:counter64;
      description
        "This indicates the number of completed collections. This excludes
         collection splits.";
    }
    container collection-time {
      description
        "Collection time statistics for this internal data collection.";
      uses collection-time;
    }
    container get {
      description
        "Get method statistics for this internal data collection.";
      uses count_error_count;
    }
    container list {
      description
        "List method statistics for this internal data collection.";
      uses count_error_count;
    }
    container datalist {
      description
        "Datalist method statistics for this internal data collection.";
      uses count_error_count;
    }
    container find-data {
      description
        "Find-data method statistics for this internal data collection.";
      uses count_error_count;
    }
    leaf total-items {
      type yang:counter64;
      description
        "Total number of items retrieved from internal data source,
         may be different from the number of items sent to the destination.";
    }
    leaf total-updates {
      type yang:counter64;
      description
        "Total number of updates.";
    }
    leaf total-deletes {
      type yang:counter64;
      description
        "Total number of deletes.";
    }
  }

  grouping subscription-common-attributes {
    description
      "Common attributes for subscriptions";
    leaf id {
      type uint64;
      description
        "System-assigned unique numeric identifier for this subscription.";
    }
    leaf state {
      type subscription-state;
      description
        "Current operational state indicating whether this subscription
         is streaming telemetry data to destinations.";
    }
    leaf collection-instances {
      type uint32;
      description
        "Number of active data collection instances associated with
         this subscription across all sensor groups and destinations.";
    }
  }

  grouping collection-instance-common-attributes {
    description
      "Common attributes for a collection instance.";
    leaf completed-collections {
      type yang:counter32;
      description
        "This indicates the total number of times a collection instance has
         completed full read of internal data of the collection.
         This excludes collection instance splits.";
    }
    leaf sample-interval {
      type uint32;
      units "milliseconds";
      description
        "Time interval between successive data collections for sample-based mode,
         in milliseconds.";
    }
    leaf heartbeat-interval {
      type uint32;
      units "milliseconds";
      description
        "The interval at which the data item(s) are re-sent.";
    }
    leaf sample-interval-state {
      type sample-interval-state;
      description
        "State of the sample interval for a TARGET_DEFINED subscription.";
    }
    container collection-time {
      description
        "Time spent collecting data from the data source.";
      uses collection-time;
    }
    container total-collection-time {
      description
        "Time spent from starting data collection at the source
         to delivering the collected data to the final destination.";
      uses collection-time;
    }
    leaf last-max-total-collection-time-ts {
      type uint64;
      description
        "This timestamp indicates the time when the last maximum total
         collection time was recorded. The value is the timestamp in
         nanoseconds since the Unix epoch (Jan 1, 1970 00:00:00 UTC).";
    }
    leaf last-collection-start-ts {
      type uint64;
      description
        "This timestamp indicates the time of the last collection start.
         The value is the timestamp in nanoseconds since the Unix
         epoch (Jan 1, 1970 00:00:00 UTC).";
    }
    leaf last-collection-end-ts {
      type uint64;
      description
        "This timestamp indicates the time of the last collection end.
         The value is the timestamp in nanoseconds since the Unix
         epoch (Jan 1, 1970 00:00:00 UTC).";
    }
    leaf missed-collections {
      type yang:counter64;
      description
        "This indicates the number of missed collections.";
    }
    leaf last-missed-collection-ts {
      type uint64;
      description
        "This timestamp indicates the time of the last missed collection.
         The value is the timestamp in nanoseconds since the Unix
         epoch (Jan 1, 1970 00:00:00 UTC).";
    }
    leaf collection-splits {
      type yang:counter32;
      description
        "Number of times a collection instance is split into multiple collection
         instances to adapt to the drain rate of a slow collector.";
    }
    leaf last-collection-split-ts {
      type uint64;
      description
        "This timestamp indicates the time of the last collection instance split.
         The value is the timestamp in nanoseconds since the Unix
         epoch (Jan 1, 1970 00:00:00 UTC).";
    }
  }

  grouping destination-common-attributes {
    description
      "Common attributes of a destination";
    leaf state {
      type destination-state;
      description
        "Current operational state indicating whether telemetry data
         is actively being transmitted to this destination.";
    }
    leaf subscription {
      type string;
      description
        "Name of the subscription associated with this destination.";
    }
    leaf encoding {
      type encoding-type;
      description
        "Data serialization format used to encode telemetry messages
         before transmission to this destination.";
    }
    leaf transport {
      type transport-type;
      description
        "Transport layer protocol used to deliver telemetry data
         to this destination.";
    }
    leaf vrf {
      type string;
      description
        "VRF associated with this destination.";
    }
    leaf vrf-id {
      type uint32;
      description
        "VRF ID associated with this destination.";
    }
    leaf udp-mtu {
      type uint32;
      units "bytes";
      description
        "UDP MTU size for this destination if is UDP.";
    }
    leaf tls {
      type boolean;
      description
        "Indicates whether TLS is enabled for this destination if
         transport is gRPC.";
    }
    leaf tls-hostname {
      type string;
      description
        "TLS hostname for this destination if transport is gRPC and
         TLS is enabled.";
    }
    leaf dscp {
      type inet:dscp;
      description
        "This indicates the DSCP marking of packets generated by the
         telemetry subsystem on the network device.";
    }
    leaf initial-updates {
      type uint32;
      description
        "Number of collection instances that have completed their initial
         full data synchronization to this destination.";
    }
    leaf last-collection-ts {
      type uint64;
      description
        "This timestamp indicates the time of the last successful data
         transmission to this destination. The value is the timestamp in
         nanoseconds since the Unix epoch (Jan 1, 1970 00:00:00 UTC).";
    }
    leaf sent-packets {
      type yang:counter64;
      description
        "This indicates the total number of packets sent to this destination.
         This is scoped. For example, when this is under a specific
         subscription, this number reflects only of this subscription.";
    }
    leaf sent-bytes {
      type yang:counter64;
      description
        "This indicates the total number of bytes sent to this destination.
         This is scoped. For example, when this is under a specific
         subscription, this number reflects only of this subscription.";
    }
    leaf pending-queue-memory {
      type uint32;
      units "bytes";
      description
        "Current memory size of the pending transmission queue for this destination.";
    }
    leaf pending-queue-messages {
      type uint32;
      description
        "Current number of messages of the pending transmission queue for this destination.";
    }
    leaf gnmi-sync-response-ts {
      type uint64;
      description
        "This timestamp indicates the time of the last gNMI sync_response message
         sent to this destination. The value is the timestamp in nanoseconds
         since the Unix epoch (Jan 1, 1970 00:00:00 UTC).";
    }
    leaf pending-on-change-messages {
      type uint32;
      description
        "Number of pending ON_CHANGE messages queued for transmission to this destination.";
    }
    leaf processed-on-change-messages {
      type uint64;
      description
        "Total number of ON_CHANGE messages processed for this destination.";
    }
    leaf compression {
      type compression-algorithm;
      description
        "Compression algorithm used for this destination, if any.";
    }
    uses destination-address-port;
  }

  grouping sensor-paths-top {
    description
      "Top-level grouping for sensor paths";
    container sensor-paths {
      description
        "Sensor paths within this sensor group";
      list sensor-path {
        key "path";
        description
          "sensor path information";
        leaf path {
          type string;
          description
            "Sensor path";
        }
        container state {
          description
            "Sensor path state attributes";
          uses sensor-path-common-attributes;
        }
      }
    }
  }

  grouping sensor-groups-top {
    description
      "Top-level grouping for sensor groups";
    container sensor-groups {
      description
        "Sensor groups for this subscription";
      list sensor-group {
        key "name";
        description
          "Sensor group information";
        leaf name {
          type string;
          description
            "Sensor group name";
        }
        container state {
          description
            "Sensor group state attributes";
          uses sensor-group-common-attributes;
        }
        uses sensor-paths-top;
      }
    }
  }

  grouping collection-path-top {
    description
      "Internal data collection information";
    container collection-paths {
      description
        "Internal data collection information for this collection";
      list collection-path {
        key "path";
        description
          "Internal collection path information";
        leaf path {
          type string;
          description
            "Internal data path";
        }
        container state {
          description
            "Internal collection path state attributes";
          uses collection-path-common-attributes;
        }
      }
    }
  }

  grouping collection-instances-top {
    description
      "Top-level grouping for collection instances";
    container collection-instances {
      description
        "Collection instances";
      list collection-instance {
        key "id";
        description
          "Collection instance";
        leaf id {
          type uint64;
          description
            "Collection instance ID";
        }
        container state {
          description
            "Collection instance state attributes";
          uses collection-instance-common-attributes;
        }
        uses collection-path-top;
      }
    }
  }

  grouping subscriptions-top {
    description
      "Top-level grouping for subscriptions";
    container subscriptions {
      description
        "Telemetry subscriptions";
      list subscription {
        key "name";
        description
          "Subscription entry";
        leaf name {
          type string;
          description
            "Subscription name";
        }
        container state {
          description
            "Subscription state attributes";
          uses subscription-common-attributes;
        }
        uses sensor-groups-top;
        container sub-collection-instance-refs {
          description
            "Collection instances associated with this subscription.";
          leaf-list collection-instance-refs {
            type leafref {
              path "/telemetry/collection-instances/collection-instance/id";
            }
            description
              "References to collection instances in the global collection-instances view.
               These are the collection instances associated with this subscription.";
          }
        }
        container sub-destination-refs {
          description
            "Destinations associated with this subscription.";
          leaf-list destination-refs {
            type leafref {
              path "/telemetry/destinations/destination/endpoint-id";
            }
            description
              "References to destinations in the global destinations view.
               These are the destinations associated with this subscription.";
          }
        }
      }
    }
  }

  grouping destinations-top {
    description
      "Top-level grouping for the destinations";
    container destinations {
      description
        "Destinations";
      list destination {
        key "endpoint-id";
        description
          "Destination";
        leaf endpoint-id {
          type uint64;
          description
            "This destination endpoint ID.";
        }
        container state {
          description
            "Destination attributes";
          uses destination-common-attributes;
        }
      }
    }
  }

  container telemetry {
    config false;
    description
      "Root container for telemetry operational data";
    uses subscriptions-top {
      refine "subscriptions" {
        description
          "Global subscription view - represents all subscriptions
           with their associated collections and destinations.";
      }
    }
    uses destinations-top {
      refine "destinations" {
        description
          "Global destination view - represents all destinations
           with their associated subscriptions and collections.";
      }
    }
    uses collection-instances-top {
      refine "collection-instances" {
        description
          "Global collection instance view - represents all collection instances
           with their per-destination information.";
      }
    }
  }
}
