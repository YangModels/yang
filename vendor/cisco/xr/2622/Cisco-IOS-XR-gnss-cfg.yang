module Cisco-IOS-XR-gnss-cfg {
  namespace "http://cisco.com/ns/yang/Cisco-IOS-XR-gnss-cfg";
  prefix gnss-cfg;

  import Cisco-IOS-XR-config-mda-cfg {
    prefix node;
  }
  import cisco-semver {
    prefix semver;
  }
  import Cisco-IOS-XR-freqsync-datatypes {
    prefix dt1;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR gnss package configuration.
     
     This YANG module augments the
       Cisco-IOS-XR-config-mda-cfg
     module with configuration data.
     
     Copyright (c) 2013-2026 by Cisco Systems, Inc.
     All rights reserved.";

  revision 2026-07-03 {
    description
      "Added task metadata for GNSS receiver configuration.";
    semver:module-version "2.0.0";
  }
  revision 2020-04-15 {
    description
      "Fixed must conditions bug.";
    semver:module-version "2.0.0";
  }
  revision 2019-04-05 {
    description
      "Establish semantic version baseline.";
    semver:module-version "1.0.1";
  }
  revision 2017-09-07 {
    description
      "Fixed type translation error.";
  }
  revision 2015-11-09 {
    description
      "IOS XR 6.0 revision.";
  }

  grouping NODE-CFG {
    description
      "active/preconfigured nodes configuration";
    container gnss-receivers {
      description
        "Configuration for a GNSS receiver";
      list gnss-receiver {
        key "number";
        description
          "Configuration for a GNSS receiver";
        container frequency-synchronization {
          description
            "Frequency Synchronization clock configuraiton";
          container output-quality-level {
            description
              "Set the output quality level";
            leaf quality-level-option {
              type dt1:Fsync-ql-option;
              must "../exact-quality-level-value or ../min-quality-level-value or ../max-quality-level-value or (../min-quality-level-value and ../max-quality-level-value)";
              description
                "Quality level option";
            }
            leaf exact-quality-level-value {
              type dt1:Fsync-ql-value;
              must "../quality-level-option and not(../min-quality-level-value or ../max-quality-level-value)";
              description
                "Exact quality level value";
            }
            leaf min-quality-level-value {
              type dt1:Fsync-ql-value;
              must "../quality-level-option and not(../exact-quality-level-value)";
              description
                "Minimum quality level value";
            }
            leaf max-quality-level-value {
              type dt1:Fsync-ql-value;
              must "../quality-level-option and not(../exact-quality-level-value)";
              description
                "Maximum quality level value";
            }
          }
          container input-quality-level {
            description
              "Set the input quality level";
            leaf quality-level-option {
              type dt1:Fsync-ql-option;
              must "../exact-quality-level-value or ../min-quality-level-value or ../max-quality-level-value or (../min-quality-level-value and ../max-quality-level-value)";
              description
                "Quality level option";
            }
            leaf exact-quality-level-value {
              type dt1:Fsync-ql-value;
              must "../quality-level-option and not(../min-quality-level-value or ../max-quality-level-value)";
              description
                "Exact quality level value";
            }
            leaf min-quality-level-value {
              type dt1:Fsync-ql-value;
              must "../quality-level-option and not(../exact-quality-level-value)";
              description
                "Minimum quality level value";
            }
            leaf max-quality-level-value {
              type dt1:Fsync-ql-value;
              must "../quality-level-option and not(../exact-quality-level-value)";
              description
                "Maximum quality level value";
            }
          }
          leaf ssm-disable {
            type empty;
            description
              "Disable SSM on this source";
          }
          leaf priority {
            type uint32 {
              range "1..254";
            }
            default "100";
            description
              "Set the priority of this source";
          }
          leaf selection-input {
            type empty;
            description
              "Assign this source as a selection input";
          }
          leaf wait-to-restore-time {
            type uint32 {
              range "0..12";
            }
            default "5";
            description
              "Set the wait-to-restore time for this source";
          }
          leaf time-of-day-priority {
            type uint32 {
              range "1..254";
            }
            default "100";
            description
              "Set the time-of-day priority of this source";
          }
        }
        leaf enable {
          type empty;
          description
            "Enable the GNSS receiver";
        }
        leaf snr-threshold {
          type uint32 {
            range "0..40";
          }
          default "0";
          description
            "Set the satellite SNR threshold, in dB-Hz";
        }
        leaf traim-threshold {
          type uint32 {
            range "0..2";
          }
          units "microsecond";
          default "0";
          description
            "Set the satellite TRAIM threshold, in
             microseconds";
        }
        leaf polarity1pps {
          type dt1:Gnss1pps-polarity;
          default "positive";
          description
            "Set the GNSS receiver 1PPS polarity";
        }
        leaf cable-delay-compensation {
          type int32 {
            range "-1000000..1000000";
          }
          units "nanosecond";
          default "0";
          description
            "Set the cable-delay compensation, in
             nanoseconds";
        }
        leaf anti-jam-disable {
          type empty;
          description
            "Stop running the GNSS receiver in anti-jam
             mode";
        }
        leaf pdop-threshold {
          type uint32 {
            range "0..10";
          }
          default "0";
          description
            "Set the satellite PDOP threshold";
        }
        leaf elevation-threshold {
          type uint32 {
            range "0..40";
          }
          default "0";
          description
            "Set the satellite elevation threshold, in
             degrees";
        }
        leaf shutdown {
          type empty;
          description
            "Shutdown the GNSS receiver";
        }
        leaf constellation {
          type dt1:Gnss-constellation;
          default "auto";
          description
            "Set the constellation to be used by the GNSS
             receiver";
        }
        leaf number {
          type uint32;
          description
            "Receiver number";
        }
      }
    }
  }

  augment "/node:active-nodes/node:active-node" {
    description
      "This augment extends active nodes configuration";
    uses NODE-CFG;
  }
  augment "/node:preconfigured-nodes/node:preconfigured-node" {
    description
      "This augment extends preconfigured nodes
       configuration";
    uses NODE-CFG;
  }
}
