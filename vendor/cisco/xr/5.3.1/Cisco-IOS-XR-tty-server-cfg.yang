module Cisco-IOS-XR-tty-server-cfg {

  /*** NAMESPACE / PREFIX DEFINITION ***/

  namespace "http://cisco.com/ns/yang/Cisco-IOS-XR-tty-server-cfg";


  prefix "tty-server-cfg";

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR tty-server package configuration.

     This module contains definitions
     for the following management objects:
       tty: TTY Line Configuration

     Copyright (c) 2013-2015 by Cisco Systems, Inc.
     All rights reserved.";

  revision "2015-01-07" {
    description
      "IOS XR 5.3.1 revision.";
  }


  container tty {
    xr:xr-xml-map "tty_server_cfg:TTY";
    description "TTY Line Configuration";

    container tty-lines {
      xr:xr-xml-map "tty_server_cfg:TTYLineTable";
      description "TTY templates";

      list tty-line {
        xr:xr-xml-map "tty_server_cfg:TTYLine";
        key "name";
        description
          "TTY Line,Use string 'console' to configure a
          console line,Use string 'default' to configure
          a default line,Use any string to configure a
          user defined template";

        container general {
          xr:xr-xml-map "tty_server_cfg:General";
          description "TTY line general configuration";
          leaf length {
            xr:xr-xml-map "tty_server_cfg:Length";
            type uint32 {
              range "0..512";
            }
            default "24";
            description "Number of lines on screen";
          }
          leaf absolute-timeout {
            xr:xr-xml-map "tty_server_cfg:AbsoluteTimeout";
            type uint32 {
              range "0..10000";
            }
            units "minute";
            default "0";
            description "Absolute timeout interval in minutes.";
          }
          leaf width {
            xr:xr-xml-map "tty_server_cfg:Width";
            type uint32 {
              range "0..512";
            }
            default "80";
            description "Number of characters on a screen line.";
          }
        }

        container telnet {
          xr:xr-xml-map "tty_server_cfg:Telnet";
          description "Telnet protocol-specific configuration";
          leaf transparent {
            xr:xr-xml-map "tty_server_cfg:Transparent";
            type empty;
            description
              "'True' to Enable  carriage retur behaviour
              for a telnet";
          }
        }

        container aaa {
          xr:xr-xml-map "tty_server_cfg:AAA";
          description
            "Container class for AAA related TTY
            configuration";

          container user-groups {
            xr:xr-xml-map "tty_server_cfg:UserGroupTable";
            description "Users characteristics";

            list user-group {
              xr:xr-xml-map "tty_server_cfg:UserGroup";
              key "name";
              description "Group to which the user will belong";
              leaf name {
                xr:xr-xml-map "tty_server_cfg:Name";
                type xr:Cisco-ios-xr-string;
                description "Name of the group";
              }
              leaf category {
                xr:xr-xml-map "tty_server_cfg:Category";
                type string;
                mandatory true;
                description
                  "Specify as 'root-system' for root-system
                  group and 'other' for remaining groups";
              }
            }
          }

          container authorization {
            xr:xr-xml-map "tty_server_cfg:Authorization";
            description "Authorization parameters";
            leaf exec {
              xr:xr-xml-map "tty_server_cfg:Exec";
              type string;
              description "Authorization list name";
            }
            leaf event-manager {
              xr:xr-xml-map "tty_server_cfg:EventManager";
              type string;
              description
                "Specify 'default' or use an authorization
                list with this name";
            }
            leaf commands {
              xr:xr-xml-map "tty_server_cfg:Commands";
              type string;
              description "Authorization list name";
            }
          }

          container authentication {
            xr:xr-xml-map "tty_server_cfg:Authentication";
            description "Authentication parameters";
            leaf login {
              xr:xr-xml-map "tty_server_cfg:Login";
              type string;
              description "Authentication list name";
            }
          }

          container accounting {
            xr:xr-xml-map "tty_server_cfg:Accounting";
            description "Accounting parameters";
            leaf exec {
              xr:xr-xml-map "tty_server_cfg:Exec";
              type string;
              description "Accounting list name";
            }
            leaf commands {
              xr:xr-xml-map "tty_server_cfg:Commands";
              type string;
              description "Accounting list name";
            }
          }
          leaf login-timeout {
            xr:xr-xml-map "tty_server_cfg:LoginTimeout";
            type uint32 {
              range "0..300";
            }
            units "second";
            default "30";
            description "Timeout in seconds";
          }
          leaf secret {
            xr:xr-xml-map "tty_server_cfg:Secret";
            type xr:Md5-password;
            description "Specify the password";
          }
          leaf password {
            xr:xr-xml-map "tty_server_cfg:Password";
            type xr:Md5-password;
            description "Specify the password";
          }
        }

        container exec {
          xr:xr-xml-map "tty_server_cfg:Exec";
          description "EXEC timeout and timestamp configurtion";

          container timeout {
            xr:xr-xml-map "tty_server_cfg:Timeout";
            presence "Indicates a timeout node is configured.";
            description "EXEC Timeout";
            leaf minutes {
              xr:xr-xml-map "tty_server_cfg:Minutes";
              type uint32 {
                range "0..35791";
              }
              units "minute";
              mandatory true;
              description "Timeout in minutes";
            }
            leaf seconds {
              xr:xr-xml-map "tty_server_cfg:Seconds";
              type uint32 {
                range "0..2147483";
              }
              units "second";
              mandatory true;
              description "Timeout in seconds";
            }
          }
          leaf time-stamp {
            xr:xr-xml-map "tty_server_cfg:TimeStamp";
            type boolean;
            description
              "'True' to Enable & 'False' to Disable time
              stamp";
          }
        }
        leaf name {
          xr:xr-xml-map "tty_server_cfg:Name";
          type xr:Cisco-ios-xr-string;
          description "Name of the template";
        }
      }
    }
  }
}
