submodule Cisco-IOS-XR-ipv6-ma-oper-sub1 {

  belongs-to Cisco-IOS-XR-ipv6-ma-oper {
    prefix Cisco-IOS-XR-ipv6-ma-oper;
  }

  /*** LINKAGE (IMPORTS / INCLUDES) ***/

  import ietf-inet-types { prefix "inet"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR ipv6-ma package operational data.

     Copyright (c) 2013-2015 by Cisco Systems, Inc.
     All rights reserved.";

  revision "2015-01-07" {
    description
      "IOS XR 5.3.1 revision.";
  }

  typedef Ipv6-ma-oper-state {
    type enumeration {
      enum oper-up {
        value 1;
        description "Interface oper state is up";
      }
      enum oper-down {
        value 2;
        description "Interface oper state is down";
      }
    }
    description "Interface oper states";
  }
  typedef Ipv6-ma-if-addr-state {
    type enumeration {
      enum active {
        value 1;
        description
          "This is an active address that can appear as
          the destination or source address of a packet";
      }
      enum deprecated {
        value 2;
        description
          "This is a valid but deprecated address that
          should no longer be used as a source address in
          new communications";
      }
      enum duplicate {
        value 3;
        description
          "This is a duplicate (invalid) address because
          of conflict";
      }
      enum inaccessible {
        value 4;
        description
          "This is not accessible because the interface to
          which this address is assigned is not
          operational";
      }
      enum tentative {
        value 5;
        description "Status can not be determined for some reason";
      }
    }
    description "Interface address states";
  }
  typedef Ipv6-ma-if-line-state {
    type enumeration {
      enum down {
        value 1;
        description "Interface state is down";
      }
      enum up {
        value 2;
        description "Interface state is up";
      }
      enum unknown {
        value 3;
        description "Interface state is unknown";
      }
      enum error {
        value 4;
        description "Interface state is incorrect";
      }
    }
    description "Interface line states";
  }

  grouping IF-SUMMARY {
    description "Count of assigned/unnumbered interfaces";
    leaf ip-assigned {
      xr:xr-xml-map "ipv6_show_interface:IPAssigned";
      type uint32;
      description "Number of interfaces with explicit addresses";
    }
    leaf ip-unnumbered {
      xr:xr-xml-map "ipv6_show_interface:IPUnnumbered";
      type uint32;
      description
        "Number of unnumbered interfaces with explicit
        addresses";
    }
  }

  grouping IPV6-IF-SUMMARY {
    description "Summary info of IPv6 interfaces";

    container if-up-up {
      description "Number of interfaces (up,up)";
      uses IF-SUMMARY;
    }

    container if-up-down {
      description "Number of interfaces (up,down)";
      uses IF-SUMMARY;
    }

    container if-down-down {
      description "Number of interfaces (down,down)";
      uses IF-SUMMARY;
    }

    container if-shutdown-down {
      description "Number of interfaces (shutdown,down)";
      uses IF-SUMMARY;
    }
    leaf if-up-down-basecaps-up {
      xr:xr-xml-map "ipv6_show_interface:IFUpDownBasecapsUp";
      type uint32;
      description "Number of interfaces (up,down) with basecaps up";
    }
  }

  grouping TIMEVAL-ENTRY {
    description "Creatation or Update Time";
  }

  grouping BGP-PA-DIR {
    description "BGP PA config for ingress/egress direction";
    leaf enable {
      xr:xr-xml-map "ipv6_show_interface:Enable";
      type uint32;
      description "Enable BGP PA for ingress/egress";
    }
    leaf source {
      xr:xr-xml-map "ipv6_show_interface:Source";
      type boolean;
      description "Enable source accouting";
    }
    leaf destination {
      xr:xr-xml-map "ipv6_show_interface:Destination";
      type boolean;
      description "Enable destination accouting";
    }
  }

  grouping BGP-PA-CONFIG {
    description "BGP PA config information";

    container input {
      description "BGP PA input config";
      uses BGP-PA-DIR;
    }

    container output {
      description "BGP PA output config";
      uses BGP-PA-DIR;
    }
  }

  grouping RPF-CONFIG {
    description "RPF config information";
    leaf enable {
      xr:xr-xml-map "ipv6_show_interface:Enable";
      type boolean;
      description "Enable RPF config";
    }
    leaf allow-default-route {
      xr:xr-xml-map "ipv6_show_interface:AllowDefaultRoute";
      type boolean;
      description "Allow Default Route";
    }
    leaf allow-self-ping {
      xr:xr-xml-map "ipv6_show_interface:AllowSelfPing";
      type boolean;
      description "Allow Self Ping";
    }
    leaf mode {
      xr:xr-xml-map "ipv6_show_interface:Mode";
      type uint32;
      description "RPF Mode (loose/strict)";
    }
  }

  grouping IPV6-ACL-CONFIG {
    description "IPV6 ACL CONFIG";
    leaf in-bound {
      xr:xr-xml-map "ipv6_show_interface:InBound";
      type string;
      description "ACL applied to incoming packets";
    }
    leaf out-bound {
      xr:xr-xml-map "ipv6_show_interface:OutBound";
      type string;
      description "ACL applied to outgoing packets";
    }
    leaf common-in-bound {
      xr:xr-xml-map "ipv6_show_interface:CommonInBound";
      type string;
      description "Common ACL applied to incoming packets";
    }
    leaf common-out-bound {
      xr:xr-xml-map "ipv6_show_interface:CommonOutBound";
      type string;
      description "Common ACL applied to outgoing packets";
    }
  }

  grouping IPV6-MCAST-GROUP {
    description "MCast Group ";
    leaf address {
      xr:xr-xml-map "ipv6_show_interface:Address";
      type inet:ipv6-address;
      description "IPv6 Address of Multicast Group";
    }
  }

  grouping IPV6-IF-DETAIL {
    description "Detailed Info of IPv6 Interface";

    container link-local-address {
      description "Link Local Address";
      uses IPV6-ADDR-NODE;
    }

    container access-control-list {
      description "IPv6 Access Control List";
      uses IPV6-ACL-CONFIG;
    }

    container rpf {
      description "RPF config on the interface";
      uses RPF-CONFIG;
    }

    container bgp-pa {
      description "BGP PA config on the interface";
      uses BGP-PA-CONFIG;
    }

    container utime {
      description "Address Publish Time";
      uses TIMEVAL-ENTRY;
    }

    container idb-utime {
      description "IDB Create Time";
      uses TIMEVAL-ENTRY;
    }

    container caps-utime {
      description "CAPS Add Time";
      uses TIMEVAL-ENTRY;
    }

    container fwd-en-utime {
      description "FWD ENABLE Time";
      uses TIMEVAL-ENTRY;
    }

    container fwd-dis-utime {
      description "FWD DISABLE Time";
      uses TIMEVAL-ENTRY;
    }
    leaf line-state {
      xr:xr-xml-map "ipv6_show_interface:LineState";
      type Ipv6-ma-if-line-state;
      description "State of Interface Line";
    }
    leaf mtu {
      xr:xr-xml-map "ipv6_show_interface:MTU";
      type uint32;
      description "IPv6 MTU";
    }
    leaf operation-state {
      xr:xr-xml-map "ipv6_show_interface:OperationState";
      type Ipv6-ma-oper-state;
      description "IPv6 Operation State";
    }
    leaf is-icmp-unreach-enabled {
      xr:xr-xml-map "ipv6_show_interface:IsICMPUnreachEnabled";
      type boolean;
      description "ICMP unreach Enable";
    }
    leaf rg-id-exists {
      xr:xr-xml-map "ipv6_show_interface:RG_IDExists";
      type boolean;
      description "Does ICCP RG ID exist on the interface?";
    }
    leaf mlacp-active {
      xr:xr-xml-map "ipv6_show_interface:mLACPActive";
      type boolean;
      description "Is mLACP state Active (valid if RG ID exists)";
    }
    leaf flow-tag-src {
      xr:xr-xml-map "ipv6_show_interface:FLOW_TAG_SRC";
      type boolean;
      description "Is BGP Flow Tag Source is enable";
    }
    leaf flow-tag-dst {
      xr:xr-xml-map "ipv6_show_interface:FLOW_TAG_DST";
      type boolean;
      description "Is BGP Flow Tag Destination is enable";
    }

    list multicast-group {
      description "IPv6 Multicast Group";
      uses IPV6-MCAST-GROUP;
    }

    list address {
      description "Address List";
      uses IPV6-ADDR-NODE;
    }
  }

  grouping IPV6-ADDR-NODE {
    description "List of IPv6 Addresses ";
    leaf address {
      xr:xr-xml-map "ipv6_show_interface:Address";
      type inet:ipv6-address;
      description "IPv6 Address";
    }
    leaf prefix-length {
      xr:xr-xml-map "ipv6_show_interface:PrefixLength";
      type uint32;
      description "Prefix Length of IPv6 Address";
    }
    leaf address-state {
      xr:xr-xml-map "ipv6_show_interface:AddressState";
      type Ipv6-ma-if-addr-state;
      description "State of Address";
    }
    leaf is-anycast {
      xr:xr-xml-map "ipv6_show_interface:IsAnycast";
      type boolean;
      description "Anycast address";
    }
    leaf route-tag {
      xr:xr-xml-map "ipv6_show_interface:RouteTag";
      type uint32;
      description "Route-tag of the Address";
    }
  }

  grouping IPV6-IF-BRIEF {
    description "Brief Summary of IPv6 Interface";

    container link-local-address {
      description "Link Local Address";
      uses IPV6-ADDR-NODE;
    }
    leaf line-state {
      xr:xr-xml-map "ipv6_show_interface:LineState";
      type Ipv6-ma-if-line-state;
      description "State of Interface Line";
    }

    list address {
      description "Address List";
      uses IPV6-ADDR-NODE;
    }
  }
}
