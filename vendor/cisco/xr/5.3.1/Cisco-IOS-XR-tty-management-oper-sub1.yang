submodule Cisco-IOS-XR-tty-management-oper-sub1 {

  belongs-to Cisco-IOS-XR-tty-management-oper {
    prefix Cisco-IOS-XR-tty-management-oper;
  }

  /*** LINKAGE (IMPORTS / INCLUDES) ***/

  import ietf-inet-types { prefix "inet"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR tty-management package operational data.

     Copyright (c) 2013-2015 by Cisco Systems, Inc.
     All rights reserved.";

  revision "2015-01-07" {
    description
      "IOS XR 5.3.1 revision.";
  }

  typedef Transport-service {
    type enumeration {
      enum unknown {
        description "Unknown service";
      }
      enum telnet {
        description "Telnet";
      }
      enum rlogin {
        description "Remote login";
      }
      enum ssh {
        description "SSH";
      }
    }
    description "Transport service protocol";
  }
  typedef Ipv6-address {
    type inet:ipv6-address;
    description "Ipv6 address";
  }
  typedef Host-af-id {
    type enumeration {
      enum ipv4 {
        value 2;
        description "IPv4 family";
      }
      enum ipv6 {
        value 26;
        description "IPv6 family";
      }
    }
    description "Host address family types";
  }

  grouping IP-ADDR-T-UNION {
    description "IP ADDR T UNION";
    leaf af-name {
      xr:xr-xml-map "outgoing_conn:AFName";
      type Host-af-id;
      description "AFName";
    }
    leaf ipv4-address {
      xr:xr-xml-map "outgoing_conn:IPv4Address";
      when "../af-name = 'ipv4'" {
        description "../AFName = 'IPv4'";
      }
      type inet:ipv4-address;
      description "IPv4 address";
    }
    leaf ipv6-address {
      xr:xr-xml-map "outgoing_conn:IPv6Address";
      when "../af-name = 'ipv6'" {
        description "../AFName = 'IPv6'";
      }
      type Ipv6-address;
      description "IPv6 address";
    }
  }

  grouping SUSPENDED-SESSIONS {
    description "Outgoing session information";

    container host-address {
      description "Host address";
      uses IP-ADDR-T-UNION;
    }
    leaf connection-id {
      xr:xr-xml-map "outgoing_conn:ConnectionID";
      type uint8;
      description "Connection ID [1-20]";
    }
    leaf host-name {
      xr:xr-xml-map "outgoing_conn:HostName";
      type string;
      description "Host name";
    }
    leaf transport-protocol {
      xr:xr-xml-map "outgoing_conn:TransportProtocol";
      type Transport-service;
      description "Session transport protocol";
    }
    leaf is-last-active-session {
      xr:xr-xml-map "outgoing_conn:IsLastActiveSession";
      type boolean;
      description "True indicates last active session";
    }
    leaf idle-time {
      xr:xr-xml-map "outgoing_conn:IdleTime";
      type uint32;
      units "second";
      description
        "Elapsed time since session was suspended (in
        seconds)";
    }
  }

  grouping CONN-OUT-TABLE-BAG {
    description "All outgoing sessions";

    list outgoing-connection {
      description "List of outgoing sessions";
      uses SUSPENDED-SESSIONS;
    }
  }
}
