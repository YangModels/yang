module Cisco-IOS-XR-parser-cfg {

  /*** NAMESPACE / PREFIX DEFINITION ***/

  namespace "http://cisco.com/ns/yang/Cisco-IOS-XR-parser-cfg";


  prefix "parser-cfg";

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR parser package configuration.

     This module contains definitions
     for the following management objects:
       parser: Parser configuration

     Copyright (c) 2013-2015 by Cisco Systems, Inc.
     All rights reserved.";

  revision "2015-01-07" {
    description
      "IOS XR 5.3.1 revision.";
  }


  container parser {
    xr:xr-xml-map "parser_cfg:Parser";
    description "Parser configuration";

    container alias {
      xr:xr-xml-map "parser_common:Alias";
      description "Alias for command mapping";

      container commands {
        xr:xr-xml-map "parser_common:CommandTable";
        description "Table of all aliases configured";

        list command {
          xr:xr-xml-map "parser_common:Command";
          key "alias-name";
          description "Alias name to command mapping";
          leaf alias-name {
            xr:xr-xml-map "parser_common:AliasName";
            type string;
            description "Alias Name";
          }
          leaf command {
            xr:xr-xml-map "parser_common:Command";
            type string;
            mandatory true;
            description "The actual command";
          }
        }
      }
    }
  }
}
