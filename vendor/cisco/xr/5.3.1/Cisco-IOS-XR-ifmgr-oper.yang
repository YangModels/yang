module Cisco-IOS-XR-ifmgr-oper {

  /*** NAMESPACE / PREFIX DEFINITION ***/

  namespace "http://cisco.com/ns/yang/Cisco-IOS-XR-ifmgr-oper";


  prefix "ifmgr-oper";

  /*** LINKAGE (IMPORTS / INCLUDES) ***/

  import Cisco-IOS-XR-types { prefix "xr"; }

  include Cisco-IOS-XR-ifmgr-oper-sub2 {
    revision-date 2015-01-07;
  }

  include Cisco-IOS-XR-ifmgr-oper-sub1 {
    revision-date 2015-01-07;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ifmgr package operational data.

     This module contains definitions
     for the following management objects:
       interface-dampening: Interface dampening data
       interface-properties: interface properties

     Copyright (c) 2013-2015 by Cisco Systems, Inc.
     All rights reserved.";

  revision "2015-01-07" {
    description
      "IOS XR 5.3.1 revision.";
  }


  grouping INTERFACE-TABLE {
    description "Common node of system-view, locationview";

    container interfaces {
      xr:xr-xml-map "ifmgr_oper:InterfaceTable";
      description
        "Operational data for all interfaces and
        controllers";

      list interface {
        xr:xr-xml-map "ifmgr_oper:Interface";
        key "interface-name";
        description
          "The operational attributes for a particular
          interface";
        leaf interface-name {
          xr:xr-xml-map "ifmgr_oper:InterfaceName";
          type xr:Interface-name;
          description "The name of the interface";
        }
        uses IMDS-IFATTR-BASE-INFO;
      }
    }
  }

  container interface-dampening {
    xr:xr-xml-map "ifmgr_dampening_oper:InterfaceDampening";
    config false;
    description "Interface dampening data";

    container nodes {
      xr:xr-xml-map "ifmgr_dampening_oper:NodeTable";
      description "The location of the interface(s) being queried";

      list node {
        xr:xr-xml-map "ifmgr_dampening_oper:Node";
        key "node-name";
        description
          "The location of the interface(s) being queried";

        container show {
          xr:xr-xml-map "ifmgr_dampening_oper:Show";
          description "Show details for the interfaces";

          container dampening {
            xr:xr-xml-map "ifmgr_dampening_oper:Dampening";
            description
              "Dampening information of the interface(s)
              being queried";

            container interfaces {
              xr:xr-xml-map "ifmgr_dampening_oper:InterfaceTable";
              description
                "Table of interfaces for which dampening info
                can be queried";

              list interface {
                xr:xr-xml-map "ifmgr_dampening_oper:Interface";
                key "interface-name";
                description "Dampening info for the interface";
                leaf interface-name {
                  xr:xr-xml-map "ifmgr_dampening_oper:InterfaceName";
                  type xr:Interface-name;
                  description "The name of the";
                }
                uses IM-SHOW-DAMP-INFO;
              }
            }
          }
        }
        leaf node-name {
          xr:xr-xml-map "ifmgr_dampening_oper:NodeName";
          type xr:Node-id;
          description "The location of the interface(s)";
        }
      }
    }
  }

  container interface-properties {
    xr:xr-xml-map "ifmgr_oper:InterfaceProperties";
    config false;
    description "interface properties";

    container data-nodes {
      xr:xr-xml-map "ifmgr_oper:DataNodeTable";
      description "Operational data for interfaces";

      list data-node {
        xr:xr-xml-map "ifmgr_oper:DataNode";
        key "data-node-name";
        description
          "The location of a (D)RP in the same LR as the
          interface being queried";

        container locationviews {
          xr:xr-xml-map "ifmgr_oper:LocationViewTable";
          description
            "Location-specific view of interface
            operational data";

          list locationview {
            xr:xr-xml-map "ifmgr_oper:LocationView";
            key "locationview-name";
            description
              "Operational data for all interfaces and
              controllers on a particular node";
            leaf locationview-name {
              xr:xr-xml-map "ifmgr_oper:LocationViewName";
              type xr:Node-id;
              description "The location to filter on";
            }
            uses INTERFACE-TABLE;
          }
        }

        container system-view {
          xr:xr-xml-map "ifmgr_oper:SystemView";
          description
            "System-wide view of interface operational data";
          uses INTERFACE-TABLE;
        }
        leaf data-node-name {
          xr:xr-xml-map "ifmgr_oper:DataNodeName";
          type xr:Node-id;
          description "The location of the (D)RP";
        }
      }
    }
  }
}
