submodule Cisco-IOS-XR-roe-oper-sub1 {
  belongs-to Cisco-IOS-XR-roe-oper {
    prefix Cisco-IOS-XR-roe-oper;
  }

  import ietf-yang-types {
    prefix yang;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR roe package operational data.
     
     Copyright (c) 2013-2021 by Cisco Systems, Inc.
     All rights reserved.";

  revision 2021-05-10 {
    description
      "Added leaf hfn-sync-disable to grouping ROE-PROFILE-INFO.
       2021-05-03
         Added mapper,demapper roe-profile parameters presync-match-threshold, resync-match-threshold, resync-mismatch-threshold. Added demapper roe-profile parameters sync-threshold, drain-threshold, presync-match-count, resync-match-count, resync-mismatch-count.";
    semver:module-version "1.1.0";
  }
  revision 2020-09-01 {
    description
      "Removed container protocol-stats. Changed type of leaf order-info-type.";
    semver:module-version "1.0.0";
  }
  revision 2020-02-27 {
    description
      "Show command subtype added for ROE";
  }
  revision 2019-04-05 {
    description
      "Establish semantic version baseline.";
  }
  revision 2015-11-09 {
    description
      "IOS XR 6.0 revision.";
  }

  grouping ROE-ETHLINK-INFO {
    description
      "ROE ethlink info";
    leaf source-mac-address {
      type yang:mac-address;
      description
        "Source Mac Address";
    }
    leaf destionation-mac-address {
      type yang:mac-address;
      description
        "Destination Mac Address";
    }
  }

  grouping ROE-PROFILE-INFO {
    description
      "ROE profile info";
    leaf mapper-flow-identifier {
      type uint8;
      description
        "Mapper Flow Identifier";
    }
    leaf demapper-flow-identifier {
      type uint8;
      description
        "Demapper Flow Identifier";
    }
    leaf order-info-type {
      type uint8;
      description
        "Sequence number or timestamp or both";
    }
    leaf mapper-type {
      type uint8;
      description
        "Structure agnostic or aware";
    }
    leaf encrypt {
      type boolean;
      description
        "Encryption supported or not";
    }
    leaf compression {
      type boolean;
      description
        "Compression supported or not";
    }
    leaf packet-length {
      type uint16;
      description
        "Length of the ROE packet";
    }
    leaf accepted-time-window {
      type uint32;
      description
        "Delay within which ROE pkts should reach
         destination";
    }
    leaf sample-width {
      type uint8;
      description
        "Sample width of I/Q samples";
    }
    leaf num-of-containers {
      type uint8;
      description
        "Num of containers";
    }
    leaf num-of-control-containers {
      type uint8;
      description
        "Num of control containers";
    }
    leaf num-of-fft {
      type uint8;
      description
        "Num of FFT objects";
    }
    leaf num-of-prach {
      type uint8;
      description
        "Num of PRACH objects";
    }
    leaf retimer-buffer-size {
      type uint32;
      description
        "Retimer buffer size";
    }
    leaf idle-frame-size {
      type uint32;
      description
        "Idle frame size";
    }
    leaf idle-frame-threshold {
      type uint32;
      description
        "Idle frame threshold";
    }
    leaf mapper-presync-match-threshold {
      type uint8;
      description
        "Mapper Presync Match Threshold";
    }
    leaf demapper-presync-match-threshold {
      type uint8;
      description
        "Demapper Presync Match Threshold";
    }
    leaf mapper-resync-match-threshold {
      type uint8;
      description
        "Mapper Resync Match Threshold";
    }
    leaf demapper-resync-match-threshold {
      type uint8;
      description
        "Demapper Resync Match Threshold";
    }
    leaf mapper-resync-mismatch-threshold {
      type uint8;
      description
        "Mapper Resync Mismatch Threshold";
    }
    leaf demapper-resync-mismatch-threshold {
      type uint8;
      description
        "Demapper Resync Mismatch Threshold";
    }
    leaf demapper-sync-threshold {
      type uint8;
      description
        "Demapper Sync Threshold";
    }
    leaf demapper-drain-threshold {
      type uint8;
      description
        "Demapper Drain Threshold";
    }
    leaf demapper-presync-match-count {
      type uint8;
      description
        "Demapper Presync Match Count";
    }
    leaf demapper-resync-match-count {
      type uint8;
      description
        "Demapper Resync Match Count";
    }
    leaf demapper-resync-mismatch-count {
      type uint8;
      description
        "Demapper Resync Mismatch Count";
    }
    leaf hfn-sync-disable {
      type boolean;
      description
        "HFN Sync disabled when set. Applicable only for
         type-0 mapper config in non auto-neg CPRI port";
    }
  }
}
