module Cisco-IOS-XR-healthcheck-oper {
  namespace "http://cisco.com/ns/yang/Cisco-IOS-XR-healthcheck-oper";
  prefix healthcheck-oper;

  import Cisco-IOS-XR-types {
    prefix xr;
  }
  import cisco-semver {
    prefix semver;
  }
  include Cisco-IOS-XR-healthcheck-oper-sub2 {
    revision-date 2020-09-18;
  }
  include Cisco-IOS-XR-healthcheck-oper-sub1 {
    revision-date 2020-09-18;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR healthcheck package operational data.
     
     This module contains definitions
     for the following management objects:
       health-check: Healthcheck Operational data space
     
     Copyright (c) 2013-2020 by Cisco Systems, Inc.
     All rights reserved.";

  revision 2020-09-18 {
    description
      "Fabric health metric updated.";
    semver:module-version "1.0.0";
  }
  revision 2019-04-05 {
    description
      "Establish semantic version baseline.";
  }
  revision 2015-11-09 {
    description
      "IOS XR 6.0 revision.";
  }

  container health-check {
    config false;
    description
      "Healthcheck Operational data space";
    container metric-info {
      description
        "Metric Info";
      container fpd {
        description
          "FPD Metric";
        uses HCMGR-FPD-METRIC-DATA;
      }
      container redundancy {
        description
          "REDUNDANCY Metric";
        uses HCMGR-REDUNDANCY-METRIC-DATA;
      }
      container fabric-health {
        description
          "FABRIC-HEALTH Metric";
        uses HCMGR-FABRIC-HEALTH-METRIC-DATA;
      }
      container platform {
        description
          "PLATFORM Metric";
        uses HCMGR-PLATFORM-METRIC-DATA;
      }
      container interface-counters {
        description
          "Interface Counters Metric";
        container interface-counters-details {
          description
            "Interface Name";
          list interface-counters-detail {
            key "intf-name";
            description
              "Interface Name";
            container interface-counters-detail-data {
              description
                "Interface Counters Metric Detail";
              uses HCMGR-INTF-COUNTERS-METRIC-DETAIL-DATA;
            }
            leaf intf-name {
              type xr:Interface-name;
              description
                "Interface Name";
            }
          }
        }
        container interface-counters-info {
          description
            "Interface Counters Metric Info";
          uses HCMGR-INTF-COUNTERS-METRIC-DATA;
        }
      }
      container asic-errors {
        description
          "Asic Errors Metric";
        container asic-errors-details {
          description
            "Node Name";
          list asic-errors-detail {
            key "node-name";
            description
              "Node Name";
            container asic-errors-detail-data {
              description
                "Asic-Errors Metric Detail";
              uses HCMGR-ASIC-ERRORS-METRIC-DETAIL-DATA;
            }
            leaf node-name {
              type xr:Cisco-ios-xr-string;
              description
                "Node Name";
            }
          }
        }
        container asic-errors-info {
          description
            "Asic-Errors Metric Info";
          uses HCMGR-ASIC-ERRORS-METRIC-DATA;
        }
      }
      container free-memory {
        description
          "Free Memory Metric";
        uses HCMGR-FREE-MEM-METRIC-DATA;
      }
      container custom-metric {
        description
          "Custom Metric Oper Data";
        container custom-metric-infos {
          description
            "name";
          list custom-metric-info {
            key "metric-name";
            description
              "Metric Name";
            container custom-metric-info-data {
              description
                "Custom-Metric Oper Data";
              uses HCMGR-CUSTOM-METRIC-DATA;
            }
            leaf metric-name {
              type xr:Cisco-ios-xr-string;
              description
                "Metric Name";
            }
          }
        }
      }
      container fabric-stats {
        description
          "Asic Errors Metric";
        container fabric-stats-info {
          description
            "Fabric-Stats Metric Info";
          uses HCMGR-FABRIC-STATS-METRIC-DATA;
        }
        container fabric-stats-details {
          description
            "Plane Id";
          list fabric-stats-detail {
            key "plane-id";
            description
              "Plane Id";
            container fabric-stats-detail-data {
              description
                "Fabric-Stats Metric Detail";
              uses HCMGR-FABRIC-STATS-METRIC-DETAIL-DATA;
            }
            leaf plane-id {
              type uint32;
              description
                "Plane Id";
            }
          }
        }
      }
      container filesystem {
        description
          "Filesystem Metric";
        uses HCMGR-FILESYSTEM-METRIC-DATA;
      }
      container shared-memory {
        description
          "Shared Memory Metric";
        uses HCMGR-SHARED-MEM-METRIC-DATA;
      }
      container cpu {
        description
          "CPU Metric";
        uses HCMGR-CPU-METRIC-DATA;
      }
    }
    container report-info {
      description
        "Report data bag";
      uses HCMGR-REPORT-DATA;
    }
    container status-info {
      description
        "Status data bag";
      uses HCMGR-STATUS-DATA;
    }
  }
}
