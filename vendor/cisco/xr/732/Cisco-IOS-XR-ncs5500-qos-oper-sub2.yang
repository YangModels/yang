submodule Cisco-IOS-XR-ncs5500-qos-oper-sub2 {
  belongs-to Cisco-IOS-XR-ncs5500-qos-oper {
    prefix Cisco-IOS-XR-ncs5500-qos-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR ncs5500-qos package operational data.
     
     Copyright (c) 2013-2019 by Cisco Systems, Inc.
     All rights reserved.";

  revision 2019-08-24 {
    description
      "Fixing pyang compilation error.";
    semver:module-version "2.1.0";
  }
  revision 2019-04-05 {
    description
      "Establish semantic version baseline.";
    semver:module-version "1.1.0";
  }
  revision 2015-11-09 {
    description
      "IOS XR 6.0 revision.";
  }

  typedef Dpa-qosea-show-wred {
    type enumeration {
      enum "wred-cos" {
        description
          "WRED based on COS";
      }
      enum "wred-dscp" {
        description
          "WRED based on DSCP";
      }
      enum "wred-precedence" {
        description
          "WRED based on Precedence";
      }
      enum "wred-discard-class" {
        description
          "WRED based on discard class";
      }
      enum "wred-mpls-exp" {
        description
          "WRED based on MPLS EXP";
      }
      enum "red-with-user-min-max" {
        description
          "RED with user defined min and max";
      }
      enum "red-with-default-min-max" {
        description
          "RED with default min and max";
      }
      enum "wred-invalid" {
        description
          "Invalid";
      }
    }
    description
      "WRED type";
  }

  typedef Dpa-qosea-show-action {
    type enumeration {
      enum "action-none" {
        description
          "None";
      }
      enum "action-transmit" {
        description
          "Transmit";
      }
      enum "action-drop" {
        description
          "Drop";
      }
      enum "action-mark" {
        description
          "Mark";
      }
    }
    description
      "Policer action type";
  }

  typedef Policy-param-unit {
    type enumeration {
      enum "policy-param-unit-invalid" {
        description
          "policy param unit invalid";
      }
      enum "policy-param-unit-bytes" {
        description
          "policy param unit bytes";
      }
      enum "policy-param-unit-kbytes" {
        description
          "policy param unit kbytes";
      }
      enum "policy-param-unit-mbytes" {
        description
          "policy param unit mbytes";
      }
      enum "policy-param-unit-gbytes" {
        description
          "policy param unit gbytes";
      }
      enum "policy-param-unit-bitsps" {
        description
          "policy param unit bitsps";
      }
      enum "policy-param-unit-kbitsps" {
        description
          "policy param unit kbitsps";
      }
      enum "policy-param-unit-mbitsps" {
        description
          "policy param unit mbitsps";
      }
      enum "policy-param-unit-gbitsps" {
        description
          "policy param unit gbitsps";
      }
      enum "policy-param-unit-cells-ps" {
        description
          "policy param unit cells ps";
      }
      enum "policy-param-unit-packets-ps" {
        description
          "policy param unit packets ps";
      }
      enum "policy-param-unit-us" {
        description
          "policy param unit us";
      }
      enum "policy-param-unit-ms" {
        description
          "policy param unit ms";
      }
      enum "policy-param-unit-seconds" {
        description
          "policy param unit seconds";
      }
      enum "policy-param-unit-packets" {
        description
          "policy param unit packets";
      }
      enum "policy-param-unit-cells" {
        description
          "policy param unit cells";
      }
      enum "policy-param-unit-percent" {
        description
          "policy param unit percent";
      }
      enum "policy-param-unit-per-thousand" {
        description
          "policy param unit per thousand";
      }
      enum "policy-param-unit-per-million" {
        description
          "policy param unit per million";
      }
      enum "policy-param-unit-hz" {
        description
          "policy param unit hz";
      }
      enum "policy-param-unit-khz" {
        description
          "policy param unit khz";
      }
      enum "policy-param-unit-mhz" {
        description
          "policy param unit mhz";
      }
      enum "policy-param-unit-ratio" {
        description
          "policy param unit ratio";
      }
      enum "policy-param-unit-inverse-ratio" {
        description
          "policy param unit inverse ratio";
      }
      enum "policy-param-unit-max" {
        description
          "policy param unit max";
      }
    }
    description
      "Policy param unit";
  }

  typedef Dpa-qosea-show-hp-level {
    type enumeration {
      enum "high-priority-level1" {
        description
          "High priority queue level 1";
      }
      enum "high-priority-level2" {
        description
          "High priority queue level 2";
      }
      enum "high-priority-level3" {
        description
          "High priority queue level 3";
      }
      enum "high-priority-level4" {
        description
          "High priority queue level 4";
      }
      enum "high-priority-level5" {
        description
          "High priority queue level 5";
      }
      enum "high-priority-level6" {
        description
          "High priority queue level 6";
      }
      enum "high-priority-level7" {
        description
          "High priority queue level 7";
      }
      enum "unknown" {
        description
          "Unknown";
      }
    }
    description
      "Priority level";
  }

  typedef Dpa-qosea-show-queue {
    type enumeration {
      enum "low-priority-default-queue" {
        description
          "Low priority default queue";
      }
      enum "low-priority-queue" {
        description
          "Low priority queue";
      }
      enum "high-priority-queue" {
        description
          "High priority queue";
      }
      enum "unknown-queue-type" {
        description
          "Queue priority unknown";
      }
    }
    description
      "Priority Queue Type";
  }

  typedef Dpa-qosea-show-mark {
    type enumeration {
      enum "mark-none" {
        description
          "None";
      }
      enum "dscp" {
        description
          "DSCP";
      }
      enum "precedence" {
        description
          "Precedence";
      }
      enum "mpls-topmost" {
        description
          "MPLS topmost";
      }
      enum "mpls-imposition" {
        description
          "MPLS imposition";
      }
      enum "qos-group" {
        description
          "Qos group";
      }
      enum "discard-class" {
        description
          "Discard class";
      }
      enum "cos" {
        description
          "COS";
      }
      enum "inner-cos" {
        description
          "Inner COS";
      }
      enum "un-supported9" {
        description
          "Unsupported type 9";
      }
      enum "un-supported10" {
        description
          "Unsupported type 10";
      }
      enum "un-supported11" {
        description
          "Unsupported type 11";
      }
      enum "dscp-tunnel" {
        description
          "DSCP tunnel";
      }
      enum "precedence-tunnel" {
        description
          "Precedence tunnel";
      }
      enum "dei" {
        description
          "DEI";
      }
      enum "dei-imposition" {
        description
          "DEI Imposition";
      }
      enum "un-supported16" {
        description
          "Unsupported type 16";
      }
      enum "un-supported17" {
        description
          "Unsupported type 17";
      }
      enum "traffic-class" {
        description
          "Traffic class";
      }
    }
    description
      "Mark type";
  }

  typedef Dpa-qosea-show-level {
    type enumeration {
      enum "level1" {
        value 0;
        description
          "QoS level1 class";
      }
      enum "level2" {
        value 1;
        description
          "QoS level2 class";
      }
      enum "level3" {
        value 2;
        description
          "QoS level3 class";
      }
      enum "level4" {
        value 3;
        description
          "QoS level4 class";
      }
      enum "level5" {
        value 4;
        description
          "QoS level5 class";
      }
    }
    description
      "Level type";
  }

  typedef Dpa-qosea-show-intf-status {
    type enumeration {
      enum "state-unknown" {
        description
          "State is unknown";
      }
      enum "state-down" {
        description
          "State is Down";
      }
    }
    description
      "Intf Status";
  }

  typedef Dpa-qosea-show-policy-status {
    type enumeration {
      enum "no-error" {
        description
          "No errors";
      }
      enum "policy-in-reset" {
        description
          "QoS policy is reset";
      }
    }
    description
      "Status";
  }

  typedef Qos-policy-account-enum {
    type enumeration {
      enum "qos-serv-policy-no-ac-count-pref" {
        description
          "qos serv policy no ac count pref";
      }
      enum "qos-serv-policy-ac-count-l2" {
        description
          "qos serv policy ac count l2";
      }
      enum "qos-serv-policy-no-ac-count-l2" {
        description
          "qos serv policy no ac count l2";
      }
      enum "qos-serv-policy-ac-count-user-def" {
        description
          "qos serv policy ac count user def";
      }
      enum "qos-serv-policy-ac-count-l1" {
        description
          "qos serv policy ac count l1";
      }
    }
    description
      "Qos policy account enum";
  }

  grouping QOS-RANGE {
    description
      "QOS RANGE";
    leaf range-start {
      type uint8;
      description
        "Start value of a range";
    }
    leaf range-end {
      type uint8;
      description
        "End value of a range";
    }
  }

  grouping DPA-QOSEA-SHOW-RED-MATCH-VALUES {
    description
      "DPA QOSEA SHOW RED MATCH VALUES";
    list dpa-qosea-show-red-match-value {
      description
        "dpa qosea show red match value";
      uses QOS-RANGE;
    }
  }

  grouping PARAMETERS {
    description
      "WRED parameters";
    container wred-match-value {
      description
        "WRED match values";
      uses DPA-QOSEA-SHOW-RED-MATCH-VALUES;
    }
    container config-min-threshold {
      description
        "Configured minimum threshold";
      uses POLICY-PARAMETER;
    }
    container config-max-threshold {
      description
        "Configured maximum threshold";
      uses POLICY-PARAMETER;
    }
    container config-drop-probability {
      description
        "Configured drop/mark probability";
      uses POLICY-PARAMETER;
    }
    leaf wred-match-type {
      type Dpa-qosea-show-wred;
      description
        "WREDMatchType";
    }
    leaf hardware-min-threshold-bytes {
      type uint32;
      description
        "Hardware minimum threshold";
    }
    leaf hardware-max-threshold-bytes {
      type uint32;
      description
        "Hardware maximum threshold";
    }
    leaf hardware-drop-probability {
      type uint32;
      description
        "Hardware drop/mark probability";
    }
    leaf first-segment {
      type uint16;
      description
        "First segment";
    }
    leaf segment-size {
      type uint32;
      description
        "Segment size";
    }
  }

  grouping POLICER-ACTION {
    description
      "POLICER ACTION";
    leaf action-type {
      type Dpa-qosea-show-action;
      description
        "Policer action type";
    }
    list mark {
      description
        "Action mark";
      uses QOS-MARK;
    }
  }

  grouping DQL-POLICY-PARAMETER {
    description
      "DQL Policy parameter";
    leaf class0-policy-value {
      type uint32;
      description
        "Discard Class0 Policy value";
    }
    leaf class1-policy-value {
      type uint32;
      description
        "Discard Class1 Policy value";
    }
    leaf dql-policy-unit {
      type Policy-param-unit;
      description
        "DQL Policy unit";
    }
  }

  grouping POLICY-PARAMETER {
    description
      "Policy parameter";
    leaf policy-value {
      type uint32;
      description
        "Policy value";
    }
    leaf policy-unit {
      type Policy-param-unit;
      description
        "Policy unit";
    }
  }

  grouping QOS-MARK {
    description
      "QoS mark";
    leaf mark-type {
      type Dpa-qosea-show-mark;
      description
        "Mark type";
    }
    leaf mark-value {
      type uint16;
      description
        "Mark value";
    }
  }

  grouping DPA-QOSEA-SHOW-CLASS-ST {
    description
      "QoS policy";
    container config-max-rate {
      description
        "Configured maximum rate";
      uses POLICY-PARAMETER;
    }
    container config-min-rate {
      description
        "Configured minimum rate";
      uses POLICY-PARAMETER;
    }
    container config-queue-limit {
      description
        "Configured queue limit";
      uses POLICY-PARAMETER;
    }
    container config-d-queue-limit {
      description
        "Configured Dual queue limit";
      uses DQL-POLICY-PARAMETER;
    }
    container config-policer-average-rate {
      description
        "Configured policer average rate";
      uses POLICY-PARAMETER;
    }
    container config-policer-peak-rate {
      description
        "Config policer peak rate";
      uses POLICY-PARAMETER;
    }
    container config-policer-conform-burst {
      description
        "Configured policer conform burst";
      uses POLICY-PARAMETER;
    }
    container config-policer-excess-burst {
      description
        "Configured policer excess burst";
      uses POLICY-PARAMETER;
    }
    container conform-action {
      description
        "Conform action";
      uses POLICER-ACTION;
    }
    container exceed-action {
      description
        "Exceed action";
      uses POLICER-ACTION;
    }
    container violate-action {
      description
        "Violate action";
      uses POLICER-ACTION;
    }
    container config-shaper-peak-burst {
      description
        "Configured shaper peak burst";
      uses POLICY-PARAMETER;
    }
    container resolved-shaper-peak-burst {
      description
        "Resolved shaper peak burst";
      uses POLICY-PARAMETER;
    }
    leaf class-level {
      type Dpa-qosea-show-level;
      description
        "Class level";
    }
    leaf egress-queue-id {
      type int32;
      description
        "Egress Queue ID";
    }
    leaf queue-type {
      type Dpa-qosea-show-queue;
      description
        "Queue type";
    }
    leaf priority-level {
      type Dpa-qosea-show-hp-level;
      description
        "Priority level";
    }
    leaf hardware-max-rate-kbps {
      type uint32;
      units "kbit/s";
      description
        "Hardware maximum rate in kbps";
    }
    leaf hardware-min-rate-kbps {
      type uint32;
      units "kbit/s";
      description
        "Hardware minimum rate in kbps";
    }
    leaf config-excess-bandwidth-percent {
      type uint32;
      units "percentage";
      description
        "Configured excess bandwidth percentage";
    }
    leaf config-excess-bandwidth-unit {
      type uint32;
      description
        "Configured excess bandwidth unit";
    }
    leaf hardware-excess-bandwidth-weight {
      type uint32;
      description
        "Hardware excess bandwidth weight";
    }
    leaf network-min-bandwidth-kbps {
      type uint32;
      description
        "Network minimum Bandwith";
    }
    leaf hardware-queue-limit-bytes {
      type uint64;
      units "byte";
      description
        "Hardware queue limit in bytes";
    }
    leaf hardware-queue-limit-microseconds {
      type uint64;
      units "microsecond";
      description
        "Hardware queue limit in microseconds";
    }
    leaf policer-bucket-id {
      type uint32;
      description
        "PolicerBucketID";
    }
    leaf policer-stats-handle {
      type uint64;
      description
        "PolicerStatsHandle";
    }
    leaf hardware-policer-average-rate-kbps {
      type uint32;
      units "kbit/s";
      description
        "Hardware policer average in kbps";
    }
    leaf hardware-policer-peak-rate-kbps {
      type uint32;
      description
        "Hardware policer peak rate";
    }
    leaf hardware-policer-conform-burst-bytes {
      type uint32;
      description
        "Hardware policer conform burst";
    }
    leaf hardware-policer-excess-burst-bytes {
      type uint32;
      description
        "Hardware policer excess burst";
    }
    leaf is-referred {
      type boolean;
      description
        "Is shared policer referred class";
    }
    leaf ecn-enabled {
      type boolean;
      description
        "ECN Enabled";
    }
    leaf hardware-shaper-peak-burst-bytes {
      type uint32;
      description
        "Hardware shaper peak burst";
    }
    list ip-mark {
      description
        "IP mark";
      uses QOS-MARK;
    }
    list common-mark {
      description
        "Common mark";
      uses QOS-MARK;
    }
    list mpls-mark {
      description
        "MPLS mark";
      uses QOS-MARK;
    }
    list wred {
      description
        "WRED parameters";
      uses PARAMETERS;
    }
  }

  grouping DPA-QOSEA-SHOW-IF-QOS-INFO-ST {
    description
      "Policy Details";
    leaf npu-id {
      type uint32;
      description
        "NPU ID";
    }
    leaf interface-handle {
      type uint32;
      description
        "InterfaceHandle";
    }
    leaf interface-bandwidth-kbps {
      type uint32;
      units "kbit/s";
      description
        "Interface Bandwidth (in kbps)";
    }
    leaf interface-bandwidthkbps {
      type uint64;
      units "kbit/s";
      description
        "Interface Bandwidth (in kbps)";
    }
    leaf policy-name {
      type string {
        length "0..64";
      }
      description
        "Policy name";
    }
    leaf spi-id {
      type uint32;
      description
        "SPI Id";
    }
    leaf total-number-of-classes {
      type uint16;
      description
        "Number of Classes";
    }
    leaf voq-base-address {
      type uint32;
      description
        "VOQ base address";
    }
    leaf voq-stats-handle {
      type uint64;
      description
        "VOQ stats handle";
    }
    leaf stats-accounting-type {
      type Qos-policy-account-enum;
      description
        "QoS Statistics Accounting Type";
    }
    leaf policy-status {
      type Dpa-qosea-show-policy-status;
      description
        "Policy Status";
    }
    leaf interface-status {
      type Dpa-qosea-show-intf-status;
      description
        "Interface Status";
    }
    leaf pfc {
      type uint8;
      description
        "Flag to indicate if PFC is enabled on the
         interface";
    }
  }
}
