module Cisco-IOS-XR-ipv4-arp-oper {
  namespace "http://cisco.com/ns/yang/Cisco-IOS-XR-ipv4-arp-oper";
  prefix ipv4-arp-oper;

  import ietf-inet-types {
    prefix inet;
  }
  import Cisco-IOS-XR-types {
    prefix xr;
  }
  import cisco-semver {
    prefix semver;
  }
  include Cisco-IOS-XR-ipv4-arp-oper-sub3 {
    revision-date 2020-12-03;
  }
  include Cisco-IOS-XR-ipv4-arp-oper-sub2 {
    revision-date 2020-12-03;
  }
  include Cisco-IOS-XR-ipv4-arp-oper-sub1 {
    revision-date 2020-12-03;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ipv4-arp package operational data.
     
     This module contains definitions
     for the following management objects:
       arp-gmp: ARP-GMP global operational data
       arp: ARP operational data
     
     Copyright (c) 2013-2020 by Cisco Systems, Inc.
     All rights reserved.";

  revision 2020-12-03 {
    description
      "Adding support for displaying client resync time";
    semver:module-version "2.0.0";
  }
  revision 2019-12-11 {
    description
      "adding oper schema support.";
    semver:module-version "1.1.0";
  }
  revision 2019-04-05 {
    description
      "Establish semantic version baseline.";
    semver:module-version "1.0.1";
  }
  revision 2018-11-21 {
    description
      "Fixing backward compatibility error in module.";
  }
  revision 2017-05-01 {
    description
      "Fixing backward compatibility error in module.";
  }
  revision 2016-12-19 {
    description
      "IOS XR 6.2.1 revision.";
  }
  revision 2015-11-09 {
    description
      "IOS XR 6.0 revision.";
  }

  container arp-gmp {
    config false;
    description
      "ARP-GMP global operational data";
    container vrf-infos {
      description
        "Table of VRF related ARP-GMP operational data";
      list vrf-info {
        key "vrf-name";
        description
          "VRF related ARP-GMP operational data";
        leaf vrf-name {
          type xr:Cisco-ios-xr-string {
            length "1..32";
          }
          description
            "VRF name for the default VRF use 'default'";
        }
        uses ARP-GMP-VRF-ENTRY;
      }
    }
    container vrfs {
      description
        "Table of per VRF ARP-GMP operational data";
      list vrf {
        key "vrf-name";
        description
          "Per VRF ARP-GMP operational data";
        container configured-ip-addresses {
          description
            "Table of ARP-GMP configured IP addresses
             information";
          list configured-ip-address {
            key "address";
            description
              "ARP-GMP configured IP address information";
            leaf address {
              type inet:ipv4-address-no-zone;
              description
                "Configured ARP-GMP IP";
            }
            uses ARP-GMP-CONFIG-ENTRY;
          }
        }
        container routes {
          description
            "Table of ARP GMP route information";
          list route {
            description
              "ARP GMP route information";
            leaf address {
              type inet:ipv4-address-no-zone;
              description
                "Host address";
            }
            leaf prefix-length {
              type uint32 {
                range "0..32";
              }
              description
                "Subnet mask";
            }
            uses ARP-GMP-ROUTE-ENTRY;
          }
        }
        container interface-configured-ip-addresses {
          description
            "Table of ARP GMP interface and associated
             configured IP data";
          list interface-configured-ip-address {
            description
              "ARP GMP interface and associated configured
               IP data";
            leaf interface-name {
              type xr:Interface-name;
              description
                "Source Interface";
            }
            leaf address {
              type inet:ipv4-address-no-zone;
              description
                "Configured ARP-GMP IP";
            }
            uses ARP-GMP-INTF-ENTRY;
          }
        }
        leaf vrf-name {
          type xr:Cisco-ios-xr-string {
            length "1..32";
          }
          description
            "VRF name for the default VRF use 'default'";
        }
      }
    }
  }
  container arp {
    config false;
    description
      "ARP operational data";
    container nodes {
      description
        "Table of per-node ARP operational data";
      list node {
        key "node-name";
        description
          "Per-node ARP operational data";
        container resolution-history-dynamic {
          description
            "Per node dynamically-resolved ARP resolution
             history data";
          uses ARP-RESHIST;
        }
        container idb-interface-names {
          description
            "ARP interface database";
          list idb-interface-name {
            key "interface-name";
            description
              "IDB for an interface";
            leaf interface-name {
              type xr:Interface-name;
              description
                "Interface name";
            }
            uses ARP-IDB-INFO;
          }
        }
        container arp-status-info {
          description
            "Per node ARP status information";
          uses ARP-STATUS-INFO;
        }
        container adjacency-history-interface-names {
          description
            "Per node adjacency history data for an
             interface";
          list adjacency-history-interface-name {
            key "interface-name";
            description
              "Per interface adjacency history data";
            leaf interface-name {
              type xr:Interface-name;
              description
                "Interface name";
            }
            uses ARP-AIBHIST;
          }
        }
        container traffic-vrfs {
          description
            "ARP Traffic information per VRF";
          list traffic-vrf {
            key "vrf-name";
            description
              "Per VRF traffic data";
            leaf vrf-name {
              type xr:Cisco-ios-xr-string {
                length "1..32";
              }
              description
                "VRF";
            }
            uses IP-ARP-STATISTICS;
          }
        }
        container client-ids {
          description
            "Stats for client registration/unregistration
             and entry count";
          list client-id {
            key "client-id";
            description
              "Per client stats";
            leaf client-id {
              type uint32 {
                range "0..4294967295";
              }
              description
                "Client ID";
            }
            uses ARP-CLIENT-STAT-INFO;
          }
        }
        container traffic-node {
          description
            "Per node ARP Traffic data";
          uses IP-ARP-STATISTICS;
        }
        container direct-attached-gateway-redundancy-interface-and-addresses {
          description
            "ARP DAGR info";
          list direct-attached-gateway-redundancy-interface-and-address {
            key "interface-name address";
            description
              "DAGR info for the given interface and address";
            leaf interface-name {
              type xr:Interface-name;
              description
                "Interface name";
            }
            leaf address {
              type inet:ipv4-address-no-zone;
              description
                "IP Address";
            }
            uses DAGR-GROUP-INFO;
          }
        }
        container resolution-history-client {
          description
            "Per node client-installed ARP resolution
             history data";
          uses ARP-RESHIST;
        }
        container packet-history-interface-names {
          description
            "Per node packet history data for an interface";
          list packet-history-interface-name {
            key "interface-name";
            description
              "Per interface packet history data";
            leaf interface-name {
              type xr:Interface-name;
              description
                "Interface name";
            }
            uses ARP-PAKHIST;
          }
        }
        container packet-history-all {
          description
            "Per node packet history data";
          uses ARP-PAKHIST;
        }
        container arp-red-sync-gids {
          description
            "ARP sync redundancy entry data";
          list arp-red-sync-gid {
            key "group-id";
            description
              "ARP sync redundancy entry data";
            leaf group-id {
              type uint32 {
                range "0..4294967295";
              }
              description
                "group ID";
            }
            uses ARP-SYNC-ENTRY;
          }
        }
        container arp-stats {
          description
            "Per node ARP statistics";
          uses IP-ARP-STATISTICS;
        }
        container adjacency-history-all {
          description
            "Per node adjacency history data";
          uses ARP-AIBHIST;
        }
        container idb-events-interface-names {
          description
            "ARP interface database events";
          list idb-events-interface-name {
            key "interface-name";
            description
              "IDB events for an interface";
            leaf interface-name {
              type xr:Interface-name;
              description
                "Interface name";
            }
            uses EVT-HIST-INFO;
          }
        }
        container entries {
          description
            "Table of ARP entries";
          list entry {
            key "address interface-name";
            description
              "ARP entry";
            leaf address {
              type inet:ipv4-address-no-zone;
              description
                "IP Address of ARP entry";
            }
            leaf interface-name {
              type xr:Interface-name;
              description
                "Interface name";
            }
            uses IP-ARP-TABLE-ENTRY;
          }
        }
        container traffic-interfaces {
          description
            "ARP Traffic information per interface";
          list traffic-interface {
            key "interface-name";
            description
              "Per interface traffic data";
            leaf interface-name {
              type xr:Interface-name;
              description
                "Interface name";
            }
            uses IP-ARP-STATISTICS;
          }
        }
        leaf node-name {
          type xr:Node-id;
          description
            "Node name";
        }
      }
    }
  }
}
