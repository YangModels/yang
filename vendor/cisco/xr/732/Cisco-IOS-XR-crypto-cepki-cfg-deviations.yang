module Cisco-IOS-XR-crypto-cepki-cfg-deviations {
  namespace "http://cisco.com/ns/yang/Cisco-IOS-XR-crypto-cepki-cfg-deviations";
  prefix crypto-cepki-cfg-deviations;

  import Cisco-IOS-XR-crypto-cepki-cfg {
    prefix crypto-cepki-cfg;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR crypto-cepki package configuration.
     
     Copyright (c) 2013-2021 by Cisco Systems, Inc.
     All rights reserved.";

  revision 2020-06-23 {
    description
      "Fips mode disabled for aarch64 platform";
  }

  deviation "/crypto-cepki-cfg:crypto-ca/crypto-cepki-cfg:fips-mode/crypto-cepki-cfg:enable" {
    deviate not-supported;
  }
}
