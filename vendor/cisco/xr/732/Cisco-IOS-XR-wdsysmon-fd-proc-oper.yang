module Cisco-IOS-XR-wdsysmon-fd-proc-oper {
  namespace "http://cisco.com/ns/yang/Cisco-IOS-XR-wdsysmon-fd-proc-oper";
  prefix wdsysmon-fd-proc-oper;

  import Cisco-IOS-XR-types {
    prefix xr;
  }
  import cisco-semver {
    prefix semver;
  }
  include Cisco-IOS-XR-wdsysmon-fd-proc-oper-sub1 {
    revision-date 2020-04-19;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR wdsysmon-fd-proc package operational data.
     
     This module contains definitions
     for the following management objects:
       process-monitoring: Processes operational data
     
     Copyright (c) 2013-2020 by Cisco Systems, Inc.
     All rights reserved.";

  revision 2020-04-19 {
    description
      "Initial version.";
    semver:module-version "1.0.0";
  }
  revision 2019-04-05 {
    description
      "Establish semantic version baseline.";
  }
  revision 2015-11-09 {
    description
      "IOS XR 6.0 revision.";
  }

  container process-monitoring {
    config false;
    description
      "Processes operational data";
    container nodes {
      description
        "List of nodes";
      list node {
        key "node-name";
        description
          "Node ID";
        container process-name {
          description
            "Process <WORD> information";
          container proc-cpu-utilizations {
            description
              "Process <WORD> information";
            list proc-cpu-utilization {
              key "process-name";
              description
                "Process CPU utilization information";
              leaf process-name {
                type xr:Cisco-ios-xr-string;
                description
                  "Process name";
              }
              uses NODE-CPU-UTIL;
            }
          }
        }
        leaf node-name {
          type xr:Node-id;
          description
            "Node name";
        }
      }
    }
  }
}
