submodule Cisco-IOS-XR-controller-cpri-oper-sub1 {
  belongs-to Cisco-IOS-XR-controller-cpri-oper {
    prefix Cisco-IOS-XR-controller-cpri-oper;
  }

  import ietf-yang-types {
    prefix yang;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR controller-cpri package operational data.
     
     Copyright (c) 2013-2021 by Cisco Systems, Inc.
     All rights reserved.";

  revision 2021-06-03 {
    description
      "Added leaf cpri-hfn-sync-event to container stats.
       2021-05-10
         Added leaf hfn-sync-disable to grouping CPRI-PORT-ROE-PARAMS
       2021-05-03
         Added mapper,demapper roe-profile parameters presync-match-threshold, resync-match-threshold, resync-mismatch-threshold, sync-threshold, drain-threshold, presync-match-count, resync-match-count, resync-mismatch-count.
       2021-04-30
         Added roe-pkt-len-in-use to container info.
       2020-11-04
         Added auto-neg-status, auto-neg-fail-reason, hfn-sync-time, roe-sync-time and auto-neg-completion-time to container info. Added rx-cpri-hyper-frames and tx-cpri-hyper-frames to container stats.";
    semver:module-version "2.1.0";
  }
  revision 2020-08-03 {
    description
      "Changed leaf packet-len type to uint16. Renamed leaf errored-packets to errored-length-packets. Added leaves receive-good-packets and receive-roe-lcv-count.";
    semver:module-version "2.0.0";
  }
  revision 2019-12-02 {
    description
      "Show command subtype added for CPRI controller";
    semver:module-version "1.1.0";
  }
  revision 2019-04-05 {
    description
      "Establish semantic version baseline.";
    semver:module-version "1.0.0";
  }
  revision 2015-11-09 {
    description
      "IOS XR 6.0 revision.";
  }

  typedef Loopback-info {
    type enumeration {
      enum "none" {
        description
          "None";
      }
      enum "line" {
        description
          "Line loopback";
      }
      enum "line-level2" {
        description
          "Line loopback at level 2";
      }
      enum "line-level3" {
        description
          "Line loopback at level 3";
      }
      enum "internal" {
        description
          "Internal loopback";
      }
      enum "internal-level2" {
        description
          "Internal loopback at level 2";
      }
      enum "internal-level3" {
        description
          "Internal loopback at level 3";
      }
    }
    description
      "loopback info";
  }

  typedef Cpri-sec-state-et {
    type enumeration {
      enum "normal" {
        value 0;
        description
          "Normal";
      }
      enum "maintenance" {
        value 1;
        description
          "Maintenance";
      }
      enum "ains" {
        value 2;
        description
          "Automatic In Service";
      }
    }
    description
      "Cpri sec state et";
  }

  typedef Cpri-derived-admin-state {
    type enumeration {
      enum "in-service" {
        description
          "In Service";
      }
      enum "out-of-service" {
        description
          "Out of Service";
      }
      enum "maintenance" {
        description
          "Maintenance";
      }
      enum "ains" {
        description
          "Automatic In Service";
      }
    }
    description
      "Cpri derived admin state";
  }

  typedef Cpri-state-et {
    type enumeration {
      enum "not-ready" {
        value 0;
        description
          "Not Ready";
      }
      enum "admin-down" {
        value 1;
        description
          "Admin Down";
      }
      enum "down" {
        value 2;
        description
          "Down";
      }
      enum "up" {
        value 3;
        description
          "Up";
      }
      enum "shutdown" {
        value 4;
        description
          "Shutdown";
      }
      enum "error-disable" {
        value 5;
        description
          "Error Disable";
      }
      enum "down-immediate" {
        value 6;
        description
          "Down Immediate";
      }
      enum "down-immediate-admin" {
        value 7;
        description
          "Down Immediate Admin";
      }
      enum "down-graceful" {
        value 8;
        description
          "Down Graceful";
      }
      enum "begin-shutdown" {
        value 9;
        description
          "Begin Shutdown";
      }
      enum "end-shutdown" {
        value 10;
        description
          "End Shutdown";
      }
      enum "begin-error-disable" {
        value 11;
        description
          "Begin Error Disable";
      }
      enum "end-error-disable" {
        value 12;
        description
          "End Error Disable";
      }
      enum "begin-down-graceful" {
        value 13;
        description
          "Begin Down Graceful";
      }
      enum "reset" {
        value 14;
        description
          "Reset";
      }
      enum "operational" {
        value 15;
        description
          "Operational";
      }
      enum "not-operational" {
        value 16;
        description
          "Not Operational";
      }
      enum "unknown" {
        value 17;
        description
          "Unknown";
      }
      enum "last" {
        value 18;
        description
          "Last";
      }
    }
    description
      "Cpri state et";
  }

  typedef Cpri-sync-mode {
    type enumeration {
      enum "slave" {
        description
          "Slave";
      }
      enum "master" {
        description
          "Master";
      }
    }
    description
      "CPRI synchronization mode";
  }

  typedef Cpri-line-rate-et {
    type enumeration {
      enum "none" {
        description
          "None";
      }
      enum "option1-614mbps" {
        description
          "Rate 614.4Mbps";
      }
      enum "option2-1228mbps" {
        description
          "Rate 1228.8Mbps";
      }
      enum "option3-2457mbps" {
        description
          "Rate 2457.6Mbps";
      }
      enum "option4-3072mbps" {
        description
          "Rate 3072Mbps";
      }
      enum "option5-4915mbps" {
        description
          "Rate 4915.2Mbps";
      }
      enum "option6-6144mbps" {
        description
          "Rate 6144Mbps";
      }
      enum "option7-9830mbps" {
        description
          "Rate 9830.4Mbps";
      }
      enum "option7a-8110mbps" {
        description
          "Rate 8110.08Mbps";
      }
      enum "option8-10137mbps" {
        description
          "Rate 10137.6Mbps";
      }
      enum "option9-12165mbps" {
        description
          "Rate 12165.12Mbps";
      }
      enum "option10-24330mbps" {
        description
          "Rate 24330.24Mbps";
      }
    }
    description
      "cpri line rate";
  }

  grouping CPRI-PORT-ROE-PARAMS {
    description
      "CPRI port ROE profile parameters";
    leaf profile-id {
      type uint16;
      description
        "ROE profile Id";
    }
    leaf flow-id {
      type uint8;
      description
        "Flow Id";
    }
    leaf source-mac {
      type yang:mac-address;
      description
        "Source Mac address";
    }
    leaf destination-mac {
      type yang:mac-address;
      description
        "Destination Mac address";
    }
    leaf order-info {
      type uint32;
      description
        "Order Info";
    }
    leaf mapper-type {
      type uint8;
      description
        "Mapper Type";
    }
    leaf encrypt {
      type uint8;
      description
        "Encryption";
    }
    leaf compress {
      type uint8;
      description
        "Compress";
    }
    leaf packet-len {
      type uint16;
      description
        "Packet length in terms of CPRI basic frames";
    }
    leaf accept-time-window {
      type uint32;
      description
        "Accept Time Window";
    }
    leaf sample-width {
      type uint8;
      description
        "Sample Width";
    }
    leaf num-of-containers {
      type uint8;
      description
        "Number of Containers";
    }
    leaf num-of-control-containers {
      type uint8;
      description
        "Number of control containers";
    }
    leaf num-fft {
      type uint8;
      description
        "Number of FFT Objects";
    }
    leaf num-prach {
      type uint8;
      description
        "Number of PRACH";
    }
    leaf retimer-buffer-size {
      type uint32;
      description
        "Retimer Buffer Size";
    }
    leaf idle-frame-size {
      type uint32;
      description
        "Idle Frame Size";
    }
    leaf idle-frame-threshold {
      type uint32;
      description
        "Idle Frame Threshold";
    }
    leaf presync-match-threshold {
      type uint8;
      description
        "Presync Match Threshold- applicable in mapper
         ,demapper profile";
    }
    leaf resync-match-threshold {
      type uint8;
      description
        "Resync Match Threshold- applicable in mapper
         ,demapper profile";
    }
    leaf resync-mismatch-threshold {
      type uint8;
      description
        "Resync Mismatch Threshold- applicable in mapper
         ,demapper profile";
    }
    leaf sync-threshold {
      type uint8;
      description
        "Sync Threshold- applicable only in demapper
         profile";
    }
    leaf drain-threshold {
      type uint8;
      description
        "Drain Threshold- applicable only in demapper
         profile";
    }
    leaf presync-match-count {
      type uint8;
      description
        "Presync Match Count- applicable only in demapper
         profile";
    }
    leaf resync-match-count {
      type uint8;
      description
        "Resync Match Count- applicable only in demapper
         profile";
    }
    leaf resync-mismatch-count {
      type uint8;
      description
        "Resync Mismatch Count- applicable only in
         demapper profile";
    }
    leaf hfn-sync-disable {
      type boolean;
      description
        "HFN Sync disabled when set. Applicable only for
         type-0 mapper config in non auto-neg CPRI port";
    }
    leaf-list idle-frame-data {
      type uint8;
      description
        "Idle Frame Data";
    }
  }

  grouping CPRI-PORT-ROE-PROFILE {
    description
      "CPRI port ROE profile Info";
    container roe-mapper-profile-params {
      description
        "CPRI port's ROE Mapper Profile params";
      uses CPRI-PORT-ROE-PARAMS;
    }
    container roe-demapper-profile-params {
      description
        "CPRI port's ROE Mapper Profile params";
      uses CPRI-PORT-ROE-PARAMS;
    }
    leaf is-roe-configured {
      type boolean;
      description
        "Is ROE profile configured?";
    }
  }

  grouping ROE-PDV-STATS {
    description
      "ROE packet delay variation values";
    leaf minval {
      type uint64;
      description
        "Minimun PDV value";
    }
    leaf max-val {
      type uint64;
      description
        "Maximun PDV value";
    }
    leaf avg-val {
      type uint64;
      description
        "Average PDV value";
    }
  }

  grouping CPRI-PORT-ROE-STATS {
    description
      "CPRI port operational RoE stats";
    container pkt-dly-var-max {
      description
        "Packet delay variation";
      uses ROE-PDV-STATS;
    }
    leaf rx-frames {
      type uint64;
      description
        "Received Frames";
    }
    leaf rx-octets {
      type uint64;
      description
        "Received Octets";
    }
    leaf lost-frames-detected {
      type uint64;
      description
        "Lost frames detected";
    }
    leaf stray-frames-detected {
      type uint64;
      description
        "Stray frames detected";
    }
    leaf duplicate-frames-detected {
      type uint64;
      description
        "Duplicate frames detected";
    }
    leaf out-of-seq-frames-detected {
      type uint64;
      description
        "Out of Sequence frames detected";
    }
    leaf out-of-seq-frames-dropped {
      type uint64;
      description
        "Out of Sequence frames dropped";
    }
    leaf retimer-buffer-overrun {
      type uint64;
      description
        "Retimer buffer overrun";
    }
    leaf retimer-buffer-underrun {
      type uint64;
      description
        "Retimer buffer underrun";
    }
    leaf tx-frames {
      type uint64;
      description
        "Transmitted Frames";
    }
    leaf tx-octets {
      type uint64;
      description
        "Transmitted Octets";
    }
    leaf idle-frames-sent {
      type uint64;
      description
        "Idle frames transmitted";
    }
    leaf idle-octets-sent {
      type uint64;
      description
        "Idle octets transmitted";
    }
    leaf errored-length-packets {
      type uint64;
      description
        "Errored packets";
    }
    leaf kbyte-mismatch {
      type uint64;
      description
        "K byte mismatch";
    }
    leaf link-td-transitions {
      type uint64;
      description
        "Link teardown transitions";
    }
    leaf idle-frame-tca {
      type uint64;
      description
        "Idle Frame Threshold Crossing Alarm";
    }
    leaf receive-roe-lcv-count {
      type uint64;
      description
        "RoE receive side LCV count";
    }
    leaf receive-good-packets {
      type uint64;
      description
        "RoE receive side good packets";
    }
  }

  grouping CPRI-PORT-STATS {
    description
      "CPRI port operational stats";
    container los {
      description
        "Loss of signal";
      uses CPRI-ALARM-INFO;
    }
    container lof {
      description
        "Loss of frame";
      uses CPRI-ALARM-INFO;
    }
    container rai {
      description
        "Remote Alarm Indication";
      uses CPRI-ALARM-INFO;
    }
    container sdi {
      description
        "SAP Defect Indication";
      uses CPRI-ALARM-INFO;
    }
    container remote-los {
      description
        "Remote Loss of signal";
      uses CPRI-ALARM-INFO;
    }
    container remote-lof {
      description
        "Remote Loss of frame";
      uses CPRI-ALARM-INFO;
    }
    container remote-rai {
      description
        "Remote side Remote Alarm Indication";
      uses CPRI-ALARM-INFO;
    }
    container remote-sdi {
      description
        "Remote SAP Defect Indication";
      uses CPRI-ALARM-INFO;
    }
    leaf state-changes {
      type uint64;
      description
        "CPRI controller state change count";
    }
    leaf rx-failure {
      type uint64;
      description
        "Received Failures";
    }
    leaf tx-failure {
      type uint64;
      description
        "Transmitted Failures";
    }
    leaf lcv-count {
      type uint64;
      description
        "Line Coding Violation count";
    }
    leaf rx-cpri-hyper-frames {
      type uint64;
      description
        "Received CPRI hyper frames";
    }
    leaf tx-cpri-hyper-frames {
      type uint64;
      description
        "Transmitted CPRI hyper frames";
    }
    leaf hfn-sync-event-cpri {
      type uint64;
      description
        "CPRI HFN Sync Event. Not applicable when Type-0
         enhancement is disabled";
    }
  }

  grouping CPRI-ALARM-INFO {
    description
      "CPRI Alarm info";
    leaf reporting-enabled {
      type boolean;
      description
        "Is reporting enabled?";
    }
    leaf is-detected {
      type boolean;
      description
        "Is defect detected?";
    }
    leaf is-asserted {
      type boolean;
      description
        "Is defect delared?";
    }
    leaf count {
      type uint64;
      description
        "Alarm count";
    }
  }

  grouping CPRI-PORT-INFO {
    description
      "CPRI port operational info";
    container los {
      description
        "Loss of signal";
      uses CPRI-ALARM-INFO;
    }
    container lof {
      description
        "Loss of frame";
      uses CPRI-ALARM-INFO;
    }
    container rai {
      description
        "Remote Alarm Indication";
      uses CPRI-ALARM-INFO;
    }
    container sdi {
      description
        "SAP Defect Indication";
      uses CPRI-ALARM-INFO;
    }
    container remote-los {
      description
        "Remote Loss of signal";
      uses CPRI-ALARM-INFO;
    }
    container remote-lof {
      description
        "Remote Loss of frame";
      uses CPRI-ALARM-INFO;
    }
    container remote-rai {
      description
        "Remote side Remote Alarm Indication";
      uses CPRI-ALARM-INFO;
    }
    container remote-sdi {
      description
        "Remote SAP Defect Indication";
      uses CPRI-ALARM-INFO;
    }
    leaf negotiated-rate {
      type Cpri-line-rate-et;
      description
        "Negotiated CPRI rate";
    }
    leaf negotiation-list-size {
      type uint32;
      description
        "Size of negotiation rate list";
    }
    leaf synchronization-mode {
      type Cpri-sync-mode;
      description
        "Synchronization Mode";
    }
    leaf l1-startup-timer {
      type uint32;
      description
        "L1 Startup Timer";
    }
    leaf operational-state {
      type Cpri-state-et;
      description
        "Port's IM state";
    }
    leaf derived-admin-state {
      type Cpri-derived-admin-state;
      description
        "Derived Admin State";
    }
    leaf config-sec-state {
      type Cpri-sec-state-et;
      description
        "Configured Sec Admin State";
    }
    leaf inherited-sec-state {
      type Cpri-sec-state-et;
      description
        "Inherited Sec Admin State";
    }
    leaf loopback {
      type Loopback-info;
      description
        "Loopback info";
    }
    leaf last-clear-time {
      type uint32;
      description
        "Time Duration Since Last Clear";
    }
    leaf auto-neg-status {
      type int8;
      description
        "Auto negotiation status";
    }
    leaf auto-neg-fail-reason {
      type string {
        length "0..64";
      }
      description
        "Auto negotiation failure reason";
    }
    leaf hfn-sync-time {
      type int32;
      units "millisecond";
      description
        "High Frame Number sync time in milli seconds.
         Value -1 refers to Not Applicable";
    }
    leaf roe-sync-time {
      type int32;
      units "millisecond";
      description
        "Radio-over-Ethernet sync time in milli seconds.
         Value -1 refers to Not Applicable";
    }
    leaf auto-neg-completion-time {
      type int32;
      units "millisecond";
      description
        "Auto negotiation completion time in milli
         seconds. Value -1 refers to Not Applicable";
    }
    leaf is-roe-configured {
      type boolean;
      description
        "Is ROE profile is attached to CPRI";
    }
    leaf idle-frame-tca {
      type boolean;
      description
        "Idle Frame Threshold Crossing Alarm";
    }
    leaf pers-str-frm-det {
      type boolean;
      description
        "Persistent Stray Frame Detected";
    }
    leaf pers-lost-frm-det {
      type boolean;
      description
        "Persistent Lost Frame Detected";
    }
    leaf retimer-buf-overrun {
      type boolean;
      description
        "Retimer buffer overrun";
    }
    leaf retimer-buf-underrun {
      type boolean;
      description
        "Retimer buffer underrun";
    }
    leaf roe-pkt-len-in-use {
      type int32;
      units "byte";
      description
        "ROE packet length in use in bytes";
    }
    leaf-list supported-line-rate {
      type Cpri-line-rate-et;
      description
        "Hardware supported CPRI rates";
    }
    leaf-list configured-negotiation-rate {
      type Cpri-line-rate-et;
      description
        "Configured negotiation rates";
    }
  }

  grouping CPRI-PORT-DETAIL {
    description
      "CPRI port operational detail";
    container info {
      description
        "cpri port basic details";
      uses CPRI-PORT-INFO;
    }
    container stats {
      description
        "cpri statistics";
      uses CPRI-PORT-STATS;
    }
    container roe-stats {
      description
        "CPRI port's ROE statistics";
      uses CPRI-PORT-ROE-STATS;
    }
    container roe-profile-info {
      description
        "CPRI port's ROE Profile Info";
      uses CPRI-PORT-ROE-PROFILE;
    }
  }
}
