module Cisco-IOS-XR-osa-cfg {
  namespace "http://cisco.com/ns/yang/Cisco-IOS-XR-osa-cfg";
  prefix osa-cfg;

  import Cisco-IOS-XR-config-mda-cfg {
    prefix node;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR osa package configuration.
     
     This YANG module augments the
       Cisco-IOS-XR-config-mda-cfg
     module with configuration data.
     
     Copyright (c) 2013-2020 by Cisco Systems, Inc.
     All rights reserved.";

  revision 2020-10-09 {
    description
      "Initial Revision.";
    semver:module-version "2.0.0";
  }
  revision 2019-10-11 {
    description
      "Enhancement in CLI for 50G trunk-rate";
    semver:module-version "1.2.0";
  }
  revision 2019-08-13 {
    description
      "Aligning modifications to 7.1.1.";
    semver:module-version "1.1.0";
  }
  revision 2019-04-05 {
    description
      "Establish semantic version baseline.";
    semver:module-version "1.0.0";
  }
  revision 2018-09-26 {
    description
      "Ains DTHO caveats fix.";
  }
  revision 2018-08-30 {
    description
      "Add Ains support.";
  }
  revision 2018-05-23 {
    description
      "Initial Revision.";
  }
  revision 2015-11-09 {
    description
      "IOS XR 6.0 revision.";
  }

  typedef Trunk-data-rate {
    type enumeration {
      enum "fifty-gig" {
        value 1;
        description
          "FiftyGig";
      }
      enum "hundred-gig" {
        value 2;
        description
          "HundredGig";
      }
      enum "one-hundred-fifty-gig" {
        value 3;
        description
          "OneHundredFiftyGig";
      }
      enum "two-hundred-gig" {
        value 4;
        description
          "TwoHundredGig";
      }
      enum "two-hundred-fifty-gig" {
        value 5;
        description
          "TwoHundredFifty";
      }
      enum "three-hundred-gig" {
        value 6;
        description
          "ThreeHundredGig";
      }
      enum "three-hundred-fifty-gig" {
        value 7;
        description
          "ThreeHundredFiftyGig";
      }
      enum "four-hundred-gig" {
        value 8;
        description
          "FourHundredGig";
      }
      enum "four-hundred-fifty-gig" {
        value 9;
        description
          "FourHundredFiftyGig";
      }
      enum "five-hundred-gig" {
        value 10;
        description
          "FiveHundredGig";
      }
      enum "five-hundred-fifty-gig" {
        value 11;
        description
          "FiveHundredFiftyGig";
      }
      enum "six-hundred-gig" {
        value 12;
        description
          "SixHundredGig";
      }
    }
    description
      "Trunk data rate";
  }

  typedef Ains-soak-hours-range {
    type uint32 {
      range "0..48";
    }
    description
      "Ains soak hours range";
  }

  typedef Client-data-rate {
    type enumeration {
      enum "ten-gig-e" {
        value 1;
        description
          "TenGigE";
      }
      enum "hundred-gig-e" {
        value 2;
        description
          "HundredGigE";
      }
      enum "otu4" {
        value 3;
        description
          "OTU4";
      }
      enum "otu2" {
        value 4;
        description
          "OTU2";
      }
      enum "otu2e" {
        value 5;
        description
          "OTU2E";
      }
      enum "otu3" {
        value 6;
        description
          "OTU3";
      }
      enum "forty-gig-e" {
        value 7;
        description
          "FortyGigE";
      }
      enum "four-hundred-gig-e" {
        value 8;
        description
          "FourHundredGigE";
      }
    }
    description
      "Client data rate";
  }

  typedef Ains-soak-minutes-range {
    type uint32 {
      range "0..59";
    }
    description
      "Ains soak minutes range";
  }

  grouping NODE-CFG {
    description
      "active/preconfigured nodes configuration";
    container regen {
      description
        "Regenerator Module configuration";
      leaf trunk-rates {
        type Trunk-data-rate;
        description
          "Trunk  data rates";
      }
    }
    container mxponder-slices {
      description
        "Mxponder slice configuration";
      list mxponder-slice {
        key "slice-id";
        description
          "Slice configuration";
        container client-ains {
          description
            "AINS Soak Interval Value";
          leaf hours {
            type Ains-soak-hours-range;
            units "hour";
            description
              "Hours";
          }
          leaf minutes {
            type Ains-soak-minutes-range;
            units "minute";
            description
              "Minutes";
          }
        }
        container mxp-slice-client-ports {
          description
            "Client Mode";
          list mxp-slice-client-port {
            key "mxp-slice-port-id";
            description
              "client port number";
            container mxp-slice-client-port-mode {
              description
                "Client Port Mode";
              leaf client-type {
                type Client-data-rate;
                description
                  "client traffic type";
              }
            }
            container mxp-slice-client-optics-lanes {
              description
                "Client Port";
              list mxp-slice-client-optics-lane {
                key "optics-lane-id";
                description
                  "client lane number";
                leaf client-type {
                  type Client-data-rate;
                  description
                    "client traffic type";
                }
                leaf optics-lane-id {
                  type uint32 {
                    range "1..4";
                  }
                  description
                    "Set client optics lane";
                }
              }
            }
            leaf mxp-slice-port-id {
              type uint32 {
                range "0..12";
              }
              description
                "Set client port number";
            }
          }
        }
        leaf trunk-rates {
          type Trunk-data-rate;
          description
            "Trunk  data rates";
        }
        leaf lldp {
          type boolean;
          description
            "Drop LLDP Packets";
        }
        leaf arp-snoop {
          type boolean;
          description
            "Enable ARP Snooping";
        }
        leaf client-rates {
          type Client-data-rate;
          description
            "Client  data rates";
        }
        leaf slice-id {
          type uint32 {
            range "0..1";
          }
          description
            "Set Slice";
        }
      }
    }
    container mxponder {
      description
        "Mxponder module configuration";
      container client-ports {
        description
          "Client Mode";
        list client-port {
          key "port-id";
          description
            "client port number";
          container client-port-mode {
            description
              "Client Port Mode";
            leaf client-type {
              type Client-data-rate;
              description
                "client traffic type";
            }
          }
          container client-optics-lanes {
            description
              "Client Port";
            list client-optics-lane {
              key "lane-id";
              description
                "client lane number";
              leaf client-type {
                type Client-data-rate;
                description
                  "client traffic type";
              }
              leaf lane-id {
                type uint32 {
                  range "1..4";
                }
                description
                  "Set client optics lane";
              }
            }
          }
          leaf port-id {
            type uint32 {
              range "0..12";
            }
            description
              "Set client port number";
          }
        }
      }
      container client-ains {
        description
          "AINS Soak Interval Value";
        leaf hours {
          type Ains-soak-hours-range;
          units "hour";
          description
            "Hours";
        }
        leaf minutes {
          type Ains-soak-minutes-range;
          units "minute";
          description
            "Minutes";
        }
      }
      leaf trunk-rates {
        type Trunk-data-rate;
        description
          "Trunk  data rates";
      }
      leaf lldp {
        type boolean;
        description
          "Drop LLDP Packets";
      }
      leaf arp-snoop {
        type boolean;
        description
          "Enable ARP Snoop";
      }
      leaf client-rates {
        type Client-data-rate;
        description
          "Client  data rates";
      }
    }
  }

  augment "/node:active-nodes/node:active-node" {
    description
      "This augment extends active nodes configuration";
    uses NODE-CFG;
  }
  augment "/node:preconfigured-nodes/node:preconfigured-node" {
    description
      "This augment extends preconfigured nodes
       configuration";
    uses NODE-CFG;
  }
}
