module Cisco-IOS-XR-ncs1k-mxp-cfg {
  namespace "http://cisco.com/ns/yang/Cisco-IOS-XR-ncs1k-mxp-cfg";
  prefix ncs1k-mxp-cfg;

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ncs1k-mxp package configuration.
     
     This module contains definitions
     for the following management objects:
       hardware-module: NCS1k HW module config
     
     Copyright (c) 2013-2019 by Cisco Systems, Inc.
     All rights reserved.";

  revision 2019-10-31 {
    description
      "Added mandatory nodes and presence containers.";
    semver:module-version "2.0.0";
  }
  revision 2019-04-05 {
    description
      "Establish semantic version baseline.";
    semver:module-version "2.0.0";
  }
  revision 2015-11-09 {
    description
      "IOS XR 6.0 revision.";
  }

  typedef Trunk-data-rate {
    type enumeration {
      enum "hundred-gig" {
        value 2;
        description
          "HundredGig";
      }
      enum "two-hundred-gig" {
        value 3;
        description
          "TwoHundredGig";
      }
      enum "two-hundred-fifty-gig" {
        value 4;
        description
          "TwoHundredFiftyGig";
      }
    }
    description
      "Trunk data rate";
  }

  typedef Ains-soak-hours-range {
    type uint32 {
      range "0..48";
    }
    description
      "Ains soak hours range";
  }

  typedef Client-data-rate {
    type enumeration {
      enum "ten-gig" {
        value 1;
        description
          "TenGig";
      }
      enum "forty-gig" {
        value 2;
        description
          "FortyGig";
      }
      enum "hundred-gig" {
        value 3;
        description
          "HundredGig";
      }
      enum "ten-and-hundred-gig" {
        value 4;
        description
          "TenAndHundredGig";
      }
    }
    description
      "Client data rate";
  }

  typedef Fec {
    type enumeration {
      enum "sd7" {
        value 1;
        description
          "SoftDecision7";
      }
      enum "sd20" {
        value 2;
        description
          "SoftDecision20";
      }
    }
    description
      "Fec";
  }

  typedef Ains-soak-minutes-range {
    type uint32 {
      range "0..59";
    }
    description
      "Ains soak minutes range";
  }

  container hardware-module {
    description
      "NCS1k HW module config";
    list node {
      key "location";
      description
        "Node";
      leaf location {
        type xr:Cisco-ios-xr-string;
        description
          "Fully qualified line card specification";
      }
      list slice {
        key "slice-id";
        description
          "Slice to be Provisioned";
        container values {
          presence "Contains mandatory nodes that used to set default values";
          description
            "Data rates & FEC";
          leaf client-rate {
            type Client-data-rate;
            description
              "Client Rate";
          }
          leaf trunk-rate {
            type Trunk-data-rate;
            description
              "TrunkRate";
          }
          leaf fec {
            type Fec;
            description
              "FEC";
          }
          leaf encrypted {
            type boolean;
            mandatory true;
            description
              "Encrypted";
          }
        }
        container client-ains {
          description
            "AINS Soak Interval Value";
          leaf hours {
            type Ains-soak-hours-range;
            units "hour";
            description
              "Hours";
          }
          leaf minutes {
            type Ains-soak-minutes-range;
            units "minute";
            description
              "Minutes";
          }
        }
        leaf lldp {
          type boolean;
          description
            "Drop LLDP Packets";
        }
        leaf slice-id {
          type xr:Cisco-ios-xr-string;
          description
            "Set Slice";
        }
      }
    }
  }
}
