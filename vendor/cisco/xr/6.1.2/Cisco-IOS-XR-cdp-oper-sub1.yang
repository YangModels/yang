submodule Cisco-IOS-XR-cdp-oper-sub1 {

  belongs-to Cisco-IOS-XR-cdp-oper {
    prefix Cisco-IOS-XR-cdp-oper;
  }

  /*** LINKAGE (IMPORTS / INCLUDES) ***/

  import ietf-inet-types { prefix "inet"; }

  import ietf-yang-types { prefix "yang"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR cdp package operational data.

     Copyright (c) 2013-2016 by Cisco Systems, Inc.
     All rights reserved.";

  revision "2015-07-30" {
    description
      "Revison descritption string.";
  }

  revision "2015-01-07" {
    description
      "IOS XR 5.3.1 revision.";
  }

  typedef Im-state {
    type uint32;
    description "Im state";
  }
  typedef Cdp-duplex {
    type enumeration {
      enum cdp-dplx-none {
        value 0;
        description "cdp dplx none";
      }
      enum cdp-dplx-half {
        value 1;
        description "cdp dplx half";
      }
      enum cdp-dplx-full {
        value 2;
        description "cdp dplx full";
      }
    }
    description "Cdp duplex";
  }
  typedef In6-addr {
    type inet:ipv6-address;
    description "In6 addr";
  }
  typedef Cdp-l3-addr-protocol {
    type enumeration {
      enum ipv4 {
        description "IPv4";
      }
      enum ipv6 {
        description "IPv6";
      }
    }
    description "Cdp l3 addr protocol";
  }

  grouping CDP-INTERFACE {
    description
      "Information about an interface that CDP is
      running on";
    leaf interface-name-xr {
      type xr:Interface-name;
      description "Interface";
    }
    leaf basecaps-state {
      type Im-state;
      description "Interface basecaps state";
    }
    leaf cdp-protocol-state {
      type Im-state;
      description "CDP protocol state";
    }
    leaf interface-encaps {
      type string;
      description "Interface encapsulation";
    }
  }

  grouping CDP-STATS {
    description "CDP statistics";
    leaf received-packets {
      type uint32;
      description "Received packets";
    }
    leaf received-packets-v1 {
      type uint32;
      description "Received v1 packets";
    }
    leaf received-packets-v2 {
      type uint32;
      description "Received v2 packets";
    }
    leaf transmitted-packets {
      type uint32;
      description "Transmitted packets";
    }
    leaf transmitted-packets-v1 {
      type uint32;
      description "Transmitted v1 packets";
    }
    leaf transmitted-packets-v2 {
      type uint32;
      description "Transmitted v2 packets";
    }
    leaf header-errors {
      type uint32;
      description "Header syntax errors";
    }
    leaf checksum-errors {
      type uint32;
      description "Checksum errors";
    }
    leaf encapsulation-errors {
      type uint32;
      description "Transmission errors";
    }
    leaf bad-packet-errors {
      type uint32;
      description "Bad packet received and dropped";
    }
    leaf out-of-memory-errors {
      type uint32;
      description "Out-of-memory conditions";
    }
    leaf truncated-packet-errors {
      type uint32;
      description "Truncated messages";
    }
    leaf header-version-errors {
      type uint32;
      description "Can't handle receive version";
    }
    leaf open-file-errors {
      type uint32;
      description "Cannot open file";
    }
  }

  grouping CDP-PROTOCOL-HELLO-ENTRY {
    description "CDP Protocol Hello entry";

    list cdp-prot-hello-entry {
      description "cdp prot hello entry";
      leaf hello-message {
        type yang:hex-string;
        description "Protocol Hello msg";
      }
    }
  }

  grouping CDP-L3-ADDR {
    description "CDP L3 ADDR";
    leaf address-type {
      type Cdp-l3-addr-protocol;
      description "AddressType";
    }
    leaf ipv4-address {
      when "../address-type = 'ipv4'" {
        description "../AddressType = 'IPv4'";
      }
      type inet:ipv4-address;
      description "IPv4 address";
    }
    leaf ipv6-address {
      when "../address-type = 'ipv6'" {
        description "../AddressType = 'IPv6'";
      }
      type In6-addr;
      description "IPv6 address";
    }
  }

  grouping CDP-ADDRESS-ENTRY {
    description "CDP Address entry";

    list cdp-addr-entry {
      description "cdp addr entry";

      container address {
        description "Network layer address";
        uses CDP-L3-ADDR;
      }
    }
  }

  grouping CDP-NEIGHBOR-ENTRY-DETAILS {
    description "Detailed neighbor info";

    container network-addresses {
      description "List of network addresses ";
      uses CDP-ADDRESS-ENTRY;
    }

    container protocol-hello-list {
      description "List of protocol hello entries";
      uses CDP-PROTOCOL-HELLO-ENTRY;
    }
    leaf version {
      type string;
      description "Version TLV";
    }
    leaf vtp-domain {
      type string;
      description "VTP domain";
    }
    leaf native-vlan {
      type uint32;
      description "Native VLAN";
    }
    leaf duplex {
      type Cdp-duplex;
      description "Duplex setting";
    }
    leaf system-name {
      type string;
      description "SysName";
    }
  }

  grouping CDP-NEIGHBOR {
    description "CDP neighbor info";

    list cdp-neighbor {
      description "cdp neighbor";

      container detail {
        description "Detailed neighbor info";
        uses CDP-NEIGHBOR-ENTRY-DETAILS;
      }
      leaf receiving-interface-name {
        type xr:Interface-name;
        description "Interface the neighbor entry was received on ";
      }
      leaf device-id {
        type string;
        description "Device identifier";
      }
      leaf port-id {
        type string;
        description "Outgoing port identifier";
      }
      leaf header-version {
        type uint8;
        description "Version number";
      }
      leaf hold-time {
        type uint16;
        description "Remaining hold time";
      }
      leaf capabilities {
        type string;
        description "Capabilities";
      }
      leaf platform {
        type string;
        description "Platform type";
      }
    }
  }
}
