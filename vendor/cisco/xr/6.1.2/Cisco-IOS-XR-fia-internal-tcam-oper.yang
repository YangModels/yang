module Cisco-IOS-XR-fia-internal-tcam-oper {

  /*** NAMESPACE / PREFIX DEFINITION ***/

  namespace "http://cisco.com/ns/yang"+
    "/Cisco-IOS-XR-fia-internal-tcam-oper";


  prefix "fia-internal-tcam-oper";

  /*** LINKAGE (IMPORTS / INCLUDES) ***/

  import Cisco-IOS-XR-types { prefix "xr"; }

  include Cisco-IOS-XR-fia-internal-tcam-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR fia-internal-tcam package operational data.

     This module contains definitions
     for the following management objects:
       controller: Controller Resources

     Copyright (c) 2013-2016 by Cisco Systems, Inc.
     All rights reserved.";

  revision "2015-11-09" {
    description
      "IOS XR 6.0 revision.";
  }


  container controller {
    config false;
    description "Controller Resources";

    container dpa {
      description "Controller DPA operational data";

      container nodes {
        description "DPA data for available nodes";

        list node {
          key "node-name";
          description "DPA operational data for a particular node";

          container internal-tcam-resources {
            description "Internal TCAM Resource Information";
            uses FIA-CARD-TCAM;
          }
          leaf node-name {
            type xr:Node-id;
            description "Node ID";
          }
        }
      }
    }
  }
}
