module Cisco-IOS-XR-man-netconf-cfg {

  /*** NAMESPACE / PREFIX DEFINITION ***/

  namespace "http://cisco.com/ns/yang/Cisco-IOS-XR-man-netconf-cfg";


  prefix "man-netconf-cfg";

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR man-netconf package configuration.

     This module contains definitions
     for the following management objects:
       netconf-yang: NETCONF YANG configuration commands

     Copyright (c) 2013-2016 by Cisco Systems, Inc.
     All rights reserved.";

  revision "2016-03-15" {
    description
      "Descriptions updated.";
  }

  revision "2015-01-07" {
    description
      "IOS XR 5.3.1 revision.";
  }


  container netconf-yang {
    description "NETCONF YANG configuration commands";

    container agent {
      description "NETCONF YANG agent configuration commands";

      container ssh {
        description "NETCONF YANG agent over SSH connection";
        leaf enable {
          type empty;
          description
            "Enable NETCONF YANG agent over SSH connection";
        }
      }

      container session {
        description "Session settings";
        leaf limit {
          type uint32 {
            range "1..50";
          }
          default "50";
          description
            "Count of allowable concurrent netconf-yang
            sessions";
        }
        leaf absolute-timeout {
          type uint32 {
            range "1..1440";
          }
          units "minute";
          description "Absolute timeout in minutes";
        }
        leaf idle-timeout {
          type uint32 {
            range "1..1440";
          }
          units "minute";
          description "Non-active session lifetime";
        }
      }
      leaf rate-limit {
        type uint32 {
          range "4096..4294967295";
        }
        units "byte";
        description "Number of bytes to process per sec";
      }
    }
  }
}
