module Cisco-IOS-XR-asr9k-prm-cfg {

  /*** NAMESPACE / PREFIX DEFINITION ***/

  namespace "http://cisco.com/ns/yang/Cisco-IOS-XR-asr9k-prm-cfg";


  prefix "asr9k-prm-cfg";

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR asr9k-prm package configuration.

     This module contains definitions
     for the following management objects:
       hardware-module-qos-mode: QoS mode in hardware module port(s)
       hardware-module-tcp-mss-adjust: hardware module tcp mss adjust
       hardware-module-load-balance: hardware module load balance
       hardware-module-tcam: hardware module tcam
       hardware-module-efd: hardware module efd

     Copyright (c) 2013-2016 by Cisco Systems, Inc.
     All rights reserved.";

  revision "2015-11-09" {
    description
      "IOS XR 6.0 revision.";
  }

  typedef Asr9k-efd-operation {
    type enumeration {
      enum less-than {
        value 2;
        description "Less than";
      }
      enum greater-than-or-equal {
        value 3;
        description "Greater than or equal";
      }
    }
    description "Asr9k efd operation";
  }
  typedef Asr9k-efd-mode {
    type enumeration {
      enum only-outer-encap {
        value 0;
        description "Only check outer encap";
      }
      enum include-inner-encap {
        value 1;
        description "Check outer and inner encap";
      }
    }
    description "Asr9k efd mode";
  }
  typedef Prm-tcam-profile {
    type enumeration {
      enum profile0 {
        value 0;
        description "Profile 0";
      }
      enum profile1 {
        value 1;
        description "Profile 1";
      }
      enum profile2 {
        value 2;
        description "Profile 2";
      }
    }
    description "Prm tcam profile";
  }

  container hardware-module-qos-mode {
    description "QoS mode in hardware module port(s)";

    container nodes {
      description "QoS applicable nodes";

      list node {
        key "node-name";
        description "A node";
        leaf child-shaping-disable {
          type empty;
          description "Disable child level/flat policy shaping";
        }
        leaf lowburst-enable {
          type empty;
          description "Enable low burst mode for TM entity";
        }
        leaf node-name {
          type xr:Node-id;
          description "Node ID";
        }
      }
    }
  }

  container hardware-module-tcp-mss-adjust {
    description "hardware module tcp mss adjust";

    container nodes {
      description "TCP MSS Adjust applicable nodes";

      list node {
        key "node-name";
        description "A node";

        container nps {
          description "TCP MSS Adjust NPs";

          list np {
            key "np-id";
            description "NP number";
            leaf adjust-value {
              type uint32 {
                range "1280..1535";
              }
              units "byte";
              description "TCP MSS Adjust value";
            }
            leaf np-id {
              type uint32 {
                range "0..7";
              }
              description "Number between 0-7";
            }
          }
        }
        leaf node-name {
          type xr:Node-id;
          description "Node ID";
        }
      }
    }
  }

  container hardware-module-load-balance {
    description "hardware module load balance";

    container bundle {
      description "Bundle load balance options";

      container l2-service {
        description "Load balance for L2 services";
        leaf l3-parameters {
          type empty;
          description
            "Load balance L2 services over bundle with L3
            parameters";
        }
      }
    }
  }

  container hardware-module-tcam {
    description "hardware module tcam";

    container nodes {
      description "TCAM applicable nodes";

      list node {
        key "node-name";
        description "A TCAM applicable node";
        leaf profile {
          type Prm-tcam-profile;
          default "profile0";
          description "A TCAM partition profile";
        }
        leaf node-name {
          type xr:Node-id;
          description "Node ID";
        }
      }
    }
    leaf global-profile {
      type Prm-tcam-profile;
      default "profile0";
      description
        "Global TCAM partition profile for all TCAM
        applicable nodes";
    }
  }

  container hardware-module-efd {
    description "hardware module efd";

    container nodes {
      description "EFD applicable nodes";

      list node {
        key "node-name";
        description "A node";

        container ip-precedence {
          presence "Indicates a ip-precedence node is configured.";
          description "EFD IP parameters";
          leaf precedence {
            type uint32 {
              range "0..7";
            }
            mandatory true;
            description "IP TOS precedence threshold";
          }
          leaf operation {
            type Asr9k-efd-operation;
            default "greater-than-or-equal";
            description "IP operation";
          }
        }

        container vlan-cos {
          presence "Indicates a vlan-cos node is configured.";
          description "EFD VLAN parameters";
          leaf cos {
            type uint32 {
              range "0..7";
            }
            mandatory true;
            description "VLAN COS threshold";
          }
          leaf operation {
            type Asr9k-efd-operation;
            default "greater-than-or-equal";
            description "VLAN operation";
          }
        }

        container mpls-exp {
          presence "Indicates a mpls-exp node is configured.";
          description "EFD MPLS parameters";
          leaf exp {
            type uint32 {
              range "0..7";
            }
            mandatory true;
            description "MPLS EXP threshold";
          }
          leaf operation {
            type Asr9k-efd-operation;
            default "greater-than-or-equal";
            description "MPLS operation";
          }
        }
        leaf enable {
          type empty;
          description "Enable EFD for this node";
        }
        leaf mode {
          type Asr9k-efd-mode;
          description "EFD mode parameter.";
        }
        leaf node-name {
          type xr:Node-id;
          description "Node Name";
        }
      }
    }
  }
}
