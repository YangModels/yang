module Cisco-IOS-XR-ipv4-pim-cfg {

  /*** NAMESPACE / PREFIX DEFINITION ***/

  namespace "http://cisco.com/ns/yang/Cisco-IOS-XR-ipv4-pim-cfg";


  prefix "ipv4-pim-cfg";

  /*** LINKAGE (IMPORTS / INCLUDES) ***/

  import ietf-inet-types { prefix "inet"; }

  import Cisco-IOS-XR-types { prefix "xr"; }

  import Cisco-IOS-XR-ipv4-autorp-datatypes { prefix "dt1"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ipv4-pim package configuration.

     This module contains definitions
     for the following management objects:
       pim: PIM configuration

     Copyright (c) 2013-2016 by Cisco Systems, Inc.
     All rights reserved.";

  revision "2016-06-01" {
    description
      "Migrated multipath and ssm commands to PIM";
  }

  revision "2015-11-09" {
    description
      "IOS XR 6.0 revision.";
  }

  typedef Auto-rp-announce-period {
    type uint32 {
      range "1..600";
    }
    description "Auto rp announce period";
  }
  typedef Pim-multipath {
    type enumeration {
      enum enable {
        value 0;
        description "Enable PIM multipath";
      }
      enum interface-hash {
        value 1;
        description
          "Enable PIM multipath with interface based
          hashing";
      }
      enum source-hash {
        value 2;
        description
          "Enable PIM multipath with source based hashing";
      }
      enum source-next-hop-hash {
        value 3;
        description
          "Enable PIM multipath with source next-hop
          hashing";
      }
      enum source-group-hash {
        value 4;
        description
          "Enable PIM multipath with source, group based
          hashing";
      }
    }
    description "Pim multipath";
  }
  typedef Protocol-mode {
    type uint32 {
      range "0..1";
    }
    description "Protocol mode";
  }
  typedef Auto-rp-ttl {
    type uint32 {
      range "1..255";
    }
    description "Auto rp ttl";
  }
  typedef Priority {
    type uint32 {
      range "1..255";
    }
    description "Priority";
  }

  grouping SUPPRESS-DATA-REGISTERS {
    description "Common node of ipv4, ipv6";
    leaf suppress-data-registers {
      type empty;
      description
        "Suppress data registers after initial state
        setup";
    }
  }

  grouping ROUTE-POLICY {
    description "Common node of rpf, rpf-redirect";
    leaf route-policy {
      type string;
      description "Route policy to select RPF topology";
    }
  }

  grouping JOIN-PRUNE-MTU {
    description "Common node of inheritable-defaults, interface";
    leaf join-prune-mtu {
      type uint32 {
        range "576..65535";
      }
      units "byte";
      description "Join-Prune MTU in Bytes";
    }
  }

  grouping NEIGHBOR-CHECK-ON-RECEIVE {
    description "Common node of ipv4, ipv6";
    leaf neighbor-check-on-receive {
      type empty;
      description
        "Enable PIM neighbor checking when receiving PIM
        messages";
    }
  }

  grouping RPF {
    description "Common node of ipv4, ipv6";

    container rpf {
      description "Configure RPF options";
      uses ROUTE-POLICY;
    }
  }

  grouping NEIGHBOR-CHECK-ON-SEND {
    description "Common node of ipv4, ipv6";
    leaf neighbor-check-on-send {
      type empty;
      description
        "Enable PIM neighbor checking when sending
        join-prunes";
    }
  }

  grouping BSR {
    description "Common node of ipv4, ipv6";

    container bsr {
      description "PIM BSR configuration";

      container candidate-rps {
        description "PIM RP configuration";

        list candidate-rp {
          key "address";
          description "BSR Candidate RP Configuration";

          grouping PARAMS {
            description
              "Parameters of BSR Candidate RP Configuration";
            leaf access-list-name {
              type string;
              description
                "Access-list specifying the group range for
                the Candidate-RP";
            }
            leaf priority {
              type Priority;
              default "192";
              description "Priority of the CRP";
            }
            leaf protocol-mode {
              type Protocol-mode;
              description "CRP Mode";
            }
            leaf interval {
              type uint32 {
                range "30..600";
              }
              default "60";
              description "Advertisement interval";
            }
          }

          container sm {
            must "protocol-mode = 0" {
              description "Must specify SM";
            }
            description "Parameters of PIM SM BSR Candidate-RP";
            uses PARAMS;
          }

          container bidir {
            must "protocol-mode = 1" {
              description "Must specify Bidir";
            }
            description "Parameters of PIM Bidir BSR Candidate-RP";
            uses PARAMS;
          }
          leaf address {
            type inet:ip-address-no-zone;
            description "Address of Candidate-RP";
          }
        }
      }

      container candidate-bsr {
        presence "Indicates a candidate-bsr node is configured.";
        description "PIM Candidate BSR configuration";
        leaf address {
          type inet:ip-address-no-zone;
          mandatory true;
          description "BSR Address configured";
        }
        leaf prefix-length {
          type int32;
          default "30";
          description "Hash Mask Length for this candidate BSR";
        }
        leaf priority {
          type Priority;
          default "1";
          description "Priority of the Candidate BSR";
        }
      }
    }
  }

  grouping SPARSE-MODE-RP-ADDRESS-TABLE {
    description "Common node of ipv4, ipv6";

    container sparse-mode-rp-addresses {
      description "Configure Sparse-Mode Rendezvous Point";

      list sparse-mode-rp-address {
        key "rp-address";
        description "Address of the Rendezvous Point";
        leaf rp-address {
          type inet:ip-address-no-zone;
          description "RP address of Rendezvous Point";
        }
        leaf access-list-name {
          type string;
          description
            "Access list of groups that should map to a 
            given RP";
        }
        leaf auto-rp-override {
          type boolean;
          description
            "TRUE Indicates if static RP config overrides
            AutoRP and BSR";
        }
      }
    }
  }

  grouping INHERITABLE-DEFAULTS {
    description "Common node of ipv4, ipv6";

    container inheritable-defaults {
      description "Inheritable defaults";
      leaf convergency {
        type uint32 {
          range "1800..2400";
        }
        units "second";
        description "Convergency timeout in seconds";
      }
      uses HELLO-INTERVAL;
      uses PROPAGATION-DELAY;
      uses DR-PRIORITY;
      uses JOIN-PRUNE-MTU;
      uses JP-INTERVAL;
      uses OVERRIDE-INTERVAL;
    }
  }

  grouping RP-STATIC-DENY {
    description "Common node of ipv4, ipv6";
    leaf rp-static-deny {
      type string;
      description "Configure static RP deny range";
    }
  }

  grouping SSM {
    description "Common node of ipv4, ipv6";

    container ssm {
      description "Configure IP Multicast SSM";
      leaf disable {
        type boolean;
        default "false";
        description "TRUE if SSM is disabled on this router";
      }
      leaf range {
        type string;
        description "Access list of groups enabled with SSM";
      }
    }
  }

  grouping OVERRIDE-INTERVAL {
    description "Common node of inheritable-defaults, interface";
    leaf override-interval {
      type uint32 {
        range "400..65535";
      }
      units "millisecond";
      description "Override interval in milliseconds";
    }
  }

  grouping CONVERGENCE {
    description "Common node of ipv4, ipv6";

    container convergence {
      description "Configure convergence parameters";
      leaf rpf-conflict-join-delay {
        type uint32 {
          range "0..15";
        }
        units "second";
        description
          "Dampen first join if RPF path is through one of
          the downstream neighbor";
      }
      leaf link-down-prune-delay {
        type uint32 {
          range "0..60";
        }
        units "second";
        description
          "Delay prunes if route join state transitions to
          not-joined on link down";
      }
    }
  }

  grouping REGISTER-SOURCE {
    description "Common node of ipv4, ipv6";
    leaf register-source {
      type xr:Interface-name;
      description "Source address to use for register messages";
    }
  }

  grouping PROPAGATION-DELAY {
    description "Common node of inheritable-defaults, interface";
    leaf propagation-delay {
      type uint32 {
        range "100..32767";
      }
      units "millisecond";
      description "Propagation delay in milli seconds";
    }
  }

  grouping SPT-THRESHOLD-INFINITY {
    description "Common node of ipv4, ipv6";
    leaf spt-threshold-infinity {
      type string;
      description
        "Configure threshold of infinity for switching to
        SPT on last-hop";
    }
  }

  grouping NEIGHBOR-FILTER {
    description "Common node of ipv4, ipv6";
    leaf neighbor-filter {
      type string;
      description "Access-list of neighbors to be filtered";
    }
  }

  grouping SSM-ALLOW-OVERRIDE {
    description "Common node of ipv4, ipv6";
    leaf ssm-allow-override {
      type empty;
      description
        "Allow SSM ranges to be overridden by more
        specific ranges";
    }
  }

  grouping IPV4 {
    description "Common node of vrf, default-context";

    container ipv4 {
      description "IPV4 commands";

      container cs-multicast-only-frrs {
        description "Clone Source Multicast Only FRR";

        list cs-multicast-only-frr {
          key "source primary backup prefix-length";
          description "Clone Source Multicast Only FRR";
          leaf source {
            type inet:ip-address-no-zone;
            description "Original address";
          }
          leaf primary {
            type inet:ip-address-no-zone;
            description "Primary address";
          }
          leaf backup {
            type inet:ip-address-no-zone;
            description "Backup address";
          }
          leaf prefix-length {
            type int32;
            description "Masklen";
          }
        }
      }

      container multicast-only-frr {
        description "Multicast Only FRR";
        leaf non-revertive-multicast-only-frr {
          type empty;
          description "Non-revertive Multicast Only FRR";
        }
        leaf flow-multicast-only-frr {
          type string;
          description
            "Access-list specifying SG that should do FLOW
            MOFRR";
        }
        leaf enable {
          type empty;
          description "Enable Multicast Only FRR";
        }
        leaf rib-multicast-only-frr {
          type string;
          description
            "Access-list specifying SG that should do RIB
            MOFRR";
        }
      }

      container rpf-redirect {
        description "Configure RPF-redirect feature";
        uses ROUTE-POLICY;
      }

      container paths {
        description "Inject PIM RPF Vector Proxy's";

        list path {
          key "source-address prefix-length";
          description "Inject PIM RPF Vector Proxy's";
          leaf source-address {
            type inet:ip-address-no-zone;
            description "Source Address";
          }
          leaf prefix-length {
            type int32;
            description "Masklen";
          }
          leaf-list rpf-proxy-address {
            type inet:ipv4-address-no-zone;
            min-elements "1";
            max-elements "22";
            description "RPF Proxy Address";
          }
        }
      }

      container cj-multicast-only-frrs {
        description "Clone Join Multicast Only FRR";

        list cj-multicast-only-frr {
          key "source primary backup prefix-length";
          description "Clone Join Multicast Only FRR";
          leaf source {
            type inet:ip-address-no-zone;
            description "Original address";
          }
          leaf primary {
            type inet:ip-address-no-zone;
            description "Primary address";
          }
          leaf backup {
            type inet:ip-address-no-zone;
            description "Backup address";
          }
          leaf prefix-length {
            type int32;
            description "Masklen";
          }
        }
      }

      container auto-rp {
        description "PIM AutoRP configuration";
      }

      container auto-rp-mapping-agent {
        description "Configure AutoRP Mapping Agent";

        container parameters {
          presence "Indicates a parameters node is configured.";
          description
            "Specifications for Mapping Agent configured on
            this box";
          leaf interface-name {
            type xr:Interface-name;
            mandatory true;
            description
              "Interface from which mapping packets will be
              sourced ";
          }
          leaf ttl {
            type Auto-rp-ttl;
            mandatory true;
            description "TTL in Hops";
          }
          leaf announce-period {
            type Auto-rp-announce-period;
            units "second";
            default "60";
            description
              "Time between discovery messages <in seconds>";
          }
        }

        container cache-limit {
          presence "Indicates a cache-limit node is configured.";
          description "Mapping Agent cache size limit";
          leaf maximum-cache-entry {
            type uint32 {
              range "1..1000";
            }
            mandatory true;
            description "Maximum number of mapping cache entries";
          }
          leaf threshold-cache-entry {
            type uint32 {
              range "1..1000";
            }
            default "450";
            description "Warning threshold number of cache entries";
          }
        }
      }

      container candidate-rps {
        description "Configure Candidate-RPs";

        list candidate-rp {
          key "interface-name protocol-mode";
          description "Specifications for a Candidate-RP";

          container candidate-rp-range {
            presence "Indicates a candidate-rp-range node is"+
              " configured.";
            description
              "Configure the group range for the
              Candidate-RP";
            leaf ttl {
              type Auto-rp-ttl;
              mandatory true;
              description "TTL in Hops";
            }
            leaf access-list-name {
              type string;
              default "224-4";
              description
                "Access-list specifying the group range for
                the Candidate-RP";
            }
            leaf announce-period {
              type Auto-rp-announce-period;
              units "second";
              default "60";
              description
                "Time between announcements <in seconds> ";
            }
          }
          leaf interface-name {
            type xr:Interface-name;
            description
              "Interface from which Candidate-RP packets
              will be sourced";
          }
          leaf protocol-mode {
            type dt1:Auto-rp-protocol-mode;
            description "Protocol Mode";
          }
        }
      }

      container injects {
        description "Inject Explicit PIM RPF Vector Proxy's";

        list inject {
          key "source-address prefix-length";
          description "Inject Explicit PIM RPF Vector Proxy's";
          leaf source-address {
            type inet:ip-address-no-zone;
            description "Source Address";
          }
          leaf prefix-length {
            type int32;
            description "Masklen";
          }
          leaf-list rpf-proxy-address {
            type inet:ipv4-address-no-zone;
            min-elements "1";
            max-elements "22";
            description "RPF Proxy Address";
          }
        }
      }
      leaf auto-rp-disable {
        type empty;
        description
          "Disable Rendezvous Point discovery through the
          AutoRP protocol";
      }
      uses NEIGHBOR-CHECK-ON-RECEIVE;
      uses OLD-REGISTER-CHECKSUM;
      uses SPARSE-MODE-RP-ADDRESS-TABLE;
      uses NEIGHBOR-FILTER;
      uses INHERITABLE-DEFAULTS;
      uses SPT-THRESHOLD-INFINITY;
      uses LOG-NEIGHBOR-CHANGES;
      uses RPF;
      uses REGISTER-SOURCE;
      uses ACCEPT-REGISTER;
      uses SG-EXPIRY-TIMER;
      uses RPF-VECTOR-ENABLE;
      uses NSF;
      uses SUPPRESS-RPF-PRUNES;
      uses MAXIMUM;
      uses SSM;
      uses ASSERT-DISABLE;
      uses BIDIR-RP-ADDRESS-TABLE;
      uses SSM-ALLOW-OVERRIDE;
      uses BSR;
      uses MULTIPATH;
      uses INTERFACE-TABLE;
      uses RP-STATIC-DENY;
      uses ALLOW-RP;
      uses SUPPRESS-DATA-REGISTERS;
      uses NEIGHBOR-CHECK-ON-SEND;
      uses CONVERGENCE;
    }
  }

  grouping IPV6 {
    description "Common node of vrf, default-context";

    container ipv6 {
      description "IPV6 commands";

      container embedded-rp-addresses {
        description "Set Embedded RP processing support";

        list embedded-rp-address {
          key "rp-address";
          description "Set Embedded RP processing support";
          leaf rp-address {
            type inet:ip-address-no-zone;
            description "RP address of the Rendezvous Point";
          }
          leaf access-list-name {
            type string;
            mandatory true;
            description
              "Access list of groups that should map to a
              given RP";
          }
        }
      }
      leaf embedded-rp-disable {
        type empty;
        description "Set Embedded RP processing support";
      }
      uses NEIGHBOR-CHECK-ON-RECEIVE;
      uses OLD-REGISTER-CHECKSUM;
      uses SPARSE-MODE-RP-ADDRESS-TABLE;
      uses NEIGHBOR-FILTER;
      uses INHERITABLE-DEFAULTS;
      uses SPT-THRESHOLD-INFINITY;
      uses LOG-NEIGHBOR-CHANGES;
      uses RPF;
      uses REGISTER-SOURCE;
      uses ACCEPT-REGISTER;
      uses SG-EXPIRY-TIMER;
      uses RPF-VECTOR-ENABLE;
      uses NSF;
      uses SUPPRESS-RPF-PRUNES;
      uses MAXIMUM;
      uses SSM;
      uses ASSERT-DISABLE;
      uses BIDIR-RP-ADDRESS-TABLE;
      uses SSM-ALLOW-OVERRIDE;
      uses BSR;
      uses MULTIPATH;
      uses INTERFACE-TABLE;
      uses RP-STATIC-DENY;
      uses ALLOW-RP;
      uses SUPPRESS-DATA-REGISTERS;
      uses NEIGHBOR-CHECK-ON-SEND;
      uses CONVERGENCE;
    }
  }

  grouping LOG-NEIGHBOR-CHANGES {
    description "Common node of ipv4, ipv6";
    leaf log-neighbor-changes {
      type empty;
      description
        "PIM neighbor state change logging is turned on
        if configured";
    }
  }

  grouping MAXIMUM {
    description "Common node of ipv4, ipv6";

    container maximum {
      description "Configure PIM State Limits";

      container group-mappings-auto-rp {
        description
          "Override default maximum for number of group
          mappings from autorp mapping agent";
        leaf maximum-group-ranges-auto-rp {
          type uint32 {
            range "1..10000";
          }
          default "500";
          description
            "Maximum number of PIM group mappings from
            autorp";
        }
        leaf threshold-group-ranges-auto-rp {
          type uint32 {
            range "1..10000";
          }
          default "450";
          description
            "Warning threshold number of PIM group mappings
            from autorp";
        }
      }

      container bsr-global-group-mappings {
        presence "Indicates a bsr-global-group-mappings node is"+
          " configured.";
        description
          "Override default global maximum and threshold
          for PIM group mapping ranges from BSR";
        leaf bsr-maximum-global-group-mappings {
          type uint32 {
            range "1..10000";
          }
          mandatory true;
          description
            "Global Maximum number of PIM group mapping
            ranges from BSR";
        }
        leaf warning-threshold {
          type uint32 {
            range "1..10000";
          }
          default "500";
          description "Set threshold to print warning";
        }
      }

      container global-routes {
        description "Override default maximum for number of routes";
        leaf maximum-routes {
          type uint32 {
            range "1..200000";
          }
          default "100000";
          description "Maximum number of PIM routes";
        }
        leaf warning-threshold {
          type uint32 {
            range "1..200000";
          }
          default "100000";
          description "Set threshold to print warning";
        }
      }

      container bsr-group-mappings {
        description
          "Override default maximum and threshold for
          number of group mappings from BSR";
        leaf bsr-maximum-group-ranges {
          type uint32 {
            range "1..10000";
          }
          default "500";
          description
            "Maximum number of PIM group mappings from BSR";
        }
        leaf warning-threshold {
          type uint32 {
            range "1..10000";
          }
          default "500";
          description "Set threshold to print warning";
        }
      }

      container global-group-mappings-auto-rp {
        description
          "Maximum for number of group mappings from
          autorp mapping agent";
        leaf maximum-global-group-ranges-auto-rp {
          type uint32 {
            range "1..10000";
          }
          default "500";
          description
            "Maximum number of PIM group mappings from
            autorp";
        }
        leaf threshold-global-group-ranges-auto-rp {
          type uint32 {
            range "1..10000";
          }
          default "450";
          description
            "Warning threshold number of PIM group mappings
            from autorp";
        }
      }

      container register-states {
        description
          "Override default maximum for number of
          sparse-mode source registers";
        leaf maximum-register-states {
          type uint32 {
            range "0..75000";
          }
          default "20000";
          description
            "Maximum number of PIM Sparse-Mode register
            states";
        }
        leaf warning-threshold {
          type uint32 {
            range "0..75000";
          }
          default "20000";
          description "Set threshold to print warning";
        }
      }

      container route-interfaces {
        description
          "Override default maximum for number of
          route-interfaces";
        leaf maximum-route-interfaces {
          type uint32 {
            range "1..1100000";
          }
          default "300000";
          description "Maximum number of PIM route-interfaces";
        }
        leaf warning-threshold {
          type uint32 {
            range "1..1100000";
          }
          default "300000";
          description "Set threshold to print warning";
        }
      }

      container bsr-global-candidate-rp-cache {
        presence "Indicates a bsr-global-candidate-rp-cache node is"+
          " configured.";
        description
          "Override default global maximum and threshold
          for C-RP set in BSR";
        leaf bsr-maximum-global-candidate-rp-cache {
          type uint32 {
            range "1..10000";
          }
          mandatory true;
          description
            "Global Maximum number of PIM C-RP Sets from
            BSR";
        }
        leaf warning-threshold {
          type uint32 {
            range "1..10000";
          }
          default "100";
          description "Set threshold to print warning";
        }
      }

      container bsr-candidate-rp-cache {
        description
          "Override default maximum and threshold for BSR
          C-RP cache setting";
        leaf bsr-maximum-candidate-rp-cache {
          type uint32 {
            range "1..10000";
          }
          default "100";
          description "Maximum number of BSR C-RP cache setting";
        }
        leaf warning-threshold {
          type uint32 {
            range "1..10000";
          }
          default "100";
          description "Set threshold to print warning";
        }
      }

      container global-register-states {
        description
          "Override default maximum for number of
          sparse-mode source registers";
        leaf maximum-register-states {
          type uint32 {
            range "0..75000";
          }
          default "20000";
          description
            "Maximum number of PIM Sparse-Mode register
            states";
        }
        leaf warning-threshold {
          type uint32 {
            range "0..75000";
          }
          default "20000";
          description "Set threshold to print warning";
        }
      }

      container global-route-interfaces {
        description
          "Override default maximum for number of
          route-interfaces";
        leaf maximum-route-interfaces {
          type uint32 {
            range "1..1100000";
          }
          default "300000";
          description "Maximum number of PIM route-interfaces";
        }
        leaf warning-threshold {
          type uint32 {
            range "1..1100000";
          }
          default "300000";
          description "Set threshold to print warning";
        }
      }

      container routes {
        description "Override default maximum for number of routes";
        leaf maximum-routes {
          type uint32 {
            range "1..200000";
          }
          default "100000";
          description "Maximum number of PIM routes";
        }
        leaf warning-threshold {
          type uint32 {
            range "1..200000";
          }
          default "100000";
          description "Set threshold to print warning";
        }
      }
      leaf gloabal-high-priority-packet-queue {
        type uint32 {
          range "0..2147483648";
        }
        units "byte";
        description "Maximum packet queue size in bytes";
      }
      leaf gloabal-low-priority-packet-queue {
        type uint32 {
          range "0..2147483648";
        }
        units "byte";
        description "Maximum packet queue size in bytes";
      }
    }
  }

  grouping SG-EXPIRY-TIMER {
    description "Common node of ipv4, ipv6";

    container sg-expiry-timer {
      description "Configure expiry timer for S,G routes";
      leaf interval {
        type uint32 {
          range "40..57600";
        }
        units "second";
        description "(S,G) expiry time in seconds";
      }
      leaf access-list-name {
        type string;
        description "Access-list of applicable S,G routes";
      }
    }
  }

  grouping INTERFACE-TABLE {
    description "Common node of ipv4, ipv6";

    container interfaces {
      description "Interface-level Configuration";

      list interface {
        key "interface-name";
        description "The name of the interface";

        container redirect-bundle {
          presence "Indicates a redirect-bundle node is configured.";
          description
            "Configure RPF-redirect bundle for interface.
            Applicable for IPv4 only";
          leaf bundle-name {
            type string;
            mandatory true;
            description "Bundle name";
          }
          leaf interface-bandwidth {
            type uint32 {
              range "0..100000000";
            }
            units "kbit/s";
            description "Interface bandwidth in Kbps";
          }
          leaf threshold-bandwidth {
            type uint32 {
              range "0..100000000";
            }
            units "kbit/s";
            description "Threshold bandwidth in Kbps";
          }
        }

        container bfd {
          description "BFD configuration";
          leaf detection-multiplier {
            type uint32 {
              range "2..50";
            }
            description
              "Detection multiplier for BFD sessions created
              by PIM";
          }
          leaf interval {
            type uint32 {
              range "3..30000";
            }
            units "millisecond";
            description
              "Hello interval for BFD sessions created by
              PIM";
          }
          leaf enable {
            type boolean;
            description
              "TRUE to enable BFD. FALSE to disable and to
              prevent inheritance from a parent";
          }
        }

        container oor {
          description "Enable maximum routes per Interface";
          leaf maximum {
            type uint32 {
              range "1..1100000";
            }
            description "Maximum number of Routes per interface";
          }
          leaf warning-threshold {
            type uint32 {
              range "1..1100000";
            }
            description "Set threshold to print warning";
          }
          leaf access-list-name {
            type xr:Cisco-ios-xr-string {
              length "0..64";
            }
            description "Access-list to account for";
          }
        }
        leaf neighbor-filter {
          type string;
          description "Access-list of neighbors to be filtered";
        }
        leaf bsr-border {
          type boolean;
          description "BSR Border configuration for Interface";
        }
        leaf enable {
          type empty;
          description "Enter PIM Interface processing";
        }
        leaf interface-enable {
          type boolean;
          description "Enable PIM processing on the interface";
        }
        leaf interface-name {
          type xr:Interface-name;
          description "The name of interface";
        }
        uses HELLO-INTERVAL;
        uses PROPAGATION-DELAY;
        uses DR-PRIORITY;
        uses JOIN-PRUNE-MTU;
        uses JP-INTERVAL;
        uses OVERRIDE-INTERVAL;
      }
    }
  }

  grouping MULTIPATH {
    description "Common node of ipv4, ipv6";
    leaf multipath {
      type Pim-multipath;
      description "Enable equal-cost multipath routing";
    }
  }

  grouping HELLO-INTERVAL {
    description "Common node of inheritable-defaults, interface";
    leaf hello-interval {
      type uint32 {
        range "1..3600";
      }
      units "second";
      description "Hello interval in seconds";
    }
  }

  grouping BIDIR-RP-ADDRESS-TABLE {
    description "Common node of ipv4, ipv6";

    container bidir-rp-addresses {
      description "Configure Bidirectional PIM Rendezvous Point";

      list bidir-rp-address {
        key "rp-address";
        description "Address of the Rendezvous Point";
        leaf rp-address {
          type inet:ip-address-no-zone;
          description "RP address of Rendezvous Point";
        }
        leaf access-list-name {
          type string;
          description
            "Access list of groups that should map to a
            given RP";
        }
        leaf auto-rp-override {
          type boolean;
          description
            "TRUE Indicates if static RP config overrides
            AutoRP and BSR";
        }
      }
    }
  }

  grouping JP-INTERVAL {
    description "Common node of inheritable-defaults, interface";
    leaf jp-interval {
      type uint32 {
        range "10..600";
      }
      units "second";
      description "Join-Prune interval in seconds";
    }
  }

  grouping NSF {
    description "Common node of ipv4, ipv6";

    container nsf {
      description "Configure Non-stop forwarding (NSF) options";
      leaf lifetime {
        type uint32 {
          range "10..600";
        }
        units "second";
        description
          "Override default maximum lifetime for PIM NSF
          mode";
      }
    }
  }

  grouping ASSERT-DISABLE {
    description "Common node of ipv4, ipv6";
    leaf assert-disable {
      type empty;
      description "Configuring batch asserts disable";
    }
  }

  grouping DR-PRIORITY {
    description "Common node of inheritable-defaults, interface";
    leaf dr-priority {
      type uint32 {
        range "0..4294967295";
      }
      description
        "Hello DR priority, preference given to larger
        value";
    }
  }

  grouping ACCEPT-REGISTER {
    description "Common node of ipv4, ipv6";
    leaf accept-register {
      type string;
      description
        "Access-list which specifies unauthorized sources";
    }
  }

  grouping OLD-REGISTER-CHECKSUM {
    description "Common node of ipv4, ipv6";
    leaf old-register-checksum {
      type empty;
      description
        "Generate registers compatible with older IOS
        versions";
    }
  }

  grouping ALLOW-RP {
    description "Common node of ipv4, ipv6";

    container allow-rp {
      presence "enable allow-rp";
      description "Enable allow-rp filtering for SM joins";
      leaf rp-list-name {
        type string;
        description "Access-list specifiying applicable RPs";
      }
      leaf group-list-name {
        type string;
        description "Access-list specifiying applicable groups";
      }
    }
  }

  grouping SUPPRESS-RPF-PRUNES {
    description "Common node of ipv4, ipv6";
    leaf suppress-rpf-prunes {
      type empty;
      description
        "Suppress prunes triggered as a result of RPF
        changes";
    }
  }

  grouping RPF-VECTOR-ENABLE {
    description "Common node of ipv4, ipv6";

    container rpf-vector-enable {
      presence "Indicates a rpf-vector-enable node is configured.";
      description "Enable PIM RPF Vector Proxy's";
      leaf enable {
        type empty;
        mandatory true;
        description "RPF Vector is turned on if configured";
      }
      leaf allow-ebgp {
        type boolean;
        description
          "Allow RPF Vector origination over eBGP sessions";
      }
      leaf disable-ibgp {
        type boolean;
        description
          "Disable RPF Vector origination over iBGP
          sessions";
      }
    }
  }

  container pim {
    presence "Indicates a pim node is configured.";
    description "PIM configuration";

    container vrfs {
      description "VRF table";

      list vrf {
        key "vrf-name";
        description "VRF name";
        leaf vrf-name {
          type xr:Cisco-ios-xr-string;
          description "VRF name";
        }
        uses IPV6;
        uses IPV4;
      }
    }

    container default-context {
      presence "Indicates a default-context node is configured.";
      description "Default Context";
      uses IPV6;
      uses IPV4;
    }
  }
}
