module Cisco-IOS-XR-fretta-bcm-dpa-resources-oper {

  /*** NAMESPACE / PREFIX DEFINITION ***/

  namespace "http://cisco.com/ns/yang"+
    "/Cisco-IOS-XR-fretta-bcm-dpa-resources-oper";


  prefix "fretta-bcm-dpa-resources-oper";

  /*** LINKAGE (IMPORTS / INCLUDES) ***/

  import Cisco-IOS-XR-types { prefix "xr"; }

  include Cisco-IOS-XR-fretta-bcm-dpa-resources-oper-sub2 {
    revision-date 2015-11-09;
  }

  include Cisco-IOS-XR-fretta-bcm-dpa-resources-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR fretta-bcm-dpa-resources package operational data.

     This module contains definitions
     for the following management objects:
       dpa: DPA operational data

     Copyright (c) 2013-2016 by Cisco Systems, Inc.
     All rights reserved.";

  revision "2015-11-09" {
    description
      "IOS XR 6.0 revision.";
  }

  typedef Max-trap-s {
    type uint32 {
      range "0..4294967295";
    }
    description "Max trap s";
  }
  typedef Max-lc-intf-hand-les {
    type uint32 {
      range "0..4294967295";
    }
    description "Max lc intf hand les";
  }
  typedef Max-re-source-s-table {
    type uint32 {
      range "0..85";
    }
    description "Max re source s table";
  }

  container dpa {
    config false;
    description "DPA operational data";

    container resources {
      description "DPA Resources Data";

      container nodes {
        description "DPA data for available nodes";

        list node {
          key "node-name";
          description "DPA operational data for a particular node";

          container table-datas {
            description "DPA Resources table";

            list table-data {
              key "resource";
              description "Resources table";
              leaf resource {
                type Max-re-source-s-table;
                description "Resource type";
              }
              uses DPA-SYSDB-TABLE-RESOURCE;
            }
          }
          leaf node-name {
            type xr:Node-id;
            description "Node ID";
          }
        }
      }
    }

    container stats {
      description "DPA voq data";

      container nodes {
        description "DPA data for available nodes";

        list node {
          key "node-name";
          description "DPA operational data for a particular node";

          container voq-base-number-stats-clears {
            description "Clear DPA voq base stats ";

            list voq-base-number-stats-clear {
              key "npu-number";
              description "Filter by npu number";
              leaf npu-number {
                type int32;
                description "Npu Number";
              }

              list voq-base-stats-clear-data {
                key "base-number";
                description
                  "Clear stats  for a particular voq base
                  number";
                leaf base-number {
                  type Max-lc-intf-hand-les;
                  description "Interface handle";
                }
                uses CLEAR-STATS;
              }
            }
          }

          container npu-number-for-trap-datas {
            description "Trap stats for all traps";

            list npu-number-for-trap-data {
              key "npu-id";
              description "All trap stats for a particular npu";
              leaf npu-id {
                type int32;
                description "NPU number";
              }

              list trap-specific-stats-data {
                key "trap-data";
                description "Filter by specific trap id";
                leaf trap-data {
                  type Max-trap-s;
                  description "Trap Number";
                }
                uses DPA-TRAP-STATS;
              }
            }
          }

          container voq-base-numbers {
            description "DPA voq base stats ";

            list voq-base-number {
              key "npu-number";
              description "Filter by npu number";
              leaf npu-number {
                type int32;
                description "Npu Number";
              }

              list voq-base-stats-data {
                key "base-number";
                description "Voq Base Number for a particular voq";
                leaf base-number {
                  type Max-lc-intf-hand-les;
                  description "Interface handle";
                }
                uses DPA-VOQ-INTF-PORT;
              }
            }
          }

          container npu-number-for-voq-datas {
            description "DPA voq ingress stats for all interfaces";

            list npu-number-for-voq-data {
              key "npu-id";
              description "All voq stats for a particular npu";
              leaf npu-id {
                type int32;
                description "Npu number";
              }

              list voq-specific-stats-data {
                key "voq-data";
                description "Filter data by interface handle";
                leaf voq-data {
                  type int32;
                  description "Interface Handle";
                }
                uses DPA-VOQ-INTF-PORT;
              }
            }
          }

          container clear-voq-data-for-npu-numbers {
            description
              "Clear voq ingress stats for all interfaces on
              particular npu";

            list clear-voq-data-for-npu-number {
              key "npu-id";
              description "Npu id on which stats will be cleared";
              leaf npu-id {
                type int32;
                description "Npu number";
              }

              list voq-specific-stats-data-clear {
                key "voq-data";
                description "Filter data by interface handle";
                leaf voq-data {
                  type int32;
                  description "Interface Handle";
                }
                uses CLEAR-STATS;
              }
            }
          }

          container npu-number-for-trap-data-clears {
            description "Trap stats for all traps";

            list npu-number-for-trap-data-clear {
              key "npu-id";
              description "All trap stats for a particular npu";
              leaf npu-id {
                type int32;
                description "NPU number";
              }

              list trap-specific-stats-data {
                key "trap-data";
                description "Filter by specific trap id";
                leaf trap-data {
                  type Max-trap-s;
                  description "Trap Number";
                }
                uses CLEAR-STATS;
              }
            }
          }
          leaf node-name {
            type xr:Node-id;
            description "Node ID";
          }
        }
      }
    }
  }
}
