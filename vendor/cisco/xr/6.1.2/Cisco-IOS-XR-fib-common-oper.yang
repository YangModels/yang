module Cisco-IOS-XR-fib-common-oper {

  /*** NAMESPACE / PREFIX DEFINITION ***/

  namespace "http://cisco.com/ns/yang/Cisco-IOS-XR-fib-common-oper";


  prefix "fib-common-oper";

  /*** LINKAGE (IMPORTS / INCLUDES) ***/

  import ietf-inet-types { prefix "inet"; }

  import Cisco-IOS-XR-types { prefix "xr"; }

  include Cisco-IOS-XR-fib-common-oper-sub4 {
    revision-date 2015-11-09;
  }

  include Cisco-IOS-XR-fib-common-oper-sub3 {
    revision-date 2015-11-09;
  }

  include Cisco-IOS-XR-fib-common-oper-sub2 {
    revision-date 2015-11-09;
  }

  include Cisco-IOS-XR-fib-common-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR fib-common package operational data.

     This module contains definitions
     for the following management objects:
       fib-statistics: cef interface drops operational data
       fib: fib
       mpls-forwarding: mpls forwarding
       fib-mpls: fib mpls

     Copyright (c) 2013-2016 by Cisco Systems, Inc.
     All rights reserved.";

  revision "2015-11-09" {
    description
      "IOS XR 6.0 revision.";
  }

  typedef Fib-route-source {
    type enumeration {
      enum lsd {
        value 5;
        description "LSD";
      }
      enum rib {
        value 7;
        description "RIB";
      }
      enum mrib {
        value 13;
        description "MRIB";
      }
    }
    description "Fib route source";
  }
  typedef Fib-protocol {
    type enumeration {
      enum ipv4 {
        value 0;
        description "ipv4 protocol";
      }
      enum ipv6 {
        value 1;
        description "ipv6 protocol";
      }
      enum mpls {
        value 2;
        description "MPLS protocol";
      }
    }
    description "Fib protocol";
  }
  typedef Eos {
    type enumeration {
      enum eos0 {
        value 0;
        description "EOS Disable";
      }
      enum eos1 {
        value 1;
        description "EOS Enable";
      }
    }
    description "Eos";
  }
  typedef Fib-label {
    type uint32 {
      range "16..1048575";
    }
    description "Fib label";
  }
  typedef Fibllc-entry {
    type enumeration {
      enum xc {
        value 1;
        description "LabelXconnect";
      }
      enum pfx {
        value 2;
        description "IPPrefix";
      }
    }
    description "Fibllc entry";
  }
  typedef Fib-link {
    type enumeration {
      enum link-ipv4 {
        value 0;
        description "IPv4 link protocol";
      }
      enum link-ipv6 {
        value 1;
        description "IPv6 link protocol";
      }
      enum link-mpls {
        value 2;
        description "MPLS link protocol";
      }
    }
    description "Fib link";
  }
  typedef Mplseos {
    type enumeration {
      enum eos0 {
        value 0;
        description "EOS Disable";
      }
      enum eos1 {
        value 1;
        description "EOS Enable";
      }
    }
    description "Mplseos";
  }

  container fib-statistics {
    config false;
    description "cef interface drops operational data";

    container nodes {
      description "List of nodes";

      list node {
        key "node-name";
        description "Specific node operational data";

        container drops {
          description "Specific node drops";
          uses FIB-STATISTICS-BAG-DROPS;
        }
        leaf node-name {
          type xr:Node-id;
          description "Node name";
        }
      }
    }
  }

  container fib {
    config false;
    description "fib";

    container nodes {
      description "Table of nodes";

      list node {
        key "node-name";
        description "Operational data for a specific Node";

        container protocols {
          description "Protocol table";

          list protocol {
            key "protocol-name";
            description "Protocol table entry";

            container issu-state {
              description "CEF ISSU State";
              uses FIB-ISSU-STATE;
            }

            container summaries {
              description "Summary for FIB tables";

              list summary {
                description "Summary for the requested fib table";
                leaf protocol-name {
                  type Fib-protocol;
                  description "Protocol Name ";
                }
                leaf vrf-name {
                  type xr:Cisco-ios-xr-string;
                  description "VRF Name";
                }
                leaf table-id {
                  type int32;
                  description "FIB table id";
                }
                uses FIB-SH-SUM;
              }
            }

            container external-summary-all {
              description "Summary for all external clients";
              uses FIB-SH-TBL-EXT-SUM-ALL;
            }

            container frr-log {
              description "Table of Fast Reroute activation logs";

              container frr-interfaces {
                description "FRR Interface Table";

                list frr-interface {
                  key "frr-interface-name";
                  description "Specify FRR Interface Name";

                  container logs {
                    description "FRR log table";

                    list log {
                      key "log-index";
                      description
                        "Specify index into frr log table";
                      leaf log-index {
                        type int32;
                        description "FRR Log Index";
                      }
                      uses FIB-SH-FRR-LOG;
                    }
                  }
                  leaf frr-interface-name {
                    type xr:Interface-name;
                    description "Interface Name";
                  }
                }
              }
            }

            container vrfs {
              description "VRF table";

              list vrf {
                key "vrf-name";
                description "VRF table entry";

                container ip-prefix-details {
                  description "IP FIB prefix detail table";

                  list ip-prefix-detail {
                    description "IP FIB prefix detail table entry";
                    leaf prefix {
                      type inet:ip-address-no-zone;
                      description "Destination IP address";
                    }
                    leaf prefix-length {
                      type xr:Ipv6-prefix-length;
                      description "IP prefix length";
                    }
                    uses FIB-SH-TBL-FIB;
                  }
                }

                container summary {
                  description "Operational data for FIB Tablee";
                  uses FIB-SH-SUM;
                }

                container interface-infos {
                  description "Table of InterfaceInfo";

                  list interface-info {
                    key "link-type";
                    description "Specify link type";

                    container interfaces {
                      description "Table of interfaces";

                      list interface {
                        key "interface-name";
                        description "Specify Interface name";
                        leaf interface-name {
                          type xr:Interface-name;
                          description "Interface Name";
                        }
                        uses FIB-SH-INT;
                      }
                    }
                    leaf link-type {
                      type Fib-link;
                      description "Link type";
                    }
                  }
                }

                container ip-prefix-briefs {
                  description "IP FIB prefix brief table";

                  list ip-prefix-brief {
                    description "IP FIB prefix brief table entry";
                    leaf prefix {
                      type inet:ip-address-no-zone;
                      description "Destination IP address";
                    }
                    leaf prefix-length {
                      type xr:Ipv6-prefix-length;
                      description "IP prefix length";
                    }
                    uses FIB-SH-TBL-FIB;
                  }
                }
                leaf vrf-name {
                  type xr:Cisco-ios-xr-string;
                  description "VRF Name";
                }
              }
            }

            container external-client-summaries {
              description "External Client Summary Table";

              list external-client-summary {
                description "Summary of the external clients";
                leaf ecd-ver {
                  type int32;
                  description "Ecd Version";
                }
                leaf id {
                  type int32;
                  description
                    "ID of the client: ECDv1 is component id,
                    ECDv2 is client id";
                }
                uses FIB-SH-TBL-EXT-CLIENT-SUM;
              }
            }

            container misc {
              description "CEF misc hidden data";
              uses FIB-SH-MISC;
            }

            container local-label {
              description "Local label";

              container conflicts {
                description "FIB Local-label conflicts database";

                list conflict {
                  description "CEF Local-label conflicts entry";
                  leaf label {
                    type Fib-label;
                    description "Local label";
                  }
                  leaf source {
                    type Fib-route-source;
                    description "Route source";
                  }
                  leaf ll-ctype {
                    type Fibllc-entry;
                    description "Type of entry";
                  }
                  leaf pfx-tbl-id {
                    type int32;
                    description "Table ID of IP prefix";
                  }
                  leaf prefix {
                    type xr:Cisco-ios-xr-string;
                    description "IP Prefix";
                  }
                  leaf prefix-len {
                    type int32;
                    description "Length of IP Prefix";
                  }
                  uses FIB-MPLS-LLC;
                }
              }
            }
            leaf protocol-name {
              type Fib-protocol;
              description "Protocol Name ";
            }
          }
        }
        leaf node-name {
          type xr:Node-id;
          description "Node name";
        }
      }
    }
  }

  container mpls-forwarding {
    config false;
    description "mpls forwarding";

    container nodes {
      description "Table of Nodes";

      list node {
        key "node-name";
        description "Operational data for a specific Node";

        container forwarding-summary {
          description "FIB MPLS forwarding summary";
          uses MPLS-FWDING-SUMMARY;
        }

        container label-fib {
          description "Labels For FIB";

          container forwarding-details {
            description "MPLS Forwarding Detail table";

            list forwarding-detail {
              description "FIB MPLS forwarding details";
              leaf label-value {
                type int32;
                description "Local label value";
              }
              leaf eos {
                type Mplseos;
                description "End of stack flag";
              }
              uses MPLS-SH-LEAF;
            }
          }

          container informations {
            description "Forwarding filtering details";

            list information {
              description "FIB MPLS forwarding information";
              leaf label-value {
                type int32;
                description "Local label value";
              }
              leaf eos {
                type Mplseos;
                description "End of stack flag";
              }
              uses MPLS-SH-LEAF;
            }
          }

          container label-security {
            description "MPLS label security";

            container interfaces {
              description "MPLS label security interface table";

              list interface {
                key "interface-name";
                description "Specify interface Name";
                leaf interface-name {
                  type xr:Interface-name;
                  description "Interface Name";
                }
                uses MPLS-LABEL-SECURITY-INTF;
              }
            }

            container summary {
              description "MPLS label security summary";
              uses MPLS-LABEL-SECURITY-SUMMARY;
            }
          }
        }
        leaf node-name {
          type xr:Node-id;
          description "Node ID";
        }
      }
    }
  }

  container fib-mpls {
    config false;
    description "fib mpls";

    container nodes {
      description "Table of Nodes";

      list node {
        key "node-name";
        description "Operational data for a specific Node";

        container label-fib {
          description "Labels For FIB";

          container forwardings {
            description "Forwarding filtering details";

            list forwarding {
              description "FIB MPLS forwarding information";
              leaf local-label {
                type int32;
                description "Local label value";
              }
              leaf eos {
                type Eos;
                description "End of stack flag";
              }
              uses FIB-MPLS-SH-LEAF;
            }
          }

          container forwarding-details {
            description "MPLS Forwarding Detail table";

            list forwarding-detail {
              description "FIB MPLS forwarding details";
              leaf local-label {
                type int32;
                description "Local label value";
              }
              leaf eos {
                type Eos;
                description "End of stack flag";
              }
              uses FIB-MPLS-SH-LEAF;
            }
          }
        }

        container tunnel {
          description "Tunnels Operations";

          container forwarding-tunnels {
            description "Forwarding details";

            list forwarding-tunnel {
              key "interface-name";
              description "FIB MPLS Tunnels Interfaces operation";
              leaf interface-name {
                type xr:Interface-name;
                description "Interface Name";
              }
              uses FIB-MPLS-SH-TEHEAD;
            }
          }
        }

        container frr-database {
          description "FIB MPLS FRR Database";

          container frrdb-tunnel-head-summary {
            description "FIB MPLS FRR Database Tunnel Head Summary";
            uses FIB-MPLS-FRR-DB-SUM;
          }

          container frrdb-backup-interface-summaries {
            description
              "FIB MPLS FRR Database Backup Interface
              Summary Table";

            list frrdb-backup-interface-summary {
              key "interface-name";
              description
                "FIB MPLS FRR Database Backup Interface
                Summary";
              leaf interface-name {
                type xr:Interface-name;
                description "Interface Name";
              }
              uses FIB-MPLS-FRR-DB-SUM;
            }
          }

          container frrdb-summary {
            description "FIB MPLS FRR Database Summary";
            uses FIB-MPLS-FRR-DB-SUM;
          }

          container frrdb-protected-interface-table-summaries {
            description
              "FIB MPLS FRR Database Protected Interface
              Summary Table";

            list frrdb-protected-interface-table-summary {
              key "interface-name";
              description
                "FIB MPLS FRR Database Protected Interface
                Summary";
              leaf interface-name {
                type xr:Interface-name;
                description "Interface Name";
              }
              uses FIB-MPLS-FRR-DB-SUM;
            }
          }

          container frrdb-tunnel-midpoint-summary {
            description
              "FIB MPLS FRR Database Tunnel Midpoint Summary";
            uses FIB-MPLS-FRR-DB-SUM;
          }

          container frrdb-tunnel-midpoints {
            description
              "FIB MPLS FRR Database Tunnel Midpoint Table";

            list frrdb-tunnel-midpoint {
              key "local-label";
              description
                "FIB MPLS FRR Database Tunnel Midpoint Entry";
              leaf local-label {
                type int32;
                description "Local label value";
              }
              uses FIB-MPLS-FRR-DB-ENTRY;
            }
          }

          container frrdb-tunnel-heads {
            description "FIB MPLS FRR Database Tunnel Head Table";

            list frrdb-tunnel-head {
              key "interface-name";
              description "FIB MPLS FRR Database Tunnel Head Entry";
              leaf interface-name {
                type xr:Interface-name;
                description "Interface Name";
              }
              uses FIB-MPLS-FRR-DB-ENTRY;
            }
          }
        }

        container forwarding-summary {
          description "FIB MPLS forwarding summary";
          uses FIB-MPLS-FWDING-SUMMARY;
        }

        container frr-logs {
          description "FRR Log Table";

          list frr-log {
            key "event-id";
            description "FRR Log information";
            leaf event-id {
              type int32;
              description "Event ID";
            }
            uses FIB-MPLS-FRR-EVENT;
          }
        }
        leaf node-name {
          type xr:Node-id;
          description "Node name";
        }
      }
    }
  }
}
