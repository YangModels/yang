module Cisco-IOS-XR-crypto-macsec-pl-oper {

  /*** NAMESPACE / PREFIX DEFINITION ***/

  namespace "http://cisco.com/ns/yang"+
    "/Cisco-IOS-XR-crypto-macsec-pl-oper";


  prefix "crypto-macsec-pl-oper";

  /*** LINKAGE (IMPORTS / INCLUDES) ***/

  import Cisco-IOS-XR-types { prefix "xr"; }

  include Cisco-IOS-XR-crypto-macsec-pl-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR crypto-macsec-pl package operational data.

     This module contains definitions
     for the following management objects:
       macsec: MACSec operational data

     Copyright (c) 2013-2016 by Cisco Systems, Inc.
     All rights reserved.";

  revision "2015-11-09" {
    description
      "IOS XR 6.0 revision.";
  }


  container macsec {
    config false;
    description "MACSec operational data";

    container nodes {
      description "NodeTable for all the nodes";

      list node {
        key "node-name";
        description "Node where macsec interfaces exist";

        container interfaces {
          description "Table of Interfaces";

          list interface {
            key "name";
            description "Interface Where Macsec is configured";

            container hw-statistics {
              description "The Hardware Statistics";
              uses PL-MACSEC-STATS;
            }

            container sw-sas {
              description "Table of Software SAs";

              list sw-sa {
                key "sa-id";
                description "Software Security Association";
                leaf sa-id {
                  type int32;
                  description "SA ID";
                }
                uses PL-MACSEC-SA;
              }
            }

            container hw-sas {
              description "Table of Hardware SAs";

              list hw-sa {
                key "sa-id";
                description "Hardware Security Association";
                leaf sa-id {
                  type int32;
                  description "SA ID";
                }
                uses PL-MACSEC-SA;
              }
            }

            container hw-flow-s {
              description "Table of Hardware Flows";

              list hw-flow {
                key "flow-id";
                description "Hardware Flow";
                leaf flow-id {
                  type int32;
                  description "FLOW ID";
                }
                uses PL-MACSEC-FLOW;
              }
            }

            container sw-flow-s {
              description "Table of sofware Flows";

              list sw-flow {
                key "flow-id";
                description "Software Flow";
                leaf flow-id {
                  type int32;
                  description "FLOW ID";
                }
                uses PL-MACSEC-FLOW;
              }
            }

            container sw-statistics {
              description "The Software Statistics";
              uses PL-MACSEC-STATS;
            }
            leaf name {
              type xr:Interface-name;
              description "Value";
            }
          }
        }
        leaf node-name {
          type xr:Node-id;
          description "Node";
        }
      }
    }
  }
}
