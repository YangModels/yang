submodule Cisco-IOS-XR-adt-oper-sub2 {
  belongs-to Cisco-IOS-XR-adt-oper {
    prefix Cisco-IOS-XR-adt-oper;
  }

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR adt package operational data.
     
     Copyright (c) 2013-2020 by Cisco Systems, Inc.
     All rights reserved.";

  revision 2020-05-05 {
    description
      "IOS XR 7.3.1 Initial version.";
    semver:module-version "1.0.0";
  }
  revision 2019-04-05 {
    description
      "Establish semantic version baseline.";
  }
  revision 2015-11-09 {
    description
      "IOS XR 6.0 revision.";
  }

  typedef Ip-version {
    type enumeration {
      enum "unknown" {
        description
          "unknown";
      }
      enum "ipv4" {
        description
          "ipv4";
      }
      enum "ipv6" {
        description
          "ipv6";
      }
    }
    description
      "Ip version";
  }

  grouping VAL-PREFIX {
    description
      "VAL PREFIX";
    container ipv4-prefix {
      when "../prefix-type = '1'" {
        description
          "../prefix_type = '1'";
      }
      description
        "ipv4 prefix";
      uses VAL-STRING;
    }
    container ipv6-prefix {
      when "../prefix-type = '2'" {
        description
          "../prefix_type = '2'";
      }
      description
        "ipv6 prefix";
      uses VAL-STRING;
    }
    leaf prefix-type {
      type int32;
      description
        "prefix type";
    }
  }

  grouping VAL-STRING {
    description
      "VAL STRING";
    leaf val-str {
      type string;
      description
        "val str";
    }
  }

  grouping COUNTER-VAL-TYPE {
    description
      "COUNTER VAL TYPE";
    container stringdata {
      when "../value-type = '5'" {
        description
          "../value_type = '5'";
      }
      description
        "stringdata";
      uses VAL-STRING;
    }
    container ip-prefix {
      when "../value-type = '19'" {
        description
          "../value_type = '19'";
      }
      description
        "ip prefix";
      uses VAL-PREFIX;
    }
    leaf value-type {
      type int32;
      description
        "value type";
    }
    leaf not-set {
      when "../value-type = '0'" {
        description
          "../value_type = '0'";
      }
      type uint32;
      description
        "not set";
    }
    leaf val-u32 {
      when "../value-type = '1'" {
        description
          "../value_type = '1'";
      }
      type uint32;
      description
        "val u32";
    }
    leaf val-i32 {
      when "../value-type = '2'" {
        description
          "../value_type = '2'";
      }
      type int32;
      description
        "val i32";
    }
    leaf val-u64 {
      when "../value-type = '3'" {
        description
          "../value_type = '3'";
      }
      type uint64;
      description
        "val u64";
    }
    leaf val-i64 {
      when "../value-type = '4'" {
        description
          "../value_type = '4'";
      }
      type int64;
      description
        "val i64";
    }
    leaf val-counter32 {
      when "../value-type = '6'" {
        description
          "../value_type = '6'";
      }
      type uint32;
      description
        "val counter32";
    }
    leaf val-zero-based-counter32 {
      when "../value-type = '7'" {
        description
          "../value_type = '7'";
      }
      type uint32;
      description
        "val zero based counter32";
    }
    leaf val-counter64 {
      when "../value-type = '8'" {
        description
          "../value_type = '8'";
      }
      type uint64;
      description
        "val counter64";
    }
    leaf val-zero-based-counter64 {
      when "../value-type = '9'" {
        description
          "../value_type = '9'";
      }
      type uint64;
      description
        "val zero based counter64";
    }
    leaf val-guage32 {
      when "../value-type = '10'" {
        description
          "../value_type = '10'";
      }
      type uint32;
      description
        "val guage32";
    }
    leaf val-gauge64 {
      when "../value-type = '11'" {
        description
          "../value_type = '11'";
      }
      type uint64;
      description
        "val gauge64";
    }
    leaf val-timeticks {
      when "../value-type = '12'" {
        description
          "../value_type = '12'";
      }
      type uint64;
      description
        "val timeticks";
    }
    leaf val-timestamp {
      when "../value-type = '13'" {
        description
          "../value_type = '13'";
      }
      type uint64;
      description
        "val timestamp";
    }
    leaf val-ip-version {
      when "../value-type = '14'" {
        description
          "../value_type = '14'";
      }
      type Ip-version;
      description
        "val ip version";
    }
    leaf val-dscp {
      when "../value-type = '15'" {
        description
          "../value_type = '15'";
      }
      type uint32;
      description
        "val dscp";
    }
    leaf val-ipv6-flow-label {
      when "../value-type = '16'" {
        description
          "../value_type = '16'";
      }
      type uint32;
      description
        "val ipv6 flow label";
    }
    leaf val-port-number {
      when "../value-type = '17'" {
        description
          "../value_type = '17'";
      }
      type uint32;
      description
        "val port number";
    }
    leaf val-as-number {
      when "../value-type = '18'" {
        description
          "../value_type = '18'";
      }
      type uint32;
      description
        "val as number";
    }
  }

  grouping DATA-DEF {
    description
      "DATA DEF";
    container value {
      description
        "value";
      uses COUNTER-VAL-TYPE;
    }
    leaf timestamp {
      type uint64;
      description
        "timestamp";
    }
  }

  grouping CHANGE-LIST-DEF {
    description
      "CHANGE LIST DEF";
    leaf sensor-path {
      type string;
      description
        "sensor path";
    }
    leaf sensor-path-tags {
      type string;
      description
        "sensor path tags";
    }
    leaf sensor-path-message {
      type string;
      description
        "sensor path message";
    }
    list data {
      description
        "data";
      uses DATA-DEF;
    }
  }

  grouping ADT-EVENT-DEF {
    description
      "ADT EVENT DEF";
    leaf event-id {
      type uint32;
      description
        "Event id used as key";
      xr:event-telemetry "Subscribe Telemetry Event";
    }
    leaf change-description {
      type string;
      description
        "change description";
    }
    leaf timestamp {
      type uint64;
      description
        "timestamp";
    }
    list change {
      description
        "change";
      uses CHANGE-LIST-DEF;
    }
  }

  grouping ADT-EVENTS {
    description
      "ADT EVENTS";
    list adt-event {
      description
        "adt event";
      uses ADT-EVENT-DEF;
    }
  }
}
