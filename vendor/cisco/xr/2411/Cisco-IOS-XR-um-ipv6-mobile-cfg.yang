module Cisco-IOS-XR-um-ipv6-mobile-cfg {
  namespace "http://cisco.com/ns/yang/Cisco-IOS-XR-um-ipv6-mobile-cfg";
  prefix um-ipv6-mobile-cfg;

  import Cisco-IOS-XR-types {
    prefix xr;
  }
  import ietf-inet-types {
    prefix inet;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ipv6-mobile package configuration.
     
     This YANG module augments the
     modules with configuration data.
     
     Copyright (c) 2020-2022 by Cisco Systems, Inc.
     All rights reserved.";

  revision 2020-12-07 {
    description
      "Initial release";
    semver:module-version "1.0.0";
  }

  container ipv6 {
    description
      "Global IPv6 configuration commands";
    container mobile {
      description
        "MobileIP configuration";
      container pmipv6-domains {
        description
          "PMIPv6 domain configuration";
        list pmipv6-domain {
          key "pmipv6-domain-name";
          description
            "PMIPv6 domain configuration";
          leaf pmipv6-domain-name {
            type xr:Cisco-ios-xr-string {
              length "2..125" {
                description
                  "Domain Name";
              }
            }
            description
              "PMIPv6 domain configuration";
          }
          container nais {
            description
              "Network access identifier or Realm";
            list nai {
              key "nai-name";
              description
                "Network access identifier or Realm";
              leaf nai-name {
                type string {
                  length "2..125" {
                    description
                      "MN Identifier";
                  }
                }
                description
                  "Network access identifier or Realm";
              }
              leaf apn {
                type xr:Cisco-ios-xr-string {
                  length "2..125" {
                    description
                      "APN name";
                  }
                }
                description
                  "Access point network for this MN";
              }
              leaf network {
                type xr:Cisco-ios-xr-string {
                  length "2..125" {
                    description
                      "Network name";
                  }
                }
                description
                  "Network name (Address pool) for this MN";
              }
              leaf service {
                type enumeration {
                  enum "ipv4" {
                    value 1;
                    description
                      "ipv4 service type";
                  }
                  enum "ipv6" {
                    value 2;
                    description
                      "ipv6 service type";
                  }
                  enum "dual" {
                    value 3;
                    description
                      "dual service type";
                  }
                }
                description
                  "Service type for this MN";
              }
              leaf customer {
                type xr:Cisco-ios-xr-string {
                  length "2..125" {
                    description
                      "Customer name";
                  }
                }
                description
                  "Customer name for this MN";
              }
            }
          }
          container auth-option {
            description
              "Authentication option between PMIPV6 entities";
            leaf spi {
              type uint32 {
                range "0..4294967295" {
                  description
                    "SPI in hex value";
                }
              }
              description
                "Security parameter index";
            }
            container key {
              description
                "Security Key";
              leaf ascii {
                type xr:Cisco-ios-xr-string {
                  length "2..125" {
                    description
                      "ASCII string";
                  }
                }
                description
                  "Key in ASCII string";
              }
            }
          }
        }
      }
      container pmipv6-lmas {
        description
          "PMIPv6 LMA configuration";
        list pmipv6-lma {
          key "pmipv6-lma-name domain-name";
          description
            "PMIPv6 LMA configuration";
          leaf pmipv6-lma-name {
            type string {
              length "2..125" {
                description
                  "LMA name";
              }
            }
            description
              "PMIPv6 LMA configuration";
          }
          leaf domain-name {
            type string {
              length "2..125" {
                description
                  "Domain name";
              }
            }
            description
              "PMIPv6 domain for this LMA";
          }
          container address {
            description
              "Specify LMAs IPv4 and IPv6 address";
            container ipv4s {
              description
                "Configure IPv4 address for this LMA";
              list ipv4 {
                key "address";
                description
                  "Configure IPv4 address for this LMA";
                leaf address {
                  type inet:ipv4-address-no-zone;
                  description
                    "Configure IPv4 address for this LMA";
                }
              }
            }
            container ipv6s {
              description
                "Configure IPv6 address for this LMA";
              list ipv6 {
                key "address";
                description
                  "Configure IPv6 address for this LMA";
                leaf address {
                  type inet:ipv6-address-no-zone;
                  description
                    "Configure IPv6 address for this LMA";
                }
              }
            }
          }
          container bce {
            description
              "LMA binding attributes";
            leaf delete-wait-time {
              type uint32 {
                range "100..65535" {
                  description
                    "Specify in millisec";
                }
              }
              description
                "bce delete wait time interval";
            }
            leaf create-wait-time {
              type uint32 {
                range "100..65535" {
                  description
                    "Specify in millisec";
                }
              }
              description
                "bce create wait time interval";
            }
            leaf lifetime {
              type uint32 {
                range "10..65535" {
                  description
                    "Specify in seconds";
                }
              }
              description
                "Maximum bce lifetime permitted";
            }
            leaf refresh-time {
              type uint32 {
                range "4..65000" {
                  description
                    "Specify in seconds, (multiples of 4)";
                }
              }
              description
                "Bce refresh interval";
            }
            leaf maximum {
              type uint32 {
                range "1..128000" {
                  description
                    "Specify max. number of bindings";
                }
              }
              description
                "Maximum bindings permitted";
            }
          }
          container hnp {
            description
              "LMA HNP options";
            leaf maximum {
              type uint32 {
                range "1..3" {
                  description
                    "Specify maximum HNPs allowed";
                }
              }
              description
                "maximum HNPs allowed per MN interface";
            }
          }
          container bri {
            description
              "LMA Binding Revocation Attributes";
            container delay {
              description
                "Time to wait before Retransmitting BRI Message";
              leaf min {
                type uint32 {
                  range "500..65535" {
                    description
                      "Specify in millisec";
                  }
                }
                must "../max";
                description
                  "Minimum time delay to send BRI";
              }
              leaf max {
                type uint32 {
                  range "500..65535" {
                    description
                      "Specify in millisec";
                  }
                }
                must "../min";
                description
                  "Maximum time delay to send BRI";
              }
            }
            leaf retries {
              type uint32 {
                range "1..10" {
                  description
                    "Retries count";
                }
              }
              description
                "Number of Retransmissons Allowed for BRI Message";
            }
          }
          container replay-protection {
            description
              "Replay Protection Method";
            container timestamp {
              description
                "Timestamp Option";
              leaf window {
                type uint32 {
                  range "1..255" {
                    description
                      "Specify timestamp window value in seconds";
                  }
                }
                description
                  "Window Value";
              }
            }
          }
          container default {
            description
              "Default MN profile for LMA";
            leaf profile {
              type string {
                length "2..125" {
                  description
                    " MN profile name";
                }
              }
              description
                "MN profile";
            }
          }
          container aaa {
            description
              "AAA configuration for this LMA";
            container accounting {
              presence "Indicates a accounting node is configured.";
              description
                "AAA accounting for this LMA";
              leaf interim {
                type uint32 {
                  range "1..86400" {
                    description
                      "Interim acounting interval (in minutes)";
                  }
                }
                description
                  "Send interim accounting update messages";
              }
            }
          }
          container dynamic {
            description
              "enable dynamic mag learning for LMA";
            container mag {
              description
                "learn mag dynamically for this LMA";
              container learning {
                presence "Indicates a learning node is configured.";
                description
                  "learn mag dynamically for this LMA";
              }
            }
          }
          container enforce {
            description
              "enforce heartbeat values to MAG";
            container heartbeat-to-mag {
              presence "Indicates a heartbeat-to-mag node is configured.";
              description
                "send heartbeat values to MAG";
            }
          }
          container heartbeat {
            description
              "heartbeat config for this LMA";
            leaf interval {
              type uint32 {
                range "10..3600" {
                  description
                    "Specify the interval value in second";
                }
              }
              must "../retries";
              description
                "interval value";
            }
            leaf retries {
              type uint32 {
                range "1..10" {
                  description
                    "Specify the retry value";
                }
              }
              must "../interval and ../timeout";
              description
                "interval value";
            }
            leaf timeout {
              type uint32 {
                range "1..3600" {
                  description
                    "Specify the timeout value";
                }
              }
              must "../retries";
              description
                "timeout value";
            }
          }
          container dscp {
            description
              "DSCP for packets originating from this LMA";
            leaf control-plane {
              type uint32 {
                range "1..63" {
                  description
                    "Specify the DSCP value";
                }
              }
              description
                "DSCP value for control plane messages";
            }
            container force {
              must "../control-plane";
              presence "Indicates a force node is configured.";
              description
                "Force DSCP from incoming packets into outgoing packets";
            }
          }
          leaf redistribute {
            type enumeration {
              enum "home-address" {
                value 1;
                description
                  "Redistribute HoA/HNP routes";
              }
            }
            must "../ho-a-hnp-host-routes";
            description
              "Redistribute routes";
          }
          leaf ho-a-hnp-host-routes {
            type enumeration {
              enum "host-prefix" {
                value 1;
                description
                  "Redistribute HoA/HNP host prefix routes";
              }
              enum "disable" {
                value 2;
                description
                  "Disable redistribution of HoA/HNP host and pool refix routes";
              }
            }
            must "../redistribute";
            description
              "configure this node";
          }
          container pgw {
            description
              "Feature related to interface with PGW";
            container subscriber {
              description
                "Enable Subscriber Continuity";
              container continuity {
                presence "Indicates a continuity node is configured.";
                description
                  "Enable Subscriber Continuity";
              }
            }
          }
          container mobile-route {
            description
              "Configuration related to M Route";
            leaf admin-distance {
              type uint32 {
                range "1..254" {
                  description
                    "Specify the Admin Distance value";
                }
              }
              description
                "Admin Distance of the M Route";
            }
          }
          container networks {
            description
              "network for this LMA";
            list network {
              key "network-name";
              description
                "network for this LMA";
              leaf network-name {
                type string {
                  length "2..125" {
                    description
                      "Network name";
                  }
                }
                description
                  "network for this LMA";
              }
              container pool {
                description
                  "Pool configs for this network";
                container mobile-node {
                  description
                    "pool configs for the mobile nodes";
                  container ipv4 {
                    description
                      "ipv4 pool";
                    leaf start-address {
                      type inet:ipv4-address-no-zone;
                      must "../pool-prefix";
                      description
                        "ipv4 pool start address";
                    }
                    leaf pool-prefix {
                      type uint32 {
                        range "8..30" {
                          description
                            "IPv4 Pool Prefix value";
                        }
                      }
                      must "../start-address";
                      description
                        "ipv4 pool prefix";
                    }
                  }
                  container ipv6 {
                    description
                      "ipv6 pool";
                    leaf start-address {
                      type inet:ipv6-address-no-zone;
                      must "../pool-prefix";
                      description
                        "ipv6 pool start address";
                    }
                    leaf pool-prefix {
                      type uint32 {
                        range "8..62" {
                          description
                            "IPv6 Pool Prefix value";
                        }
                      }
                      must "../start-address";
                      description
                        "ipv6 pool prefix";
                    }
                  }
                }
                container mobile-network {
                  description
                    "pool configs for the mobile network";
                  container ipv4 {
                    description
                      "ipv4 pool";
                    container start-addresses {
                      description
                        "ipv4 network pool start address";
                      list start-address {
                        key "address";
                        description
                          "ipv4 network pool start address";
                        leaf address {
                          type inet:ipv4-address-no-zone;
                          description
                            "ipv4 network pool start address";
                        }
                        leaf pool-prefix {
                          type uint32 {
                            range "8..30" {
                              description
                                "IPv4 Pool Prefix value";
                            }
                          }
                          must "../network-prefix";
                          description
                            "ipv4 pool prefix";
                        }
                        leaf network-prefix {
                          type uint32 {
                            range "8..32" {
                              description
                                "IPv4 Network Prefix value";
                            }
                          }
                          must "../pool-prefix";
                          description
                            "ipv4 network prefix";
                        }
                      }
                    }
                  }
                  container ipv6 {
                    description
                      "ipv6 pool";
                    container start-addresses {
                      description
                        "ipv6 pool start address";
                      list start-address {
                        key "address";
                        description
                          "ipv6 pool start address";
                        leaf address {
                          type inet:ipv6-address-no-zone;
                          description
                            "ipv6 pool start address";
                        }
                        leaf pool-prefix {
                          type uint32 {
                            range "8..64" {
                              description
                                "IPv6 Pool Prefix value";
                            }
                          }
                          must "../network-prefix";
                          description
                            "ipv6 network prefix";
                        }
                        leaf network-prefix {
                          type uint32 {
                            range "8..64" {
                              description
                                "IPv4 Network Prefix value";
                            }
                          }
                          must "../pool-prefix";
                          description
                            "ipv6 network prefix";
                        }
                      }
                    }
                  }
                }
              }
            }
          }
          container mobility-services {
            description
              "Service of this LMA";
            list mobility-service {
              key "mobility-service-id";
              description
                "Service of this LMA";
              leaf mobility-service-id {
                type enumeration {
                  enum "mobile-local-loop" {
                    value 1;
                    description
                      "Wireless Private Routing service";
                  }
                }
                description
                  "Service of this LMA";
              }
              container ignore {
                description
                  "Ignore options for Mobile Local Loop service";
                container home-address {
                  presence "Indicates a home-address node is configured.";
                  description
                    "Ignore HoA/HNP option";
                }
              }
              container mnp {
                description
                  "configure mobile node prefix limits";
                container ipv4 {
                  description
                    "configure mobile node IPv4 prefix limits";
                  container logical-mn {
                    description
                      "mnp limit config for all logical mn's";
                    leaf maximum {
                      type uint32 {
                        range "1..32" {
                          description
                            "Number of IPv4 MNPs";
                        }
                      }
                      description
                        "Maximum Prefixes for all Logical MN's";
                    }
                  }
                  container customer {
                    description
                      "mnp limit config for all customer's";
                    leaf maximum {
                      type uint32 {
                        range "1..4000000" {
                          description
                            "Number of IPv4 MNPs";
                        }
                      }
                      description
                        "Maximum Prefixes for all customer's";
                    }
                  }
                }
                container ipv6 {
                  description
                    "configure mobile node IPv6 prefix limits";
                  container logical-mn {
                    description
                      "mnp limit config for all logical mn's";
                    leaf maximum {
                      type uint32 {
                        range "1..32" {
                          description
                            "Number of IPv6 MNPs";
                        }
                      }
                      description
                        "Maximum Prefixes for all Logical MN's";
                    }
                  }
                  container customer {
                    description
                      "mnp limit config for all customer's";
                    leaf maximum {
                      type uint32 {
                        range "1..4000000" {
                          description
                            "Number of IPv6 MNPs";
                        }
                      }
                      description
                        "Maximum Prefixes for all customer's";
                    }
                  }
                }
                container afi-all {
                  description
                    "configure mobile node prefix limits";
                  container logical-mn {
                    description
                      "mnp limit config for all logical mn's";
                    leaf maximum {
                      type uint32 {
                        range "1..32" {
                          description
                            "Number of MNPs";
                        }
                      }
                      description
                        "Maximum Prefixes for all Logical MN's";
                    }
                  }
                  container customer {
                    description
                      "mnp limit config for all customer's";
                    leaf maximum {
                      type uint32 {
                        range "1..4000000" {
                          description
                            "Number of MNPs";
                        }
                      }
                      description
                        "Maximum Prefixes for all customer's";
                    }
                  }
                }
              }
              container customers {
                description
                  "customer configuration on this mobile local loop service";
                list customer {
                  key "customer-name vrf-name";
                  description
                    "customer configuration on this mobile local loop service";
                  leaf customer-name {
                    type string {
                      length "1..32" {
                        description
                          "Customer name";
                      }
                    }
                    description
                      "customer configuration on this mobile local loop service";
                  }
                  leaf vrf-name {
                    type string {
                      length "1..32" {
                        description
                          "VRF name";
                      }
                    }
                    description
                      "Vrf for this customer";
                  }
                  container auth-option {
                    description
                      "Authentication option between PMIPV6 entities";
                    leaf spi {
                      type uint32 {
                        range "0..4294967295" {
                          description
                            "SPI in hex value";
                        }
                      }
                      description
                        "Security parameter index";
                    }
                    container key {
                      description
                        "Security Key";
                      leaf ascii {
                        type xr:Cisco-ios-xr-string {
                          length "2..125" {
                            description
                              "ASCII string";
                          }
                        }
                        description
                          "Key in ASCII string";
                      }
                    }
                  }
                  container mnp {
                    description
                      "configure mobile node prefix limits";
                    container ipv4 {
                      description
                        "configure mobile node IPv4 prefix limits";
                      container logical-mn {
                        description
                          "mnp limit config for customer specific logical mn";
                        leaf maximum {
                          type uint32 {
                            range "1..32" {
                              description
                                "Number of IPv4 MNPs";
                            }
                          }
                          description
                            "Maximum Prefixes for this customers' Logical MN's";
                        }
                      }
                      container customer {
                        description
                          "mnp limit config for customer";
                        leaf maximum {
                          type uint32 {
                            range "1..4000000" {
                              description
                                "Number of IPv4 MNPs";
                            }
                          }
                          description
                            "Maximum Prefixes for this customer";
                        }
                      }
                    }
                    container ipv6 {
                      description
                        "configure mobile node IPv6 prefix limits";
                      container logical-mn {
                        description
                          "mnp limit config for customer specific logical mn";
                        leaf maximum {
                          type uint32 {
                            range "1..32" {
                              description
                                "Number of IPv6 MNPs";
                            }
                          }
                          description
                            "Maximum Prefixes for this customers' Logical MN's";
                        }
                      }
                      container customer {
                        description
                          "mnp limit config for customer";
                        leaf maximum {
                          type uint32 {
                            range "1..4000000" {
                              description
                                "Number of IPv6 MNPs";
                            }
                          }
                          description
                            "Maximum Prefixes for this customer";
                        }
                      }
                    }
                    container afi-all {
                      description
                        "configure mobile node prefix limits";
                      container logical-mn {
                        description
                          "mnp limit config for customer specific logical mn";
                        leaf maximum {
                          type uint32 {
                            range "1..32" {
                              description
                                "Number of MNPs";
                            }
                          }
                          description
                            "Maximum Prefixes for this customers' Logical MN's";
                        }
                      }
                      container customer {
                        description
                          "mnp limit config for customer";
                        leaf maximum {
                          type uint32 {
                            range "1..4000000" {
                              description
                                "Number of MNPs";
                            }
                          }
                          description
                            "Maximum Prefixes for this customer";
                        }
                      }
                    }
                  }
                  container heartbeat {
                    description
                      "heartbeat config for this Customer";
                    leaf interval {
                      type uint32 {
                        range "10..3600" {
                          description
                            "Specify the interval value in second";
                        }
                      }
                      must "../retries";
                      description
                        "interval value";
                    }
                    leaf retries {
                      type uint32 {
                        range "1..10" {
                          description
                            "Specify the retry value";
                        }
                      }
                      must "../interval and ../timeout";
                      description
                        "retry value";
                    }
                    leaf timeout {
                      type uint32 {
                        range "1..3600" {
                          description
                            "Specify the timeout value";
                        }
                      }
                      must "../retries";
                      description
                        "timeout value";
                    }
                  }
                  container network {
                    description
                      "network parameters for the customer";
                    container unauthorized {
                      presence "Indicates a unauthorized node is configured.";
                      description
                        "not authorize the network prefixes";
                    }
                    container authorizeds {
                      description
                        "not authorize the network prefixes";
                      list authorized {
                        key "authorized-name";
                        description
                          "not authorize the network prefixes";
                        leaf authorized-name {
                          type string {
                            length "2..125" {
                              description
                                "ASCII string";
                            }
                          }
                          description
                            "not authorize the network prefixes";
                        }
                        container pool {
                          description
                            "Pool configs for this network";
                          container mobile-node {
                            description
                              "pool configs for the mobile nodes";
                            container ipv4 {
                              description
                                "ipv4 pool";
                              leaf start-address {
                                type inet:ipv4-address-no-zone;
                                must "../pool-prefix";
                                description
                                  "ipv4 pool start address";
                              }
                              leaf pool-prefix {
                                type uint32 {
                                  range "8..30" {
                                    description
                                      "IPv4 Pool Prefix value";
                                  }
                                }
                                must "../start-address";
                                description
                                  "ipv4 pool prefix";
                              }
                            }
                            container ipv6 {
                              description
                                "ipv6 pool";
                              leaf start-address {
                                type inet:ipv6-address-no-zone;
                                must "../pool-prefix";
                                description
                                  "ipv6 pool start address";
                              }
                              leaf pool-prefix {
                                type uint32 {
                                  range "8..62" {
                                    description
                                      "IPv6 Pool Prefix value";
                                  }
                                }
                                must "../start-address";
                                description
                                  "ipv6 pool prefix";
                              }
                            }
                          }
                          container mobile-network {
                            description
                              "pool configs for the mobile network";
                            container ipv4 {
                              description
                                "ipv4 pool";
                              container start-addresses {
                                description
                                  "ipv4 network pool start address";
                                list start-address {
                                  key "address";
                                  description
                                    "ipv4 network pool start address";
                                  leaf address {
                                    type inet:ipv4-address-no-zone;
                                    description
                                      "ipv4 network pool start address";
                                  }
                                  leaf pool-prefix {
                                    type uint32 {
                                      range "8..30" {
                                        description
                                          "IPv4 Pool Prefix value";
                                      }
                                    }
                                    must "../network-prefix";
                                    description
                                      "ipv4 pool prefix";
                                  }
                                  leaf network-prefix {
                                    type uint32 {
                                      range "8..32" {
                                        description
                                          "IPv4 Network Prefix value";
                                      }
                                    }
                                    must "../pool-prefix";
                                    description
                                      "ipv4 network prefix";
                                  }
                                }
                              }
                            }
                            container ipv6 {
                              description
                                "ipv6 pool";
                              container start-addresses {
                                description
                                  "ipv6 pool start address";
                                list start-address {
                                  key "address";
                                  description
                                    "ipv6 pool start address";
                                  leaf address {
                                    type inet:ipv6-address-no-zone;
                                    description
                                      "ipv6 pool start address";
                                  }
                                  leaf pool-prefix {
                                    type uint32 {
                                      range "8..64" {
                                        description
                                          "IPv6 Pool Prefix value";
                                      }
                                    }
                                    must "../network-prefix";
                                    description
                                      "ipv6 network prefix";
                                  }
                                  leaf network-prefix {
                                    type uint32 {
                                      range "8..64" {
                                        description
                                          "IPv4 Network Prefix value";
                                      }
                                    }
                                    must "../pool-prefix";
                                    description
                                      "ipv6 network prefix";
                                  }
                                }
                              }
                            }
                          }
                        }
                      }
                    }
                  }
                  container bce {
                    description
                      "Customer specific binding attributes";
                    leaf lifetime {
                      type uint32 {
                        range "10..65535" {
                          description
                            "Specify in seconds";
                        }
                      }
                      description
                        "Maximum bce lifetime permitted";
                    }
                  }
                  leaf gre-key {
                    type enumeration {
                      enum "symmetric" {
                        value 1;
                        description
                          "Symmetric GRE Key (same Uplink and Downlink key)";
                      }
                    }
                    must "../gre-key-value";
                    description
                      "Customer specific GRE key";
                  }
                  leaf gre-key-value {
                    type uint32 {
                      range "1..4294967295" {
                        description
                          "GRE key value";
                      }
                    }
                    must "../gre-key";
                    description
                      "GRE key value";
                  }
                  container bandwidth {
                    description
                      "Bandwidth allocated to this customer";
                    leaf aggregate {
                      type uint32 {
                        range "1..4294967295" {
                          description
                            "Bandwidth in kbps";
                        }
                      }
                      description
                        "Aggregate bandwidth across all logical MNs";
                    }
                  }
                  container mobile-route {
                    description
                      "Configuration related to M Route";
                    leaf admin-distance {
                      type uint32 {
                        range "1..254" {
                          description
                            "Specify the Admin Distance value";
                        }
                      }
                      description
                        "Admin Distance of the M Route";
                    }
                  }
                  container transport {
                    description
                      "Customer transport attributes";
                    container vrfs {
                      description
                        "vrf for this transport";
                      list vrf {
                        key "vrf-name";
                        description
                          "vrf for this transport";
                        leaf vrf-name {
                          type string {
                            length "2..125" {
                              description
                                "VRF Name";
                            }
                          }
                          description
                            "vrf for this transport";
                        }
                        container address {
                          description
                            "Specify LMAs IPv4 and IPv6 address";
                          leaf ipv4 {
                            type inet:ipv4-address-no-zone;
                            description
                              "Configure IPv4 address for this LMA";
                          }
                          leaf ipv6 {
                            type inet:ipv6-address-no-zone;
                            description
                              "Configure IPv6 address for this LMA";
                          }
                        }
                      }
                    }
                    container address {
                      description
                        "Specify LMAs IPv4 and IPv6 address";
                      leaf ipv4 {
                        type inet:ipv4-address-no-zone;
                        description
                          "Configure IPv4 address for this LMA";
                      }
                      leaf ipv6 {
                        type inet:ipv6-address-no-zone;
                        description
                          "Configure IPv6 address for this LMA";
                      }
                    }
                  }
                }
              }
            }
          }
        }
      }
    }
  }
}
