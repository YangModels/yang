module Cisco-IOS-XR-es-acl-datatypes {
  namespace "http://cisco.com/ns/yang/Cisco-IOS-XR-es-acl-datatypes";
  prefix es-acl-datatypes;

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of generally useful
     derived YANG data types.
     
     Copyright (c) 2013-2019 by Cisco Systems, Inc.
     All rights reserved.";

  revision 2019-04-05 {
    description
      "Establish semantic version baseline.";
    semver:module-version "1.0.0";
  }
  revision 2017-05-01 {
    description
      "Fixing backward compatibility error in module.";
  }
  revision 2015-11-09 {
    description
      "IOS XR 6.0 revision.";
  }

  typedef Es-acl-dei-range {
    type uint32 {
      range "0..1";
    }
    description
      "Es acl dei range";
  }

  typedef Es-acl-name {
    type xr:Cisco-ios-xr-string {
      length "1..64";
    }
    description
      "Es acl name";
  }

  typedef Es-acl-vlan-range {
    type uint32 {
      range "0..4095";
    }
    description
      "Es acl vlan range";
  }

  typedef Acl-usage-app-id-enum {
    type enumeration {
      enum "pfilter" {
        value 1;
        description
          "General Usage Statistics";
      }
      enum "bgp" {
        value 2;
        description
          "Usage staistics related to BGP Traffic";
      }
      enum "ospf" {
        value 3;
        description
          "Usage staistics related to OSPF Traffic";
      }
    }
    description
      "Acl usage app id enum";
  }

  typedef Es-acl-cos-range {
    type uint32 {
      range "0..7";
    }
    description
      "Es acl cos range";
  }

  typedef Acl-sequence-number-range {
    type uint32 {
      range "1..2147483646";
    }
    description
      "Acl sequence number range";
  }

  typedef Es-acl-log-range {
    type uint32 {
      range "0..1";
    }
    description
      "Es acl log range";
  }
}
