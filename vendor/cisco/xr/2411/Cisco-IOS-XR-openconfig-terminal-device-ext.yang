module Cisco-IOS-XR-openconfig-terminal-device-ext {
  namespace "http://cisco.com/ns/yang/Cisco-IOS-XR-openconfig-terminal-device-ext";
  prefix oc-opt-ext;

  import openconfig-platform {
    prefix oc-platform;
  }
  import openconfig-terminal-device {
    prefix oc-opt-term;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module is an extension of optical terminal device model
      and contains the definition of extended parameters for Optical
      Channels in order to optimize the AC1200 settings to get the highest
      performance and spectral efficiency.
     
      This module contains definitions for the following management objects:
      General Parameters
      Submarine Parameters
     
      Copyright (c) 2013-2024 by Cisco Systems, Inc.
      All rights reserved.";

  revision 2024-01-23 {
    description
      "Updated baud-rate length";
  }
  revision 2023-12-19 {
    description
      "Range increased for chromatic dispersion";
  }
  revision 2023-05-08 {
    description
      "Addition of baud-rate configuration";
  }
  revision 2023-02-28 {
    description
      "Addition of input power lower and upper thresholds parameters and
       Fastpoll enable configuration";
    reference "7.8.1";
  }
  revision 2020-08-30 {
    description
      "IOS XR 6.0 revision";
    reference "7.3.1";
  }

  grouping terminal-device-optical-channel-ext-info {
    description
      "Submarine parameteres for optical channel";
    leaf optics-cd-min {
      type int32 {
        range "-600000..600000";
      }
      description
        "Select min chromatic dispersion (in units of
         ps/nm)";
    }
    leaf optics-cd-max {
      type int32 {
        range "-600000..600000";
      }
      description
        "Select max chromatic dispersion (in units of
         ps/nm)";
    }
    leaf optics-cd-low-threshold {
      type int32 {
        range "-600000..600000";
      }
      description
        "Select chromatic dispersion low threshold(in
         units of ps/nm)";
    }
    leaf optics-cd-high-threshold {
      type int32 {
        range "-600000..600000";
      }
      description
        "Select chromatic dispersion high threshold(in
         units of ps/nm)";
    }
    leaf filter-roll-off-factor {
      type string {
        length "5";
      }
      description
        "RRC Filter Roll-Off factor in increments of 0
         .001 and default value is 0.1";
    }
    leaf enh-colorless-mode {
      type uint32 {
        range "1..3";
      }
      description
        "Enhanced Colorless Mode
         0 - Disabled (Colored Rx)
         1 - Weak colorless interface
         2 - Medium colorless interface
         3 - Strong colorless interface
         Default value is 0";
    }
    leaf enh-sop-tol-mode {
      type uint32 {
        range "1..3";
      }
      description
        "Enhanced SOP Tolerance Mode
         0 - Disabled
         1 - Mode A (enhanced SOP mode)
         Mode A can only be used in the pure modulation modes such as two BPS,
                 three BPS, and four BPS. It does not support fraction QAM modes.
         2 - Mode B (unused)
         3 - Mode C (submarine mode)
         Default value is 0
         When the enhanced SOP tolerance mode is set to 1 (Mode A),
             the carrier phase recovery cross polarization gain mode must
             also be set to a value of 10 on the optics controller. ";
    }
    leaf nleq-compensation {
      type uint32 {
        range "1..4";
      }
      description
        "Non Linear Effect Compenstation
         1 - Compensation optimized for D+ High Dispersion
                 fiber transmission 60 G to 72 Gbaud
         2 - Compensation optimized for D+ High Dispersion
         \t fiber transmission 30 G to 72 Gbaud
         3 - Compensation optimized for D+ Low Dispersion
                 fiber transmission
         4 - Compensation optimized for D+ Low Dispersion
         \t fiber transmission longer distance
         Default value is 0";
    }
    leaf cross-pol-gain-mode {
      type uint32 {
        range "1..15";
      }
      description
        "Carrier Phase Recovery Cross Polarization Gain
         Mode 0, 1, 2, and 7 through 15 are allowed but not optimal values
         Default value is 0";
    }
    leaf cross-pol-weight-mode {
      type uint32 {
        range "1..7";
      }
      description
        "Carrier Phase Recovery Cross Polarization Weight
         Mode 1,2,3, and 4 are preferred optimal values
         0,5,6, and 7 are allowed but not optimal values
         Default value is 0";
    }
    leaf cpr-win-mode {
      type uint32 {
        range "1..4";
      }
      description
        "Carrier Phase Recovery Window Mode
         0 - 160 symbols
         1 - 8 symbols
         2 - 16 symbols
         3 - 32 symbols
         4 - 4 symbols
         Default value is 0";
    }
    leaf cpr-ext-win-mode {
      type uint32 {
        range "1..9";
      }
      description
        "Carrier Phase Recovery Extended Window Mode
         0 - 160 Symbols (288 symbols if the baud rate is greater than 52 Gbaud)
         1 - 64 symbols
         2 - 65 symbols
         3 - 66 symbols
         4 - 69 symbols
         5 - 75 symbols
         6 - 96 symbols
         7 - 160 symbols
         8 - 288 symbols
         9 - 544 symbols
         Default value is 0";
    }
    leaf baud-rate {
      type string {
        length "1..20";
      }
      description
        "Baud-Rate in GBd with precision 0.0000001";
    }
  }

  augment "/oc-platform:components/oc-platform:component/oc-opt-term:optical-channel" {
    description
      "This augment extends the configuration data of
            'oc-opt-term:terminal-optical-channel-top'";
    container extended {
      description
        "Enclosing container for the list of Subsea parameters";
      container config {
        description
          "Extended Configuration parameters";
        leaf rx-voa-target-power {
          type int32 {
            range "-190..30";
          }
          description
            "Receive Target Power in increments of 0.1 dBm
             Default value is -5 dBm";
        }
        leaf rx-voa-fixed-ratio {
          type int32 {
            range "100..1700";
          }
          description
            "Receive Ratio of Optical Attenuation in
             increments of 0.01 dB Default value is 15 dB";
        }
        leaf fastpoll-sop-enable {
          type boolean;
          description
            "Receive Fastpoll status if it is enabled or
             disabled";
        }
        uses terminal-device-optical-channel-ext-info;
      }
      container state {
        config false;
        description
          "Extended Operational parameters";
        leaf rx-voa-target-power {
          type string;
          description
            "Receive Target Power in increments of 0.1 dBm
             Default value is -5 dBm";
        }
        leaf rx-voa-fixed-ratio {
          type string;
          description
            "Receive Ratio of Optical Attenuation in
             increments of 0.01 dB Default value is 15 dB";
        }
        leaf fastpoll-sop-enable {
          type boolean;
          description
            "Receive Fastpoll status if it is enabled or
             disabled";
        }
        uses terminal-device-optical-channel-ext-info;
      }
      container thresholds {
        description
          "Enclosing container for alarm thresholds.";
        container config {
          description
            "Extended Thresholds Configuration parameters";
          leaf input-signal-power-lower {
            type decimal64 {
              fraction-digits 2;
            }
            units "dBm";
            description
              "Lower power threshold for laser input power
                       in unit of 0.01dBm";
          }
          leaf input-signal-power-upper {
            type decimal64 {
              fraction-digits 2;
            }
            units "dBm";
            description
              "Upper power threshold for laser input power
                       in unit of 0.01dBm";
          }
        }
        container state {
          config false;
          description
            "Extended Thresholds Operational parameters";
          leaf input-signal-power-lower {
            type decimal64 {
              fraction-digits 2;
            }
            description
              "Lower power threshold for laser input power
                    in unit of 0.01dBm";
          }
          leaf input-signal-power-upper {
            type decimal64 {
              fraction-digits 2;
            }
            description
              "Upper power threshold for laser input power
                       in unit of 0.01dBm";
          }
        }
      }
    }
  }
}
