submodule Cisco-IOS-XR-Subscriber-infra-subdb-oper-sub2 {
  belongs-to Cisco-IOS-XR-Subscriber-infra-subdb-oper {
    prefix Cisco-IOS-XR-Subscriber-infra-subdb-oper;
  }

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR Subscriber-infra-subdb package operational data.
     
     Copyright (c) 2013-2023 by Cisco Systems, Inc.
     All rights reserved.";

  revision 2023-06-06 {
    description
      "Added new bag for SIR flapped process information
       2021-11-29
         Added new statistics to SIR flap history.
       2021-09-17
         Adding new bag for retrieving subdb sirflap history .";
    semver:module-version "2.2.0";
  }
  revision 2021-02-22 {
    description
      "Adding yang support to retrive server connection time-stats.";
    semver:module-version "2.1.0";
  }
  revision 2020-04-02 {
    description
      "Added new bag for Subscriber database transition states and cfg object types.";
    semver:module-version "2.0.0";
  }
  revision 2019-04-05 {
    description
      "Establish semantic version baseline.";
    semver:module-version "1.0.1";
  }
  revision 2018-09-28 {
    description
      "Fixed Subscriber database Association.";
  }
  revision 2015-11-09 {
    description
      "IOS XR 6.0 revision.";
  }

  typedef Subdb-sir-state {
    type enumeration {
      enum "sub-db-sir-state-up" {
        value 0;
        description
          "SIR in Up State";
      }
      enum "sub-db-sir-state-down" {
        value 1;
        description
          "SIR in Down State";
      }
      enum "sub-db-sir-state-unknown" {
        value 2;
        description
          "SIR in Unknown State";
      }
    }
    description
      "Subdb sir state";
  }

  typedef Subdb-req-time-stats-id {
    type enumeration {
      enum "activate-time-stats" {
        description
          "activate time stats";
      }
      enum "config-gen-time-stats" {
        description
          "config gen time stats";
      }
      enum "config-done-time-stats" {
        description
          "config done time stats";
      }
      enum "apply-time-stats" {
        description
          "apply time stats";
      }
      enum "time-stats-max" {
        description
          "time stats max";
      }
    }
    description
      "Subdb req time stats id";
  }

  grouping SUBDB-SIR-EVENT-PROCESS-INFO {
    description
      "SIR event process info";
    leaf pid {
      type uint32;
      description
        "PID of process involved in SIR flap";
    }
    leaf jid {
      type uint32;
      description
        "JID of process involved in SIR flap";
    }
    leaf process-name {
      type string {
        length "0..32";
      }
      description
        "Name of process involved in SIR flap";
    }
  }

  grouping SUBDB-SIR-STATE-INFO-BAG {
    description
      "SIR state in Subscriber Database";
    container publisher {
      description
        "SIR publisher Process Info";
      uses SUBDB-SIR-EVENT-PROCESS-INFO;
    }
    container owner {
      description
        "SIR owner Process Info";
      uses SUBDB-SIR-EVENT-PROCESS-INFO;
    }
    leaf sir-state {
      type Subdb-sir-state;
      description
        "Process Subscriber Infra Readiness state";
      xr:event-telemetry "Subscribe Telemetry Event";
    }
    leaf sir-flap-reason {
      type string {
        length "0..255";
      }
      description
        "SIR flap reason";
    }
  }

  grouping SUBDB-REQ-TIME-STATS-BAG {
    description
      "SUBDB REQ TIME STATS BAG";
    leaf request-count {
      type uint32;
      description
        "RequestCount";
    }
    leaf accumulative-time-seconds {
      type uint32;
      units "second";
      description
        "Acumulative time seconds";
    }
    leaf accumulative-time-nano-seconds {
      type uint32;
      units "nanosecond";
      description
        "Acumulative time nano-seconds";
    }
    leaf average-time-seconds {
      type uint32;
      units "second";
      description
        "Average time seconds";
    }
    leaf average-time-nano-seconds {
      type uint32;
      units "nanosecond";
      description
        "Average time nano-seconds";
    }
    leaf minimum-time-seconds {
      type uint32;
      units "second";
      description
        "Minimum time seconds";
    }
    leaf minimum-time-nano-seconds {
      type uint32;
      units "nanosecond";
      description
        "Minimum time nano-seconds";
    }
    leaf maximum-time-seconds {
      type uint32;
      units "second";
      description
        "Maximum time seconds";
    }
    leaf maximum-time-nano-seconds {
      type uint32;
      units "nanosecond";
      description
        "Maximum time nano-seconds";
    }
    leaf create-timestamp-for-maximum-seconds {
      type uint32;
      units "second";
      description
        "Create timestamp (seconds) for max time session";
    }
    leaf create-timestamp-for-maximum-nano-seconds {
      type uint32;
      units "nanosecond";
      description
        "Create timestamp (nano-seconds) for max time
         session";
    }
    leaf sub-label-for-maximum {
      type uint32;
      description
        "Sub-label for max time session";
    }
  }

  grouping SUBDB-SERVER-TIMESTAT-INFO {
    description
      "per client timestat";
    container time-statistics {
      description
        "Time Statistics";
      uses SUBDB-REQ-TIME-STATS-BAG;
    }
    leaf client-name-xr {
      type string;
      description
        "Subdb Client name";
    }
    leaf timestat-index {
      type Subdb-req-time-stats-id;
      description
        "Type of statistics";
    }
  }

  grouping SUBDB-SUBSCRIBER-IN-STATE-COUNTS {
    description
      "SUBDB SUBSCRIBER IN STATE COUNTS";
    leaf init-state {
      type uint32;
      description
        "Sessions in initialized state";
    }
    leaf destroying-state {
      type uint32;
      description
        "Sessions in Destroying state";
    }
    leaf config-gen-state {
      type uint32;
      description
        "Sessions in Config gen state";
    }
    leaf fat-gen-state {
      type uint32;
      description
        "Sessions in Fat gen state";
    }
    leaf config-apply-state {
      type uint32;
      description
        "Sessions in Config apply state";
    }
    leaf config-done-state {
      type uint32;
      description
        "Sessions in Config done state";
    }
    leaf config-unapply-state {
      type uint32;
      description
        "Sessions in Config unapply state";
    }
    leaf config-error-state {
      type uint32;
      description
        "Sessions in Config error state";
    }
    leaf error-state {
      type uint32;
      description
        "Sessions in error state";
    }
    leaf pre-sync-state {
      type uint32;
      description
        "Sessions in pre sync state";
    }
    leaf sync-state {
      type uint32;
      description
        "Sessions in sync state";
    }
  }

  grouping SUBDB-CFG-OBJECT-TYPE {
    description
      "SUBDB CFG OBJECT TYPE";
    leaf object-type-min {
      type uint32;
      description
        "Object type min";
    }
    leaf object-type-user-profile {
      type uint32;
      description
        "Object type user profile";
    }
    leaf object-type-service-profile {
      type uint32;
      description
        "Object type service profile";
    }
    leaf object-type-subsc-svc-template {
      type uint32;
      description
        "Object type subsc svc template";
    }
    leaf object-type-ppp-template {
      type uint32;
      description
        "Object type ppp template";
    }
    leaf object-type-ip-sub-template {
      type uint32;
      description
        "Object type ipsub template";
    }
    leaf object-type-sub-template {
      type uint32;
      description
        "Object type sub template";
    }
  }

  grouping SUBDB-SUMMARY-COUNTS-BAG {
    description
      "SUBDB SUMMARY COUNTS BAG";
    container subdb-obj-counts-by-type {
      description
        "The count of the various configuration objects
         by type";
      uses SUBDB-CFG-OBJECT-TYPE;
    }
    container subscribers-in-state {
      description
        "Number of subscribers in the various states";
      uses SUBDB-SUBSCRIBER-IN-STATE-COUNTS;
    }
    container num-transitions-through-state {
      description
        "Cumulative number of transitions through the
         various states";
      uses SUBDB-SUBSCRIBER-IN-STATE-COUNTS;
    }
    leaf assoc-db-entries {
      type uint32;
      description
        "Number of Entries in Association DB";
    }
    leaf assoc-db-associations {
      type uint32;
      description
        "Number of Associations in Association DB";
    }
    leaf derived-db-entries {
      type uint32;
      description
        "Number of Entries in Derived DB";
    }
    leaf config-db-entries {
      type uint32;
      description
        "Number of Entries in Configuration DB";
    }
    leaf interface-db-entries {
      type uint32;
      description
        "Number of Entries in Interface DB";
    }
    leaf num-ipsub-dhcp {
      type uint32;
      description
        "Number of IPSUB DHCP subscribers";
    }
    leaf num-ipsub-inband {
      type uint32;
      description
        "Number of IPSUB Inband subscribers";
    }
    leaf num-pppoe {
      type uint32;
      description
        "Number of PPPOE subscribers";
    }
  }
}
