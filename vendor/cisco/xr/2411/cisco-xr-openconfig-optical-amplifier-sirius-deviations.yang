//*************  DO-NOT EDIT  **************
//*********** Auto-generated file ********** 

 module cisco-xr-openconfig-optical-amplifier-deviations {

  prefix  "oc-opt-ampdevs";

  namespace "http://cisco.com/ns/yang/cisco-xr-openconfig-optical-amplifier-deviations";

  import openconfig-optical-amplifier { prefix oc-opt-amp; }

  organization "Cisco Systems, Inc.";

  contact
    "Cisco Systems, Inc.
     Customer Service

     Postal: 170 West Tasman Drive
     San Jose, CA 95134

     Tel: +1 800 553-NETS

     E-mail: cs-yang@cisco.com";

  description
    "This module contains a set of deviations for 

     openconfig-optical-amplifier.yang@2019-12-06 

     on Cisco IOS-XR devices.

     Copyright (c) 2017 by Cisco Systems, Inc.
     All rights reserved.";

  revision "2023-05-05" {
    description
      "Initial revision applicable to IOS-XR 6.4.1";
  }


  deviation /oc-opt-amp:optical-amplifier/oc-opt-amp:amplifiers/oc-opt-amp:amplifier/oc-opt-amp:state/oc-opt-amp:component {
    deviate not-supported;
  }

  deviation /oc-opt-amp:optical-amplifier/oc-opt-amp:amplifiers/oc-opt-amp:amplifier/oc-opt-amp:state/oc-opt-amp:actual-gain/oc-opt-amp:instant {
    deviate not-supported;
  }

  deviation /oc-opt-amp:optical-amplifier/oc-opt-amp:amplifiers/oc-opt-amp:amplifier/oc-opt-amp:state/oc-opt-amp:actual-gain/oc-opt-amp:avg {
    deviate not-supported;
  }

  deviation /oc-opt-amp:optical-amplifier/oc-opt-amp:amplifiers/oc-opt-amp:amplifier/oc-opt-amp:state/oc-opt-amp:actual-gain/oc-opt-amp:min {
    deviate not-supported;
  }

  deviation /oc-opt-amp:optical-amplifier/oc-opt-amp:amplifiers/oc-opt-amp:amplifier/oc-opt-amp:state/oc-opt-amp:actual-gain/oc-opt-amp:max {
    deviate not-supported;
  }

  deviation /oc-opt-amp:optical-amplifier/oc-opt-amp:amplifiers/oc-opt-amp:amplifier/oc-opt-amp:state/oc-opt-amp:actual-gain/oc-opt-amp:interval {
    deviate not-supported;
  }

  deviation /oc-opt-amp:optical-amplifier/oc-opt-amp:amplifiers/oc-opt-amp:amplifier/oc-opt-amp:state/oc-opt-amp:actual-gain/oc-opt-amp:min-time {
    deviate not-supported;
  }

  deviation /oc-opt-amp:optical-amplifier/oc-opt-amp:amplifiers/oc-opt-amp:amplifier/oc-opt-amp:state/oc-opt-amp:actual-gain/oc-opt-amp:max-time {
    deviate not-supported;
  }

  deviation /oc-opt-amp:optical-amplifier/oc-opt-amp:amplifiers/oc-opt-amp:amplifier/oc-opt-amp:state/oc-opt-amp:actual-gain-tilt/oc-opt-amp:instant {
    deviate not-supported;
  }

  deviation /oc-opt-amp:optical-amplifier/oc-opt-amp:amplifiers/oc-opt-amp:amplifier/oc-opt-amp:state/oc-opt-amp:actual-gain-tilt/oc-opt-amp:avg {
    deviate not-supported;
  }

  deviation /oc-opt-amp:optical-amplifier/oc-opt-amp:amplifiers/oc-opt-amp:amplifier/oc-opt-amp:state/oc-opt-amp:actual-gain-tilt/oc-opt-amp:min {
    deviate not-supported;
  }

  deviation /oc-opt-amp:optical-amplifier/oc-opt-amp:amplifiers/oc-opt-amp:amplifier/oc-opt-amp:state/oc-opt-amp:actual-gain-tilt/oc-opt-amp:max {
    deviate not-supported;
  }

  deviation /oc-opt-amp:optical-amplifier/oc-opt-amp:amplifiers/oc-opt-amp:amplifier/oc-opt-amp:state/oc-opt-amp:actual-gain-tilt/oc-opt-amp:interval {
    deviate not-supported;
  }

  deviation /oc-opt-amp:optical-amplifier/oc-opt-amp:amplifiers/oc-opt-amp:amplifier/oc-opt-amp:state/oc-opt-amp:actual-gain-tilt/oc-opt-amp:min-time {
    deviate not-supported;
  }

  deviation /oc-opt-amp:optical-amplifier/oc-opt-amp:amplifiers/oc-opt-amp:amplifier/oc-opt-amp:state/oc-opt-amp:actual-gain-tilt/oc-opt-amp:max-time {
    deviate not-supported;
  }

  deviation /oc-opt-amp:optical-amplifier/oc-opt-amp:amplifiers/oc-opt-amp:amplifier/oc-opt-amp:state/oc-opt-amp:input-power-total/oc-opt-amp:instant {
    deviate not-supported;
  }

  deviation /oc-opt-amp:optical-amplifier/oc-opt-amp:amplifiers/oc-opt-amp:amplifier/oc-opt-amp:state/oc-opt-amp:input-power-total/oc-opt-amp:avg {
    deviate not-supported;
  }

  deviation /oc-opt-amp:optical-amplifier/oc-opt-amp:amplifiers/oc-opt-amp:amplifier/oc-opt-amp:state/oc-opt-amp:input-power-total/oc-opt-amp:min {
    deviate not-supported;
  }

  deviation /oc-opt-amp:optical-amplifier/oc-opt-amp:amplifiers/oc-opt-amp:amplifier/oc-opt-amp:state/oc-opt-amp:input-power-total/oc-opt-amp:max {
    deviate not-supported;
  }

  deviation /oc-opt-amp:optical-amplifier/oc-opt-amp:amplifiers/oc-opt-amp:amplifier/oc-opt-amp:state/oc-opt-amp:input-power-total/oc-opt-amp:interval {
    deviate not-supported;
  }

  deviation /oc-opt-amp:optical-amplifier/oc-opt-amp:amplifiers/oc-opt-amp:amplifier/oc-opt-amp:state/oc-opt-amp:input-power-total/oc-opt-amp:min-time {
    deviate not-supported;
  }

  deviation /oc-opt-amp:optical-amplifier/oc-opt-amp:amplifiers/oc-opt-amp:amplifier/oc-opt-amp:state/oc-opt-amp:input-power-total/oc-opt-amp:max-time {
    deviate not-supported;
  }

  deviation /oc-opt-amp:optical-amplifier/oc-opt-amp:amplifiers/oc-opt-amp:amplifier/oc-opt-amp:state/oc-opt-amp:input-power-c-band/oc-opt-amp:instant {
    deviate not-supported;
  }

  deviation /oc-opt-amp:optical-amplifier/oc-opt-amp:amplifiers/oc-opt-amp:amplifier/oc-opt-amp:state/oc-opt-amp:input-power-c-band/oc-opt-amp:avg {
    deviate not-supported;
  }

  deviation /oc-opt-amp:optical-amplifier/oc-opt-amp:amplifiers/oc-opt-amp:amplifier/oc-opt-amp:state/oc-opt-amp:input-power-c-band/oc-opt-amp:min {
    deviate not-supported;
  }

  deviation /oc-opt-amp:optical-amplifier/oc-opt-amp:amplifiers/oc-opt-amp:amplifier/oc-opt-amp:state/oc-opt-amp:input-power-c-band/oc-opt-amp:max {
    deviate not-supported;
  }

  deviation /oc-opt-amp:optical-amplifier/oc-opt-amp:amplifiers/oc-opt-amp:amplifier/oc-opt-amp:state/oc-opt-amp:input-power-c-band/oc-opt-amp:interval {
    deviate not-supported;
  }

  deviation /oc-opt-amp:optical-amplifier/oc-opt-amp:amplifiers/oc-opt-amp:amplifier/oc-opt-amp:state/oc-opt-amp:input-power-c-band/oc-opt-amp:min-time {
    deviate not-supported;
  }

  deviation /oc-opt-amp:optical-amplifier/oc-opt-amp:amplifiers/oc-opt-amp:amplifier/oc-opt-amp:state/oc-opt-amp:input-power-c-band/oc-opt-amp:max-time {
    deviate not-supported;
  }

  deviation /oc-opt-amp:optical-amplifier/oc-opt-amp:amplifiers/oc-opt-amp:amplifier/oc-opt-amp:state/oc-opt-amp:input-power-l-band/oc-opt-amp:instant {
    deviate not-supported;
  }

  deviation /oc-opt-amp:optical-amplifier/oc-opt-amp:amplifiers/oc-opt-amp:amplifier/oc-opt-amp:state/oc-opt-amp:input-power-l-band/oc-opt-amp:avg {
    deviate not-supported;
  }

  deviation /oc-opt-amp:optical-amplifier/oc-opt-amp:amplifiers/oc-opt-amp:amplifier/oc-opt-amp:state/oc-opt-amp:input-power-l-band/oc-opt-amp:min {
    deviate not-supported;
  }

  deviation /oc-opt-amp:optical-amplifier/oc-opt-amp:amplifiers/oc-opt-amp:amplifier/oc-opt-amp:state/oc-opt-amp:input-power-l-band/oc-opt-amp:max {
    deviate not-supported;
  }

  deviation /oc-opt-amp:optical-amplifier/oc-opt-amp:amplifiers/oc-opt-amp:amplifier/oc-opt-amp:state/oc-opt-amp:input-power-l-band/oc-opt-amp:interval {
    deviate not-supported;
  }

  deviation /oc-opt-amp:optical-amplifier/oc-opt-amp:amplifiers/oc-opt-amp:amplifier/oc-opt-amp:state/oc-opt-amp:input-power-l-band/oc-opt-amp:min-time {
    deviate not-supported;
  }

  deviation /oc-opt-amp:optical-amplifier/oc-opt-amp:amplifiers/oc-opt-amp:amplifier/oc-opt-amp:state/oc-opt-amp:input-power-l-band/oc-opt-amp:max-time {
    deviate not-supported;
  }

  deviation /oc-opt-amp:optical-amplifier/oc-opt-amp:amplifiers/oc-opt-amp:amplifier/oc-opt-amp:state/oc-opt-amp:output-power-total/oc-opt-amp:instant {
    deviate not-supported;
  }

  deviation /oc-opt-amp:optical-amplifier/oc-opt-amp:amplifiers/oc-opt-amp:amplifier/oc-opt-amp:state/oc-opt-amp:output-power-total/oc-opt-amp:avg {
    deviate not-supported;
  }

  deviation /oc-opt-amp:optical-amplifier/oc-opt-amp:amplifiers/oc-opt-amp:amplifier/oc-opt-amp:state/oc-opt-amp:output-power-total/oc-opt-amp:min {
    deviate not-supported;
  }

  deviation /oc-opt-amp:optical-amplifier/oc-opt-amp:amplifiers/oc-opt-amp:amplifier/oc-opt-amp:state/oc-opt-amp:output-power-total/oc-opt-amp:max {
    deviate not-supported;
  }

  deviation /oc-opt-amp:optical-amplifier/oc-opt-amp:amplifiers/oc-opt-amp:amplifier/oc-opt-amp:state/oc-opt-amp:output-power-total/oc-opt-amp:interval {
    deviate not-supported;
  }

  deviation /oc-opt-amp:optical-amplifier/oc-opt-amp:amplifiers/oc-opt-amp:amplifier/oc-opt-amp:state/oc-opt-amp:output-power-total/oc-opt-amp:min-time {
    deviate not-supported;
  }

  deviation /oc-opt-amp:optical-amplifier/oc-opt-amp:amplifiers/oc-opt-amp:amplifier/oc-opt-amp:state/oc-opt-amp:output-power-total/oc-opt-amp:max-time {
    deviate not-supported;
  }

  deviation /oc-opt-amp:optical-amplifier/oc-opt-amp:amplifiers/oc-opt-amp:amplifier/oc-opt-amp:state/oc-opt-amp:output-power-c-band/oc-opt-amp:instant {
    deviate not-supported;
  }

  deviation /oc-opt-amp:optical-amplifier/oc-opt-amp:amplifiers/oc-opt-amp:amplifier/oc-opt-amp:state/oc-opt-amp:output-power-c-band/oc-opt-amp:avg {
    deviate not-supported;
  }

  deviation /oc-opt-amp:optical-amplifier/oc-opt-amp:amplifiers/oc-opt-amp:amplifier/oc-opt-amp:state/oc-opt-amp:output-power-c-band/oc-opt-amp:min {
    deviate not-supported;
  }

  deviation /oc-opt-amp:optical-amplifier/oc-opt-amp:amplifiers/oc-opt-amp:amplifier/oc-opt-amp:state/oc-opt-amp:output-power-c-band/oc-opt-amp:max {
    deviate not-supported;
  }

  deviation /oc-opt-amp:optical-amplifier/oc-opt-amp:amplifiers/oc-opt-amp:amplifier/oc-opt-amp:state/oc-opt-amp:output-power-c-band/oc-opt-amp:interval {
    deviate not-supported;
  }

  deviation /oc-opt-amp:optical-amplifier/oc-opt-amp:amplifiers/oc-opt-amp:amplifier/oc-opt-amp:state/oc-opt-amp:output-power-c-band/oc-opt-amp:min-time {
    deviate not-supported;
  }

  deviation /oc-opt-amp:optical-amplifier/oc-opt-amp:amplifiers/oc-opt-amp:amplifier/oc-opt-amp:state/oc-opt-amp:output-power-c-band/oc-opt-amp:max-time {
    deviate not-supported;
  }

  deviation /oc-opt-amp:optical-amplifier/oc-opt-amp:amplifiers/oc-opt-amp:amplifier/oc-opt-amp:state/oc-opt-amp:output-power-l-band/oc-opt-amp:instant {
    deviate not-supported;
  }

  deviation /oc-opt-amp:optical-amplifier/oc-opt-amp:amplifiers/oc-opt-amp:amplifier/oc-opt-amp:state/oc-opt-amp:output-power-l-band/oc-opt-amp:avg {
    deviate not-supported;
  }

  deviation /oc-opt-amp:optical-amplifier/oc-opt-amp:amplifiers/oc-opt-amp:amplifier/oc-opt-amp:state/oc-opt-amp:output-power-l-band/oc-opt-amp:min {
    deviate not-supported;
  }

  deviation /oc-opt-amp:optical-amplifier/oc-opt-amp:amplifiers/oc-opt-amp:amplifier/oc-opt-amp:state/oc-opt-amp:output-power-l-band/oc-opt-amp:max {
    deviate not-supported;
  }

  deviation /oc-opt-amp:optical-amplifier/oc-opt-amp:amplifiers/oc-opt-amp:amplifier/oc-opt-amp:state/oc-opt-amp:output-power-l-band/oc-opt-amp:interval {
    deviate not-supported;
  }

  deviation /oc-opt-amp:optical-amplifier/oc-opt-amp:amplifiers/oc-opt-amp:amplifier/oc-opt-amp:state/oc-opt-amp:output-power-l-band/oc-opt-amp:min-time {
    deviate not-supported;
  }

  deviation /oc-opt-amp:optical-amplifier/oc-opt-amp:amplifiers/oc-opt-amp:amplifier/oc-opt-amp:state/oc-opt-amp:output-power-l-band/oc-opt-amp:max-time {
    deviate not-supported;
  }

  deviation /oc-opt-amp:optical-amplifier/oc-opt-amp:amplifiers/oc-opt-amp:amplifier/oc-opt-amp:state/oc-opt-amp:laser-bias-current/oc-opt-amp:instant {
    deviate not-supported;
  }

  deviation /oc-opt-amp:optical-amplifier/oc-opt-amp:amplifiers/oc-opt-amp:amplifier/oc-opt-amp:state/oc-opt-amp:laser-bias-current/oc-opt-amp:avg {
    deviate not-supported;
  }

  deviation /oc-opt-amp:optical-amplifier/oc-opt-amp:amplifiers/oc-opt-amp:amplifier/oc-opt-amp:state/oc-opt-amp:laser-bias-current/oc-opt-amp:min {
    deviate not-supported;
  }

  deviation /oc-opt-amp:optical-amplifier/oc-opt-amp:amplifiers/oc-opt-amp:amplifier/oc-opt-amp:state/oc-opt-amp:laser-bias-current/oc-opt-amp:max {
    deviate not-supported;
  }

  deviation /oc-opt-amp:optical-amplifier/oc-opt-amp:amplifiers/oc-opt-amp:amplifier/oc-opt-amp:state/oc-opt-amp:laser-bias-current/oc-opt-amp:interval {
    deviate not-supported;
  }

  deviation /oc-opt-amp:optical-amplifier/oc-opt-amp:amplifiers/oc-opt-amp:amplifier/oc-opt-amp:state/oc-opt-amp:laser-bias-current/oc-opt-amp:min-time {
    deviate not-supported;
  }

  deviation /oc-opt-amp:optical-amplifier/oc-opt-amp:amplifiers/oc-opt-amp:amplifier/oc-opt-amp:state/oc-opt-amp:laser-bias-current/oc-opt-amp:max-time {
    deviate not-supported;
  }

  deviation /oc-opt-amp:optical-amplifier/oc-opt-amp:amplifiers/oc-opt-amp:amplifier/oc-opt-amp:state/oc-opt-amp:optical-return-loss/oc-opt-amp:instant {
    deviate not-supported;
  }

  deviation /oc-opt-amp:optical-amplifier/oc-opt-amp:amplifiers/oc-opt-amp:amplifier/oc-opt-amp:state/oc-opt-amp:optical-return-loss/oc-opt-amp:avg {
    deviate not-supported;
  }

  deviation /oc-opt-amp:optical-amplifier/oc-opt-amp:amplifiers/oc-opt-amp:amplifier/oc-opt-amp:state/oc-opt-amp:optical-return-loss/oc-opt-amp:min {
    deviate not-supported;
  }

  deviation /oc-opt-amp:optical-amplifier/oc-opt-amp:amplifiers/oc-opt-amp:amplifier/oc-opt-amp:state/oc-opt-amp:optical-return-loss/oc-opt-amp:max {
    deviate not-supported;
  }

  deviation /oc-opt-amp:optical-amplifier/oc-opt-amp:amplifiers/oc-opt-amp:amplifier/oc-opt-amp:state/oc-opt-amp:optical-return-loss/oc-opt-amp:interval {
    deviate not-supported;
  }

  deviation /oc-opt-amp:optical-amplifier/oc-opt-amp:amplifiers/oc-opt-amp:amplifier/oc-opt-amp:state/oc-opt-amp:optical-return-loss/oc-opt-amp:min-time {
    deviate not-supported;
  }

  deviation /oc-opt-amp:optical-amplifier/oc-opt-amp:amplifiers/oc-opt-amp:amplifier/oc-opt-amp:state/oc-opt-amp:optical-return-loss/oc-opt-amp:max-time {
    deviate not-supported;
  }

  deviation /oc-opt-amp:optical-amplifier/oc-opt-amp:supervisory-channels/oc-opt-amp:supervisory-channel/oc-opt-amp:config/oc-opt-amp:interface {
    deviate not-supported;
  }

  deviation /oc-opt-amp:optical-amplifier/oc-opt-amp:supervisory-channels/oc-opt-amp:supervisory-channel/oc-opt-amp:state/oc-opt-amp:interface {
    deviate not-supported;
  }

  deviation /oc-opt-amp:optical-amplifier/oc-opt-amp:supervisory-channels/oc-opt-amp:supervisory-channel/oc-opt-amp:state/oc-opt-amp:input-power/oc-opt-amp:instant {
    deviate not-supported;
  }

  deviation /oc-opt-amp:optical-amplifier/oc-opt-amp:supervisory-channels/oc-opt-amp:supervisory-channel/oc-opt-amp:state/oc-opt-amp:input-power/oc-opt-amp:avg {
    deviate not-supported;
  }

  deviation /oc-opt-amp:optical-amplifier/oc-opt-amp:supervisory-channels/oc-opt-amp:supervisory-channel/oc-opt-amp:state/oc-opt-amp:input-power/oc-opt-amp:min {
    deviate not-supported;
  }

  deviation /oc-opt-amp:optical-amplifier/oc-opt-amp:supervisory-channels/oc-opt-amp:supervisory-channel/oc-opt-amp:state/oc-opt-amp:input-power/oc-opt-amp:max {
    deviate not-supported;
  }

  deviation /oc-opt-amp:optical-amplifier/oc-opt-amp:supervisory-channels/oc-opt-amp:supervisory-channel/oc-opt-amp:state/oc-opt-amp:input-power/oc-opt-amp:interval {
    deviate not-supported;
  }

  deviation /oc-opt-amp:optical-amplifier/oc-opt-amp:supervisory-channels/oc-opt-amp:supervisory-channel/oc-opt-amp:state/oc-opt-amp:input-power/oc-opt-amp:min-time {
    deviate not-supported;
  }

  deviation /oc-opt-amp:optical-amplifier/oc-opt-amp:supervisory-channels/oc-opt-amp:supervisory-channel/oc-opt-amp:state/oc-opt-amp:input-power/oc-opt-amp:max-time {
    deviate not-supported;
  }

  deviation /oc-opt-amp:optical-amplifier/oc-opt-amp:supervisory-channels/oc-opt-amp:supervisory-channel/oc-opt-amp:state/oc-opt-amp:output-power/oc-opt-amp:instant {
    deviate not-supported;
  }

  deviation /oc-opt-amp:optical-amplifier/oc-opt-amp:supervisory-channels/oc-opt-amp:supervisory-channel/oc-opt-amp:state/oc-opt-amp:output-power/oc-opt-amp:avg {
    deviate not-supported;
  }

  deviation /oc-opt-amp:optical-amplifier/oc-opt-amp:supervisory-channels/oc-opt-amp:supervisory-channel/oc-opt-amp:state/oc-opt-amp:output-power/oc-opt-amp:min {
    deviate not-supported;
  }

  deviation /oc-opt-amp:optical-amplifier/oc-opt-amp:supervisory-channels/oc-opt-amp:supervisory-channel/oc-opt-amp:state/oc-opt-amp:output-power/oc-opt-amp:max {
    deviate not-supported;
  }

  deviation /oc-opt-amp:optical-amplifier/oc-opt-amp:supervisory-channels/oc-opt-amp:supervisory-channel/oc-opt-amp:state/oc-opt-amp:output-power/oc-opt-amp:interval {
    deviate not-supported;
  }

  deviation /oc-opt-amp:optical-amplifier/oc-opt-amp:supervisory-channels/oc-opt-amp:supervisory-channel/oc-opt-amp:state/oc-opt-amp:output-power/oc-opt-amp:min-time {
    deviate not-supported;
  }

  deviation /oc-opt-amp:optical-amplifier/oc-opt-amp:supervisory-channels/oc-opt-amp:supervisory-channel/oc-opt-amp:state/oc-opt-amp:output-power/oc-opt-amp:max-time {
    deviate not-supported;
  }

  deviation /oc-opt-amp:optical-amplifier/oc-opt-amp:supervisory-channels/oc-opt-amp:supervisory-channel/oc-opt-amp:state/oc-opt-amp:laser-bias-current/oc-opt-amp:instant {
    deviate not-supported;
  }

  deviation /oc-opt-amp:optical-amplifier/oc-opt-amp:supervisory-channels/oc-opt-amp:supervisory-channel/oc-opt-amp:state/oc-opt-amp:laser-bias-current/oc-opt-amp:avg {
    deviate not-supported;
  }

  deviation /oc-opt-amp:optical-amplifier/oc-opt-amp:supervisory-channels/oc-opt-amp:supervisory-channel/oc-opt-amp:state/oc-opt-amp:laser-bias-current/oc-opt-amp:min {
    deviate not-supported;
  }

  deviation /oc-opt-amp:optical-amplifier/oc-opt-amp:supervisory-channels/oc-opt-amp:supervisory-channel/oc-opt-amp:state/oc-opt-amp:laser-bias-current/oc-opt-amp:max {
    deviate not-supported;
  }

  deviation /oc-opt-amp:optical-amplifier/oc-opt-amp:supervisory-channels/oc-opt-amp:supervisory-channel/oc-opt-amp:state/oc-opt-amp:laser-bias-current/oc-opt-amp:interval {
    deviate not-supported;
  }

  deviation /oc-opt-amp:optical-amplifier/oc-opt-amp:supervisory-channels/oc-opt-amp:supervisory-channel/oc-opt-amp:state/oc-opt-amp:laser-bias-current/oc-opt-amp:min-time {
    deviate not-supported;
  }

  deviation /oc-opt-amp:optical-amplifier/oc-opt-amp:supervisory-channels/oc-opt-amp:supervisory-channel/oc-opt-amp:state/oc-opt-amp:laser-bias-current/oc-opt-amp:max-time {
    deviate not-supported;
  }

  deviation /oc-opt-amp:optical-amplifier/oc-opt-amp:supervisory-channels/oc-opt-amp:supervisory-channel/oc-opt-amp:state/oc-opt-amp:output-frequency {
    deviate not-supported;
  }


}
//total deviations:95
