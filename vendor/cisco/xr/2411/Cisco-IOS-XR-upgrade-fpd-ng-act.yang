module Cisco-IOS-XR-upgrade-fpd-ng-act {
  namespace "http://cisco.com/ns/yang/Cisco-IOS-XR-upgrade-fpd-ng-act";
  prefix upgrade-fpd-act;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR upgrade-fpd package action data.
     
     This module contains definitions
     for the following management objects:
       fpd: Field programmable device (FPD) operational data
     
     Copyright (c) 2013-2019, 2022 by Cisco Systems, Inc.
     All rights reserved.";

  revision 2019-10-01 {
    description
      "Made changes to be RFC6087 compliant";
    semver:module-version "1.1.0";
  }
  revision 2019-04-05 {
    description
      "Establish semantic version baseline.";
    semver:module-version "1.0.0";
  }
  revision 2017-04-04 {
    description
      "IOS XR 6.3.1 revision.";
  }

  rpc upgrade-fpd {
    description
      "Execute FPD upgrade";
    input {
      leaf location {
        type string;
        mandatory true;
        description
          "Location of the FPD to be upgraded";
      }
      leaf fpd {
        type string;
        mandatory true;
        description
          "name of the fpd to be upgraded";
      }
      leaf force {
        type empty;
        description
          "Force the upgrade process";
      }
    }
  }
}
