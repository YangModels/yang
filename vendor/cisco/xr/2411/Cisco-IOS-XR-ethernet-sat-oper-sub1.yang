submodule Cisco-IOS-XR-ethernet-sat-oper-sub1 {
  belongs-to Cisco-IOS-XR-ethernet-sat-oper {
    prefix Cisco-IOS-XR-ethernet-sat-oper;
  }

  import ietf-yang-types {
    prefix yang;
  }
  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR ethernet-sat package operational data.
     
     Copyright (c) 2013-2023 by Cisco Systems, Inc.
     All rights reserved.";

  revision 2023-06-19 {
    description
      "Add support for configuring the subtype used in SAT packets
       2022-12-13
         Add support for configuring the ethertype used in SAT packets
       2022-11-22
         Add support for specifying OAM level for loss measurement packets
       2022-10-24
         Add support for starting a SAT with optional source MAC addresses
       2022-07-20
         Add minimum-delay config item
       2021-12-10
         Add support for reporting packet-format
       2021-12-10
         Add burst config option";
    semver:module-version "1.2.0";
  }
  revision 2021-03-29 {
    description
      "Add support for reporting frame delay statistics";
    semver:module-version "1.1.0";
  }
  revision 2019-04-05 {
    description
      "Establish semantic version baseline.";
    semver:module-version "1.0.0";
  }
  revision 2015-11-09 {
    description
      "IOS XR 6.0 revision.";
  }

  typedef Sat-pkt-fmt {
    type enumeration {
      enum "sat-prf-fmt-mef-48" {
        description
          "sat prf fmt mef 48";
      }
      enum "sat-prf-fmt-lbm" {
        description
          "sat prf fmt lbm";
      }
    }
    description
      "Sat pkt fmt";
  }

  typedef Sat-mode {
    type enumeration {
      enum "sat-mode-invalid" {
        value 0;
        description
          "sat mode invalid";
      }
      enum "sat-mode-one-way" {
        value 248836892;
        description
          "sat mode one way";
      }
      enum "sat-mode-two-way" {
        value 248836893;
        description
          "sat mode two way";
      }
    }
    description
      "Sat mode";
  }

  typedef Sat-direction {
    type enumeration {
      enum "sat-direct-ion-invalid" {
        value 0;
        description
          "sat direct ion invalid";
      }
      enum "sat-direct-ion-external" {
        value 1578901335;
        description
          "sat direct ion external";
      }
      enum "sat-direct-ion-internal" {
        value 1578901336;
        description
          "sat direct ion internal";
      }
    }
    description
      "Sat direction";
  }

  typedef Sat-ma-permit {
    type enumeration {
      enum "sat-ma-permit-none" {
        value 0;
        description
          "sat ma permit none";
      }
      enum "sat-ma-permit-internal" {
        value 1;
        description
          "sat ma permit internal";
      }
      enum "sat-ma-permit-external" {
        value 2;
        description
          "sat ma permit external";
      }
      enum "sat-ma-permit-all" {
        value 3;
        description
          "sat ma permit all";
      }
      enum "sat-ma-permit-count" {
        value 4;
        description
          "sat ma permit count";
      }
    }
    description
      "Sat ma permit";
  }

  typedef Sat-ir-units {
    type enumeration {
      enum "sat-ir-units-kbps" {
        value 1197769489;
        description
          "sat ir units kbps";
      }
      enum "sat-ir-units-mbps" {
        value 1197769490;
        description
          "sat ir units mbps";
      }
      enum "sat-ir-units-gbps" {
        value 1197769491;
        description
          "sat ir units gbps";
      }
    }
    description
      "Sat ir units";
  }

  typedef Sat-ma-state {
    type enumeration {
      enum "sat-ma-state-invalid" {
        value 0;
        description
          "sat ma state invalid";
      }
      enum "sat-ma-state-enabled" {
        value 782787904;
        description
          "sat ma state enabled";
      }
      enum "sat-ma-state-running" {
        value 782787905;
        description
          "sat ma state running";
      }
      enum "sat-ma-state-completed" {
        value 782787906;
        description
          "sat ma state completed";
      }
      enum "sat-ma-state-aborted" {
        value 782787907;
        description
          "sat ma state aborted";
      }
    }
    description
      "Sat ma state";
  }

  grouping SAT-FRAME-DELAY-PARAMS-TYPE {
    description
      "SAT FRAME DELAY PARAMS TYPE";
    leaf frame-delay-collection-enabled {
      type int32;
      description
        "frame delay collection enabled";
    }
    leaf bin-count {
      type uint32;
      description
        "bin count";
    }
    leaf bin-width {
      type uint32;
      description
        "bin width";
    }
    leaf percentile {
      type uint32;
      description
        "percentile";
    }
    leaf minimum-delay {
      type uint32;
      description
        "minimum delay";
    }
  }

  grouping SAT-OAM-LEVEL-TYPE {
    description
      "SAT OAM LEVEL TYPE";
    leaf is-set {
      type int32;
      description
        "is set";
    }
    leaf value {
      type uint8;
      description
        "value";
    }
  }

  grouping SAT-PACKET-CONTENTS-TYPE {
    description
      "SAT PACKET CONTENTS TYPE";
    leaf emix {
      type int32;
      description
        "emix";
    }
    leaf sequence {
      type string {
        length "0..33";
      }
      description
        "sequence";
    }
    leaf u-value {
      type uint32;
      description
        "u value";
    }
    leaf size {
      type uint32;
      description
        "size";
    }
    leaf pseudo-random {
      type int32;
      description
        "pseudo random";
    }
    leaf hex-pattern {
      type uint8;
      description
        "hex pattern";
    }
  }

  grouping SAT-COS-TYPE {
    description
      "SAT COS TYPE";
    leaf is-set {
      type int32;
      description
        "is set";
    }
    leaf value {
      type uint8;
      description
        "value";
    }
  }

  grouping SAT-COLOR-AWARE-TYPE {
    description
      "SAT COLOR AWARE TYPE";
    container eir-cos {
      description
        "eir cos";
      uses SAT-COS-TYPE;
    }
    leaf is-color-aware {
      type int32;
      description
        "is color aware";
    }
    leaf cir-units {
      type Sat-ir-units;
      description
        "cir units";
    }
    leaf cir-value {
      type uint32;
      description
        "cir value";
    }
    leaf eir-dei {
      type int32;
      description
        "eir dei";
    }
  }

  grouping SAT-IR-RANGE-TYPE {
    description
      "SAT IR RANGE TYPE";
    leaf units {
      type Sat-ir-units;
      description
        "units";
    }
    leaf min-value {
      type uint32;
      description
        "min value";
    }
    leaf max-value {
      type uint32;
      description
        "max value";
    }
    leaf step-size {
      type uint32;
      description
        "step size";
    }
    leaf cbs {
      type uint32;
      description
        "cbs";
    }
  }

  grouping SAT-DURATION-TYPE {
    description
      "SAT DURATION TYPE";
    leaf is-per-step {
      type int32;
      description
        "is per step";
    }
    leaf seconds {
      type uint32;
      description
        "seconds";
    }
  }

  grouping ETHER-MACADDR-TYPE {
    description
      "ETHER MACADDR TYPE";
    leaf macaddr {
      type yang:hex-string;
      description
        "macaddr";
    }
  }

  grouping SAT-MA-PROFILE-BAG-TYPE {
    description
      "SAT MA PROFILE BAG TYPE";
    container destination {
      description
        "destination";
      uses ETHER-MACADDR-TYPE;
    }
    container source {
      description
        "source";
      uses ETHER-MACADDR-TYPE;
    }
    container duration {
      description
        "duration";
      uses SAT-DURATION-TYPE;
    }
    container ir-range {
      description
        "ir range";
      uses SAT-IR-RANGE-TYPE;
    }
    container color-aware {
      description
        "color aware";
      uses SAT-COLOR-AWARE-TYPE;
    }
    container packet-contents {
      description
        "packet contents";
      uses SAT-PACKET-CONTENTS-TYPE;
    }
    container outer-cos {
      description
        "outer cos";
      uses SAT-COS-TYPE;
    }
    container inner-cos {
      description
        "inner cos";
      uses SAT-COS-TYPE;
    }
    container oam-level {
      description
        "oam level";
      uses SAT-OAM-LEVEL-TYPE;
    }
    container frame-delay {
      description
        "frame delay";
      uses SAT-FRAME-DELAY-PARAMS-TYPE;
    }
    leaf name {
      type string;
      description
        "name";
    }
    leaf desc {
      type string;
      description
        "desc";
    }
    leaf direction {
      type Sat-direction;
      description
        "direction";
    }
    leaf mode {
      type Sat-mode;
      description
        "mode";
    }
    leaf packet-format {
      type Sat-pkt-fmt;
      description
        "packet format";
    }
    leaf combined-delay-loss {
      type int32;
      description
        "combined delay loss";
    }
    leaf ethertype-value {
      type uint16;
      description
        "ethertype value";
    }
    leaf subtype-value {
      type uint16;
      description
        "subtype value";
    }
  }

  grouping SAT-MA-OPER-FDR-BIN-TYPE {
    description
      "SAT MA OPER FDR BIN TYPE";
    leaf bin-min-fd {
      type uint32;
      description
        "bin min fd";
    }
    leaf bin-max-fd {
      type uint32;
      description
        "bin max fd";
    }
    leaf count {
      type uint64;
      description
        "count";
    }
  }

  grouping SAT-MA-OPER-FDR-RESULTS-TYPE {
    description
      "SAT MA OPER FDR RESULTS TYPE";
    leaf fdr {
      type uint32;
      description
        "fdr";
    }
    leaf percentile {
      type uint32;
      description
        "percentile";
    }
    leaf minimum-delay {
      type uint32;
      description
        "minimum delay";
    }
    list bins {
      description
        "bins";
      uses SAT-MA-OPER-FDR-BIN-TYPE;
    }
  }

  grouping SAT-XIR-RESULTS-TYPE {
    description
      "SAT XIR RESULTS TYPE";
    container fdr {
      description
        "fdr";
      uses SAT-MA-OPER-FDR-RESULTS-TYPE;
    }
    leaf tx-packets {
      type uint64;
      description
        "tx packets";
    }
    leaf rx-packets {
      type uint64;
      description
        "rx packets";
    }
    leaf tx-bytes {
      type uint64;
      description
        "tx bytes";
    }
    leaf rx-bytes {
      type uint64;
      description
        "rx bytes";
    }
    leaf frames-lost {
      type uint64;
      description
        "frames lost";
    }
    leaf fd-min {
      type uint64;
      description
        "fd min";
    }
    leaf fd-max {
      type uint64;
      description
        "fd max";
    }
    leaf fd-mean {
      type uint64;
      description
        "fd mean";
    }
    leaf fdv-min {
      type uint64;
      description
        "fdv min";
    }
    leaf fdv-max {
      type uint64;
      description
        "fdv max";
    }
    leaf fdv-avg {
      type uint64;
      description
        "fdv avg";
    }
    leaf fdv-not-supported {
      type int32;
      description
        "fdv not supported";
    }
    leaf out-of-order-pkt-cnt {
      type uint64;
      description
        "out of order pkt cnt";
    }
    leaf err-pkt-cnt {
      type uint64;
      description
        "err pkt cnt";
    }
  }

  grouping SAT-MA-OPER-RESULTS-TYPE {
    description
      "SAT MA OPER RESULTS TYPE";
    container cir {
      description
        "cir";
      uses SAT-XIR-RESULTS-TYPE;
    }
    container eir {
      description
        "eir";
      uses SAT-XIR-RESULTS-TYPE;
    }
  }

  grouping SAT-MA-OPER-PHASE-TYPE {
    description
      "SAT MA OPER PHASE TYPE";
    container results {
      description
        "Results for this phase";
      uses SAT-MA-OPER-RESULTS-TYPE;
    }
    leaf ir-units {
      type Sat-ir-units;
      description
        "Information rate units";
    }
    leaf ir-value {
      type uint32;
      description
        "Information rate value";
    }
  }

  grouping SAT-MA-OPER-TEST-STATUS {
    description
      "Sat MA Test Status";
    container profile {
      description
        "Test profile";
      uses SAT-MA-PROFILE-BAG-TYPE;
    }
    leaf interface-handle {
      type xr:Interface-name;
      description
        "Interface handle";
    }
    leaf interface-name-xr {
      type string;
      description
        "Interface name";
    }
    leaf state {
      type Sat-ma-state;
      description
        "Test state";
    }
    leaf permissions {
      type Sat-ma-permit;
      description
        "Permissions";
    }
    leaf abort-reason {
      type string;
      description
        "Abort reason for aborted SAT";
    }
    leaf seconds-remaining {
      type uint32;
      units "second";
      description
        "Seconds remaining on a running SAT";
    }
    leaf current-phase-number {
      type uint32;
      description
        "During a SAT, the current phase number (starting
         from 1)";
    }
    leaf has-results-mid-phase {
      type int32;
      description
        "Shows if the platform provide results during a
         SAT phase";
    }
    list phase {
      description
        "Test phases";
      uses SAT-MA-OPER-PHASE-TYPE;
    }
  }
}
