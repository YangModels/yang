submodule Cisco-IOS-XR-adt-oper-sub1 {
  belongs-to Cisco-IOS-XR-adt-oper {
    prefix Cisco-IOS-XR-adt-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR adt package operational data.
     
     Copyright (c) 2013-2020 by Cisco Systems, Inc.
     All rights reserved.";

  revision 2020-05-05 {
    description
      "IOS XR 7.3.1 Initial version.";
    semver:module-version "1.0.0";
  }
  revision 2019-04-05 {
    description
      "Establish semantic version baseline.";
  }
  revision 2015-11-09 {
    description
      "IOS XR 6.0 revision.";
  }

  grouping ADT-SENSOR-PATHS {
    description
      "Sensor paths";
    leaf sensor-path {
      type string;
      description
        "Sensor path ";
    }
    leaf cadence {
      type uint32;
      units "second";
      description
        "Cadence in seconds";
    }
    leaf is-implicitly-added {
      type uint8;
      description
        "Is implicity added sensor-path";
    }
    leaf subscription-id {
      type uint64;
      description
        "Subscription Id ";
    }
  }

  grouping ADT-SENSOR-GROUPS {
    description
      "Sensor groups";
    leaf sensor-group-name {
      type string;
      description
        "Sensor group name ";
    }
    list sensor-path {
      description
        "Sensor paths";
      uses ADT-SENSOR-PATHS;
    }
  }

  grouping ADT-SUBSCRIPTION-INFO {
    description
      "ADT subscription details";
    list sensor-group {
      description
        "Subscribed sensor groups";
      uses ADT-SENSOR-GROUPS;
    }
    list missed-collection {
      description
        "Missed sensor group collections ";
      uses ADT-SENSOR-GROUPS;
    }
  }

  grouping DETECTOR-STATISTICS {
    description
      "ADT detector statistics";
    leaf-list detector-state {
      type uint32;
      max-elements "4";
      description
        "detector state";
    }
  }

  grouping TUNER-STATISTICS {
    description
      "ADT tuner statistics";
    leaf tuner-state {
      type uint8;
      description
        "Current tuner state";
    }
    leaf sys-cpu-state {
      type uint8;
      description
        "system CPU state 1:OK 0:NOK";
    }
    leaf sys-mem-state {
      type uint8;
      description
        "system memory state 1:OK 0:NOK";
    }
    leaf proc-cpu-state {
      type uint8;
      description
        "adt process CPU state 1:OK 0:NOK";
    }
    leaf proc-soft-limit {
      type uint32;
      description
        "adt proc soft limit";
    }
    leaf proc-mem-state {
      type uint8;
      description
        "adt process  memory state 1:OK 0:NOK";
    }
    leaf default-path-collection-total {
      type uint64;
      description
        "total default path collections";
    }
    leaf default-path-collection-status {
      type uint8;
      description
        "status of default path collections 1:OK 0:NOK";
    }
    leaf user-path-collection-total {
      type uint64;
      description
        "total user path collections";
    }
    leaf user-path-collection-status {
      type uint8;
      description
        "status of user path collections 1:OK 0:NOK";
    }
    leaf time-in-curr-state {
      type uint64;
      units "second";
      description
        "time :seconds: spend in current state";
    }
    leaf sysdb-path-count {
      type uint64;
      description
        "count of sysdb paths collected by ADT";
    }
    leaf item-count {
      type uint64;
      description
        "item count collected by ADT";
    }
    leaf-list sys-cpu-stae {
      type uint32;
      max-elements "4";
      description
        "last 4 samples of system cpu";
    }
    leaf-list sys-mem-data {
      type uint32;
      max-elements "4";
      description
        "last 4 samples of system memory data";
    }
    leaf-list proc-cpu-stae {
      type uint32;
      max-elements "4";
      description
        "last 4 samples of adt process cpu";
    }
    leaf-list proc-mem-data {
      type uint32;
      max-elements "4";
      description
        "last 4 samples of adt process memory data";
    }
    leaf-list default-path-collection-missed-data {
      type uint32;
      max-elements "4";
      description
        "last 4 samples of missed collection for default
         paths";
    }
    leaf-list user-path-collection-missed-data {
      type uint32;
      max-elements "4";
      description
        "last 4 samples of missed collection for user
         paths";
    }
  }

  grouping MEMORY-STATISTICS {
    description
      "ADT memory statistics";
    leaf current-memory-total {
      type uint32;
      units "byte";
      description
        "Current memory usage Total in bytes";
    }
    leaf current-memory-py {
      type uint32;
      units "byte";
      description
        "Current memory usage Py in bytes";
    }
    leaf peak-memory-total {
      type uint32;
      units "byte";
      description
        "Peak memory usage Total in bytes";
    }
    leaf peak-memory-py {
      type uint32;
      units "byte";
      description
        "Peak memory usage Py in bytes";
    }
  }

  grouping OUTPUT-STATISTICS {
    description
      "ADT output statistics";
    leaf total-output-messages {
      type uint32;
      description
        "Total output messages from selector";
    }
    leaf total-notify {
      type uint32;
      description
        "Total ADT notifies";
    }
    leaf total-hints {
      type uint32;
      description
        "Total Hints";
    }
    leaf total-pending-selector-messages {
      type uint32;
      description
        "Total pending selector messages not pushed to
         MDT";
    }
    leaf total-mdt-reads {
      type uint32;
      description
        "Total MDT reads";
    }
    leaf total-edt-events {
      type uint32;
      description
        "Total EDT events";
    }
  }

  grouping INPUT-STATISTICS {
    description
      "ADT input statistics";
    leaf total-input-messages {
      type uint32;
      description
        "Total input messages received by pal";
    }
    leaf total-output-messages {
      type uint32;
      description
        "Total output messages send to collector";
    }
    leaf total-collection-errors {
      type uint32;
      description
        "Total Collection errors";
    }
    leaf total-decode-errors {
      type uint32;
      description
        "Total decode errors";
    }
    leaf total-bytes-received {
      type uint64;
      units "byte";
      description
        "Total bytes received from MDT sensor";
    }
    leaf total-bytes-sent {
      type uint64;
      units "byte";
      description
        "Total bytes sent to collector ";
    }
  }

  grouping ADT-STATISTICS {
    description
      "ADT statistics";
    container input-stats {
      description
        "Input statistics";
      uses INPUT-STATISTICS;
    }
    container output-stats {
      description
        "Output statistics";
      uses OUTPUT-STATISTICS;
    }
    container memory-stats {
      description
        "Memory statistics";
      uses MEMORY-STATISTICS;
    }
    container tuner-stats {
      description
        "Tuner statistics";
      uses TUNER-STATISTICS;
    }
    container detector-stats {
      description
        "Detector statistics";
      uses DETECTOR-STATISTICS;
    }
    leaf last-telemetry-message-timestamp {
      type uint64;
      description
        "Timestamp of last telemetry message received";
    }
    leaf last-selector-output-timestamp {
      type uint64;
      description
        "Timestanmp of last selector output";
    }
  }
}
