module Cisco-IOS-XR-um-sks-server-cfg {
  namespace "http://cisco.com/ns/yang/Cisco-IOS-XR-um-sks-server-cfg";
  prefix um-sks-server-cfg;

  import Cisco-IOS-XR-types {
    prefix xr;
  }
  import ietf-inet-types {
    prefix inet;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR sks-server package configuration.
     
     This YANG module augments the
     modules with configuration data.
     
     Copyright (c) 2022-2023 by Cisco Systems, Inc.
     All rights reserved.";

  revision 2023-08-28 {
    description
      "added pre-shared key support";
    semver:module-version "1.0.0";
  }
  revision 2023-02-06 {
    description
      "updated feature support";
  }
  revision 2022-12-22 {
    description
      "added support for http proxy";
  }
  revision 2022-11-11 {
    description
      "added support for server hostname";
  }
  revision 2022-11-08 {
    description
      "updated task and feature support";
  }
  revision 2022-10-14 {
    description
      "Initial release";
  }

  feature is-sks-server-supported {
    description
      "SKS server configuration support within this model";
  }

  container sks-server {
    if-feature "is-sks-server-supported";
    description
      "session key service";
    container profiles {
      description
        "session key service profile";
      list profile {
        key "profile-name";
        description
          "session key service profile";
        leaf profile-name {
          type xr:Cisco-ios-xr-string {
            length "1..127" {
              description
                "profile name";
            }
          }
          description
            "session key service profile";
        }
        container type {
          description
            "profile type";
          container remote {
            presence "Indicates a remote node is configured.";
            description
              "remote sks profile";
            container kme {
              presence "Indicates a kme node is configured.";
              description
                "exernal key management server configuration";
              container server {
                description
                  "Key management entity server configuration";
                leaf ipv4 {
                  type inet:ipv4-address-no-zone;
                  must "../port and not (../ipv6 or ../hostname)";
                  description
                    "IPv4 server";
                }
                leaf ipv6 {
                  type inet:ipv6-address-no-zone;
                  must "../port and not (../ipv4 or ../hostname)";
                  description
                    "IPv6 server";
                }
                leaf hostname {
                  type xr:Cisco-ios-xr-string {
                    length "1..255" {
                      description
                        "server hostname";
                    }
                    pattern "[a-zA-Z0-9_.-]+";
                  }
                  must "../port and not (../ipv4 or ../ipv6)";
                  description
                    "server hostname";
                }
                leaf port {
                  type uint32 {
                    range "1..65535" {
                      description
                        "Port Number";
                    }
                  }
                  must "(../ipv4 or ../ipv6 or ../hostname)";
                  description
                    "server port configuration";
                }
                leaf vrf {
                  type xr:Cisco-ios-xr-string {
                    length "1..31" {
                      description
                        "vrf name";
                    }
                  }
                  must "../port";
                  description
                    "vrf table";
                }
              }
              container psk {
                presence "Indicates a psk node is configured.";
                description
                  "authenticate via pre-shared key";
                leaf id {
                  type xr:Cisco-ios-xr-string {
                    length "1..127" {
                      description
                        "pre-shared key identity string";
                    }
                  }
                  must "../key/seven";
                  description
                    "pre-shared key identity";
                }
                container key {
                  description
                    "psk key";
                  leaf seven {
                    type xr:Proprietary-password {
                      length "1..128" {
                        description
                          "type 7 encrypted pre-shared key or Plaintext pre-shared-key prefixed with !";
                      }
                      pattern "([^!](([0-9]+)|([a-f]+)|([A-F]+))+)|(!(.*))";
                    }
                    must "../../id";
                    description
                      "specify an type7 encrypted pre-shared key";
                  }
                }
              }
              leaf source-interface {
                type xr:Interface-name;
                description
                  "source interface configuration";
              }
              container http-proxy {
                description
                  "Http proxy server for reaching the KME sever";
                leaf ipv4 {
                  type inet:ipv4-address-no-zone;
                  must "../port and not (../ipv6 or ../hostname)";
                  description
                    "IPv4 proxy";
                }
                leaf ipv6 {
                  type inet:ipv6-address-no-zone;
                  must "../port and not (../ipv4 or ../hostname)";
                  description
                    "IPv6 proxy";
                }
                leaf hostname {
                  type xr:Cisco-ios-xr-string {
                    length "1..255" {
                      description
                        "Proxy hostname";
                    }
                    pattern "[a-zA-Z0-9_.-]+";
                  }
                  must "../port and not (../ipv4 or ../ipv6)";
                  description
                    "Hostname proxy";
                }
                leaf port {
                  type uint32 {
                    range "1..65535" {
                      description
                        "Http proxy port Number";
                    }
                  }
                  must "(../ipv4 or ../ipv6 or ../hostname)";
                  description
                    "http proxy port configuration";
                }
              }
            }
          }
        }
        container device-identifiers {
          description
            "enter a unique id to represent the device";
          list device-identifier {
            key "device-identifier-name";
            description
              "enter a unique id to represent the device";
            leaf device-identifier-name {
              type xr:Cisco-ios-xr-string {
                length "1..23" {
                  description
                    "enter a unique device identifier";
                }
              }
              description
                "enter a unique id to represent the device";
            }
            container peer-identifiers {
              description
                "Enter peer identifier name";
              list peer-identifier {
                key "peer-identifier-name";
                description
                  "Enter peer identifier name";
                leaf peer-identifier-name {
                  type xr:Cisco-ios-xr-string {
                    length "1..24" {
                      description
                        "peer name";
                    }
                  }
                  description
                    "Enter peer identifier name";
                }
                container primary {
                  presence "Indicates a primary node is configured.";
                  description
                    "Peer role as primary, seed needs to be imported from peer.";
                }
              }
            }
            leaf live-keys {
              type uint32 {
                range "1..120" {
                  description
                    "enter number of live keys";
                }
              }
              description
                "Number of live keys";
            }
            container pool {
              presence "Indicates a pool node is configured.";
              description
                "single or double pool for keys";
              container single {
                presence "Indicates a single node is configured.";
                description
                  "Single pool for all peer";
              }
            }
          }
        }
      }
    }
  }
}
