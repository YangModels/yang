module Cisco-IOS-XR-infra-script-mgmt-cfg {
  namespace "http://cisco.com/ns/yang/Cisco-IOS-XR-infra-script-mgmt-cfg";
  prefix infra-script-mgmt-cfg;

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR infra-script-mgmt package configuration.
     
     This module contains definitions
     for the following management objects:
       scripts: Script-mgmt configuration data
     
     Copyright (c) 2013-2022 by Cisco Systems, Inc.
     All rights reserved.";

  revision 2022-09-22 {
    description
      "Fixed default values, deprecated redundant classes ie., manual-update, scheduled-update, runtime-update. Added 'script-update' class
       2022-08-03
         Changes to Precommit script priority configuration
       2022-08-02
         Fixed 'SNMP' checksum configuration
       2022-04-29
         Fixed 'precommit' checksum configuration issue
       2022-04-29
         Extend schema to support precommit priority config.
       2022-03-23
         Added 'precommit' as a new script type supported by script management.
       2021-12-13
         Added 'snmp' as a new script type supported by script management.";
    semver:module-version "3.0.0";
  }
  revision 2021-08-31 {
    description
      "Define range for update interval in yang
       2021-08-25
          Encrypt password in auto-update config
       2021-08-14
          Extend schema to support auto-update feature
       2021-07-20
          revert checksum type to Enum";
    semver:module-version "2.0.0";
  }
  revision 2019-04-05 {
    description
      "Establish semantic version baseline.";
    semver:module-version "1.0.0";
  }
  revision 2015-11-09 {
    description
      "IOS XR 6.0 revision.";
  }

  typedef Config-checksum {
    type enumeration {
      enum "sha256" {
        value 1;
        description
          "SHA256";
      }
    }
    description
      "Config checksum";
  }

  typedef On-failure {
    type enumeration {
      enum "do-not-run" {
        value 0;
        description
          "do not run";
      }
      enum "run-local" {
        value 1;
        description
          "run local";
      }
    }
    description
      "On failure";
  }

  grouping SCRIPT-UPDATE-TABLE {
    description
      "Common node of eem-script, config-script";
    container script-updates {
      description
        "Name of script";
      list script-update {
        key "script-name";
        description
          "Config Script activation item";
        leaf script-name {
          type xr:Cisco-ios-xr-string;
          description
            "Script name";
        }
        uses CONDITION-SCHEDULE;
        uses CONDITION-MANUAL;
      }
    }
  }

  grouping CONDITION-SCHEDULE {
    description
      "Common node of script, script-update,
       script-precommit";
    container condition-schedule {
      presence "Indicates a condition-schedule node is configured.";
      description
        "auto-update condition";
      leaf url {
        type string;
        mandatory true;
        description
          "URL location";
      }
      leaf update-interval {
        type uint32 {
          range "60..262800";
        }
        mandatory true;
        description
          "update interval";
      }
      leaf username {
        type string;
        description
          "Username";
      }
      leaf password {
        type xr:Proprietary-password;
        description
          "Password";
      }
      leaf vrf {
        type string;
        mandatory true;
        description
          "VRF name";
      }
    }
  }

  grouping CONDITION-MANUAL {
    description
      "Common node of script, script-update,
       script-precommit";
    container condition-manual {
      presence "Indicates a condition-manual node is configured.";
      description
        "auto-update condition";
      leaf url {
        type string;
        mandatory true;
        description
          "URL location";
      }
      leaf username {
        type string;
        description
          "Username";
      }
      leaf password {
        type xr:Proprietary-password;
        description
          "Password";
      }
      leaf vrf {
        type string;
        mandatory true;
        description
          "VRF name";
      }
    }
  }

  grouping SCRIPT-TABLE {
    description
      "Common node of exec-script, process-script,
       snmp-script";
    container scripts {
      description
        "Name of script";
      list script {
        key "script-name";
        description
          "Config Script activation item";
        container condition-runtime {
          presence "Indicates a condition-runtime node is configured.";
          description
            "auto-update condition";
          leaf url {
            type string;
            mandatory true;
            description
              "URL location";
          }
          leaf failure {
            type On-failure;
            mandatory true;
            description
              "run local/do not run";
          }
          leaf username {
            type string;
            description
              "Username";
          }
          leaf password {
            type xr:Proprietary-password;
            description
              "Password";
          }
          leaf vrf {
            type string;
            mandatory true;
            description
              "VRF name";
          }
        }
        container checksum {
          presence "Indicates a checksum node is configured.";
          description
            "Checksum of script";
          leaf checksum-type {
            type Config-checksum;
            mandatory true;
            description
              "Checksum type";
          }
          leaf checksum {
            type string {
              length "64";
            }
            mandatory true;
            description
              "Checksum value";
          }
        }
        leaf script-name {
          type xr:Cisco-ios-xr-string;
          description
            "Script name";
        }
        uses CONDITION-SCHEDULE;
        uses CONDITION-MANUAL;
      }
    }
  }

  container scripts {
    description
      "Script-mgmt configuration data";
    container exec-script {
      description
        "Exec script";
      uses SCRIPT-TABLE;
    }
    container snmp-script {
      description
        "Snmp script";
      uses SCRIPT-TABLE;
    }
    container config-script {
      description
        "Config scripts";
      uses SCRIPT-UPDATE-TABLE;
    }
    container eem-script {
      description
        "Eem script";
      uses SCRIPT-UPDATE-TABLE;
    }
    container process-script {
      description
        "Process script";
      uses SCRIPT-TABLE;
    }
    container precommit-script {
      description
        "Precommit script";
      container script-precommits {
        description
          "Name of script";
        list script-precommit {
          key "script-name";
          description
            "Config Script activation item";
          container precommit-checksum {
            presence "Indicates a precommit-checksum node is configured.";
            description
              "Checksum of script";
            leaf checksum-type {
              type Config-checksum;
              mandatory true;
              description
                "Checksum type";
            }
            leaf checksum {
              type string {
                length "64";
              }
              mandatory true;
              description
                "Checksum value";
            }
            leaf priority {
              type uint32 {
                range "1..100";
              }
              mandatory true;
              description
                "Precommit Script priority";
            }
          }
          leaf active {
            type empty;
            description
              "Activate Precommit script";
          }
          leaf script-name {
            type xr:Cisco-ios-xr-string;
            description
              "Script name";
          }
          uses CONDITION-SCHEDULE;
          uses CONDITION-MANUAL;
        }
      }
    }
  }
}
