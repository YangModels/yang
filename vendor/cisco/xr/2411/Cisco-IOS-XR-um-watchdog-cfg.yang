module Cisco-IOS-XR-um-watchdog-cfg {
  namespace "http://cisco.com/ns/yang/Cisco-IOS-XR-um-watchdog-cfg";
  prefix um-watchdog-cfg;

  import Cisco-IOS-XR-um-location-cfg {
    prefix location;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR watchdog package configuration.
     
     This YANG module augments the
     modules with configuration data.
     
     Copyright (c) 2021-2022 by Cisco Systems, Inc.
     All rights reserved.";

  revision 2022-07-11 {
    description
      "Added missing description statement to nodes";
    semver:module-version "1.0.0";
  }
  revision 2022-04-20 {
    description
      "Updated range for severe and critical nodes under threshold/memory";
  }
  revision 2021-11-09 {
    description
      "Initial release";
  }

  grouping LOCATION-BODY {
    description
      "Grouping for location";
    container watchdog {
      description
        "Watchdog configuration commands";
      container threshold {
        description
          "Watchdog threshold configuration";
        container memory {
          description
            "Memory thresholds";
          leaf minor {
            type uint32 {
              range "5..40" {
                description
                  "memory consumption in percentage";
              }
            }
            must "../severe";
            description
              "Threshold for minor state";
          }
          leaf severe {
            type uint32 {
              range "4..40" {
                description
                  "memory consumption in percentage";
              }
            }
            must "../minor and ../critical";
            description
              "Threshold for severe state ";
          }
          leaf critical {
            type uint32 {
              range "3..40" {
                description
                  "memory consumption in percentage";
              }
            }
            must "../severe";
            description
              "Threshold for critical state ";
          }
        }
        container disk {
          description
            "Disk thresholds";
          leaf minor {
            type uint32 {
              range "1..97" {
                description
                  "disk consumption in percentage";
              }
            }
            must "../severe";
            description
              "Threshold for minor state";
          }
          leaf severe {
            type uint32 {
              range "1..98" {
                description
                  "disk consumption in percentage";
              }
            }
            must "../minor and ../critical";
            description
              "Threshold for severe state ";
          }
          leaf critical {
            type uint32 {
              range "1..99" {
                description
                  "disk consumption in percentage";
              }
            }
            must "../severe";
            description
              "Threshold for critical state ";
          }
        }
      }
    }
  }

  augment "/location:locations/location:location" {
    description
      "This augment extends active nodes configuration";
    uses LOCATION-BODY;
  }
  container watchdog {
    description
      "Watchdog configuration commands";
    container restart {
      description
        "Watchdog restart configurations";
      container memory-hog {
        description
          "Watchdog restart memory-hog configuration";
        container disable {
          presence "Indicates a disable node is configured.";
          description
            "Disable watchdog restart memory-hog";
        }
      }
      container deadlock {
        description
          "Watchdog restart deadlock configuration";
        container disable {
          presence "Indicates a disable node is configured.";
          description
            "Disable watchdog restart deadlock";
        }
      }
    }
    container threshold {
      description
        "Watchdog threshold configuration";
      container memory {
        description
          "Memory thresholds";
        leaf minor {
          type uint32 {
            range "5..40" {
              description
                "memory consumption in percentage";
            }
          }
          must "../severe";
          description
            "Threshold for minor state";
        }
        leaf severe {
          type uint32 {
            range "4..40" {
              description
                "memory consumption in percentage";
            }
          }
          must "../minor and ../critical";
          description
            "Threshold for severe state ";
        }
        leaf critical {
          type uint32 {
            range "3..40" {
              description
                "memory consumption in percentage";
            }
          }
          must "../severe";
          description
            "Threshold for critical state ";
        }
      }
      container switchover {
        description
          "Memory threshold switchover";
        leaf enable {
          type enumeration {
            enum "minor" {
              value 2;
              description
                "Perform RPFO on minor memory state if standby is ready";
            }
            enum "severe" {
              value 3;
              description
                "Perform RPFO on severe memory state if standby is ready";
            }
            enum "critical" {
              value 4;
              description
                "Perform RPFO on critical memory state if standby is ready";
            }
          }
          description
            "Set swithover parameters for memory threshold switchover";
        }
      }
      container disk {
        description
          "Disk thresholds";
        leaf minor {
          type uint32 {
            range "1..97" {
              description
                "disk consumption in percentage";
            }
          }
          must "../severe";
          description
            "Threshold for minor state";
        }
        leaf severe {
          type uint32 {
            range "1..98" {
              description
                "disk consumption in percentage";
            }
          }
          must "../minor and ../critical";
          description
            "Threshold for severe state ";
        }
        leaf critical {
          type uint32 {
            range "1..99" {
              description
                "disk consumption in percentage";
            }
          }
          must "../severe";
          description
            "Threshold for critical state ";
        }
      }
    }
    container overload {
      description
        "Watchdog monitor configurations";
      leaf throttle-timeout {
        type uint32 {
          range "5..120" {
            description
              "Length of timeout in seconds";
          }
        }
        description
          "Watchdog overload throttle timeout configuration";
      }
      container notification {
        description
          "Critical event notification configuration";
        container disable {
          presence "Indicates a disable node is configured.";
          description
            "Disable critical event notification";
        }
      }
    }
  }
}
