module Cisco-IOS-XR-fib-hal-event-stats-oper {
  namespace "http://cisco.com/ns/yang/Cisco-IOS-XR-fib-hal-event-stats-oper";
  prefix fib-hal-event-stats-oper;

  import Cisco-IOS-XR-types {
    prefix xr;
  }
  import cisco-semver {
    prefix semver;
  }
  include Cisco-IOS-XR-fib-hal-event-stats-oper-sub1 {
    revision-date 2019-04-05;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR fib-hal-event-stats package operational data.
     
     This module contains definitions
     for the following management objects:
       fib-plat: Platform table
     
     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  container fib-plat {
    config false;
    description
      "Platform table";
    container nodes {
      description
        "Table of Nodes";
      list node {
        key "node-name";
        description
          "Information about a particular node";
        container fib-plat-event {
          description
            "FIB/CEF Platform event information";
          container stats {
            description
              "FIB/CEF Platform event statistics information";
            uses FIB-HAL-BAG-EVENT-STATS;
          }
        }
        leaf node-name {
          type xr:Node-id;
          description
            "Node name";
        }
      }
    }
  }
}
