module Cisco-IOS-XR-ipv6-nd-subscriber-cfg {
  namespace "http://cisco.com/ns/yang/Cisco-IOS-XR-ipv6-nd-subscriber-cfg";
  prefix ipv6-nd-subscriber-cfg;

  import ietf-inet-types {
    prefix inet;
  }
  import Cisco-IOS-XR-types {
    prefix xr;
  }
  import cisco-semver {
    prefix semver;
  }
  import Cisco-IOS-XR-subscriber-infra-tmplmgr-cfg {
    prefix a1;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ipv6-nd-subscriber package configuration.
     
     This YANG module augments the
       Cisco-IOS-XR-subscriber-infra-tmplmgr-cfg
     module with configuration data.
     
     Copyright (c) 2013-2022 by Cisco Systems, Inc.
     All rights reserved.";

  revision 2022-11-19 {
    description
      "Support for DNS options.";
    semver:module-version "1.1.0";
  }
  revision 2019-04-05 {
    description
      "Establish semantic version baseline.";
    semver:module-version "1.0.0";
  }
  revision 2016-12-19 {
    description
      "IOS XR 6.2.1 revision.";
  }
  revision 2015-11-09 {
    description
      "IOS XR 6.0 revision.";
  }

  typedef Ipv6-nd-router-pref-template {
    type enumeration {
      enum "high" {
        value 1;
        description
          "High preference";
      }
      enum "medium" {
        value 2;
        description
          "Medium preference";
      }
      enum "low" {
        value 3;
        description
          "Low preference";
      }
    }
    description
      "Ipv6 nd router pref template";
  }

  grouping IPV6-NEIGHBOR {
    description
      "Common node of ip-subscriber, ppp,
       subscriber-service";
    container ipv6-neighbor {
      description
        "Interface IPv6 Network configuration data";
      container ra-interval {
        presence "Indicates a ra-interval node is configured.";
        description
          "Set IPv6 Router Advertisement (RA) interval in
           seconds";
        leaf maximum {
          type uint32 {
            range "4..1800";
          }
          units "second";
          mandatory true;
          description
            "Maximum RA interval in seconds";
        }
        leaf minimum {
          type uint32 {
            range "3..1800";
          }
          units "second";
          description
            "Minimum RA interval in seconds. Must be less
             than 0.75 * maximum interval";
        }
      }
      container framed-prefix {
        presence "Indicates a framed-prefix node is configured.";
        description
          "Set the IPv6 framed ipv6 prefix for a
           subscriber interface ";
        leaf prefix-length {
          type xr:Ipv6-prefix-length;
          mandatory true;
          description
            "IPv6 framed prefix length";
        }
        leaf prefix {
          type string;
          mandatory true;
          description
            "IPV6 framed prefix address";
        }
      }
      container radns-servers {
        description
          "IPv6 Router Advertisement (RA) DNS Servers";
        list radns-server {
          key "dns-server";
          description
            "IPv6 Router Advertisement (RA) DNS Server";
          leaf dns-server {
            type inet:ipv6-address-no-zone;
            description
              "IPv6 Address";
          }
          leaf address {
            type inet:ipv6-address-no-zone;
            description
              "IPv6 DNS server addresses list";
          }
          leaf lifetime {
            type uint32 {
              range "0..4294967295";
            }
            units "second";
            description
              "Lifetime value in seconds";
          }
        }
      }
      container duplicate-address-detection {
        description
          "Duplicate Address Detection (DAD)";
        leaf attempts {
          type uint32 {
            range "0..600";
          }
          description
            "Set IPv6 duplicate address detection transmits";
        }
      }
      container ra-initial {
        presence "Indicates a ra-initial node is configured.";
        description
          "IPv6 ND RA Initial";
        leaf count {
          type uint32 {
            range "0..32";
          }
          mandatory true;
          description
            "Initial RA count";
        }
        leaf interval {
          type uint32 {
            range "4..1800";
          }
          units "second";
          mandatory true;
          description
            "Initial RA interval in seconds";
        }
      }
      leaf framed-prefix-pool {
        type string;
        description
          "Set the IPv6 framed ipv6 prefix pool for a
           subscriber interface ";
      }
      leaf managed-config {
        type empty;
        description
          "Host to use stateful protocol for address
           configuration";
      }
      leaf other-config {
        type empty;
        description
          "Host to use stateful protocol for non-address
           configuration";
      }
      leaf start-ra-on-ipv6-enable {
        type empty;
        description
          "Start RA on ipv6-enable config";
      }
      leaf nud-enable {
        type empty;
        description
          "NUD enable";
      }
      leaf ra-lifetime {
        type uint32 {
          range "0..9000";
        }
        units "second";
        description
          "Set IPv6 Router Advertisement (RA) lifetime in
           seconds";
      }
      leaf router-preference {
        type Ipv6-nd-router-pref-template;
        description
          "RA Router Preference";
      }
      leaf ra-suppress {
        type empty;
        description
          "Enable suppress IPv6 router advertisement";
      }
      leaf ra-unicast {
        type empty;
        description
          "Enable RA unicast Flag";
      }
      leaf ra-unspecify-hoplimit {
        type empty;
        description
          "Unspecify IPv6 Router Advertisement (RA)
           hop-limit";
      }
      leaf ra-suppress-mtu {
        type empty;
        description
          "RA suppress MTU flag";
      }
      leaf suppress-cache-learning {
        type empty;
        description
          "Suppress cache learning flag";
      }
      leaf reachable-time {
        type uint32 {
          range "0..3600000";
        }
        units "millisecond";
        description
          "Set advertised reachability time in
           milliseconds";
      }
      leaf ns-interval {
        type uint32 {
          range "1000..4294967295";
        }
        units "millisecond";
        description
          "Set advertised NS retransmission interval in
           milliseconds";
      }
    }
  }

  augment "/a1:dynamic-template/a1:subscriber-services/a1:subscriber-service" {
    description
      "This augment extends the configuration data of
       'Cisco-IOS-XR-subscriber-infra-tmplmgr-cfg'";
    uses IPV6-NEIGHBOR;
  }
  augment "/a1:dynamic-template/a1:ppps/a1:ppp" {
    description
      "This augment extends the configuration data of
       'Cisco-IOS-XR-subscriber-infra-tmplmgr-cfg'";
    uses IPV6-NEIGHBOR;
  }
  augment "/a1:dynamic-template/a1:ip-subscribers/a1:ip-subscriber" {
    description
      "This augment extends the configuration data of
       'Cisco-IOS-XR-subscriber-infra-tmplmgr-cfg'";
    uses IPV6-NEIGHBOR;
  }
}
