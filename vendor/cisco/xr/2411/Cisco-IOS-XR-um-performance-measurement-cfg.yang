module Cisco-IOS-XR-um-performance-measurement-cfg {
  namespace "http://cisco.com/ns/yang/Cisco-IOS-XR-um-performance-measurement-cfg";
  prefix um-performance-measurement-cfg;

  import Cisco-IOS-XR-types {
    prefix xr;
  }
  import ietf-inet-types {
    prefix inet;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR performance-measurement package configuration.
     
     This YANG module augments the
     modules with configuration data.
     
     Copyright (c) 2023-2024 by Cisco Systems, Inc.
     All rights reserved.";

  revision 2024-01-30 {
    description
      "Deprecate 'enable' keyword in npu-offload
       2023-12-19
         Remove distribution node;
       Remove hardware offload node under performance-measurement.
       2023-11-08
         Change supported number of flow labels from 16 to 31 for explicit values;
       Change supported number of flow labels from 16 to 128 for ranged values;
       Add flow label for named delay profiles;
       Update destination sweeping path.
       2023-10-26
         Add destination sweeping for endpoint profiles.
       Add packet anomaly loss config for delay profiles.
       2023-07-19
         Add logging config for PM named liveness profile
       2023-04-24
         Fix errors introduced by revision 2023-04-06.
       The errors were originated by the meatdata generator,
       due to its limitations of handling same-name containers.
       
       1. delay-profile container was misplaced in a couple of places.
       2. liveness-detection container was misplaced in a couple of places.
       3. segment-routing container sysdb path violations.
       4. names container under delay-profile and liveness-profile was not generated.
       2023-04-06
         Incorporate all config changes after revision 2022-04-25, except the change made in revision 2023-03-17
       2023-03-17
         Added containers for allowed-querier and allowed-responder configs
       2022-04-25
         Removed container distribute-sessions and updated range for tx-interval
       2022-03-29
         Added containers for path tracing midpoint configs
       2022-03-02
         Added containers for npu-offload config for generic profiles
       2021-12-08
         Added name and tx-interval nodes support under delay-profile and liveness-profile";
    semver:module-version "2.0.0";
  }
  revision 2021-06-29 {
    description
      "Initial release";
    semver:module-version "1.0.0";
  }

  container performance-measurement {
    presence "Indicates a performance-measurement node is configured.";
    description
      "Enter the Performance Measurement submode";
    container interfaces {
      description
        "Enable Performance Measurement on an interface";
      list interface {
        key "interface-name";
        description
          "Enable Performance Measurement on an interface";
        leaf interface-name {
          type xr:Interface-name;
          description
            "Enable Performance Measurement on an interface";
        }
        container delay-measurement {
          presence "Indicates a delay-measurement node is configured.";
          description
            "Enable delay-measurement on the interface";
          leaf advertise-delay {
            type uint32 {
              range "1..16777215" {
                description
                  "Advertisement delay (uSec)";
              }
            }
            description
              "Advertisement delay";
          }
          container delay-profile {
            description
              "Interface delay profile";
            leaf name {
              type xr:Cisco-ios-xr-string {
                length "1..256" {
                  description
                    "Profile name";
                }
              }
              description
                "Profile name";
            }
          }
          leaf static-delay {
            type uint32 {
              range "1..4294967295" {
                description
                  "Static delay (nsec)";
              }
            }
            description
              "Static delay";
          }
        }
        container next-hop {
          description
            "next-hop address";
          leaf ipv4 {
            type inet:ipv4-address-no-zone;
            must "not(../ipv6)";
            description
              "IPv4 address";
          }
          leaf ipv6 {
            type inet:ipv6-address-no-zone;
            must "not(../ipv4)";
            description
              "IPv6 address";
          }
        }
        container path-tracing {
          presence "Indicates a path-tracing node is configured.";
          description
            "Enable path-tracing and enter its submode";
          leaf interface-id {
            type uint32 {
              range "1..4095" {
                description
                  "Path tracing interface ID value";
              }
            }
            description
              "Config interface ID for path tracing";
          }
          container timestamp {
            description
              "Timestamp";
            container template {
              description
                "Template";
              container st0 {
                must
                  "not(../st1 or ../st2
                   or ../st3)";
                presence "Indicates a st0 node is configured.";
                description
                  "PTP timestamp nanosecond bits [8:15]";
              }
              container st1 {
                must
                  "not(../st0 or ../st2
                   or ../st3)";
                presence "Indicates a st1 node is configured.";
                description
                  "PTP timestamp nanosecond bits [12:19]";
              }
              container st2 {
                must
                  "not(../st0 or ../st1
                   or ../st3)";
                presence "Indicates a st2 node is configured.";
                description
                  "PTP timestamp nanosecond bits [16:23]";
              }
              container st3 {
                must
                  "not(../st0 or ../st1
                   or ../st2)";
                presence "Indicates a st3 node is configured.";
                description
                  "PTP timestamp nanosecond bits [20:27]";
              }
            }
          }
        }
      }
    }
    container endpoint {
      description
        "Enable Performance Measurement for an endpoint";
      container ipv4s {
        description
          "IPv4 endpoint";
        list ipv4 {
          must "vrf";
          key "address";
          description
            "IPv4 endpoint";
          leaf address {
            type inet:ipv4-address-no-zone;
            description
              "IPv4 endpoint";
          }
          list vrf {
            key "vrf-name";
            description
              "Endpoint vrf table";
            leaf vrf-name {
              type xr:Cisco-ios-xr-string {
                length "1..32" {
                  description
                    "VRF name, default name is 'default'";
                }
              }
              description
                "endpoint vrf table";
            }
            container source-address {
              description
                "Source address of the endpoint";
              leaf ipv4 {
                type inet:ipv4-address-no-zone;
                description
                  "IPv4 address";
              }
            }
            leaf description {
              type string {
                length "1..255" {
                  description
                    "Description of the endpoint";
                }
              }
              description
                "Description of the endpoint";
            }
            container delay-measurement {
              presence "Indicates a delay-measurement node is configured.";
              description
                "Enable delay-measurement on the endpoint";
              container delay-profile {
                description
                  "Endpoint delay profile name";
                leaf name {
                  type xr:Cisco-ios-xr-string {
                    length "1..256" {
                      description
                        "Profile name";
                    }
                  }
                  description
                    "Profile name";
                }
              }
            }
            container segment-list {
              description
                "'segment-list' option will be deprecated in IOS XR 7.10.1. Use segment-routing traffic-eng explicit segment-list name";
              container names {
                description
                  "Segment-list name";
                list name {
                  key "list-name";
                  description
                    "Segment-list name";
                  leaf list-name {
                    type xr:Cisco-ios-xr-string {
                      length "1..128" {
                        description
                          "Identifying name for segment-list";
                      }
                    }
                    description
                      "Segment-list name";
                  }
                }
              }
            }
            container liveness-detection {
              presence "Indicates a liveness-detection node is configured.";
              description
                "Enable liveness-detection on the endpoint";
              container liveness-profile {
                description
                  "Endpoint liveness profile name";
                leaf name {
                  type xr:Cisco-ios-xr-string {
                    length "1..256" {
                      description
                        "Profile name";
                    }
                  }
                  description
                    "Profile name";
                }
              }
              container collect-hbh {
                presence "Indicates a collect-hbh node is configured.";
                description
                  "Collect hop by hop data for liveness sessions";
              }
            }
            container segment-routing {
              presence "Indicates a segment-routing node is configured.";
              description
                "Enable segment list on the endpoint";
              container traffic-eng {
                description
                  "TE on the endpoint";
                container explicit {
                  description
                    "explicit segment list on the endpoint";
                  container segment-list {
                    description
                      "Configure segment list on the endpoint";
                    container names {
                      description
                        "Segment-list name";
                      list name {
                        key "list-name";
                        description
                          "Segment-list name";
                        leaf list-name {
                          type xr:Cisco-ios-xr-string {
                            length "1..128" {
                              description
                                "Identifying name for segment-list";
                            }
                          }
                          description
                            "Segment-list name";
                        }
                        container reverse-path {
                          description
                            "reverse path segment-list coupled with forward segment-list";
                          container segment-list {
                            description
                              "Configure segment-list on the endpoint";
                            leaf name {
                              type xr:Cisco-ios-xr-string {
                                length "1..128" {
                                  description
                                    "Identifying name for segment-list";
                                }
                              }
                              description
                                "Segment-list name";
                            }
                          }
                        }
                      }
                    }
                  }
                  container reverse-path {
                    description
                      "reverse-path segment list on the endpoint";
                    container segment-list {
                      description
                        "Configure segment list on the endpoint";
                      leaf name {
                        type xr:Cisco-ios-xr-string {
                          length "1..128" {
                            description
                              "Identifying name for segment-list";
                          }
                        }
                        description
                          "Segment-list name";
                      }
                    }
                  }
                }
              }
            }
            container path-tracing {
              presence "Indicates a path-tracing node is configured.";
              description
                "Enable path-tracing and enter its submode";
              container session-ids {
                description
                  "Configure session-id to create a probe session";
                list session-id {
                  key "session-id";
                  description
                    "Configure session-id to create a probe session";
                  leaf session-id {
                    type uint32 {
                      range "1..65535" {
                        description
                          "Session ID";
                      }
                    }
                    description
                      "Configure session-id to create a probe session";
                  }
                  container probe-profile {
                    description
                      "Configure a named profile for a probe session";
                    leaf name {
                      type xr:Cisco-ios-xr-string {
                        length "1..256" {
                          description
                            "Profile name";
                        }
                      }
                      description
                        "Probe session profile";
                    }
                  }
                  container segment-routing {
                    description
                      "Configure a named profile for a probe session";
                    container traffic-eng {
                      description
                        "Configure a named profile for a probe session";
                      leaf segment-list {
                        type xr:Cisco-ios-xr-string {
                          length "1..128" {
                            description
                              "Segment List name";
                          }
                        }
                        description
                          "Segment List";
                      }
                    }
                  }
                }
              }
            }
            container path-assurance {
              presence "Indicates a path-assurance node is configured.";
              description
                "Enable path-assurance and enter its submode";
              container session-ids {
                description
                  "Configure session-id to create a probe session";
                list session-id {
                  key "session-id";
                  description
                    "Configure session-id to create a probe session";
                  leaf session-id {
                    type uint32 {
                      range "1..65535" {
                        description
                          "Session ID";
                      }
                    }
                    description
                      "Configure session-id to create a probe session";
                  }
                  container probe-profile {
                    description
                      "Configure a named profile for a probe session";
                    leaf name {
                      type xr:Cisco-ios-xr-string {
                        length "1..256" {
                          description
                            "Profile name";
                        }
                      }
                      description
                        "Probe session profile";
                    }
                  }
                  container segment-routing {
                    description
                      "Configure a named profile for a probe session";
                    container traffic-eng {
                      description
                        "Configure a named profile for a probe session";
                      leaf segment-list {
                        type xr:Cisco-ios-xr-string {
                          length "1..128" {
                            description
                              "Segment List name";
                          }
                        }
                        description
                          "Segment List";
                      }
                    }
                  }
                }
              }
            }
          }
        }
      }
      container ipv6s {
        description
          "IPv6 endpoint";
        list ipv6 {
          must "vrf";
          key "address";
          description
            "IPv6 endpoint";
          leaf address {
            type inet:ipv6-address-no-zone;
            description
              "IPv6 endpoint";
          }
          list vrf {
            key "vrf-name";
            description
              "Endpoint vrf table";
            leaf vrf-name {
              type xr:Cisco-ios-xr-string {
                length "1..32" {
                  description
                    "VRF name, default name is 'default'";
                }
              }
              description
                "endpoint vrf table";
            }
            container source-address {
              description
                "Source address of the endpoint";
              leaf ipv6 {
                type inet:ipv6-address-no-zone;
                description
                  "IPv6 address";
              }
            }
            leaf description {
              type string {
                length "1..255" {
                  description
                    "Description of the endpoint";
                }
              }
              description
                "Description of the endpoint";
            }
            container delay-measurement {
              presence "Indicates a delay-measurement node is configured.";
              description
                "Enable delay-measurement on the endpoint";
              container delay-profile {
                description
                  "Endpoint delay profile name";
                leaf name {
                  type xr:Cisco-ios-xr-string {
                    length "1..256" {
                      description
                        "Profile name";
                    }
                  }
                  description
                    "Profile name";
                }
              }
            }
            container segment-list {
              description
                "'segment-list' option will be deprecated in IOS XR 7.10.1. Use segment-routing traffic-eng explicit segment-list name";
              container names {
                description
                  "Segment-list name";
                list name {
                  key "list-name";
                  description
                    "Segment-list name";
                  leaf list-name {
                    type xr:Cisco-ios-xr-string {
                      length "1..128" {
                        description
                          "Identifying name for segment-list";
                      }
                    }
                    description
                      "Segment-list name";
                  }
                }
              }
            }
            container liveness-detection {
              presence "Indicates a liveness-detection node is configured.";
              description
                "Enable liveness-detection on the endpoint";
              container liveness-profile {
                description
                  "Endpoint liveness profile name";
                leaf name {
                  type xr:Cisco-ios-xr-string {
                    length "1..256" {
                      description
                        "Profile name";
                    }
                  }
                  description
                    "Profile name";
                }
              }
              container collect-hbh {
                presence "Indicates a collect-hbh node is configured.";
                description
                  "Collect hop by hop data for liveness sessions";
              }
            }
            container segment-routing {
              presence "Indicates a segment-routing node is configured.";
              description
                "Enable segment list on the endpoint";
              container traffic-eng {
                description
                  "TE on the endpoint";
                container explicit {
                  description
                    "explicit segment list on the endpoint";
                  container segment-list {
                    description
                      "Configure segment list on the endpoint";
                    container names {
                      description
                        "Segment-list name";
                      list name {
                        key "list-name";
                        description
                          "Segment-list name";
                        leaf list-name {
                          type xr:Cisco-ios-xr-string {
                            length "1..128" {
                              description
                                "Identifying name for segment-list";
                            }
                          }
                          description
                            "Segment-list name";
                        }
                        container reverse-path {
                          description
                            "reverse path segment-list coupled with forward segment-list";
                          container segment-list {
                            description
                              "Configure segment-list on the endpoint";
                            leaf name {
                              type xr:Cisco-ios-xr-string {
                                length "1..128" {
                                  description
                                    "Identifying name for segment-list";
                                }
                              }
                              description
                                "Segment-list name";
                            }
                          }
                        }
                      }
                    }
                  }
                  container reverse-path {
                    description
                      "reverse-path segment list on the endpoint";
                    container segment-list {
                      description
                        "Configure segment list on the endpoint";
                      leaf name {
                        type xr:Cisco-ios-xr-string {
                          length "1..128" {
                            description
                              "Identifying name for segment-list";
                          }
                        }
                        description
                          "Segment-list name";
                      }
                    }
                  }
                }
              }
            }
            container path-tracing {
              presence "Indicates a path-tracing node is configured.";
              description
                "Enable path-tracing and enter its submode";
              container session-ids {
                description
                  "Configure session-id to create a probe session";
                list session-id {
                  key "session-id";
                  description
                    "Configure session-id to create a probe session";
                  leaf session-id {
                    type uint32 {
                      range "1..65535" {
                        description
                          "Session ID";
                      }
                    }
                    description
                      "Configure session-id to create a probe session";
                  }
                  container probe-profile {
                    description
                      "Configure a named profile for a probe session";
                    leaf name {
                      type xr:Cisco-ios-xr-string {
                        length "1..256" {
                          description
                            "Profile name";
                        }
                      }
                      description
                        "Probe session profile";
                    }
                  }
                  container segment-routing {
                    description
                      "Configure a named profile for a probe session";
                    container traffic-eng {
                      description
                        "Configure a named profile for a probe session";
                      leaf segment-list {
                        type xr:Cisco-ios-xr-string {
                          length "1..128" {
                            description
                              "Segment List name";
                          }
                        }
                        description
                          "Segment List";
                      }
                    }
                  }
                }
              }
            }
            container path-assurance {
              presence "Indicates a path-assurance node is configured.";
              description
                "Enable path-assurance and enter its submode";
              container session-ids {
                description
                  "Configure session-id to create a probe session";
                list session-id {
                  key "session-id";
                  description
                    "Configure session-id to create a probe session";
                  leaf session-id {
                    type uint32 {
                      range "1..65535" {
                        description
                          "Session ID";
                      }
                    }
                    description
                      "Configure session-id to create a probe session";
                  }
                  container probe-profile {
                    description
                      "Configure a named profile for a probe session";
                    leaf name {
                      type xr:Cisco-ios-xr-string {
                        length "1..256" {
                          description
                            "Profile name";
                        }
                      }
                      description
                        "Probe session profile";
                    }
                  }
                  container segment-routing {
                    description
                      "Configure a named profile for a probe session";
                    container traffic-eng {
                      description
                        "Configure a named profile for a probe session";
                      leaf segment-list {
                        type xr:Cisco-ios-xr-string {
                          length "1..128" {
                            description
                              "Segment List name";
                          }
                        }
                        description
                          "Segment List";
                      }
                    }
                  }
                }
              }
            }
          }
        }
      }
    }
    container source-address {
      description
        "Configure a source address";
      leaf ipv4 {
        type inet:ipv4-address-no-zone;
        description
          "IPv4 endpoint";
      }
      leaf ipv6 {
        type inet:ipv6-address-no-zone;
        description
          "IPv6 endpoint";
      }
    }
    container delay-profile {
      description
        "Delay profile";
      container interfaces {
        description
          "Enter interface delay profile submode";
        container default {
          presence "Indicates a default node is configured.";
          description
            "Default profile";
          container probe {
            description
              "Enter interface delay probe submode";
            leaf computation-interval {
              type uint32 {
                range "1..3600" {
                  description
                    "Computation interval (seconds)";
                }
              }
              description
                "Interval for metric computation";
            }
            leaf burst-interval {
              type uint32 {
                range "30..15000" {
                  description
                    "Burst interval (msec) (Deprecated in IOS-XR 7.6.1. Please use tx-interval.)";
                }
              }
              description
                "Burst interval (Deprecated in IOS-XR 7.6.1. Please use tx-interval.)";
            }
            leaf tx-interval {
              type uint32 {
                range "30000..15000000" {
                  description
                    "TX interval (usec. Minimum tx interval supported for CPU sessions is 30000 usec)";
                }
              }
              description
                "TX interval";
            }
            container protocol {
              description
                "Configure protocol type for delay measurement probe messages";
              container pm-mpls {
                must "not(../twamp-light)";
                presence "Indicates a pm-mpls node is configured.";
                description
                  "Interface delay measurement using RFC6374 with MPLS encap";
              }
              container twamp-light {
                must "not(../pm-mpls)";
                presence "Indicates a twamp-light node is configured.";
                description
                  "Interface delay measurement using RFC5357";
              }
            }
            container tos {
              description
                "Enter interface delay probe type of service submode";
              leaf traffic-class {
                type uint32 {
                  range "0..7" {
                    description
                      "Traffic Class value";
                  }
                }
                description
                  "Traffic Class value indicating TOS level used by protocol pm-mpls";
              }
              leaf dscp {
                type uint32 {
                  range "0..63" {
                    description
                      "DSCP value";
                  }
                }
                description
                  "DSCP value indicating TOS level used by protocol twamp-light";
              }
            }
            container measurement-mode {
              description
                "Delay measurement mode";
              container one-way {
                must "not(../two-way)";
                presence "Indicates a one-way node is configured.";
                description
                  "Measure one way delay with timestamp 1 and 2";
              }
              container two-way {
                must "not(../one-way)";
                presence "Indicates a two-way node is configured.";
                description
                  "Measure one way delay with timestamp 1, 2, 3 and 4 without clock synchronization";
              }
            }
          }
          container advertisement {
            description
              "Enter interface delay profile advertisement submode";
            container periodic {
              description
                "Go into interface delay periodic advertisement submode";
              container disabled {
                presence "Indicates a disabled node is configured.";
                description
                  "Periodic advertisement disabled";
              }
              leaf interval {
                type uint32 {
                  range "30..3600" {
                    description
                      "Periodic advertisement and metric aggregation interval (seconds)";
                  }
                }
                description
                  "Periodic advertisement and metric aggregation interval";
              }
              leaf threshold {
                type uint32 {
                  range "0..100" {
                    description
                      "Periodic advertisement threshold percentage change (compared to last advertisement)";
                  }
                }
                description
                  "Periodic advertisement threshold (compared to last advertisement)";
              }
              leaf minimum-change {
                type uint32 {
                  range "0..100000" {
                    description
                      "Periodic advertisement minimum change in uSec (compared to last advertisement)";
                  }
                }
                description
                  "Periodic advertisement minimum change (compared to last advertisement)";
              }
            }
            container logging {
              description
                "Enter interface delay profile advertisement logging submode";
              container delay-exceeded {
                presence "Indicates a delay-exceeded node is configured.";
                description
                  "Emit syslog when the delay exceeds the threshold";
              }
            }
            container accelerated {
              presence "Indicates a accelerated node is configured.";
              description
                "Enter interface delay profile advertisement accelerated submode";
              leaf threshold {
                type uint32 {
                  range "0..100" {
                    description
                      "Accelerated advertisement threshold percentage change";
                  }
                }
                description
                  "Accelerated advertisement threshold";
              }
              leaf minimum-change {
                type uint32 {
                  range "0..100000" {
                    description
                      "Accelerated advertisement minimum change (uSec)";
                  }
                }
                description
                  "Accelerated advertisement minimum change";
              }
            }
            container anomaly-check {
              presence "Indicates a anomaly-check node is configured.";
              description
                "Enter interface delay profile advertisement anomaly submode";
              leaf upper-bound {
                type uint32 {
                  range "2..200000" {
                    description
                      "Anomaly Check advertisement upper-bound (uSec)";
                  }
                }
                must "../lower-bound";
                description
                  "Anomaly Check advertisement upper-bound";
              }
              leaf lower-bound {
                type uint32 {
                  range "1..199999" {
                    description
                      "Anomaly Check advertisement lower-bound (uSec)";
                  }
                }
                must "../upper-bound";
                description
                  "Anomaly Check advertisement lower-bound";
              }
            }
            container anomaly-loss {
              presence "Indicates a anomaly-loss node is configured.";
              description
                "Enter interface delay profile advertisement anomaly loss submode";
              leaf upper-bound {
                type uint32 {
                  range "1..99" {
                    description
                      "Anomaly Check advertisement upper-bound (uSec)";
                  }
                }
                must "../lower-bound";
                description
                  "Anomaly Check advertisement upper-bound";
              }
              leaf lower-bound {
                type uint32 {
                  range "0..98" {
                    description
                      "Anomaly Check advertisement lower-bound (uSec)";
                  }
                }
                must "../upper-bound";
                description
                  "Anomaly Check advertisement lower-bound";
              }
            }
          }
        }
      }
      container rsvp-te {
        description
          "Enter RSVP-TE delay profile submode";
        container default {
          presence "Indicates a default node is configured.";
          description
            "Default profile";
          container probe {
            description
              "Enter RSVP-TE delay probe submode";
            leaf computation-interval {
              type uint32 {
                range "1..3600" {
                  description
                    "Computation interval (seconds)";
                }
              }
              description
                "Interval for metric computation";
            }
            leaf burst-interval {
              type uint32 {
                range "30..15000" {
                  description
                    "Burst interval (msec) (Deprecated in IOS-XR 7.6.1. Please use tx-interval.)";
                }
              }
              description
                "Burst interval (Deprecated in IOS-XR 7.6.1. Please use tx-interval.)";
            }
            leaf tx-interval {
              type uint32 {
                range "30000..15000000" {
                  description
                    "TX interval (usec. Minimum tx interval supported for CPU sessions is 30000 usec)";
                }
              }
              description
                "TX interval";
            }
            container protocol {
              description
                "Configure protocol type for delay measurement probe messages";
              container pm-mpls {
                must "not(../twamp-light)";
                presence "Indicates a pm-mpls node is configured.";
                description
                  "RSVP-TE tunnel delay measurement using RFC6374 with MPLS encap";
              }
              container twamp-light {
                must "not(../pm-mpls)";
                presence "Indicates a twamp-light node is configured.";
                description
                  "RSVP-TE tunnel delay measurement using RFC5357";
              }
            }
            container tos {
              description
                "Enter RSVP-TE delay probe type of service submode";
              leaf traffic-class {
                type uint32 {
                  range "0..7" {
                    description
                      "Traffic Class value";
                  }
                }
                description
                  "Traffic Class value indicating TOS level used by protocol pm-mpls";
              }
              leaf dscp {
                type uint32 {
                  range "0..63" {
                    description
                      "DSCP value";
                  }
                }
                description
                  "DSCP value indicating TOS level used by protocol twamp-light";
              }
            }
            container measurement-mode {
              description
                "Delay measurement mode";
              container one-way {
                presence "Indicates a one-way node is configured.";
                description
                  "Measure one way delay with timestamp 1 and 2";
              }
            }
          }
          container advertisement {
            description
              "Enter RSVP-TE delay profile advertisement submode";
            container periodic {
              description
                "Go into RSVP-TE delay periodic advertisement submode";
              container disabled {
                presence "Indicates a disabled node is configured.";
                description
                  "Periodic advertisement disabled";
              }
              leaf interval {
                type uint32 {
                  range "30..3600" {
                    description
                      "Periodic advertisement and metric aggregation interval (seconds)";
                  }
                }
                description
                  "Periodic advertisement and metric aggregation interval";
              }
              leaf threshold {
                type uint32 {
                  range "0..100" {
                    description
                      "Periodic advertisement threshold percentage change (compared to last advertisement)";
                  }
                }
                description
                  "Periodic advertisement threshold (compared to last advertisement)";
              }
              leaf minimum-change {
                type uint32 {
                  range "0..100000" {
                    description
                      "Periodic advertisement minimum change in uSec (compared to last advertisement)";
                  }
                }
                description
                  "Periodic advertisement minimum change (compared to last advertisement)";
              }
            }
            container logging {
              description
                "Enter RSVP-TE delay profile advertisement logging submode";
              container delay-exceeded {
                presence "Indicates a delay-exceeded node is configured.";
                description
                  "Emit syslog when the delay exceeds the threshold";
              }
            }
            container accelerated {
              presence "Indicates a accelerated node is configured.";
              description
                "Enter RSVP-TE delay profile advertisement accelerated submode";
              leaf threshold {
                type uint32 {
                  range "0..100" {
                    description
                      "Accelerated advertisement threshold percentage change";
                  }
                }
                description
                  "Accelerated advertisement threshold";
              }
              leaf minimum-change {
                type uint32 {
                  range "0..100000" {
                    description
                      "Accelerated advertisement minimum change (uSec)";
                  }
                }
                description
                  "Accelerated advertisement minimum change";
              }
            }
            container threshold-check {
              description
                "Configure threshold-check for delay measurement advertisement (default: maximum-delay)";
              container average-delay {
                presence "Indicates a average-delay node is configured.";
                description
                  "Enable average-delay threshold-check";
              }
              container minimum-delay {
                presence "Indicates a minimum-delay node is configured.";
                description
                  "Enable minimum-delay threshold-check";
              }
              container maximum-delay {
                presence "Indicates a maximum-delay node is configured.";
                description
                  "Enable maximum-delay threshold-check";
              }
            }
            container anomaly-loss {
              presence "Indicates a anomaly-loss node is configured.";
              description
                "Enter RSVP-TE delay profile advertisement anomaly loss submode";
              leaf upper-bound {
                type uint32 {
                  range "1..99" {
                    description
                      "Anomaly Check advertisement upper-bound (uSec)";
                  }
                }
                must "../lower-bound";
                description
                  "Anomaly Check advertisement upper-bound";
              }
              leaf lower-bound {
                type uint32 {
                  range "0..98" {
                    description
                      "Anomaly Check advertisement lower-bound (uSec)";
                  }
                }
                must "../upper-bound";
                description
                  "Anomaly Check advertisement lower-bound";
              }
            }
            container anomaly-check {
              presence "Indicates a anomaly-check node is configured.";
              description
                "Enter RSVP-TE delay profile advertisement anomaly submode";
              leaf upper-bound {
                type uint32 {
                  range "2..200000" {
                    description
                      "Anomaly Check advertisement upper-bound (uSec)";
                  }
                }
                must "../lower-bound";
                description
                  "Anomaly Check advertisement upper-bound";
              }
              leaf lower-bound {
                type uint32 {
                  range "1..199999" {
                    description
                      "Anomaly Check advertisement lower-bound (uSec)";
                  }
                }
                must "../upper-bound";
                description
                  "Anomaly Check advertisement lower-bound";
              }
            }
          }
        }
      }
      container sr-policy {
        description
          "Enter SR Policy delay profile submode";
        container default {
          presence "Indicates a default node is configured.";
          description
            "Default profile";
          container probe {
            description
              "Enter SR Policy delay probe submode";
            leaf computation-interval {
              type uint32 {
                range "1..3600" {
                  description
                    "Computation interval (seconds)";
                }
              }
              description
                "Interval for metric computation";
            }
            leaf burst-interval {
              type uint32 {
                range "30..15000" {
                  description
                    "Burst interval (msec) (Deprecated in IOS-XR 7.6.1. Please use tx-interval.)";
                }
              }
              description
                "Burst interval (Deprecated in IOS-XR 7.6.1. Please use tx-interval.)";
            }
            leaf tx-interval {
              type uint32 {
                range "30000..15000000" {
                  description
                    "TX interval (usec. Minimum tx interval supported for CPU sessions is 30000 usec)";
                }
              }
              description
                "TX interval";
            }
            container sweep {
              description
                "Enable ECMP hashing by sweeping a field in the probe packet";
              container destination {
                description
                  "Sweep a range of IP destination addresses";
                leaf ipv4 {
                  type inet:ipv4-address-no-zone;
                  must "../range";
                  description
                    "Start of the IPv4 address range, used by IPv4, IPv6 and NULL endpoint SR Policy";
                }
                leaf range {
                  type uint32 {
                    range "0..128" {
                      description
                        "Sweeping range (Should fully be in the 127.0.0.0/8 space)";
                    }
                  }
                  must "../ipv4";
                  description
                    "Number of IP addresses to sweep ";
                }
              }
            }
            container protocol {
              description
                "Configure protocol type for delay measurement probe messages";
              container pm-mpls {
                must "not(../twamp-light)";
                presence "Indicates a pm-mpls node is configured.";
                description
                  "SR Policy delay measurement using RFC6374 with MPLS encap";
              }
              container twamp-light {
                must "not(../pm-mpls)";
                presence "Indicates a twamp-light node is configured.";
                description
                  "SR Policy delay measurement using RFC5357";
              }
            }
            container tos {
              description
                "Enter SR Policy delay probe type of service submode";
              leaf traffic-class {
                type uint32 {
                  range "0..7" {
                    description
                      "Traffic Class value";
                  }
                }
                description
                  "Traffic Class value indicating TOS level used by protocol pm-mpls";
              }
              leaf dscp {
                type uint32 {
                  range "0..63" {
                    description
                      "DSCP value";
                  }
                }
                description
                  "DSCP value indicating TOS level used by protocol twamp-light";
              }
            }
            container measurement-mode {
              description
                "Delay measurement mode";
              container one-way {
                must "not(../two-way)";
                presence "Indicates a one-way node is configured.";
                description
                  "Measure one way delay with timestamp 1 and 2";
              }
              container two-way {
                must "not(../one-way)";
                presence "Indicates a two-way node is configured.";
                description
                  "Measure one way delay with timestamp 1, 2, 3 and 4 without clock synchronization";
              }
            }
            leaf static-delay {
              type uint32 {
                range "0..1000000" {
                  description
                    "static-delay (in microseconds)";
                }
              }
              description
                "Configure static-delay";
            }
          }
          container advertisement {
            description
              "Enter SR Policy delay profile advertisement submode";
            container logging {
              description
                "Enter SR Policy delay profile advertisement logging submode";
              container delay-exceeded {
                presence "Indicates a delay-exceeded node is configured.";
                description
                  "Emit syslog when the delay exceeds the threshold";
              }
            }
            container threshold-check {
              description
                "Configure threshold-check for delay measurement advertisement (default: maximum-delay)";
              container average-delay {
                presence "Indicates a average-delay node is configured.";
                description
                  "Enable average-delay threshold-check";
              }
              container minimum-delay {
                presence "Indicates a minimum-delay node is configured.";
                description
                  "Enable minimum-delay threshold-check";
              }
              container maximum-delay {
                presence "Indicates a maximum-delay node is configured.";
                description
                  "Enable maximum-delay threshold-check";
              }
            }
            container periodic {
              description
                "Go into SR Policy delay periodic advertisement submode";
              container disabled {
                presence "Indicates a disabled node is configured.";
                description
                  "Periodic advertisement disabled";
              }
              leaf interval {
                type uint32 {
                  range "30..3600" {
                    description
                      "Periodic advertisement and metric aggregation interval (seconds)";
                  }
                }
                description
                  "Periodic advertisement and metric aggregation interval";
              }
              leaf threshold {
                type uint32 {
                  range "0..100" {
                    description
                      "Periodic advertisement threshold percentage change (compared to last advertisement)";
                  }
                }
                description
                  "Periodic advertisement threshold (compared to last advertisement)";
              }
              leaf minimum-change {
                type uint32 {
                  range "0..100000" {
                    description
                      "Periodic advertisement minimum change in uSec (compared to last advertisement)";
                  }
                }
                description
                  "Periodic advertisement minimum change (compared to last advertisement)";
              }
            }
            container accelerated {
              presence "Indicates a accelerated node is configured.";
              description
                "Enter SR Policy delay profile advertisement accelerated submode";
              leaf threshold {
                type uint32 {
                  range "0..100" {
                    description
                      "Accelerated advertisement threshold percentage change";
                  }
                }
                description
                  "Accelerated advertisement threshold";
              }
              leaf minimum-change {
                type uint32 {
                  range "0..100000" {
                    description
                      "Accelerated advertisement minimum change (uSec)";
                  }
                }
                description
                  "Accelerated advertisement minimum change";
              }
            }
            container anomaly-check {
              presence "Indicates a anomaly-check node is configured.";
              description
                "Enter SR Policy delay profile advertisement anomaly submode";
              leaf upper-bound {
                type uint32 {
                  range "2..200000" {
                    description
                      "Anomaly Check advertisement upper-bound (uSec)";
                  }
                }
                must "../lower-bound";
                description
                  "Anomaly Check advertisement upper-bound";
              }
              leaf lower-bound {
                type uint32 {
                  range "1..199999" {
                    description
                      "Anomaly Check advertisement lower-bound (uSec)";
                  }
                }
                must "../upper-bound";
                description
                  "Anomaly Check advertisement lower-bound";
              }
            }
            container anomaly-loss {
              presence "Indicates a anomaly-loss node is configured.";
              description
                "Enter SR Policy delay profile advertisement anomaly loss submode";
              leaf upper-bound {
                type uint32 {
                  range "1..99" {
                    description
                      "Anomaly Check advertisement upper-bound (uSec)";
                  }
                }
                must "../lower-bound";
                description
                  "Anomaly Check advertisement upper-bound";
              }
              leaf lower-bound {
                type uint32 {
                  range "0..98" {
                    description
                      "Anomaly Check advertisement lower-bound (uSec)";
                  }
                }
                must "../upper-bound";
                description
                  "Anomaly Check advertisement lower-bound";
              }
            }
          }
        }
      }
      container endpoint {
        description
          "Enter endpoint delay profile submode";
        container default {
          presence "Indicates a default node is configured.";
          description
            "Default profile";
          container probe {
            description
              "Enter endpoint delay probe submode";
            leaf burst-interval {
              type uint32 {
                range "30..15000" {
                  description
                    "Burst interval (msec) (Deprecated in IOS-XR 7.6.1. Please use tx-interval.)";
                }
              }
              description
                "Burst interval (Deprecated in IOS-XR 7.6.1. Please use tx-interval.)";
            }
            leaf tx-interval {
              type uint32 {
                range "30000..15000000" {
                  description
                    "TX interval (usec. Minimum tx interval supported for CPU sessions is 30000 usec)";
                }
              }
              description
                "TX interval";
            }
            leaf computation-interval {
              type uint32 {
                range "1..3600" {
                  description
                    "Computation interval (seconds)";
                }
              }
              description
                "Interval for metric computation";
            }
            container flow-label {
              description
                "Specify flow labels";
              container explicits {
                must "explicit and not (../from)";
                presence "Indicates an explicits node is configured.";
                description
                  "explicit list of flow labels";
                leaf-list explicit {
                  type uint32 {
                    range "0..1048575" {
                      description
                        "Set a flow label";
                    }
                  }
                  max-elements "28";
                  description
                    "explicit list of flow labels";
                }
              }
              leaf from {
                type uint32 {
                  range "0..1048575" {
                    description
                      "value";
                  }
                }
                must "../to";
                description
                  "Lower bound";
              }
              leaf to {
                type uint32 {
                  range "3..1048575" {
                    description
                      "value";
                  }
                }
                must "../from and ../increment";
                description
                  "Upper bound";
              }
              leaf increment {
                type uint32 {
                  range "1..1048575" {
                    description
                      "value";
                  }
                }
                must "../to";
                description
                  "Increment";
              }
            }
            container sweep {
              description
                "Enable ECMP hashing by sweeping a field in the probe packet";
              container destination {
                description
                  "Sweep a range of IP destination addresses";
                leaf ipv4 {
                  type inet:ipv4-address-no-zone;
                  must "../range";
                  description
                    "Start of the IPv4 address range";
                }
                leaf range {
                  type uint32 {
                    range "0..128" {
                      description
                        "Sweeping range (Should fully be in the 127.0.0.0/8 space)";
                    }
                  }
                  must "../ipv4";
                  description
                    "Number of IP addresses to sweep ";
                }
              }
            }
            container measurement-mode {
              description
                "Delay measurement mode";
              container one-way {
                must "not(../two-way)";
                presence "Indicates a one-way node is configured.";
                description
                  "Measure one way delay with timestamp 1 and 2";
              }
              container two-way {
                must "not(../one-way)";
                presence "Indicates a two-way node is configured.";
                description
                  "Measure one way delay with timestamp 1, 2, 3 and 4 without clock synchronization";
              }
            }
            container tos {
              description
                "Enter endpoint delay probe type of service submode";
              leaf dscp {
                type uint32 {
                  range "0..63" {
                    description
                      "DSCP value";
                  }
                }
                description
                  "DSCP value indicating TOS level used by protocol twamp-light";
              }
            }
          }
          container advertisement {
            description
              "Enter endpoint delay profile advertisement submode";
            container logging {
              description
                "Enter Endpoint delay profile advertisement logging submode";
              container delay-exceeded {
                presence "Indicates a delay-exceeded node is configured.";
                description
                  "Emit syslog when the delay exceeds the threshold";
              }
            }
            container threshold-check {
              description
                "Configure threshold-check for delay measurement advertisement (default: maximum-delay)";
              container average-delay {
                presence "Indicates a average-delay node is configured.";
                description
                  "Enable average-delay threshold-check";
              }
              container minimum-delay {
                presence "Indicates a minimum-delay node is configured.";
                description
                  "Enable minimum-delay threshold-check";
              }
              container maximum-delay {
                presence "Indicates a maximum-delay node is configured.";
                description
                  "Enable maximum-delay threshold-check";
              }
            }
            container periodic {
              description
                "Enter endpoint delay periodic advertisement submode";
              container disabled {
                presence "Indicates a disabled node is configured.";
                description
                  "Periodic advertisement disabled";
              }
              leaf interval {
                type uint32 {
                  range "30..3600" {
                    description
                      "Periodic advertisement and metric aggregation interval (seconds)";
                  }
                }
                description
                  "Periodic advertisement and metric aggregation interval";
              }
              leaf threshold {
                type uint32 {
                  range "0..100" {
                    description
                      "Periodic advertisement threshold percentage change (compared to last advertisement)";
                  }
                }
                description
                  "Periodic advertisement threshold (compared to last advertisement)";
              }
              leaf minimum-change {
                type uint32 {
                  range "0..100000" {
                    description
                      "Periodic advertisement minimum change in uSec (compared to last advertisement)";
                  }
                }
                description
                  "Periodic advertisement minimum change (compared to last advertisement)";
              }
            }
            container accelerated {
              presence "Indicates a accelerated node is configured.";
              description
                "Enter endpoint delay profile advertisement accelerated submode";
              leaf threshold {
                type uint32 {
                  range "0..100" {
                    description
                      "Accelerated advertisement threshold percentage change";
                  }
                }
                description
                  "Accelerated advertisement threshold";
              }
              leaf minimum-change {
                type uint32 {
                  range "0..100000" {
                    description
                      "Accelerated advertisement minimum change (uSec)";
                  }
                }
                description
                  "Accelerated advertisement minimum change";
              }
            }
            container anomaly-check {
              presence "Indicates a anomaly-check node is configured.";
              description
                "Enter endpoint delay profile advertisement anomaly submode";
              leaf upper-bound {
                type uint32 {
                  range "2..200000" {
                    description
                      "Anomaly Check advertisement upper-bound (uSec)";
                  }
                }
                must "../lower-bound";
                description
                  "Anomaly Check advertisement upper-bound";
              }
              leaf lower-bound {
                type uint32 {
                  range "1..199999" {
                    description
                      "Anomaly Check advertisement lower-bound (uSec)";
                  }
                }
                must "../upper-bound";
                description
                  "Anomaly Check advertisement lower-bound";
              }
            }
            container anomaly-loss {
              presence "Indicates a anomaly-loss node is configured.";
              description
                "Enter endpoint delay profile advertisement anomaly loss submode";
              leaf upper-bound {
                type uint32 {
                  range "1..99" {
                    description
                      "Anomaly Check advertisement upper-bound (uSec)";
                  }
                }
                must "../lower-bound";
                description
                  "Anomaly Check advertisement upper-bound";
              }
              leaf lower-bound {
                type uint32 {
                  range "0..98" {
                    description
                      "Anomaly Check advertisement lower-bound (uSec)";
                  }
                }
                must "../upper-bound";
                description
                  "Anomaly Check advertisement lower-bound";
              }
            }
          }
        }
      }
      container names {
        description
          "Delay profile name";
        list name {
          key "profile-name";
          description
            "Delay profile name";
          leaf profile-name {
            type xr:Cisco-ios-xr-string {
              length "1..256" {
                description
                  "Profile name";
              }
            }
            description
              "Profile name";
          }
          container probe {
            description
              "Enter SR Policy delay probe submode";
            leaf computation-interval {
              type uint32 {
                range "1..3600" {
                  description
                    "Computation interval (seconds)";
                }
              }
              description
                "Interval for metric computation";
            }
            leaf tx-interval {
              type uint32 {
                range "30000..15000000" {
                  description
                    "TX interval (usec. Minimum tx interval supported for CPU sessions is 30000 usec)";
                }
              }
              description
                "TX interval";
            }
            container sweep {
              description
                "Enable ECMP hashing by sweeping a field in the probe packet";
              container destination {
                description
                  "Sweep a range of IP destination addresses";
                leaf ipv4 {
                  type inet:ipv4-address-no-zone;
                  must "../range";
                  description
                    "Start of the IPv4 address range, used by IPv4, IPv6 and NULL endpoint SR Policy";
                }
                leaf range {
                  type uint32 {
                    range "0..128" {
                      description
                        "Sweeping range (Should fully be in the 127.0.0.0/8 space)";
                    }
                  }
                  must "../ipv4";
                  description
                    "Number of IP addresses to sweep ";
                }
              }
            }
            container flow-label {
              description
                "Specify flow labels";
              container explicits {
                must "explicit and not (../from)";
                presence "Indicates an explicits node is configured.";
                description
                  "explicit list of flow labels";
                leaf-list explicit {
                  type uint32 {
                    range "0..1048575" {
                      description
                        "Set a flow label";
                    }
                  }
                  max-elements "28";
                  description
                    "explicit list of flow labels";
                }
              }
              leaf from {
                type uint32 {
                  range "0..1048575" {
                    description
                      "value";
                  }
                }
                must "../to";
                description
                  "Lower bound";
              }
              leaf to {
                type uint32 {
                  range "3..1048575" {
                    description
                      "value";
                  }
                }
                must "../from and ../increment";
                description
                  "Upper bound";
              }
              leaf increment {
                type uint32 {
                  range "1..1048575" {
                    description
                      "value";
                  }
                }
                must "../to";
                description
                  "Increment";
              }
            }
            container protocol {
              description
                "Configure protocol type for delay measurement probe messages";
              container pm-mpls {
                must "not(../twamp-light)";
                presence "Indicates a pm-mpls node is configured.";
                description
                  "SR Policy delay measurement using RFC6374 with MPLS encap";
              }
              container twamp-light {
                must "not(../pm-mpls)";
                presence "Indicates a twamp-light node is configured.";
                description
                  "SR Policy delay measurement using RFC5357";
              }
            }
            container tos {
              description
                "Enter SR Policy delay probe type of service submode";
              leaf traffic-class {
                type uint32 {
                  range "0..7" {
                    description
                      "Traffic Class value";
                  }
                }
                description
                  "Traffic Class value indicating TOS level used by protocol pm-mpls";
              }
              leaf dscp {
                type uint32 {
                  range "0..63" {
                    description
                      "DSCP value";
                  }
                }
                description
                  "DSCP value indicating TOS level used by protocol twamp-light";
              }
            }
            container measurement-mode {
              description
                "Delay measurement mode";
              container one-way {
                must "not(../two-way)";
                presence "Indicates a one-way node is configured.";
                description
                  "Measure one way delay with timestamp 1 and 2";
              }
              container two-way {
                must "not(../one-way)";
                presence "Indicates a two-way node is configured.";
                description
                  "Measure one way delay with timestamp 1, 2, 3 and 4 without clock synchronization";
              }
            }
            leaf static-delay {
              type uint32 {
                range "0..1000000" {
                  description
                    "static-delay (in microseconds)";
                }
              }
              description
                "Configure static-delay";
            }
          }
          container advertisement {
            description
              "Enter SR Policy delay profile advertisement submode";
            container logging {
              description
                "Enter SR Policy delay profile advertisement logging submode";
              container delay-exceeded {
                presence "Indicates a delay-exceeded node is configured.";
                description
                  "Emit syslog when the delay exceeds the threshold";
              }
            }
            container threshold-check {
              description
                "Configure threshold-check for delay measurement advertisement (default: maximum-delay)";
              container average-delay {
                presence "Indicates a average-delay node is configured.";
                description
                  "Enable average-delay threshold-check";
              }
              container minimum-delay {
                presence "Indicates a minimum-delay node is configured.";
                description
                  "Enable minimum-delay threshold-check";
              }
              container maximum-delay {
                presence "Indicates a maximum-delay node is configured.";
                description
                  "Enable maximum-delay threshold-check";
              }
            }
            container periodic {
              description
                "Go into SR Policy delay periodic advertisement submode";
              container disabled {
                presence "Indicates a disabled node is configured.";
                description
                  "Periodic advertisement disabled";
              }
              leaf interval {
                type uint32 {
                  range "30..3600" {
                    description
                      "Periodic advertisement and metric aggregation interval (seconds)";
                  }
                }
                description
                  "Periodic advertisement and metric aggregation interval";
              }
              leaf threshold {
                type uint32 {
                  range "0..100" {
                    description
                      "Periodic advertisement threshold percentage change (compared to last advertisement)";
                  }
                }
                description
                  "Periodic advertisement threshold (compared to last advertisement)";
              }
              leaf minimum-change {
                type uint32 {
                  range "0..100000" {
                    description
                      "Periodic advertisement minimum change in uSec (compared to last advertisement)";
                  }
                }
                description
                  "Periodic advertisement minimum change (compared to last advertisement)";
              }
            }
            container accelerated {
              presence "Indicates a accelerated node is configured.";
              description
                "Enter SR Policy delay profile advertisement accelerated submode";
              leaf threshold {
                type uint32 {
                  range "0..100" {
                    description
                      "Accelerated advertisement threshold percentage change";
                  }
                }
                description
                  "Accelerated advertisement threshold";
              }
              leaf minimum-change {
                type uint32 {
                  range "0..100000" {
                    description
                      "Accelerated advertisement minimum change (uSec)";
                  }
                }
                description
                  "Accelerated advertisement minimum change";
              }
            }
            container anomaly-check {
              presence "Indicates a anomaly-check node is configured.";
              description
                "Enter SR Policy delay profile advertisement anomaly submode";
              leaf upper-bound {
                type uint32 {
                  range "2..200000" {
                    description
                      "Anomaly Check advertisement upper-bound (uSec)";
                  }
                }
                must "../lower-bound";
                description
                  "Anomaly Check advertisement upper-bound";
              }
              leaf lower-bound {
                type uint32 {
                  range "1..199999" {
                    description
                      "Anomaly Check advertisement lower-bound (uSec)";
                  }
                }
                must "../upper-bound";
                description
                  "Anomaly Check advertisement lower-bound";
              }
            }
            container anomaly-loss {
              presence "Indicates a anomaly-loss node is configured.";
              description
                "Enter interface delay profile advertisement anomaly loss submode";
              leaf upper-bound {
                type uint32 {
                  range "1..99" {
                    description
                      "Anomaly Check advertisement upper-bound (uSec)";
                  }
                }
                must "../lower-bound";
                description
                  "Anomaly Check advertisement upper-bound";
              }
              leaf lower-bound {
                type uint32 {
                  range "0..98" {
                    description
                      "Anomaly Check advertisement lower-bound (uSec)";
                  }
                }
                must "../upper-bound";
                description
                  "Anomaly Check advertisement lower-bound";
              }
            }
          }
        }
      }
    }
    container liveness-profile {
      description
        "Liveness profile";
      container sr-policy {
        description
          "Enter SR Policy delay profile submode";
        container default {
          presence "Indicates a default node is configured.";
          description
            "Default profile";
          container liveness-detection {
            description
              "Enter SR Policy liveness-profile liveness detection submode";
            leaf multiplier {
              type uint32 {
                range "2..10" {
                  description
                    "Detect multiplier";
                }
              }
              description
                "Configure detect multiplier";
            }
          }
          container probe {
            description
              "Enter SR Policy liveness-profile liveness detection probe submode";
            leaf burst-interval {
              type uint32 {
                range "30..15000" {
                  description
                    "Burst interval (msec) (Deprecated in IOS-XR 7.6.1. Please use tx-interval.)";
                }
              }
              description
                "Burst interval (Deprecated in IOS-XR 7.6.1. Please use tx-interval.)";
            }
            leaf tx-interval {
              type uint32 {
                range "3300..15000000" {
                  description
                    "TX interval (usec. Minimum tx interval supported for CPU sessions is 30000 usec)";
                }
              }
              description
                "TX interval";
            }
            container flow-label {
              description
                "Specify flow labels";
              container explicits {
                must "explicit and not (../from)";
                presence "Indicates an explicits node is configured.";
                description
                  "explicit list of flow labels";
                leaf-list explicit {
                  type uint32 {
                    range "0..1048575" {
                      description
                        "Set a flow label";
                    }
                  }
                  max-elements "28";
                  description
                    "explicit list of flow labels";
                }
              }
              leaf from {
                type uint32 {
                  range "0..1048575" {
                    description
                      "value";
                  }
                }
                must "../to";
                description
                  "Lower bound";
              }
              leaf to {
                type uint32 {
                  range "3..1048575" {
                    description
                      "value";
                  }
                }
                must "../from and ../increment";
                description
                  "Upper bound";
              }
              leaf increment {
                type uint32 {
                  range "1..1048575" {
                    description
                      "value";
                  }
                }
                must "../to";
                description
                  "Increment";
              }
            }
            container sweep {
              description
                "Enable ECMP hashing by sweeping a field in the probe packet";
              container destination {
                description
                  "Sweep a range of IP destination addresses";
                leaf ipv4 {
                  type inet:ipv4-address-no-zone;
                  must "../range";
                  description
                    "Start of the IPv4 address range, used by IPv4, IPv6 and NULL endpoint SR Policy";
                }
                leaf range {
                  type uint32 {
                    range "0..128" {
                      description
                        "Sweeping range (Should fully be in the 127.0.0.0/8 space)";
                    }
                  }
                  must "../ipv4";
                  description
                    "Number of IP addresses to sweep ";
                }
              }
            }
            container tos {
              description
                "SR Policy liveness probe type of service";
              leaf dscp {
                type uint32 {
                  range "0..63" {
                    description
                      "DSCP value";
                  }
                }
                description
                  "DSCP value indicating TOS level used by protocol twamp-light";
              }
            }
          }
          container npu-offload {
            presence "Indicates a npu-offload node is configured.";
            description
              "Enable offloading sessions to NPU. NPU Offload is only supported on certain platforms";
            container enable {
              presence "Indicates a enable node is configured.";
              status deprecated;
              description
                "(Keyword Deprecated in 24.1.1)";
            }
          }
        }
      }
      container endpoint {
        description
          "Enter endpoint liveness profile submode";
        container default {
          presence "Indicates a default node is configured.";
          description
            "Default profile";
          container probe {
            description
              "Enter endpoint liveness detection probe submode";
            leaf burst-interval {
              type uint32 {
                range "30..15000" {
                  description
                    "Burst interval (msec) (Deprecated in IOS-XR 7.6.1. Please use tx-interval.)";
                }
              }
              description
                "Burst interval (Deprecated in IOS-XR 7.6.1. Please use tx-interval.)";
            }
            leaf tx-interval {
              type uint32 {
                range "30000..15000000" {
                  description
                    "TX interval (usec. Minimum tx interval supported for CPU sessions is 30000 usec)";
                }
              }
              description
                "TX interval";
            }
            container flow-label {
              description
                "Specify flow labels";
              container explicits {
                must "explicit and not (../from)";
                presence "Indicates an explicits node is configured.";
                description
                  "explicit list of flow labels";
                leaf-list explicit {
                  type uint32 {
                    range "0..1048575" {
                      description
                        "Set a flow label";
                    }
                  }
                  max-elements "28";
                  description
                    "explicit list of flow labels";
                }
              }
              leaf from {
                type uint32 {
                  range "0..1048575" {
                    description
                      "value";
                  }
                }
                must "../to";
                description
                  "Lower bound";
              }
              leaf to {
                type uint32 {
                  range "3..1048575" {
                    description
                      "value";
                  }
                }
                must "../from and ../increment";
                description
                  "Upper bound";
              }
              leaf increment {
                type uint32 {
                  range "1..1048575" {
                    description
                      "value";
                  }
                }
                must "../to";
                description
                  "Increment";
              }
            }
            container sweep {
              description
                "Enable ECMP hashing by sweeping a field in the probe packet";
              container destination {
                description
                  "Sweep a range of IP destination addresses";
                leaf ipv4 {
                  type inet:ipv4-address-no-zone;
                  must "../range";
                  description
                    "Start of the IPv4 address range";
                }
                leaf range {
                  type uint32 {
                    range "0..128" {
                      description
                        "Sweeping range (Should fully be in the 127.0.0.0/8 space)";
                    }
                  }
                  must "../ipv4";
                  description
                    "Number of IP addresses to sweep ";
                }
              }
            }
            container tos {
              description
                "Endpoint liveness probe type of service";
              leaf dscp {
                type uint32 {
                  range "0..63" {
                    description
                      "DSCP value";
                  }
                }
                description
                  "DSCP value indicating TOS level used by protocol twamp-light";
              }
            }
          }
          container liveness-detection {
            description
              "Enter endpoint liveness detection submode";
            leaf multiplier {
              type uint32 {
                range "2..10" {
                  description
                    "Detect multiplier";
                }
              }
              description
                "Configure detect multiplier";
            }
            container logging {
              description
                "Endpoint liveness logging";
              container state-change {
                presence "Indicates a state-change node is configured.";
                description
                  "Emit syslog when the liveness state change detected";
              }
            }
          }
        }
      }
      container names {
        description
          "Liveness profile name";
        list name {
          key "profile-name";
          description
            "liveness-profile name";
          leaf profile-name {
            type string {
              length "1..256" {
                description
                  "Profile name";
              }
            }
            description
              "liveness-profile name";
          }
          container liveness-detection {
            description
              "Enter SR Policy liveness-profile liveness detection submode";
            leaf multiplier {
              type uint32 {
                range "2..10" {
                  description
                    "Detect multiplier";
                }
              }
              description
                "Configure detect multiplier";
            }
            container logging {
              description
                "Liveness logging";
              container state-change {
                presence "Indicates a state-change node is configured.";
                description
                  "Emit syslog when the liveness state change detected";
              }
            }
          }
          container probe {
            description
              "Enter SR Policy liveness-profile liveness detection probe submode";
            leaf burst-interval {
              type uint32 {
                range "30..15000" {
                  description
                    "Burst interval (msec) (Deprecated in IOS-XR 7.6.1. Please use tx-interval.)";
                }
              }
              description
                "Burst interval (Deprecated in IOS-XR 7.6.1. Please use tx-interval.)";
            }
            leaf tx-interval {
              type uint32 {
                range "3300..15000000" {
                  description
                    "TX interval (usec. Minimum tx interval supported for CPU sessions is 30000 usec)";
                }
              }
              description
                "TX interval";
            }
            container flow-label {
              description
                "Specify flow labels";
              container explicits {
                must "explicit and not (../from)";
                presence "Indicates an explicits node is configured.";
                description
                  "explicit list of flow labels";
                leaf-list explicit {
                  type uint32 {
                    range "0..1048575" {
                      description
                        "Set a flow label";
                    }
                  }
                  max-elements "28";
                  description
                    "explicit list of flow labels";
                }
              }
              leaf from {
                type uint32 {
                  range "0..1048575" {
                    description
                      "value";
                  }
                }
                must "../to";
                description
                  "Lower bound";
              }
              leaf to {
                type uint32 {
                  range "3..1048575" {
                    description
                      "value";
                  }
                }
                must "../from and ../increment";
                description
                  "Upper bound";
              }
              leaf increment {
                type uint32 {
                  range "1..1048575" {
                    description
                      "value";
                  }
                }
                must "../to";
                description
                  "Increment";
              }
            }
            container sweep {
              description
                "Enable ECMP hashing by sweeping a field in the probe packet";
              container destination {
                description
                  "Sweep a range of IP destination addresses";
                leaf ipv4 {
                  type inet:ipv4-address-no-zone;
                  must "../range";
                  description
                    "Start of the IPv4 address range, used by IPv4, IPv6 and NULL endpoint SR Policy";
                }
                leaf range {
                  type uint32 {
                    range "0..128" {
                      description
                        "Sweeping range (Should fully be in the 127.0.0.0/8 space)";
                    }
                  }
                  must "../ipv4";
                  description
                    "Number of IP addresses to sweep ";
                }
              }
            }
            container tos {
              description
                "SR Policy liveness probe type of service";
              leaf dscp {
                type uint32 {
                  range "0..63" {
                    description
                      "DSCP value";
                  }
                }
                description
                  "DSCP value indicating TOS level used by protocol twamp-light";
              }
            }
          }
          container npu-offload {
            presence "Indicates a npu-offload node is configured.";
            description
              "Enable offloading sessions to NPU based on hardware capability.";
            container enable {
              presence "Indicates a enable node is configured.";
              status deprecated;
              description
                "(Keyword Deprecated in 24.1.1)";
            }
          }
        }
      }
    }
    container protocol {
      description
        "Supported protocols";
      container twamp-light {
        description
          "Enter twamp-light protocol submode";
        container measurement {
          description
            "Supported measurement types";
          container delay {
            description
              "Enter delay measurement submode";
            container unauthenticated {
              description
                "Enter unauthenticated submode";
              leaf querier-dst-port {
                type uint32 {
                  range "862|1024..14999" {
                    description
                      "Port number. 862 is default TWAMP reserved UDP destination port";
                  }
                }
                description
                  "Port number";
              }
              leaf querier-src-port {
                type uint32 {
                  range "1024..14999" {
                    description
                      "Port number";
                  }
                }
                description
                  "UDP port opened on Route Processor to be used as source port in queries";
              }
              container ipv4 {
                description
                  "timestamp for ipv4 packet";
                container timestamp1 {
                  description
                    "timestamp 1";
                  leaf label {
                    type uint32 {
                      range "256..23999" {
                        description
                          "label";
                      }
                    }
                    description
                      "label";
                  }
                }
                container timestamp2 {
                  description
                    "timestamp 2";
                  leaf label {
                    type uint32 {
                      range "256..23999" {
                        description
                          "label";
                      }
                    }
                    description
                      "label";
                  }
                }
              }
              container ipv6 {
                description
                  "timestamp for ipv6 packet";
                container timestamp1 {
                  description
                    "timestamp 1";
                  leaf label {
                    type uint32 {
                      range "256..23999" {
                        description
                          "label";
                      }
                    }
                    description
                      "label";
                  }
                }
                container timestamp2 {
                  description
                    "timestamp 2";
                  leaf label {
                    type uint32 {
                      range "256..23999" {
                        description
                          "label";
                      }
                    }
                    description
                      "label";
                  }
                }
              }
            }
            container responder {
              description
                "Enter responder submode";
              container allow-querier {
                description
                  "Configure allowed querier prefix; applicable to delay measurement sessions only";
                container addresses {
                  description
                    "Configure allowed querier prefixes";
                  container ipv4-prefixes {
                    description
                      "Configure IPv4 prefixes";
                    list ipv4 {
                      key "address length";
                      description
                        "Configure IPv4 prefix";
                      leaf address {
                        type inet:ipv4-address-no-zone;
                        description
                          "Configure IPv4 prefix address";
                      }
                      leaf length {
                        type uint32 {
                          range "0..31";
                        }
                        description
                          "Configure IPv4 prefix length";
                      }
                    }
                  }
                  container ipv4-addresses {
                    description
                      "Configure IPv4 address";
                    list ipv4 {
                      key "address";
                      description
                        "Configure IPv4 address";
                      leaf address {
                        type inet:ipv4-address-no-zone;
                        description
                          "Configure IPv4 address";
                      }
                    }
                  }
                  container ipv6-prefixes {
                    description
                      "Configure IPv6 prefixes";
                    list ipv6 {
                      key "address length";
                      description
                        "Configure IPv6 prefixes";
                      leaf address {
                        type inet:ipv6-address-no-zone;
                        description
                          "Configure IPv6 prefix address";
                      }
                      leaf length {
                        type uint32 {
                          range "0..127";
                        }
                        description
                          "Configure IPv6 prefix length";
                      }
                    }
                  }
                  container ipv6-addresses {
                    description
                      "Configure IPv6 address";
                    list ipv6 {
                      key "address";
                      description
                        "Configure IPv6 address";
                      leaf address {
                        type inet:ipv6-address-no-zone;
                        description
                          "Configure IPv6 address";
                      }
                    }
                  }
                }
              }
            }
            container querier {
              description
                "Enter querier submode";
              container allow-responder {
                description
                  "Configure allowed responder prefix; applicable to delay measurement sessions only";
                container addresses {
                  description
                    "Configure allowed responder prefixes";
                  container ipv4-prefixess {
                    description
                      "Configure IPv4 prefixes";
                    list ipv4 {
                      key "address length";
                      description
                        "Configure IPv4 prefixes";
                      leaf address {
                        type inet:ipv4-address-no-zone;
                        description
                          "Configure IPv4 prefix address";
                      }
                      leaf length {
                        type uint32 {
                          range "0..31";
                        }
                        description
                          "Configure IPv4 prefix length";
                      }
                    }
                  }
                  container ipv4-addresses {
                    description
                      "Configure IPv4 address";
                    list ipv4 {
                      key "address";
                      description
                        "Configure IPv4 address";
                      leaf address {
                        type inet:ipv4-address-no-zone;
                        description
                          "Configure IPv4 address";
                      }
                    }
                  }
                  container ipv6-prefixes {
                    description
                      "Configure IPv6 prefixes";
                    list ipv6 {
                      key "address length";
                      description
                        "Configure IPv6 prefixes";
                      leaf address {
                        type inet:ipv6-address-no-zone;
                        description
                          "Configure IPv6 prefix address";
                      }
                      leaf length {
                        type uint32 {
                          range "0..127";
                        }
                        description
                          "Configure IPv6 prefix length";
                      }
                    }
                  }
                  container ipv6-addresses {
                    description
                      "Configure IPv6 address";
                    list ipv6 {
                      key "address";
                      description
                        "Configure IPv6 address";
                      leaf address {
                        type inet:ipv6-address-no-zone;
                        description
                          "Configure IPv6 address";
                      }
                    }
                  }
                }
              }
            }
          }
        }
      }
    }
    container path-tracing {
      presence "Indicates a path-tracing node is configured.";
      description
        "Enable path-tracing and enter its submode";
      container timestamp {
        description
          "Timestamp";
        container template {
          description
            "Template";
          container st0 {
            must
              "not(../st1 or ../st2
               or ../st3)";
            presence "Indicates a st0 node is configured.";
            description
              "PTP timestamp nanosecond bits [8:15]";
          }
          container st1 {
            must
              "not(../st0 or ../st2
               or ../st3)";
            presence "Indicates a st1 node is configured.";
            description
              "PTP timestamp nanosecond bits [12:19]";
          }
          container st2 {
            must
              "not(../st0 or ../st1
               or ../st3)";
            presence "Indicates a st2 node is configured.";
            description
              "PTP timestamp nanosecond bits [16:23]";
          }
          container st3 {
            must
              "not(../st0 or ../st1
               or ../st2)";
            presence "Indicates a st3 node is configured.";
            description
              "PTP timestamp nanosecond bits [20:27]";
          }
        }
      }
    }
    container probe-profile {
      description
        "Configure a named profile for a probe session";
      container names {
        description
          "Probe session profile";
        list name {
          key "profile-name";
          description
            "Probe session profile";
          leaf profile-name {
            type string {
              length "1..256" {
                description
                  "Profile name";
              }
            }
            description
              "Probe session profile";
          }
          container flow-label {
            description
              "Specify flow labels";
            container explicits {
              must "explicit and not (../from)";
              presence "Indicates an explicits node is configured.";
              description
                "explicit list of flow labels";
              leaf-list explicit {
                type uint32 {
                  range "0..1048575" {
                    description
                      "Set a flow label";
                  }
                }
                max-elements "28";
                description
                  "explicit list of flow labels";
              }
            }
            leaf from {
              type uint32 {
                range "0..1048575" {
                  description
                    "value";
                }
              }
              must "../to";
              description
                "Lower bound";
            }
            leaf to {
              type uint32 {
                range "3..1048575" {
                  description
                    "value";
                }
              }
              must "../from and ../increment";
              description
                "Upper bound";
            }
            leaf increment {
              type uint32 {
                range "1..1048575" {
                  description
                    "value";
                }
              }
              must "../to";
              description
                "Increment";
            }
          }
          container traffic-class {
            description
              "Specify traffic class";
            container explicits {
              description
                "explicit list of traffic class";
              leaf-list explicit {
                type uint32 {
                  range "0..255" {
                    description
                      "Set a traffic class";
                  }
                }
                max-elements "31";
                description
                  "explicit list of traffic class";
              }
            }
            leaf from {
              type uint32 {
                range "0..255" {
                  description
                    "value";
                }
              }
              must "../to";
              description
                "Lower bound";
            }
            leaf to {
              type uint32 {
                range "3..255" {
                  description
                    "value";
                }
              }
              must "../from and ../increment";
              description
                "Upper bound";
            }
            leaf increment {
              type uint32 {
                range "1..255" {
                  description
                    "value";
                }
              }
              must "../to";
              description
                "Increment";
            }
          }
          leaf tx-interval {
            type uint32 {
              range "3000..60000000" {
                description
                  "TX interval (usec. Minimum tx interval supported for CPU sessions is 30000 usec)";
              }
            }
            description
              "TX interval";
          }
        }
      }
    }
    container distribute-sessions {
      description
        "Distribute SR Policy DM sessions to linecards";
      container enable {
        must "not(../disable)";
        presence "Indicates a enable node is configured.";
        description
          "Enable distribute SR Policy DM sessions to linecards";
      }
      container disable {
        must "not(../enable)";
        presence "Indicates a disable node is configured.";
        description
          "Disable distribute SR Policy DM sessions to linecards (default)";
      }
    }
    container hardware-offload {
      description
        "Hardware offload";
      leaf session {
        type uint32 {
          range "0..65535" {
            description
              "Hardware offloaded session-id";
          }
        }
        description
          "Hardware offloaded session";
      }
      container up {
        must "not(../down)";
        presence "Indicates a up node is configured.";
        description
          "Set session state to up";
      }
      container down {
        must "not(../up)";
        presence "Indicates a down node is configured.";
        description
          "Set session state to down";
      }
    }
  }
}
