module Cisco-IOS-XR-segment-routing-srv6-oper {
  namespace "http://cisco.com/ns/yang/Cisco-IOS-XR-segment-routing-srv6-oper";
  prefix segment-routing-srv6-oper;

  import ietf-inet-types {
    prefix inet;
  }
  import cisco-semver {
    prefix semver;
  }
  import Cisco-IOS-XR-segment-routing-srv6-datatypes {
    prefix dt1;
  }
  include Cisco-IOS-XR-segment-routing-srv6-oper-sub1 {
    revision-date 2023-10-19;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR segment-routing-srv6 package operational data.
     
     This module contains definitions
     for the following management objects:
       srv6: Segment Routing with IPv6 dataplane
     
     Copyright (c) 2013-2023 by Cisco Systems, Inc.
     All rights reserved.";

  revision 2023-10-19 {
    description
      "New SID CTX type supported; uTEF
       2023-02-08
         Added generic static allocation context
       2023-01-20
         backed out Accounting perprefix supported and configure information
       2022-12-15
         New Accounting perprefix supported and configure information
       2022-05-19
         New uSID LIB ranges information
       2022-05-19
         New uSID End.B6 variants with PSP_USD
       2022-05-12
         Platform capabilities extended for displaying if shift-only drop route is supported
       2022-03-23
         Added support for static adjacency SID status
       2021-11-23
         Display locators delayed-delete status
       2021-11-19
         Platform capabilities report extended with Max Locator supported
       2021-10-15
         New SID CTX type supported uDT46 and DT46
       2021-09-16
         Manager will display platform requested defaults for traffic-class and hoplimit SRv6 encap parameters";
    semver:module-version "5.0.0";
  }
  revision 2021-06-23 {
    description
      "Added id name to OOR summary";
    semver:module-version "4.0.0";
  }
  revision 2020-12-11 {
    description
      "Update manager show command for 2 passes
       2020-10-16
           Rename SID count fields in SID manager summary. sids_count only includes non auto-generated SIDs.
       2020-05-06
           changes in def for some endpoint types and headend types
       2020-04-16
           Changes due to common Srv6 bag and renaming some leaf";
    semver:module-version "3.0.0";
  }
  revision 2019-11-20 {
    description
      "Changes for SRv6 end function
       2019-04-22
         Flex-Algo specific changes";
    semver:module-version "2.0.0";
  }
  revision 2019-04-05 {
    description
      "Establish semantic version baseline.";
    semver:module-version "1.0.1";
  }
  revision 2015-11-09 {
    description
      "IOS XR 6.0 revision.";
  }

  grouping LOCATOR-ALL-SID-TABLE {
    description
      "Common node of active, standby";
    container locator-all-sids {
      description
        "Operational container for all (Active and Stale)
         SIDs across all Locators";
      list locator-all-sid {
        key "locator-name sid-opcode";
        description
          "Operational data for given locator and SID
           opcode";
        leaf locator-name {
          type dt1:Srv6-locator-name;
          description
            "Locator name";
        }
        leaf sid-opcode {
          type uint32;
          description
            "Sid opcode";
        }
        uses SRV6-SID-INFO;
      }
    }
  }

  grouping LOCATOR-TABLE {
    description
      "Common node of active, standby";
    container locators {
      description
        "SRv6 locators related information";
      list locator {
        key "name";
        description
          "Operational data for given SRv6 locator";
        container info {
          description
            "Operational data for given SRv6 locator";
          uses SRV6-LOCATOR-INFO;
        }
        container sids {
          description
            "SRv6 locator SID table";
          list sid {
            key "address";
            description
              "Operational data for given SRv6 SID";
            leaf address {
              type inet:ip-address-no-zone;
              description
                "IPv6 address";
            }
            uses SRV6-SID-INFO;
          }
        }
        leaf name {
          type dt1:Srv6-locator-name;
          description
            "Locator name";
        }
      }
    }
  }

  grouping BLOCK-TABLE {
    description
      "Common node of active, standby";
    container blocks {
      description
        "SRv6 SID blocks";
      list block {
        key "prefix prefix-len";
        description
          "A SRv6 SID block";
        container info {
          description
            "Operational data for given SRv6 SID block";
          uses SRV6-IDBLOCK-INFO;
        }
        leaf prefix {
          type inet:ip-address-no-zone;
          description
            "Prefix address";
        }
        leaf prefix-len {
          type uint32 {
            range "16..64";
          }
          description
            "Prefix mask length";
        }
      }
    }
  }

  grouping MANAGER {
    description
      "Common node of active, standby";
    container manager {
      description
        "SID Manager information";
      uses SRV6-SIDMGR-INFO;
    }
  }

  grouping MICRO-SEGMENT {
    description
      "Common node of active, standby";
    container micro-segment {
      description
        "SRv6 Micro-segment info";
      container local-sids {
        description
          "SRv6 Micro-segment local-uSIDs info";
        list local-sid {
          key "sid-prefix sid-prefix-len";
          description
            "SRv6 Micro-segment local-uSID info";
          leaf sid-prefix {
            type inet:ip-address-no-zone;
            description
              "SID Prefix address";
          }
          leaf sid-prefix-len {
            type uint32 {
              range "16..64";
            }
            description
              "SID Prefix mask length";
          }
          uses SRV6-LOCAL-SID-INFO;
        }
      }
    }
  }

  grouping STATIC-ENDPOINT-TABLE {
    description
      "Common node of active, standby";
    container static-endpoints {
      description
        "SRv6 static endpoint related information";
      list static-endpoint {
        key "prefix";
        description
          "Operational data for given SRv6 static endpoint";
        leaf prefix {
          type inet:ip-address-no-zone;
          description
            "SID Prefix";
        }
        uses SRV6-STATIC-ENDPOINT-INFO;
      }
    }
  }

  grouping LOCATOR-ALL-ACTIVE-SID-TABLE {
    description
      "Common node of active, standby";
    container locator-all-active-sids {
      description
        "Operational container for Active SIDs across all
         Locators";
      list locator-all-active-sid {
        key "locator-name sid-opcode";
        description
          "Operational data for given locator and SID
           opcode";
        leaf locator-name {
          type dt1:Srv6-locator-name;
          description
            "Locator name";
        }
        leaf sid-opcode {
          type uint32;
          description
            "Sid opcode";
        }
        uses SRV6-SID-INFO;
      }
    }
  }

  container srv6 {
    config false;
    description
      "Segment Routing with IPv6 dataplane";
    container active {
      description
        "Active SRv6 operational data";
      container locator-all-stale-sids {
        description
          "Operational container for all Stale SIDs across
           all Locators";
        list locator-all-stale-sid {
          key "locator-name sid-opcode";
          description
            "Operational data for given locator and SID
             opcode";
          leaf locator-name {
            type dt1:Srv6-locator-name;
            description
              "Locator name";
          }
          leaf sid-opcode {
            type uint32;
            description
              "Sid opcode";
          }
          uses SRV6-SID-INFO;
        }
      }
      uses MANAGER;
      uses BLOCK-TABLE;
      uses MICRO-SEGMENT;
      uses LOCATOR-TABLE;
      uses LOCATOR-ALL-SID-TABLE;
      uses STATIC-ENDPOINT-TABLE;
      uses LOCATOR-ALL-ACTIVE-SID-TABLE;
    }
    container standby {
      description
        "Standby SRv6 operational data";
      uses MANAGER;
      uses BLOCK-TABLE;
      uses MICRO-SEGMENT;
      uses LOCATOR-TABLE;
      uses LOCATOR-ALL-SID-TABLE;
      uses STATIC-ENDPOINT-TABLE;
      uses LOCATOR-ALL-ACTIVE-SID-TABLE;
    }
  }
}
