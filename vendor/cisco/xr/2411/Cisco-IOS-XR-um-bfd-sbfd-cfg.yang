module Cisco-IOS-XR-um-bfd-sbfd-cfg {
  namespace "http://cisco.com/ns/yang/Cisco-IOS-XR-um-bfd-sbfd-cfg";
  prefix um-bfd-sbfd-cfg;

  import ietf-inet-types {
    prefix inet;
  }
  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco bfd package configuration.
     Copyright (c) 2023 by Cisco Systems, Inc.
     All rights reserved.";

  revision 2023-10-16 {
    description
      "Updating model for um2 changes
       2022-07-11
         Added missing description statement to nodes";
    semver:module-version "2.0.0";
  }
  revision 2020-12-18 {
    description
      "Initial release";
    semver:module-version "1.0.0";
  }

  container bfd {
    description
      "Global BFD configuration commands";
    container echo {
      description
        "Configure BFD echo parameters";
      container ipv4 {
        description
          "IPv4 commands";
        container bundle-per-member {
          description
            "Configure echo for all the micro BFD sessions over Bundles";
          leaf minimum-interval {
            type uint32 {
              range "15..2000" {
                description
                  "The preferred minimum interval (in ms) for the BFD session";
              }
            }
            description
              "Set the preferred minimum interval for the BFD session";
          }
        }
        container source {
          description
            "BFD echo source IP address";
          leaf ipv4-address {
            type inet:ipv4-address-no-zone;
            description
              "IPv4 address";
          }
        }
      }
      container startup {
        description
          "Configure BFD echo startup feature";
        container validate {
          presence "Enable BFD echo validation prior to session bringup";
          description
            "Enable BFD echo validation prior to session bringup";
          leaf force {
            type empty;
            description
              "Ignore remote 'Required Min Echo RX Interval' setting";
          }
        }
      }
      container latency {
        description
          "Configure BFD echo latency features";
        container detect {
          presence "Enable BFD echo latency detection";
          description
            "Enable BFD echo latency detection";
          leaf percentage {
            type uint32 {
              range "100..250" {
                description
                  "Percentage value (default 100)";
              }
            }
            description
              "Percentage of detection time to consider as bad latency";
          }
          leaf count {
            type uint32 {
              range "1..10" {
                description
                  "Count value (default 1)";
              }
            }
            must "../percentage";
            description
              "Count of consecutive bad latency packets to take session down";
          }
        }
      }
      leaf disable {
        type empty;
        description
          "Disable BFD echo mode";
      }
    }
    container trap {
      description
        "Configure BFD trap parameters";
      container singlehop {
        description
          "Configure BFD mode";
        leaf pre-mapped {
          type empty;
          description
            "Configure BFD trap pre-mapped";
        }
      }
    }
    container multipath {
      description
        "Configure BFD multiple path";
      container include-lc-node {
        description
          "Include a LC node";
        container locations {
          description
            "Include a LC node";
          list location {
            key "location-id";
            description
              "Specify a location";
            leaf location-id {
              type xr:Node-id;
              description
                "Fully qualified location specification";
            }
          }
        }
      }
    }
    container multihop {
      description
        "Configure BFD multihop";
      leaf ttl-drop-threshold {
        type uint32 {
          range "0..254" {
            description
              "Drop Threshold";
          }
        }
        description
          "TTL Drop Threshold";
      }
    }
    container dampening {
      description
        "Configure BFD dampening intervals";
      container bundle-member {
        description
          "Configure BFD dampening for bfd over bundle per member feature";
        leaf maximum-wait {
          type uint32 {
            range "1..518400000" {
              description
                "Delay in milliseconds (default 600000)";
            }
          }
          description
            "Maximum delay before bringing up session";
        }
        leaf secondary-wait {
          type uint32 {
            range "1..518400000" {
              description
                "Delay in milliseconds (default 20000)";
            }
          }
          description
            "Secondary delay before bringing up session";
        }
        leaf initial-wait {
          type uint32 {
            range "1..518400000" {
              description
                "Delay in milliseconds (default 16000)";
            }
          }
          description
            "Initial delay before bringing up session";
        }
        leaf l3-only-mode {
          type empty;
          description
            "Apply immediate dampening and only when failure is L3 specific";
        }
      }
      leaf disable {
        type empty;
        description
          "Disable BFD dampening";
      }
      container extensions {
        description
          "Enable dampening extensions";
        leaf down-monitoring {
          type empty;
          description
            "Enable DOWN state session monitoring extensions";
        }
      }
      leaf threshold {
        type uint32 {
          range "60000..3600000" {
            description
              "Threshold in milliseconds (default 120000)";
          }
        }
        description
          "Stability threshold to enable dampening";
      }
      leaf maximum-wait {
        type uint32 {
          range "1..3600000" {
            description
              "Delay in milliseconds (default 120000)";
          }
        }
        description
          "Maximum delay before bringing up session";
      }
      leaf secondary-wait {
        type uint32 {
          range "1..3600000" {
            description
              "Delay in milliseconds (default 5000)";
          }
        }
        description
          "Secondary delay before bringing up session";
      }
      leaf initial-wait {
        type uint32 {
          range "1..3600000" {
            description
              "Delay in milliseconds (default 2000)";
          }
        }
        description
          "Initial delay before bringing up session";
      }
    }
    container bundle {
      description
        "Option for BFD over Bundle";
      container coexistence {
        description
          "How BFD bundle features coexist";
        leaf bob-blb {
          type enumeration {
            enum "inherit" {
              value 1;
              description
                "Use inheritence mechanism";
            }
            enum "logical" {
              value 2;
              description
                "Use BFD logical Bundle natively";
            }
          }
          description
            "Coexistence for BoB and BLB";
        }
      }
    }
    container ipv6 {
      description
        "Ipv6 BFD checksum";
      container checksum {
        description
          "Configure BFD checksum parameters";
        leaf disable {
          type empty;
          description
            "Disable BFD checksum";
        }
      }
    }
    container interfaces {
      description
        "Configure BFD on an interface";
      list interface {
        key "interface-name";
        description
          "Configure BFD on an interface";
        leaf interface-name {
          type xr:Interface-name;
          description
            "Select an interface to configure";
        }
        container echo {
          description
            "Configure BFD echo mode";
          container ipv4 {
            description
              "IPv4 commands";
            container source {
              description
                "BFD echo source IP address";
              leaf ipv4-address {
                type inet:ipv4-address-no-zone;
                description
                  "IPv4 address";
              }
            }
          }
          leaf disable {
            type enumeration {
              enum "disable" {
                value 1;
                description
                  "Disable BFD echo mode for this interface";
              }
              enum "enable" {
                value 0;
                description
                  "enable";
              }
            }
            description
              "Disable BFD echo mode for this interface";
          }
        }
        container ipv6 {
          description
            "Configure BFD ipv6 checksum mode";
          container checksum {
            presence "IPv6 checksum commands";
            description
              "IPv6 checksum commands";
            leaf disable {
              type empty;
              description
                "Disable BFD ipv6 checksum mode for this interface";
            }
          }
        }
        leaf disable {
          type empty;
          description
            "Disable BFD for this interface";
        }
        leaf local-address {
          type inet:ip-address-no-zone;
          description
            "Local address to be used by BFD for this interface";
        }
        leaf tx-interval {
          type uint32 {
            range "3000..30000000" {
              description
                "tx interval in microseconds";
            }
          }
          description
            "BFD TX Interval for this interface in microseconds";
        }
        leaf rx-interval {
          type uint32 {
            range "3000..30000000" {
              description
                "rx interval in microseconds";
            }
          }
          description
            "BFD RX Interval for this interface in microseconds";
        }
        leaf multiplier {
          type uint32 {
            range "2..50" {
              description
                "multiplier";
            }
          }
          description
            "BFD multiplier for this interface";
        }
      }
    }
  }
  container sbfd {
    description
      "Global SBFD configuration commands";
    container local-discriminator {
      description
        "configure local-discriminator";
      container thirty-two-bit-local-discriminators {
        description
          "configure local-discriminator";
        list thirty-two-bit-local-discriminator {
          key "thirty-two-bit-local-discriminator-number";
          description
            "32-bit local-discriminator";
          leaf thirty-two-bit-local-discriminator-number {
            type uint32 {
              range "1..4294967295" {
                description
                  "32-bit local-discriminator";
              }
            }
            description
              "32-bit local-discriminator";
          }
        }
      }
      container ipv4-address-local-discriminators {
        description
          "configure local-discriminator";
        list ipv4-address-local-discriminator {
          key "ipv4-address-local-discriminator-address";
          description
            "ipv4 address as local-discriminator";
          leaf ipv4-address-local-discriminator-address {
            type inet:ipv4-address-no-zone;
            description
              "ipv4 address as local-discriminator";
          }
        }
      }
      leaf dynamic {
        type empty;
        description
          "configure local-discriminator dynamically";
      }
      container interfaces {
        description
          "configure local-discriminator";
        list interface {
          key "interface-name";
          description
            "Interface whose IPv4 address is to be used as local discriminator";
          leaf interface-name {
            type xr:Interface-name;
            description
              "Interface IP-address as discriminator";
          }
        }
      }
    }
    container remote-target {
      description
        "configure remote-target";

      grouping REMOTE-DISCRIMINATORS {
        description
          "Configure remote-discriminator";
        container remote-discriminators {
          description
            "Configure remote-discriminator";
          list remote-discriminator {
            key "remote-discriminator-number";
            description
              "Configure remote-discriminator";
            leaf remote-discriminator-number {
              type uint32 {
                range "1..4294967295" {
                  description
                    "32-bit remote-discriminator";
                }
              }
              description
                "32-bit remote-discriminator";
            }
          }
        }
      }
      container ipv4s {
        description
          "configure remote-target";
        list ipv4 {
          key "ipv4-address";
          description
            "IPv4 address";
          leaf ipv4-address {
            type inet:ipv4-address-no-zone;
            description
              "IPv4 address";
          }
          uses REMOTE-DISCRIMINATORS;
        }
      }
      container ipv6s {
        description
          "configure remote-target";
        list ipv6 {
          key "ipv6-address";
          description
            "IPv6 address";
          leaf ipv6-address {
            type inet:ipv6-address-no-zone;
            description
              "IPv6 address";
          }
          uses REMOTE-DISCRIMINATORS;
        }
      }
    }
  }
}
