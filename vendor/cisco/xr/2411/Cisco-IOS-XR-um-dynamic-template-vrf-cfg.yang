module Cisco-IOS-XR-um-dynamic-template-vrf-cfg {
  namespace "http://cisco.com/ns/yang/Cisco-IOS-XR-um-dynamic-template-vrf-cfg";
  prefix um-dynamic-template-vrf-cfg;

  import Cisco-IOS-XR-types {
    prefix xr;
  }
  import Cisco-IOS-XR-um-dynamic-template-cfg {
    prefix a1;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR dynamic-template-vrf package configuration.
     
     This YANG module augments the
     modules with configuration data.
     
     Copyright (c) 2020-2022 by Cisco Systems, Inc.
     All rights reserved.";

  revision 2022-07-11 {
    description
      "Added missing description statement to nodes";
    semver:module-version "1.1.0";
  }
  revision 2020-04-29 {
    description
      "Initial release";
    semver:module-version "1.0.0";
  }

  grouping TEMPLATE-BODY {
    description
      "Grouping for template";
    leaf vrf {
      type xr:Cisco-ios-xr-string {
        length "1..32" {
          description
            "VRF name";
        }
      }
      description
        "Set VRF in which the interface operates";
    }
  }

  augment "/a1:dynamic-template/a1:type/a1:ppp/a1:template" {
    description
      "This augment extends dynamic-template ppp nodes
       configuration";
    uses TEMPLATE-BODY;
  }
  augment "/a1:dynamic-template/a1:type/a1:ipsubscriber/a1:template" {
    description
      "This augment extends dynamic-template ipsubscriber nodes
       configuration";
    uses TEMPLATE-BODY;
  }
  augment "/a1:dynamic-template/a1:type/a1:service/a1:template" {
    description
      "This augment extends dynamic-template service nodes
       configuration";
    uses TEMPLATE-BODY;
  }
}
