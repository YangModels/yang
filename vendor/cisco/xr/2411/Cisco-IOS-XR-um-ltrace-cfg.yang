module Cisco-IOS-XR-um-ltrace-cfg {
  namespace "http://cisco.com/ns/yang/Cisco-IOS-XR-um-ltrace-cfg";
  prefix um-ltrace-cfg;

  import Cisco-IOS-XR-um-location-cfg {
    prefix location;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ltrace package configuration.
     
     This YANG module augments the
     modules with configuration data.
     
     Copyright (c) 2020-2022 by Cisco Systems, Inc.
     All rights reserved.";

  revision 2022-07-11 {
    description
      "Added missing description statement to nodes";
    semver:module-version "1.1.0";
  }
  revision 2020-09-15 {
    description
      "Initial release";
    semver:module-version "1.0.0";
  }

  grouping LOCATION-BODY {
    description
      "Grouping for location";
    container ltrace {
      description
        "ltrace configuration";
      container mode {
        description
          "Select a memory allocation mode";
        container static {
          must "not(../dynamic)";
          presence "Indicates a static node is configured.";
          description
            "Set ltrace memory allocation to static mode";
          leaf scale-factor {
            type enumeration {
              enum "0" {
                value 0;
                description
                  "Use platform-defined scale-factor";
              }
              enum "1" {
                value 1;
                description
                  "Do not scale down ltrace memory request";
              }
              enum "2" {
                value 2;
                description
                  "Scale down ltrace memory request by 2";
              }
              enum "4" {
                value 4;
                description
                  "Scale down ltrace memory request by 4";
              }
              enum "8" {
                value 8;
                description
                  "Scale down ltrace memory request by 8";
              }
              enum "16" {
                value 16;
                description
                  "Scale down ltrace memory request by 16";
              }
            }
            description
              "Configure a scaling down factor for memory allocation";
          }
        }
        container dynamic {
          must "not(../static)";
          presence "Indicates a dynamic node is configured.";
          description
            "Set ltrace memory allocation to dynamic mode";
          leaf scale-factor {
            type enumeration {
              enum "0" {
                value 0;
                description
                  "Use platform-defined scale-factor";
              }
              enum "1" {
                value 1;
                description
                  "Do not scale down ltrace memory request";
              }
              enum "2" {
                value 2;
                description
                  "Scale down ltrace memory request by 2";
              }
              enum "4" {
                value 4;
                description
                  "Scale down ltrace memory request by 4";
              }
              enum "8" {
                value 8;
                description
                  "Scale down ltrace memory request by 8";
              }
              enum "16" {
                value 16;
                description
                  "Scale down ltrace memory request by 16";
              }
            }
            description
              "Configure a scaling down factor for memory allocation";
          }
        }
      }
      container persist {
        description
          "configure persistent storage information";
        leaf dump-enable {
          type string {
            pattern "pre|act" {
              description
                "dump-enable value pre only in case of preconfigured locations
                  dump-enable value act only in case of active locations";
            }
          }
          description
            "enable/disable dumpimng to persistent storage";
        }
      }
    }
  }

  augment "/location:locations/location:location" {
    description
      "This augment extends active nodes configuration";
    uses LOCATION-BODY;
  }
  augment "/location:locations/location:preconfigured-location" {
    description
      "This augment extends preconfigured nodes
       configuration";
    uses LOCATION-BODY;
  }
}
