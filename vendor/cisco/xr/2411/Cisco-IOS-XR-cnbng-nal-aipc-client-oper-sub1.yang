submodule Cisco-IOS-XR-cnbng-nal-aipc-client-oper-sub1 {
  belongs-to Cisco-IOS-XR-cnbng-nal-aipc-client-oper {
    prefix Cisco-IOS-XR-cnbng-nal-aipc-client-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR cnbng-nal-aipc-client package operational data.
     
     Copyright (c) 2013-2023 by Cisco Systems, Inc.
     All rights reserved.";

  revision 2023-02-19 {
    description
      "Changed readable strings like server/service names from type char to string.
       2021-10-19
         AIPC client stats display command updated.";
    semver:module-version "2.0.0";
  }
  revision 2020-08-14 {
    description
      "adding schema support for aipc client.";
    semver:module-version "1.0.0";
  }
  revision 2019-04-05 {
    description
      "Establish semantic version baseline.";
  }
  revision 2015-11-09 {
    description
      "IOS XR 6.0 revision.";
  }

  grouping NAL-AIPC-STATS-DATA {
    description
      "aipc connection stats";
    leaf server-name-xr {
      type string {
        length "0..256";
      }
      description
        "server Name";
    }
    leaf service-name-xr {
      type string {
        length "0..256";
      }
      description
        "process Name";
    }
    leaf conn-present {
      type boolean;
      description
        "connection status";
    }
    leaf tx-attempt-count {
      type uint32;
      description
        "Tx attempt count";
    }
    leaf tx-count {
      type uint32;
      description
        "tx count";
    }
    leaf rx-count {
      type uint32;
      description
        "Rx count";
    }
    leaf notify-connect-count {
      type uint32;
      description
        "Notify connect count";
    }
    leaf notify-queue-high-count {
      type uint32;
      description
        "Notify Queue High count";
    }
    leaf notify-queue-low-count {
      type uint32;
      description
        "Notify Queue low count";
    }
    leaf notify-queue-full-count {
      type uint32;
      description
        "Notify Queue full count";
    }
    leaf notify-data-waiting-count {
      type uint32;
      description
        "Notify data waiting count";
    }
    leaf notify-error-count {
      type uint32;
      description
        "Notify error count";
    }
    leaf notify-close-count {
      type uint32;
      description
        "Notify close count";
    }
    leaf notify-sendstatus-count {
      type uint32;
      description
        "Notify send status count";
    }
    leaf notify-open-count {
      type uint32;
      description
        "Notify open count";
    }
    leaf pulse-data-waiting-count {
      type uint32;
      description
        "Pulse Data waiting count";
    }
    leaf queue-full {
      type boolean;
      description
        "Queue full";
    }
    leaf queue-full-drop {
      type uint32;
      description
        "Queue full drop";
    }
    leaf queue-ewouldblock-count {
      type uint32;
      description
        "queue would block count";
    }
    leaf outstanding-buffers {
      type uint32;
      description
        "Outstanding Buffers";
    }
    leaf cumulative-overflow-msgs {
      type uint32;
      description
        "cumulative overflow message";
    }
    leaf hwm-overflow-msgs {
      type uint32;
      description
        "Hwm overflow msg";
    }
    leaf get-mtu-failure {
      type uint32;
      description
        "Get Mtu Failure";
    }
    leaf get-buffer-failure {
      type uint32;
      description
        "get Buffer Failure";
    }
    leaf get-buffer-datap-failure {
      type uint32;
      description
        "get Buffer datap Failure";
    }
    leaf conn-failure {
      type uint32;
      description
        "Conn Failure";
    }
    leaf send-failure {
      type uint32;
      description
        "Send Failure";
    }
    leaf receive-failure {
      type uint32;
      description
        "receive Failure";
    }
    leaf release-buffer-failure {
      type uint32;
      description
        "Release Buffer failure";
    }
    leaf overflow-q-flush-count {
      type uint32;
      description
        "Overflow flush count";
    }
    leaf get-buffer-size-failure {
      type uint32;
      description
        "get Buffer size Failure";
    }
    leaf notify-queue-low-count-after-high {
      type uint32;
      description
        "notify queue low count after high";
    }
    leaf last-high-watermark-count-timestamp {
      type uint32;
      description
        "High WaterMark timestamp";
    }
    leaf last-low-watermark-count-timestamp {
      type uint32;
      description
        "Low WaterMark timestamp";
    }
  }
}
