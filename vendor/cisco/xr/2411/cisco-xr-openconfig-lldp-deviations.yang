module cisco-xr-openconfig-lldp-deviations {


  namespace "http://cisco.com/ns/yang/cisco-xr-openconfig-lldp-deviations";
  prefix  "lldpdevs";

  import openconfig-lldp { prefix oc-lldp; }

  organization "Cisco Systems, Inc.";

  contact
    "Cisco Systems, Inc.
     Customer Service

     Postal: 170 West Tasman Drive
     San Jose, CA 95134

     Tel: +1 800 553-NETS

     E-mail: cs-yang@cisco.com";

  description
    "This module contains a set of deviations for 
 
     openconfig-lldp.yang@2017-03-08 

     on Cisco IOS-XR devices.

     Copyright (c) 2023 by Cisco Systems, Inc.
     All rights reserved.";

  revision "2023-10-04" {
    description
      "Initial revision of new deviations";
  }

  deviation /oc-lldp:lldp/oc-lldp:config/oc-lldp:enabled {
    deviate replace {
      default false;
    }
  }

  deviation /oc-lldp:lldp/oc-lldp:state/oc-lldp:enabled {
    deviate replace {
      default false;
    }
  }

}
