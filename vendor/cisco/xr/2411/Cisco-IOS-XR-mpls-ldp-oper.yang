module Cisco-IOS-XR-mpls-ldp-oper {
  namespace "http://cisco.com/ns/yang/Cisco-IOS-XR-mpls-ldp-oper";
  prefix mpls-ldp-oper;

  import ietf-inet-types {
    prefix inet;
  }
  import Cisco-IOS-XR-types {
    prefix xr;
  }
  import cisco-semver {
    prefix semver;
  }
  include Cisco-IOS-XR-mpls-ldp-oper-sub3 {
    revision-date 2023-02-17;
  }
  include Cisco-IOS-XR-mpls-ldp-oper-sub2 {
    revision-date 2023-02-17;
  }
  include Cisco-IOS-XR-mpls-ldp-oper-sub1 {
    revision-date 2023-02-17;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR mpls-ldp package operational data.
     
     This module contains definitions
     for the following management objects:
       mpls-ldp: MPLS LDP operational data
     
     Copyright (c) 2013-2023 by Cisco Systems, Inc.
     All rights reserved.";

  revision 2023-02-17 {
    description
      "Added interface Auto Configure TE Tunnels parameters.
       2021-12-20
         Added new path for cloned tunnels
       2021-09-20
         Added keys for nbr-br-af-info";
    semver:module-version "2.0.0";
  }
  revision 2021-04-06 {
    description
      "Added BSID data in LDP forwarding";
    semver:module-version "1.1.0";
  }
  revision 2019-04-05 {
    description
      "Establish semantic version baseline.";
    semver:module-version "1.0.0";
  }
  revision 2017-09-07 {
    description
      "Fixed type translation error.";
  }
  revision 2017-05-01 {
    description
      "Fixing backward compatibility error in module.";
  }
  revision 2015-11-09 {
    description
      "IOS XR 6.0 revision.";
  }

  typedef Mpls-ldp-oper-af-name {
    type enumeration {
      enum "ipv4" {
        value 1;
        description
          "IPv4";
      }
      enum "ipv6" {
        value 2;
        description
          "IPv6";
      }
      enum "all" {
        value 65535;
        description
          "All";
      }
    }
    description
      "Mpls ldp oper af name";
  }

  grouping NSR-SUMMARY-ALL {
    description
      "Common node of active, standby, node";
    container nsr-summary-all {
      description
        "Summary information regarding LDP NSR State";
      uses LDP-NSR-SUM;
    }
  }

  grouping LDP-ID {
    description
      "Common node of default-vrf, vrf";
    container ldp-id {
      description
        "Local LDP Id";
      uses LDP-LDPID-INFO;
    }
  }

  grouping CAPABILITY-TABLE {
    description
      "Common node of default-vrf, vrf";
    container capabilities {
      description
        "LDP capability database information";
      list capability {
        key "capability-type";
        description
          "Information on LDP capability";
        leaf capability-type {
          type uint32;
          description
            "The capability type (IANA assigned)";
        }
        uses LDP-CAP-INFO;
      }
    }
  }

  grouping NEIGHBOR-CAPABILITY-TABLE {
    description
      "Common node of default-vrf, vrf";
    container neighbor-capabilities {
      description
        "LDP Neighbors Capabilities";
      list neighbor-capability {
        description
          "Information on capabilities of a particular LDP
           neighbor";
        leaf lsr-id {
          type inet:ipv4-address-no-zone;
          description
            "LSR ID of neighbor";
        }
        leaf label-space-id {
          type uint32 {
            range "0..65535";
          }
          description
            "Label space ID of neighbor";
        }
        uses LDP-NBR-CAP-INFO;
      }
    }
  }

  grouping VRF-TABLE {
    description
      "Common node of active, standby, node";
    container vrfs {
      description
        "VRF specific operational data";
      list vrf {
        key "vrf-name";
        description
          "Operational data for given VRF";
        leaf vrf-name {
          type xr:Cisco-ios-xr-string;
          description
            "VRF Name";
        }
        uses GRACEFUL-RESTART;
        uses CAPABILITY-TABLE;
        uses SUMMARY;
        uses AF-TABLE;
        uses NEIGHBOR-BRIEF-TABLE;
        uses BACKOFF-PARAMETERS;
        uses BACKOFF-TABLE;
        uses NSR;
        uses PARAMETERS;
        uses ISSU;
        uses NEIGHBOR-CAPABILITY-TABLE;
        uses NEIGHBOR-TABLE;
        uses LDP-ID;
        uses STATISTICS-TABLE;
      }
    }
  }

  grouping BACKOFF-PARAMETERS {
    description
      "Common node of default-vrf, vrf";
    container backoff-parameters {
      description
        "The LDP Backoff Parameters";
      uses LDP-BACKOFF-INFO;
    }
  }

  grouping HA-SUMMARY {
    description
      "Common node of nsr, issu";
    container ha-summary {
      description
        "LDP HA Summary";
      uses LDP-NSR-SUM;
    }
  }

  grouping STATISTICS-TABLE {
    description
      "Common node of default-vrf, vrf";
    container statistics {
      description
        "The LDP Statistics";
      list statistic {
        description
          "Statistical Information on a particular LDP
           neighbor";
        leaf lsr-id {
          type inet:ipv4-address-no-zone;
          description
            "LSR ID of neighbor";
        }
        leaf label-space-id {
          type uint32 {
            range "0..65535";
          }
          description
            "Label space ID of neighbor";
        }
        uses LDP-STATS-INFO;
      }
    }
  }

  grouping DISCOVERY-SUMMARY-ALL {
    description
      "Common node of active, standby, node";
    container discovery-summary-all {
      description
        "Summary information regarding LDP discovery";
      uses LDP-DISCOVERY-SUMMARY-INFO;
    }
  }

  grouping BINDINGS-SUMMARY-ALL {
    description
      "Common node of active, standby, node";
    container bindings-summary-all {
      description
        "Aggregate VRF counters for the LDP Label
         Infomation Base (LIB)";
      uses LDP-BINDING-SUMMARY;
    }
  }

  grouping DEFAULT-VRF {
    description
      "Common node of active, standby, node";
    container default-vrf {
      description
        "DefaultVRF specific operational data";
      uses GRACEFUL-RESTART;
      uses CAPABILITY-TABLE;
      uses SUMMARY;
      uses AF-TABLE;
      uses NEIGHBOR-BRIEF-TABLE;
      uses BACKOFF-PARAMETERS;
      uses BACKOFF-TABLE;
      uses NSR;
      uses PARAMETERS;
      uses ISSU;
      uses NEIGHBOR-CAPABILITY-TABLE;
      uses NEIGHBOR-TABLE;
      uses LDP-ID;
      uses STATISTICS-TABLE;
    }
  }

  grouping NEIGHBOR-BRIEF-TABLE {
    description
      "Common node of default-vrf, vrf";
    container neighbor-briefs {
      description
        "The LDP Neighbors (brief)";
      list neighbor-brief {
        description
          "Brief information on a particular LDP neighbor";
        leaf lsr-id {
          type inet:ipv4-address-no-zone;
          description
            "LSR ID of neighbor";
        }
        leaf label-space-id {
          type uint32 {
            range "0..65535";
          }
          description
            "Label space ID of neighbor";
        }
        uses LDP-NEIGHBOR-BRIEF-INFO;
      }
    }
  }

  grouping ATO-MDB-TABLE {
    description
      "Common node of active, standby, node";
    container ato-mdb-table-entries {
      description
        "AToM DB Table";
      list ato-mdb-table-entry {
        description
          "Entries in AToM DB";
        leaf peer-id {
          type inet:ip-address-no-zone;
          description
            "Peer ID";
        }
        leaf fe-ctype {
          type uint32;
          description
            "FEC Type";
        }
        leaf pw-id {
          type uint32;
          description
            "PW ID";
        }
        leaf agi-type {
          type uint32;
          description
            "AGI Type";
        }
        leaf agi {
          type uint32;
          description
            "AGI";
        }
        leaf saii-type {
          type uint32;
          description
            "SAII Type";
        }
        leaf saii-local-id {
          type inet:ip-address-no-zone;
          description
            "SAII Local ID";
        }
        leaf saii-global-id {
          type uint32;
          description
            "SAII Global ID";
        }
        leaf saii-prefix {
          type xr:Hex-integer;
          description
            "SAII Prefix";
        }
        leaf saii-ac-id {
          type uint32;
          description
            "SAII AC ID";
        }
        leaf taii-type {
          type uint32;
          description
            "TAII Type";
        }
        leaf taii-local-id {
          type inet:ip-address-no-zone;
          description
            "TAII Local ID";
        }
        leaf taii-global-id {
          type uint32;
          description
            "TAII Global ID";
        }
        leaf taii-prefix {
          type xr:Hex-integer;
          description
            "TAII Prefix";
        }
        leaf taii-ac-id {
          type uint32;
          description
            "TAII AC ID";
        }
        uses L2VPN-LDP-ATOM;
      }
    }
  }

  grouping PARAMETERS {
    description
      "Common node of default-vrf, vrf";
    container parameters {
      description
        "LDP parameters";
      uses LDP-PARAMETERS;
    }
  }

  grouping FORWARDING-SUMMARY-ALL {
    description
      "Common node of active, standby, node";
    container forwarding-summary-all {
      description
        "Summary information regarding LDP forwarding
         setup";
      uses LDP-FWD-SUMM-INFO;
    }
  }

  grouping SUMMARY {
    description
      "Common node of default-vrf, vrf";
    container summary {
      description
        "LDP VRF summary";
      uses LDP-SUMMARY-VRF;
    }
  }

  grouping MPLS-LDP-OPER-SUMMARY {
    description
      "Common node of default-vrf, vrfCommon node of
       active, standby, node";
    container summary {
      description
        "LDP summary";
      uses LDP-SUMMARY;
    }
  }

  grouping HA-STATISTICS {
    description
      "Common node of nsr, issu";
    container ha-statistics {
      description
        "LDP NSR Statistics related information";
      container ha-global {
        description
          "LDP NSR Global Statistics information";
        uses LDP-NSR-GBL-STATS-INFO;
      }
      uses HA-NEIGHBOR-TABLE;
    }
  }

  grouping NSR {
    description
      "Common node of default-vrf, vrf";
    container nsr {
      description
        "LDP NSR related information";
      container nsr-pending {
        description
          "LDP NSR Pending related information";
        uses HA-NEIGHBOR-TABLE;
      }
      uses HA-SUMMARY;
      uses HA-STATISTICS;
    }
  }

  grouping GRACEFUL-RESTART {
    description
      "Common node of default-vrf, vrf";
    container graceful-restart {
      description
        "LDP Graceful Restart info";
      uses LDP-GR-GLOBAL-INFO;
    }
  }

  grouping HA-NEIGHBOR-TABLE {
    description
      "Common node of nsr-pending, ha-statistics";
    container ha-neighbors {
      description
        "The LDP HA Neighbors";
      list ha-neighbor {
        description
          "Information on a particular LDP HA neighbor";
        leaf lsr-id {
          type inet:ipv4-address-no-zone;
          description
            "LSR ID of neighbor";
        }
        leaf label-space-id {
          type uint32 {
            range "0..65535";
          }
          description
            "Label space ID of neighbor";
        }
        uses LDP-NSR-STATS-NBR-INFO;
      }
    }
  }

  grouping NEIGHBOR-TABLE {
    description
      "Common node of default-vrf, vrf";
    container neighbors {
      description
        "The LDP Neighbors";
      list neighbor {
        description
          "Information on a particular LDP neighbor";
        leaf lsr-id {
          type inet:ipv4-address-no-zone;
          description
            "LSR ID of neighbor";
        }
        leaf label-space-id {
          type uint32 {
            range "0..65535";
          }
          description
            "Label space ID of neighbor";
        }
        uses LDP-NEIGHBOR-INFO;
      }
    }
  }

  grouping ISSU {
    description
      "Common node of default-vrf, vrf";
    container issu {
      description
        "LDP ISSU related information";
      uses HA-SUMMARY;
      uses HA-STATISTICS;
    }
  }

  grouping BACKOFF-TABLE {
    description
      "Common node of default-vrf, vrf";
    container backoffs {
      description
        "The LDP backoff";
      list backoff {
        description
          "LDP Backoff Information";
        leaf lsr-id {
          type inet:ipv4-address-no-zone;
          description
            "LSR ID of neighbor";
        }
        leaf label-space-id {
          type uint32 {
            range "0..65535";
          }
          description
            "Label space ID of neighbor";
        }
        uses LDP-BACKOFF-ENTRY-INFO;
      }
    }
  }

  grouping AF-TABLE {
    description
      "Common node of default-vrf, vrf";
    container afs {
      description
        "Address Family specific operational data";
      list af {
        key "af-name";
        description
          "Operational data for given Address Family";
        container interface-summary {
          description
            "IPv4 interface summary information";
          uses LDP-INTF-SUM;
        }
        container bindings {
          description
            "The LDP Bindings";
          list binding {
            key "prefix";
            description
              "Binding Information";
            leaf prefix {
              type inet:ip-prefix;
              description
                "The IP Prefix";
            }
            uses LDP-TIB-ENTRY-DETAIL;
          }
        }
        container igp {
          description
            "LDP IGP related information";
          container syncs {
            description
              "LDP IGP Sync related information";
            list sync {
              key "interface-name";
              description
                "LDP-IGP Synchronization related information
                 for an interface";
              leaf interface-name {
                type xr:Interface-name;
                description
                  "The Interface Name";
              }
              uses LDP-IGP-SYNC-INFO;
            }
          }
          container sync-delay-restart {
            description
              "LDP-IGP Synchronization Delay related
               information";
            uses LDP-IGP-SYNC-DELAY-RESTART-INFO;
          }
        }
        container bindings-summary {
          description
            "Counters for the LDP Label Infomation Base
             (LIB)";
          uses LDP-BINDING-SUMMARY;
        }
        container interfaces {
          description
            "LDP Interface related information";
          list interface {
            key "interface-name";
            description
              "IPv4 interface information";
            leaf interface-name {
              type xr:Interface-name;
              description
                "The Interface Name";
            }
            uses LDP-INTF;
          }
        }
        container discovery {
          description
            "The LDP Discovery";
          container link-hellos {
            description
              "The LDP Discovery link";
            list link-hello {
              key "interface-name";
              description
                "Information on LDP link discovery";
              leaf interface-name {
                type xr:Interface-name;
                description
                  "The Interface Name";
              }
              uses LDP-DISCOVERY-LINK-INFO;
            }
          }
          container summary {
            description
              "Summarized information on LDP discovery";
            uses LDP-DISCOVERY-SUMMARY-INFO;
          }
          container targeted-hellos {
            description
              "The LDP Discovery Targeted";
            list targeted-hello {
              description
                "Information on LDP targeted discovery";
              leaf local-address {
                type inet:ip-address-no-zone;
                description
                  "Local IP Address";
              }
              leaf target-address {
                type inet:ip-address-no-zone;
                description
                  "The target IP Address";
              }
              uses LDP-TARGETED-HELLO-INFO;
            }
          }
          container brief {
            description
              "Brief information on LDP discovery";
            container link-hello-briefs {
              description
                "The LDP Discovery link brief information";
              list link-hello-brief {
                key "interface-name";
                description
                  "Brief information on LDP link discovery";
                leaf interface-name {
                  type xr:Interface-name;
                  description
                    "The Interface Name";
                }
                uses LDP-DISCOVERY-LINK-BRIEF-INFO;
              }
            }
            container targeted-hello-briefs {
              description
                "The LDP Discovery Targeted brief information";
              list targeted-hello-brief {
                description
                  "Brief information on LDP targeted discovery";
                leaf local-address {
                  type inet:ip-address-no-zone;
                  description
                    "Local IP Address";
                }
                leaf target-address {
                  type inet:ip-address-no-zone;
                  description
                    "The target IP Address";
                }
                uses LDP-TARGETED-HELLO-BRIEF-INFO;
              }
            }
          }
          container stats {
            description
              "The LDP Discovery Statistics";
            list stat {
              description
                "Information on LDP discovery statistics";
              leaf lsr-id {
                type inet:ipv4-address-no-zone;
                description
                  "LSR ID of neighbor";
              }
              leaf label-space-id {
                type uint32 {
                  range "0..65535";
                }
                description
                  "Label space ID of neighbor";
              }
              uses LDP-DISCOVERY-ADJ-GRP-INFO;
            }
          }
        }
        container clone-interfaces {
          description
            "cloned tunnel information";
          list clone-interface {
            key "interface-name";
            description
              "Clonned tunnel interface information";
            leaf interface-name {
              type xr:Interface-name;
              description
                "The Interface Name";
            }
            uses LDP-CLONE-ENABLED-TUNNEL;
          }
        }
        container forwardings {
          description
            "The LDP Forwarding rewrites";
          list forwarding {
            key "prefix";
            description
              "Information on a particular LDP forwarding
               rewrite";
            leaf prefix {
              type inet:ip-prefix;
              description
                "The IP Prefix";
            }
            uses LDP-FWD-PFX-INFO;
          }
        }
        container bindings-advertise-spec {
          description
            "Advertisement Spec (ACL) for LDP Label
             Infomation Base (LIB)";
          uses LDP-BINDING-ADVT-SPEC;
        }
        container forwarding-summary {
          description
            "Summary information regarding LDP forwarding
             setup";
          uses LDP-FWD-SUMM-INFO;
        }
        leaf af-name {
          type Mpls-ldp-oper-af-name;
          description
            "Address Family name";
        }
      }
    }
  }

  container mpls-ldp {
    config false;
    description
      "MPLS LDP operational data";
    container global {
      description
        "Global MPLS LDP operational data";
      container standby {
        description
          "Standby MPLS LDP operational data";
        uses DEFAULT-VRF;
        uses FORWARDING-SUMMARY-ALL;
        uses BINDINGS-SUMMARY-ALL;
        uses ATO-MDB-TABLE;
        uses NSR-SUMMARY-ALL;
        uses MPLS-LDP-OPER-SUMMARY;
        uses VRF-TABLE;
        uses DISCOVERY-SUMMARY-ALL;
      }
      container active {
        description
          "Active MPLS LDP operational data";
        uses DEFAULT-VRF;
        uses FORWARDING-SUMMARY-ALL;
        uses BINDINGS-SUMMARY-ALL;
        uses ATO-MDB-TABLE;
        uses NSR-SUMMARY-ALL;
        uses MPLS-LDP-OPER-SUMMARY;
        uses VRF-TABLE;
        uses DISCOVERY-SUMMARY-ALL;
      }
    }
    container nodes {
      description
        "Location MPLS LDP operational data";
      list node {
        key "node-name";
        description
          "The MPLD LDP operational data for a particular
           node";
        leaf node-name {
          type xr:Node-id;
          description
            "The identifier for the node";
        }
        uses DEFAULT-VRF;
        uses FORWARDING-SUMMARY-ALL;
        uses BINDINGS-SUMMARY-ALL;
        uses ATO-MDB-TABLE;
        uses NSR-SUMMARY-ALL;
        uses MPLS-LDP-OPER-SUMMARY;
        uses VRF-TABLE;
        uses DISCOVERY-SUMMARY-ALL;
      }
    }
  }
}
