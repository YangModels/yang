module Cisco-IOS-XR-fretta-bcm-dpa-qos-resources-oper {
  namespace "http://cisco.com/ns/yang/Cisco-IOS-XR-fretta-bcm-dpa-qos-resources-oper";
  prefix fretta-bcm-dpa-qos-resources-oper;

  import Cisco-IOS-XR-types {
    prefix xr;
  }
  import cisco-semver {
    prefix semver;
  }
  include Cisco-IOS-XR-fretta-bcm-dpa-qos-resources-oper-sub1 {
    revision-date 2023-08-11;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR fretta-bcm-dpa-qos-resources package operational data.
     
     This module contains definitions
     for the following management objects:
       dpa-qos: QOS hw resources data
     
     Copyright (c) 2013-2023 by Cisco Systems, Inc.
     All rights reserved.";

  revision 2023-08-11 {
    description
      "Added reserved connector count and per-interface usage to bcmdpa_qos_connectors_info_per_core";
    semver:module-version "1.0.0";
  }
  revision 2023-06-06 {
    description
      "Added schema for qos connectors resource utilization cli";
  }
  revision 2019-04-05 {
    description
      "Establish semantic version baseline.";
  }
  revision 2015-11-09 {
    description
      "IOS XR 6.0 revision.";
  }

  container dpa-qos {
    config false;
    description
      "QOS hw resources data";
    container nodes {
      description
        "QOS hw resources data for available nodes";
      list node {
        key "node-name";
        description
          "QOS hw resources data for a particular node";
        container qos-conn-res-datas {
          description
            "QOS connector Resources";
          list qos-conn-res-data {
            key "npu-id";
            description
              "QoS connector resources data for a particular
               NPU";
            leaf npu-id {
              type uint32;
              description
                "NPU number";
            }
            uses BCMDPA-QOS-CONNECTORS-INFO;
          }
        }
        leaf node-name {
          type xr:Node-id;
          description
            "Node ID";
        }
      }
    }
  }
}
