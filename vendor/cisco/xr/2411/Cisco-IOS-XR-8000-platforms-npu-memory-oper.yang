module Cisco-IOS-XR-8000-platforms-npu-memory-oper {
  namespace "http://cisco.com/ns/yang/Cisco-IOS-XR-8000-platforms-npu-memory-oper";
  prefix xr-8000-platforms-npu-memory-oper;

  import cisco-semver {
    prefix semver;
  }
  import Cisco-IOS-XR-platforms-ofa-oper {
    prefix a1;
  }
  include Cisco-IOS-XR-8000-platforms-npu-memory-oper-sub1 {
    revision-date 2019-04-05;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR 8000-platforms-npu-memory package operational data.
     
     This YANG module augments the
       Cisco-IOS-XR-platforms-ofa-oper
     module with state data.
     
     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  augment "/a1:ofa/a1:stats/a1:nodes/a1:node" {
    description
      "This augment extends the operational data of
       'Cisco-IOS-XR-platforms-ofa-oper'";
    container hw-memory-table {
      description
        "OFA HW memory stats ";
      container hw-memory-instance {
        description
          "Instance ID";
        container hw-memory-congested-data {
          description
            "OFA HW memory congested detail";
          uses OFA-SYSDB-PKT-MEMORY-CONGESTION-ARRAY-ST;
        }
        container hw-memory-usage-data {
          description
            "OFA HW memory usage ";
          uses OFA-SYSDB-PKT-MEMORY-USAGE-ARRAY-ST;
        }
      }
    }
  }
}
