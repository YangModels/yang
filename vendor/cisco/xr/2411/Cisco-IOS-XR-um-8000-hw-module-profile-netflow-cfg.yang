module Cisco-IOS-XR-um-8000-hw-module-profile-netflow-cfg {
  namespace "http://cisco.com/ns/yang/Cisco-IOS-XR-um-8000-hw-module-profile-netflow-cfg";
  prefix um-8000-hw-module-profile-netflow-cfg;

  import Cisco-IOS-XR-types {
    prefix xr;
  }
  import Cisco-IOS-XR-um-8000-hw-module-profile-cfg {
    prefix a1;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR 8000-hw-module-profile-netflow package configuration.
     
     This YANG module augments the
     modules with configuration data.
     
     Copyright (c) 2020-2022 by Cisco Systems, Inc.
     All rights reserved.";

  revision 2022-08-19 {
    description
      "Updated the yang model as duplicate location key is removed from configuration
       2022-07-11
         Added missing description statement to nodes";
    semver:module-version "2.0.0";
  }
  revision 2020-10-20 {
    description
      "Initial release";
    semver:module-version "1.0.0";
  }

  augment "/a1:hw-module/a1:profile" {
    description
      "This augment extends 8000-hw-module profile nodes
       configuration";
    container netflow {
      description
        "Configure Netflow profile.";
      container ipfix315-enable {
        description
          "IPFIX 315 enable ";
        container locations {
          description
            "Location of NETFLOW config";
          list location {
            key "location-name";
            description
              "Location of NETFLOW config";
            leaf location-name {
              type xr:Node-id;
              description
                "Location of NETFLOW config (must be same as location-name)";
            }
          }
        }
      }
      container sflow-enable {
        description
          "sFlow enable ";
        container locations {
          description
            "Location of sFlow config";
          list location {
            key "location-name";
            description
              "Location of sFlow config";
            leaf location-name {
              type xr:Node-id;
              description
                "Location of sFlow config (must be same as location-name)";
            }
          }
        }
      }
    }
  }
}
