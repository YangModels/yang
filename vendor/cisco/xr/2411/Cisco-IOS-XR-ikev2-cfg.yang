module Cisco-IOS-XR-ikev2-cfg {
  namespace "http://cisco.com/ns/yang/Cisco-IOS-XR-ikev2-cfg";
  prefix ikev2-cfg;

  import ietf-inet-types {
    prefix inet;
  }
  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ikev2 package configuration.
     
     This module contains definitions
     for the following management objects:
       ikev2: Internet key exchange(IKEv2) config commands
     
     Copyright (c) 2013-2023 by Cisco Systems, Inc.
     All rights reserved.";

  revision 2023-01-30 {
    description
      "PPK Support
       2021-10-22
         Vrf Support";
    semver:module-version "1.2.0";
  }
  revision 2019-09-27 {
    description
      "Certificate Support";
    semver:module-version "1.1.0";
  }
  revision 2019-04-05 {
    description
      "Establish semantic version baseline.";
    semver:module-version "1.0.1";
  }
  revision 2018-12-11 {
    description
      "Encryption Type Support";
  }
  revision 2015-11-09 {
    description
      "IOS XR 6.0 revision.";
  }

  typedef Ikev2-auth-method {
    type enumeration {
      enum "rsa-signature" {
        value 1;
        description
          "RSA SIGNATURE";
      }
      enum "pre-shared-key" {
        value 2;
        description
          "PRESHARED KEY";
      }
    }
    description
      "Ikev2 auth method";
  }

  container ikev2 {
    description
      "Internet key exchange(IKEv2) config commands";
    container profile-names {
      description
        "IKEv2 profile config commands";
      list profile-name {
        key "name";
        description
          "IKEv2 profile name";
        container match-identity {
          description
            "Match a profile based on remote identity";
          container address-subs {
            description
              "Match a profile based on remote identity
               address";
            list address-sub {
              key "address mask";
              description
                "Remote ip address for matching identity";
              leaf address-mask {
                type empty;
                description
                  "This indicates existence of remote ip
                   address";
              }
              leaf address {
                type inet:ipv4-address-no-zone;
                description
                  "Address";
              }
              leaf mask {
                type inet:ipv4-address-no-zone;
                description
                  "Mask";
              }
            }
          }
          leaf any {
            type empty;
            description
              "Match any peer identity";
          }
        }
        container authentication {
          description
            "Authentication method for IKEv2";
          container remote-auth-methods {
            description
              "Remote authentication";
            list remote-auth-method {
              key "method";
              description
                "Remote auth method";
              leaf method {
                type Ikev2-auth-method;
                description
                  "Remote auth Method name";
              }
            }
          }
          container local-auth {
            description
              "Local authentication method";
            leaf local-auth-method {
              type Ikev2-auth-method;
              description
                "Local auth method";
            }
          }
        }
        container trustpoint-names {
          description
            "IKEv2 trustpoints";
          list trustpoint-name {
            key "tpname";
            description
              "IKEv2 trustpoint name";
            leaf trustpoint-val {
              type empty;
              mandatory true;
              description
                "This indicates existence of trustpoint";
            }
            leaf tpname {
              type xr:Cisco-ios-xr-string {
                length "1..32";
              }
              description
                "Trustpoint name";
            }
          }
        }
        leaf profile-sub {
          type empty;
          mandatory true;
          description
            "This indicates existence of profile";
        }
        leaf match-fvrf {
          type xr:Cisco-ios-xr-string {
            length "1..32";
          }
          description
            "fvrf to use";
        }
        leaf lifetime {
          type uint32 {
            range "120..86400";
          }
          description
            "Lifetime(in sec) for IKEv2 SA";
        }
        leaf keyring-in-profile {
          type xr:Cisco-ios-xr-string {
            length "1..32";
          }
          description
            "Keyring to use with local/remote
             authentication method";
        }
        leaf ppk-keyring-in-profile {
          type xr:Cisco-ios-xr-string {
            length "1..32";
          }
          description
            "PPK Keyring to use with local/remote
             authentication method";
        }
        leaf name {
          type xr:Cisco-ios-xr-string {
            length "1..32";
          }
          description
            "Name of the profile";
        }
      }
    }
    container policy-names {
      description
        "Configure IKEv2 policies";
      list policy-name {
        key "name";
        description
          "IKEv2 policy name";
        container address-vals {
          description
            "Match a policy based on address";
          list address-val {
            key "address";
            description
              "local address used to match policy";
            leaf address {
              type inet:ipv4-address-no-zone;
              description
                "Address";
            }
          }
        }
        container fvrfs {
          description
            "Matching fvrfs for the policy";
          list fvrf {
            key "vrf-name";
            description
              "VRF to use with configured policy";
            leaf vrf-name {
              type xr:Cisco-ios-xr-string {
                length "1..32";
              }
              description
                "Vrf name";
            }
          }
        }
        container proposals {
          description
            "proposal for the given policy";
          list proposal {
            key "proposal-name";
            description
              "Proposal to use with configured policy";
            leaf proposal-name {
              type xr:Cisco-ios-xr-string {
                length "1..32";
              }
              description
                "Proposal name";
            }
          }
        }
        leaf policy-sub {
          type empty;
          mandatory true;
          description
            "This indicates existence of policy";
        }
        leaf name {
          type xr:Cisco-ios-xr-string {
            length "1..32";
          }
          description
            "Policy name";
        }
      }
    }
    container proposal-names {
      description
        "Configure IKEv2 proposals";
      list proposal-name {
        key "name";
        description
          "IKEv2 proposal name";
        container prfses {
          description
            "Specify one or more transforms of prf";
          leaf-list prfs {
            type string {
              length "1..8";
            }
            max-elements "4";
            description
              "PRF Algorithm";
          }
        }
        container groups {
          description
            "Specify one or more transforms of group";
          leaf-list group {
            type string {
              length "1..3";
            }
            max-elements "8";
            description
              "Encryption Algorithm";
          }
        }
        container integrities {
          description
            "Specify one or more transforms of integrity";
          leaf-list integrity {
            type string {
              length "1..8";
            }
            max-elements "4";
            description
              "Integrity Algorithm";
          }
        }
        container encryptions {
          description
            "Specify one or more transforms of encryption";
          leaf-list encryption {
            type string {
              length "1..12";
            }
            max-elements "5";
            description
              "Encryption Algorithm";
          }
        }
        leaf proposal-sub {
          type empty;
          mandatory true;
          description
            "This indicates existence of proposal";
        }
        leaf name {
          type xr:Cisco-ios-xr-string {
            length "1..32";
          }
          description
            "Proposal name";
        }
      }
    }
  }
}
