module Cisco-IOS-XR-um-error-disable-cfg {
  namespace "http://cisco.com/ns/yang/Cisco-IOS-XR-um-error-disable-cfg";
  prefix um-error-disable-cfg;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR error-disable package configuration.
     
     This YANG module augments the
     modules with configuration data.
     
     Copyright (c) 2021-2022 by Cisco Systems, Inc.
     All rights reserved.";

  revision 2022-08-08 {
    description
      "Added container bad-link-error
       2021-11-23
         Removed container bundle-down";
    semver:module-version "2.0.0";
  }
  revision 2021-02-15 {
    description
      "Initial release";
    semver:module-version "1.0.0";
  }

  container error-disable {
    description
      "Configure error-disable";
    container recovery {
      description
        "Configure auto-recovery";
      container cause {
        description
          "Configure auto-recovery for a specific cause";
        container link-oam-session-down {
          description
            "Used when an Ethernet Link OAM session goes down";
          leaf interval {
            type uint32 {
              range "30..1000000" {
                description
                  "Specify an interval for the auto-recovery period in seconds";
              }
            }
            description
              "Configure an interval for the auto-recovery period";
          }
        }
        container link-oam-discovery-timeout {
          description
            "Used when an Ethernet Link OAM session fails to come up in time";
          leaf interval {
            type uint32 {
              range "30..1000000" {
                description
                  "Specify an interval for the auto-recovery period in seconds";
              }
            }
            description
              "Configure an interval for the auto-recovery period";
          }
        }
        container link-oam-capabilities-conflict {
          description
            "Used when Ethernet Link OAM configuration conflicts with the peer";
          leaf interval {
            type uint32 {
              range "30..1000000" {
                description
                  "Specify an interval for the auto-recovery period in seconds";
              }
            }
            description
              "Configure an interval for the auto-recovery period";
          }
        }
        container link-oam-miswired {
          description
            "Used when a mis-wiring is detected with Ethernet Link OAM";
          leaf interval {
            type uint32 {
              range "30..1000000" {
                description
                  "Specify an interval for the auto-recovery period in seconds";
              }
            }
            description
              "Configure an interval for the auto-recovery period";
          }
        }
        container link-oam-link-fault {
          description
            "Used when a unidirectional link is detected by Ethernet Link OAM";
          leaf interval {
            type uint32 {
              range "30..1000000" {
                description
                  "Specify an interval for the auto-recovery period in seconds";
              }
            }
            description
              "Configure an interval for the auto-recovery period";
          }
        }
        container link-oam-dying-gasp {
          description
            "Used when a dying gasp is detected by Ethernet Link OAM";
          leaf interval {
            type uint32 {
              range "30..1000000" {
                description
                  "Specify an interval for the auto-recovery period in seconds";
              }
            }
            description
              "Configure an interval for the auto-recovery period";
          }
        }
        container link-oam-critical-event {
          description
            "Used when a critical event is detected by Ethernet Link OAM";
          leaf interval {
            type uint32 {
              range "30..1000000" {
                description
                  "Specify an interval for the auto-recovery period in seconds";
              }
            }
            description
              "Configure an interval for the auto-recovery period";
          }
        }
        container link-oam-threshold-breached {
          description
            "Used when a configured error threshold has been breached";
          leaf interval {
            type uint32 {
              range "30..1000000" {
                description
                  "Specify an interval for the auto-recovery period in seconds";
              }
            }
            description
              "Configure an interval for the auto-recovery period";
          }
        }
        container stp-bpdu-guard {
          description
            "Used when an STP BPDU is received on a port on which BPDU Guard is configured";
          leaf interval {
            type uint32 {
              range "30..1000000" {
                description
                  "Specify an interval for the auto-recovery period in seconds";
              }
            }
            description
              "Configure an interval for the auto-recovery period";
          }
        }
        container stp-legacy-bpdu {
          description
            "Used when a legacy BPDU is received on a port. Only MSTP and RSTP BPDUs are supported";
          leaf interval {
            type uint32 {
              range "30..1000000" {
                description
                  "Specify an interval for the auto-recovery period in seconds";
              }
            }
            description
              "Configure an interval for the auto-recovery period";
          }
        }
        container cluster-udld {
          description
            "Used when UDLD is enabled on a Cluster port and UDLD is in aggressive mode and UDLD goes uni directional";
          leaf interval {
            type uint32 {
              range "30..1000000" {
                description
                  "Specify an interval for the auto-recovery period in seconds";
              }
            }
            description
              "Configure an interval for the auto-recovery period";
          }
        }
        container cluster-minlinks {
          description
            "Used when system is in Cluster mode and there are not enough links between them";
          leaf interval {
            type uint32 {
              range "30..1000000" {
                description
                  "Specify an interval for the auto-recovery period in seconds";
              }
            }
            description
              "Configure an interval for the auto-recovery period";
          }
        }
        container udld-unidirectional {
          description
            "Used when a link is detected to be unidirectional by UDLD";
          leaf interval {
            type uint32 {
              range "30..1000000" {
                description
                  "Specify an interval for the auto-recovery period in seconds";
              }
            }
            description
              "Configure an interval for the auto-recovery period";
          }
        }
        container udld-neighbor-mismatch {
          description
            "Used when mismatched neighbors are detected by UDLD";
          leaf interval {
            type uint32 {
              range "30..1000000" {
                description
                  "Specify an interval for the auto-recovery period in seconds";
              }
            }
            description
              "Configure an interval for the auto-recovery period";
          }
        }
        container udld-timeout {
          description
            "Used when all UDLD neigbors on the link have timed out";
          leaf interval {
            type uint32 {
              range "30..1000000" {
                description
                  "Specify an interval for the auto-recovery period in seconds";
              }
            }
            description
              "Configure an interval for the auto-recovery period";
          }
        }
        container udld-loopback {
          description
            "Used when UDLD detects that the port is in loopback mode(i.e. its Tx is directly connected to its Rx)";
          leaf interval {
            type uint32 {
              range "30..1000000" {
                description
                  "Specify an interval for the auto-recovery period in seconds";
              }
            }
            description
              "Configure an interval for the auto-recovery period";
          }
        }
        container pvrst-pvid-mismatch {
          description
            "Used when a PVRST BPDU packet is tagged with a VLAN ID which is different from the VLAN ID on which it was sent.";
          leaf interval {
            type uint32 {
              range "30..1000000" {
                description
                  "Specify an interval for the auto-recovery period in seconds";
              }
            }
            description
              "Configure an interval for the auto-recovery period";
          }
        }
        container l2vpn-bport-mac-move {
          description
            "Used when an L2VPN bridge port interface experiences a large number of MAC move events, causing high CPU usage.";
          leaf interval {
            type uint32 {
              range "30..1000000" {
                description
                  "Specify an interval for the auto-recovery period in seconds";
              }
            }
            description
              "Configure an interval for the auto-recovery period";
          }
        }
        container ot-track-state-change {
          description
            "Used when the state of Object Tracking track changes.";
          leaf interval {
            type uint32 {
              range "30..1000000" {
                description
                  "Specify an interval for the auto-recovery period in seconds";
              }
            }
            description
              "Configure an interval for the auto-recovery period";
          }
        }
        container link-oam-dampening {
          description
            "Used when Ethernet Link-OAM forces an interface down due to too many EFD down events.";
          leaf interval {
            type uint32 {
              range "30..1000000" {
                description
                  "Specify an interval for the auto-recovery period in seconds";
              }
            }
            description
              "Configure an interval for the auto-recovery period";
          }
        }
        container bad-link-error {
          description
            "Used when physical layer errors forces an interface down due to too many ASIC link error events.";
          leaf interval {
            type uint32 {
              range "30..1000000" {
                description
                  "Specify an interval for the auto-recovery period in seconds";
              }
            }
            description
              "Configure an interval for the auto-recovery period";
          }
        }
      }
    }
  }
}
