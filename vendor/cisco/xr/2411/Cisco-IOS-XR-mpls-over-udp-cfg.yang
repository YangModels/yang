module Cisco-IOS-XR-mpls-over-udp-cfg {
  namespace "http://cisco.com/ns/yang/Cisco-IOS-XR-mpls-over-udp-cfg";
  prefix mpls-over-udp-cfg;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR mpls-over-udp package configuration.
     
     This module contains definitions
     for the following management objects:
       hardware-module-pdfib: PD FIB configuration
     
     Copyright (c) 2013-2020 by Cisco Systems, Inc.
     All rights reserved.";

  revision 2020-04-15 {
    description
      "Schema added.";
    semver:module-version "1.0.0";
  }
  revision 2019-04-05 {
    description
      "Establish semantic version baseline.";
  }
  revision 2015-11-09 {
    description
      "IOS XR 6.0 revision.";
  }

  container hardware-module-pdfib {
    description
      "PD FIB configuration";
    leaf mpls-over-udp-decap {
      type empty;
      description
        "PD FIB Feature RFC 7510 MPLS-over-UDP decap";
    }
  }
}
