submodule Cisco-IOS-XR-cnbng-nal-oper-sub2 {
  belongs-to Cisco-IOS-XR-cnbng-nal-oper {
    prefix Cisco-IOS-XR-cnbng-nal-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR cnbng-nal package operational data.
     
     Copyright (c) 2013-2023 by Cisco Systems, Inc.
     All rights reserved.";

  revision 2023-10-24 {
    description
      "Removed SRG role change counters.
       2023-10-12
         Updated CP-UP connection information to include PFCP and GTPu socket bind result.
       2023-10-03
         Interface name length size is updated.
       2023-07-24
         Annotated process readiness and control-plane/user-plane connection data for EDT support.
       2023-04-07
         Added field to display api-stats viz err status, last fail time, upid for all API used by cnbng nal.
       2023-03-30
         Changed String in dynamic route bag
       2023-03-28
         Reduced failed entry bag description length from 256 to 65 bytes.
       2023-01-11
         Added counters for cp-up spa recon stats.
       2022-12-14
         Added the new field desciption in auto-loopback vrf and srg group configuration.
       2022-12-02
         Updated the data type of node feature-id to String.
       2022-11-21
         Added block size in chunk statistics and session replay response as dynamic data in bag.
       2022-11-03
         Updated binary data associated with each event in event history entry as private.
       2022-10-20
         Changed readable strings like interface/vrf names from type char to string.
       2022-09-06
         Renamed structure in bag file.
       2022-08-31
         Migrated XR library event history to internal history library.
       2022-08-30
         Added key meta-data into oper yang lists.
       2022-08-08
         Added new element outstanding_ka_expiry_cnt in bag file.
       2022-08-04
         Removed dynamic route history query from schema.
       2022-07-27
         Updated SRG group admin state datatype
       2022-07-21
         Updated nal_subscriber_session_info gateway IP format from uint32_t to in_addr_t
       2022-05-16
         added new elements in bag
       2022-03-16
         Added SRG group summary support
       2022-03-15
         Counters arrays made dynamic.
       2022-03-15
         Added counter for fast switchover timer expiry.
       2022-03-10
         Added counters for SRG group recon start and end.
       2022-03-07
         Added additional NAL disconnect types
       2022-03-04
         Added counter for zero subscribers in recon replay request.
       2022-03-02
         Added new counters for SRG stats retry enqueue.
       2022-03-02
         Added new counter for SRG group state is not ready.
       2022-02-23
         Updated SRG show command bag with reconciliation information.
       2022-02-10
         Added SRG show commands.
       2022-01-27
         Updated length of interface name string length from 64 to 72
       2022-01-20
         Updated process info bag with in-flight configuration values
       2021-12-21
         Added access interface event history
       2021-12-01
         Updated xml tree definitions
       2021-11-11
         Dynamic Route info addition in route provision flow.
       2021-10-20
         AIPC server stats display command updated.
       2021-10-10
         Added schema support for multiple show CLIs
       2021-09-30
         Added new counter for tracking empty pulses in nal_main_edm_nal_counters lac_stats.
       2021-09-29
         Added batch counter for spio resync";
    semver:module-version "3.0.0";
  }
  revision 2021-09-27 {
    description
      "Updated transport and association status enum in yang model.
       2021-07-22
          Updated nal_main_edm_process_info to include SPIO connection information.
       2021-07-06
          Added schema support for all address family in show dynamic route command.
       2021-07-02
          Added connection status information and interface counters.
       2021-06-30
          Added process readiness and transaction pending flags in nal_main_edm_process_readiness.
       2021-06-26
          Updated nal_main_edm_process_info bag to include features supported from platform.
       2021-06-20
          Added new path for getting subscriber summary based on VRF name.
       2021-06-14
          Added tunnel vrf for LAC/LNS subscriber bag
       2021-06-11
          Updated subscriber brief bag with subscriber interface handle.
       2021-05-31
          Added new NAL counter type client api
       2021-05-29
          Added new bag for getting subscriber count and global routes installed.
       2021-05-05
          Added tr459 mode enable flag in bag structure.
       2021-04-01
          added LNS subcriber info in bag
       2021-03-15
          added details for LAC subcriber in bag";
    semver:module-version "2.0.0";
  }
  revision 2021-02-17 {
    description
      "Added AFI only filters";
    semver:module-version "1.0.0";
  }
  revision 2021-02-10 {
    description
      "Removed redundant fail route index";
  }
  revision 2021-02-04 {
    description
      "Added multi framed route support, metric and tag";
  }
  revision 2021-01-23 {
    description
      "Added new NAL counter type thread_stats";
  }
  revision 2020-12-13 {
    description
      "NAL SVM service final timestamp.";
  }
  revision 2020-12-08 {
    description
      "modify Disconnect History Filter keys.";
  }
  revision 2020-11-27 {
    description
      "NAL counters.";
  }
  revision 2020-11-10 {
    description
      "Update bgen path for dynamic routes and removed schema for dynamic routes history.";
  }
  revision 2020-10-26 {
    description
      "Update bag type for AIPC server stats.";
  }
  revision 2020-10-15 {
    description
      "Added schema support for cnbng-nal filter oper commands.";
  }
  revision 2020-10-08 {
    description
      "Moved counter and AIPC stats to new bag files.";
  }
  revision 2020-10-02 {
    description
      "Modified alter gen script to modify leaf list to list.";
  }
  revision 2020-09-18 {
    description
      "Added schema support for cnbng-nal access-interface oper commands.";
  }
  revision 2020-09-15 {
    description
      "adding schema support for NAL chunk statistics oper bag.";
  }
  revision 2020-09-10 {
    description
      "Updated schema for filtering subscriber summary.";
  }
  revision 2020-09-03 {
    description
      "adding schema support for NAL Counters, Dynamic routes, summary and history bag.";
  }
  revision 2020-07-24 {
    description
      "adding schema support for disconect uniuqe and modifying unique summary.";
  }
  revision 2020-06-06 {
    description
      "adding schema support for NAL Process-Info Bag";
  }
  revision 2020-05-29 {
    description
      "adding schema support for Disconnect History Filter.";
  }
  revision 2020-05-15 {
    description
      "adding schema support for NAL CP Transport Connection Status Bag";
  }
  revision 2020-04-30 {
    description
      "adding schema support for NAL VRF Table records";
  }
  revision 2020-04-23 {
    description
      "added new elements in bag";
  }
  revision 2020-04-09 {
    description
      "modified class name for FADB records";
  }
  revision 2020-04-03 {
    description
      "adding schema support for subsriber summary and FADB records";
  }
  revision 2020-04-02 {
    description
      "adding schema support for service profiles and process readiness";
  }
  revision 2020-03-30 {
    description
      "adding schema support for v4 and v6 framed route";
  }
  revision 2019-04-05 {
    description
      "Establish semantic version baseline.";
  }
  revision 2015-11-09 {
    description
      "IOS XR 6.0 revision.";
  }

  grouping NAL-MAIN-EDM-HISTOGRAM-TABLE {
    description
      "NAL MAIN EDM HISTOGRAM TABLE";
    leaf api-name {
      type string {
        length "0..65";
      }
      description
        "API name";
    }
    leaf req-count {
      type uint32;
      description
        "Request count";
    }
    leaf avg-time-sec {
      type uint32;
      units "second";
      description
        "Average time seconds";
    }
    leaf avg-time-nsec {
      type uint32;
      units "nanosecond";
      description
        "Average time nano-seconds";
    }
    leaf min-time-sec {
      type uint32;
      units "second";
      description
        "Minimum time seconds";
    }
    leaf min-time-nsec {
      type uint32;
      units "nanosecond";
      description
        "Minimum time nano-seconds";
    }
    leaf max-time-sec {
      type uint32;
      units "second";
      description
        "Maximum time seconds";
    }
    leaf max-time-nsec {
      type uint32;
      units "nanosecond";
      description
        "Maximum time nano-seconds";
    }
    leaf upid {
      type uint32;
      description
        "UPID";
    }
    leaf time-sec {
      type uint32;
      units "second";
      description
        "timestamp seconds";
    }
    leaf time-nsec {
      type uint32;
      units "nanosecond";
      description
        "timestamp nano-seconds";
    }
    leaf-list hist-array {
      type uint32;
      max-elements "9";
      description
        "Histogram counters";
    }
  }

  grouping NAL-MAIN-EDM-32B-COUNTER {
    description
      "NAL MAIN EDM 32B COUNTER";
    leaf counter-name {
      type string {
        length "0..65";
      }
      description
        "Counter name";
    }
    leaf counter {
      type uint32;
      description
        "Counter value";
    }
  }

  grouping NAL-MAIN-EDM-NAL-COUNTERS {
    description
      "NAL counter statistics";
    list subscriber-stat {
      description
        "Subscriber statistics";
      uses NAL-MAIN-EDM-32B-COUNTER;
    }
    list error-stat {
      description
        "Error statistics";
      uses NAL-MAIN-EDM-32B-COUNTER;
    }
    list acc-stat {
      description
        "Accounting statistics";
      uses NAL-MAIN-EDM-32B-COUNTER;
    }
    list svm-stat {
      description
        "SVM statistics";
      uses NAL-MAIN-EDM-32B-COUNTER;
    }
    list spa-stat {
      description
        "SPA statistics";
      uses NAL-MAIN-EDM-32B-COUNTER;
    }
    list hist-stat {
      description
        "Histogram statistics";
      uses NAL-MAIN-EDM-HISTOGRAM-TABLE;
    }
    list spa-lib-counter {
      description
        "SPA LIB Counters";
      uses NAL-MAIN-EDM-32B-COUNTER;
    }
    list cp-recon-stat {
      description
        "CP Recon statistics";
      uses NAL-MAIN-EDM-32B-COUNTER;
    }
    list pkt-stat {
      description
        "Packet statistics";
      uses NAL-MAIN-EDM-32B-COUNTER;
    }
    list thread-stat {
      description
        "Thread statistics";
      uses NAL-MAIN-EDM-32B-COUNTER;
    }
    list lac-stat {
      description
        "LAC statistics";
      uses NAL-MAIN-EDM-32B-COUNTER;
    }
    list client-api-stat {
      description
        "Client API statistics";
      uses NAL-MAIN-EDM-32B-COUNTER;
    }
    list srg-stat {
      description
        "SRG statistics";
      uses NAL-MAIN-EDM-32B-COUNTER;
    }
  }
}
