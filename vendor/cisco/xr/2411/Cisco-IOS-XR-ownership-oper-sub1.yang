submodule Cisco-IOS-XR-ownership-oper-sub1 {
  belongs-to Cisco-IOS-XR-ownership-oper {
    prefix Cisco-IOS-XR-ownership-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR ownership package operational data.
     
     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  grouping OV-INFO {
    description
      "OV INFO";
    leaf serial-no {
      type int32;
      description
        "serial number of OV";
    }
    leaf pdc {
      type string;
      description
        "PDC of OV";
    }
  }

  grouping OWNERSHIP-INFO {
    description
      "ownership information bag ";
    container ov-summary {
      description
        "ov summary";
      uses OV-INFO;
    }
    leaf oc-info {
      type string;
      description
        "ownership certificate info";
    }
  }

  grouping ANTITHEFT-INFO {
    description
      "ANTITHEFT INFO";
    leaf reimage-status {
      type string;
      description
        "status of reimage flag";
    }
  }
}
