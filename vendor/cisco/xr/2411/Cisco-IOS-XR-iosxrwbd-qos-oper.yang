module Cisco-IOS-XR-iosxrwbd-qos-oper {
  namespace "http://cisco.com/ns/yang/Cisco-IOS-XR-iosxrwbd-qos-oper";
  prefix iosxrwbd-qos-oper;

  import Cisco-IOS-XR-types {
    prefix xr;
  }
  import cisco-semver {
    prefix semver;
  }
  include Cisco-IOS-XR-iosxrwbd-qos-oper-sub3 {
    revision-date 2022-09-27;
  }
  include Cisco-IOS-XR-iosxrwbd-qos-oper-sub2 {
    revision-date 2022-09-27;
  }
  include Cisco-IOS-XR-iosxrwbd-qos-oper-sub1 {
    revision-date 2022-09-27;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR iosxrwbd-qos package operational data.
     
     This module contains definitions
     for the following management objects:
       platform-qos: DPA QoS EA operational data
     
     Copyright (c) 2013-2022 by Cisco Systems, Inc.
     All rights reserved.";

  revision 2022-09-27 {
    description
      "qos pfc show cmd.
       2022-03-09
         qos hwmodule show cmd.
       2022-01-23
         segregating common mark to all the mark actions.";
    semver:module-version "2.0.0";
  }
  revision 2019-04-05 {
    description
      "Establish semantic version baseline.";
    semver:module-version "1.0.0";
  }
  revision 2015-11-09 {
    description
      "IOS XR 6.0 revision.";
  }

  grouping QOS-CLASS-TABLE {
    description
      "Common node of input, output";
    container qos-class-table {
      description
        "QoS list of class names";
      uses CLASS;
    }
  }

  grouping CLASS {
    description
      "Common node of class-table, qos-class-table";
    list class {
      key "level-one-class-name";
      description
        "QoS policy class";
      leaf level-one-class-name {
        type string;
        description
          "QoS policy class name at level 1";
      }
      leaf level-two-class-name {
        type string;
        description
          "QoS policy child class name at level 2";
      }
      uses DPA-QOSEA-SHOW-CLASS-ST;
    }
  }

  grouping POLICY-DETAILS {
    description
      "Common node of interface, shared-policy-instance,
       bundle-interface-single, bundle-interface,
       member-interface";
    container policy-details {
      description
        "Policy Details";
      uses DPA-QOSEA-SHOW-IF-QOS-INFO-ST;
    }
  }

  grouping INPUT {
    description
      "Common node of qos-interfaces,
       shared-policy-instance";
    container input {
      description
        "QoS policy direction ingress";
      uses QOS-CLASS-TABLE;
    }
  }

  grouping MEMBER-INTERFACE-TABLE {
    description
      "Common node of bundle-interface-single,
       bundle-interface";
    container member-interfaces {
      description
        "QoS list of member interfaces";
      list member-interface {
        key "interface-name";
        description
          "QoS interface names";
        leaf interface-name {
          type xr:Interface-name;
          description
            "Member interface";
        }
        uses POLICY-DETAILS;
        uses CLASS-TABLE;
      }
    }
  }

  grouping OUTPUT {
    description
      "Common node of qos-interfaces, interface,
       shared-policy-instance";
    container output {
      description
        "QoS policy direction egress";
      uses QOS-CLASS-TABLE;
    }
  }

  grouping CLASS-TABLE {
    description
      "Common node of interface, shared-policy-instance,
       bundle-interface-single, bundle-interface,
       member-interface";
    container class-table {
      description
        "QoS list of class names";
      uses CLASS;
    }
  }

  container platform-qos {
    config false;
    description
      "DPA QoS EA operational data";
    container nodes {
      description
        "List of nodes with platform specific QoS
         configuration";
      list node {
        key "node-name";
        description
          "Node with platform specific QoS configuration";
        container pfc-vsqs {
          description
            "Qos Pfc Vsq datalist";
          list pfc-vsq {
            key "interface-name";
            description
              "Qos Pfc Vsq Data";
            leaf interface-name {
              type xr:Interface-name;
              description
                "interface Name";
            }
            uses DNX-QOSEA-PFC-VSQ;
          }
        }
        container bundle-interfaces {
          description
            "QoS list of bundle interfaces";
          list bundle-interface {
            description
              "QoS interface names";
            leaf interface-name {
              type xr:Interface-name;
              description
                "Bundle interface name";
            }
            leaf npu-id {
              type uint32;
              description
                "NPU ID";
            }
            leaf qos-direction {
              type string;
              description
                "The interface direction on which QoS is
                 applied to.";
            }
            uses POLICY-DETAILS;
            uses MEMBER-INTERFACE-TABLE;
            uses CLASS-TABLE;
          }
        }
        container qos-inconsistancy-brief {
          description
            "Inconsistancy Brief";
          uses DNX-QOSEA-SHOW-INC-SUMMARY;
        }
        container qos-policer-res-datas {
          description
            "QOS Policer Resources";
          list qos-policer-res-data {
            key "npu-id";
            description
              "QOS Policer Resources data";
            leaf npu-id {
              type uint32;
              description
                "NPU ID";
            }
            uses DNX-QOSEA-POLICER-BANK-INFO;
          }
        }
        container interfaces {
          description
            "QoS list of interfaces";
          list interface {
            description
              "QoS interface names";
            leaf interface-name {
              type xr:Interface-name;
              description
                "The name of the interface";
            }
            leaf npu-id {
              type uint32;
              description
                "NPU ID";
            }
            leaf qos-direction {
              type string;
              description
                "The interface direction on which QoS is
                 applied to.";
            }
            uses POLICY-DETAILS;
            uses OUTPUT;
            uses CLASS-TABLE;
          }
        }
        container qos-voq-res-datas {
          description
            "QOS VOQ Resources";
          list qos-voq-res-data {
            key "npu-id";
            description
              "QOS Voq Resources data";
            leaf npu-id {
              type uint32;
              description
                "NPU ID";
            }
            uses DNX-QOSEA-VOQ-INFO;
          }
        }
        container qos-interfaces {
          description
            "QoS list of interfaces";
          list qos-interface {
            description
              "QoS interface names";
            leaf interface-name {
              type xr:Interface-name;
              description
                "The name of the interface";
            }
            leaf qos-direction {
              type string;
              description
                "The interface direction on which QoS is
                 applied to.";
            }
            uses OUTPUT;
            uses INPUT;
          }
        }
        container bundle-interface-singles {
          description
            "QoS list of bundle interfaces";
          list bundle-interface-single {
            key "interface-name";
            description
              "QoS interface names";
            leaf interface-name {
              type xr:Interface-name;
              description
                "Bundle interface name";
            }
            uses POLICY-DETAILS;
            uses MEMBER-INTERFACE-TABLE;
            uses CLASS-TABLE;
          }
        }
        container pfc-cfg {
          description
            "Qos Pfc Config data";
          uses DNX-QOSEA-PFC-CFG;
        }
        container shared-policy-instances {
          description
            "Shared Policy Instances";
          list shared-policy-instance {
            description
              "Shared Policy Instance info";
            leaf spi-name {
              type string;
              description
                "The name of the shared-policy-instance";
            }
            leaf qos-direction {
              type string;
              description
                "The interface direction on which QoS is
                 applied to.";
            }
            uses POLICY-DETAILS;
            uses OUTPUT;
            uses INPUT;
            uses CLASS-TABLE;
          }
        }
        container hw-module-status {
          description
            "Hw Module Status";
          uses DPA-QOSEA-HWMODULESTATUS-INFO-ST;
        }
        container egress-qos-map-res-datas {
          description
            "Egress QoS Map Resources";
          list egress-qos-map-res-data {
            key "npu-id";
            description
              "Egress Qos Map Resources data";
            leaf npu-id {
              type uint32;
              description
                "NPU ID";
            }
            uses DNX-QOSEA-EGRESS-MAP-INFO;
          }
        }
        container remote-interfaces {
          description
            "QoS list of remote interfaces";
          list remote-interface {
            key "interface-name";
            description
              "QoS remote interface names";
            leaf interface-name {
              type xr:Interface-name;
              description
                "The name of the remote interface";
            }
            uses DPA-QOSEA-SHOW-REMOTE-IF-INFO-ST;
          }
        }
        container qos-inconsistancy-details {
          description
            "Inconsistancy Details";
          uses DNX-QOSEA-SHOW-INC-DETAIL;
        }
        leaf node-name {
          type xr:Node-id;
          description
            "Node name";
        }
      }
    }
  }
}
