module cisco-xr-ietf-netconf-monitoring-deviations {

  /*** NAMESPACE / PREFIX DEFINITION ***/

  namespace "http://cisco.com/ns/yang/cisco-xr-ietf-netconf-monitoring-deviations";

  prefix "cisco-xr-ietf-ncm-devs";

  /*** LINKAGE (IMPORTS / INCLUDES) ***/
  import ietf-netconf-monitoring { prefix ncm; }

  /*** META INFORMATION ***/
  organization "Cisco Systems, Inc.";

  contact
    "Cisco Systems, Inc.
     Customer Service

     Postal: 170 West Tasman Drive
     San Jose, CA 95134

     Tel: +1 800 553-NETS

     E-mail: cs-yang@cisco.com";

  description 
    "This module contains a set of deviations of IETF netconf monitoring data
     model set for Cisco IOS-XR.

     Copyright (c) 2016, 2018 by Cisco Systems, Inc.
     All rights reserved.";

  revision "2018-04-09" {
    description
      "We now support sessions and statistics and these have been removed 
       from the deviations";
  }

  revision "2016-02-16" {
    description
      "Initial revision applicable to IOS-XR 6.0.1 and older releases";
  }

  deviation /ncm:netconf-state/ncm:capabilities {
    deviate not-supported;
  }

  deviation /ncm:netconf-state/ncm:datastores {
    deviate not-supported;
  }

}
