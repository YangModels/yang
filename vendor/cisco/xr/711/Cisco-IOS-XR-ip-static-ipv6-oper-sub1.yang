submodule Cisco-IOS-XR-ip-static-ipv6-oper-sub1 {
  belongs-to Cisco-IOS-XR-ip-static-ipv6-oper {
    prefix Cisco-IOS-XR-ip-static-ipv6-oper;
  }

  import ietf-inet-types {
    prefix inet;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR ip-static-ipv6 package operational data.
     
     Copyright (c) 2013-2019 by Cisco Systems, Inc.
     All rights reserved.";

  revision 2019-06-01 {
    description
      "Added oper ipv6 support for fridb, colocation, sr-policy
       2019-05-13
         Added ipv4 support for bfd sessions, object track database and segment routing";
    semver:module-version "1.1.0";
  }
  revision 2019-04-05 {
    description
      "Establish semantic version baseline.";
    semver:module-version "1.0.0";
  }
  revision 2019-01-03 {
    description
      "Added oper ipv6 support";
  }
  revision 2015-11-09 {
    description
      "IOS XR 6.0 revision.";
  }

  typedef Object-state {
    type enumeration {
      enum "object-state-unknown" {
        value 0;
        description
          "Object does not exist";
      }
      enum "object-state-down" {
        value 1;
        description
          "Object exists but state is down";
      }
      enum "object-state-up" {
        value 2;
        description
          "Object exists and state is up";
      }
    }
    description
      "Object state";
  }

  typedef Interface-state {
    type enumeration {
      enum "interface-none" {
        value 0;
        description
          "Interface does not exist";
      }
      enum "interface-down" {
        value 1;
        description
          "Interface exists but IP is down";
      }
      enum "interface-up" {
        value 2;
        description
          "Interface exists and IP is up";
      }
      enum "interface-unknown" {
        value 3;
        description
          "Unknown state";
      }
    }
    description
      "Interface state";
  }

  typedef Explicit-path-state {
    type enumeration {
      enum "explicit-path-state-unknown" {
        value 0;
        description
          "Explicit Path does not exist";
      }
      enum "explicit-path-state-up" {
        value 1;
        description
          "Explicit path exists and state is up";
      }
      enum "explicit-path-state-down" {
        value 2;
        description
          "Explicit path exists but state is down";
      }
    }
    description
      "Explicit path state";
  }

  typedef Ipv6-static-addr-bd {
    type inet:ipv6-address;
    description
      "Ipv6 static addr bd";
  }

  typedef Bfd-state {
    type enumeration {
      enum "next-hop-bfd-not-ready" {
        description
          "BFD for next-hop address is not ready";
      }
      enum "next-hop-bfd-down" {
        description
          "BFD for next-hop address is down";
      }
      enum "next-hop-bfd-up" {
        description
          "BFD for next-hop address is up";
      }
    }
    description
      "Bfd state";
  }

  typedef Nexthop-state {
    type enumeration {
      enum "next-hop-unresolved" {
        description
          "Next-hop address is not resolved";
      }
      enum "next-hop-resolved" {
        description
          "Next-hop address is resolved";
      }
      enum "next-hop-unknown" {
        description
          "Unknown state";
      }
    }
    description
      "Nexthop state";
  }

  grouping IP-STATIC-COLOCATION-NODE-BD {
    description
      "A static co-location node";
    leaf vrf-name {
      type string;
      description
        "VRF Name";
    }
    leaf table-name {
      type string;
      description
        "Table Name";
    }
    leaf table-id {
      type uint32;
      description
        "colocation table id";
    }
    leaf ref-count {
      type uint32;
      description
        "Refrence Count";
    }
  }

  grouping IP-STATIC-COLOCATION-BD {
    description
      "A static co-location list";
    list colocation {
      description
        "Colocation List of table";
      uses IP-STATIC-COLOCATION-NODE-BD;
    }
  }

  grouping IPV6-STATIC-TEDB-BD {
    description
      "A static tedb";
    leaf state {
      type Explicit-path-state;
      description
        "Explicit path state";
    }
    leaf tunnel-ifh {
      type uint32;
      description
        "Tunnel interface handle";
    }
    leaf binding-label {
      type uint32;
      description
        "Explicit path Binding label";
    }
    leaf last-te-time {
      type uint64;
      description
        "Last TE notification time";
    }
    leaf last-te-state {
      type Explicit-path-state;
      description
        "Last TE notification state";
    }
    list paths {
      description
        "Paths referenced by this tedb";
      uses IP-STATIC-PATH-ADDR-BD;
    }
  }

  grouping IPV6-STATIC-OTDB-BD {
    description
      "A static otdb";
    leaf state {
      type Object-state;
      description
        "Object state";
    }
    leaf last-ot-time {
      type uint64;
      description
        "Last OT notification time";
    }
    leaf last-ot-state {
      type Object-state;
      description
        "Last OT notification state";
    }
    list paths {
      description
        "Paths referenced by this otdb";
      uses IP-STATIC-PATH-ADDR-BD;
    }
  }

  grouping IP-STATIC-TDB-BD {
    description
      "A static tdb";
    leaf vrf-name {
      type string;
      description
        "VRF Name";
    }
    leaf table-name {
      type string;
      description
        "VRF Name";
    }
    leaf table-id-xr {
      type uint32;
      description
        "table id in table database";
    }
    leaf afi {
      type uint32;
      description
        "AFI";
    }
    leaf safi {
      type uint32;
      description
        "SAFI";
    }
  }

  grouping IP-STATIC-ADDR-INFO-BD {
    description
      "Static address route";
    leaf addr {
      type Ipv6-static-addr-bd;
      description
        "IP address";
    }
    leaf prefix-len {
      type uint32;
      description
        "Prefix length";
    }
    leaf route-tag {
      type uint32;
      description
        "Static route tag";
    }
    leaf flags {
      type uint32;
      description
        "Flags";
    }
    leaf inactive {
      type boolean;
      description
        "Active/Inactive";
    }
    leaf prefix-sid {
      type boolean;
      description
        "Prefix SID";
    }
  }

  grouping IPV6-STATIC-IDB-BD {
    description
      "A static idb";
    container evt-hist {
      description
        "Event history of interface";
      uses EVT-HIST-INFO;
    }
    leaf vrf-name {
      type string;
      description
        "VRF Name";
    }
    leaf table-id {
      type uint32;
      description
        "interface database table id";
    }
    leaf afi {
      type uint32;
      description
        "AFI";
    }
    leaf safi {
      type uint32;
      description
        "SAFI";
    }
    leaf state {
      type Interface-state;
      description
        "Interface state";
    }
    leaf ifh {
      type uint32;
      description
        "Interface handle";
    }
    leaf last-notif-time {
      type uint64;
      description
        "Last IM/RSI notification time";
    }
    leaf last-if-state {
      type Interface-state;
      description
        "Last IM notification state";
    }
    leaf ref-count {
      type uint32;
      description
        "Reference count";
    }
    leaf gl-ifh {
      type uint32;
      description
        "Global Interface handle";
    }
    leaf im-state {
      type uint32;
      description
        "Interface manager state";
    }
    leaf rsi-register {
      type boolean;
      description
        "Registration status with RSI";
    }
    leaf-list tblid-db {
      type uint32;
      description
        "IDB Table ID";
    }
    leaf-list fr-tblid-db {
      type uint32;
      description
        "FR Table ID";
    }
    list paths {
      description
        "Paths referenced by this idb";
      uses IP-STATIC-PATH-ADDR-BD;
    }
    list addr-info {
      description
        "IP address info";
      uses IP-STATIC-ADDR-INFO-BD;
    }
  }

  grouping IPV6-STATIC-PATH-BD {
    description
      "A static path";
    leaf vrf-name {
      type string;
      description
        "VRF Name";
    }
    leaf interface {
      type string;
      description
        "Next-hop interface";
    }
    leaf if-resolved {
      type boolean;
      description
        "Interface resolved indicator";
    }
    leaf object {
      type string;
      description
        "Tracking object";
    }
    leaf object-resolved {
      type boolean;
      description
        "Object resolved indicator";
    }
    leaf exp-path {
      type string;
      description
        "Explicit path";
    }
    leaf next-hop {
      type Ipv6-static-addr-bd;
      description
        "Next-hop address";
    }
    leaf nh-resolved {
      type boolean;
      description
        "Next-hop resolved indicator";
    }
    leaf path-tag {
      type uint32;
      description
        "Protocol tag";
    }
    leaf path-flags {
      type uint32;
      description
        "Topology path flags";
    }
    leaf distance {
      type uint32;
      description
        "Administrative distance";
    }
    leaf ref-count {
      type uint32;
      description
        "Reference count";
    }
    leaf metric {
      type uint32;
      description
        "UCMP Metric";
    }
    leaf status {
      type uint32;
      description
        "Path Status";
    }
    leaf rib-time {
      type uint64;
      description
        "RIB add or delete time";
    }
    leaf version {
      type uint32;
      description
        "Path version";
    }
    leaf index {
      type string;
      description
        "OC index";
    }
    leaf local-label {
      type uint32;
      description
        "Route local Label";
    }
    leaf last-notif-time {
      type uint64;
      description
        "Last IM notification time";
    }
    leaf last-rib-time {
      type uint64;
      description
        "Last RIB notification time for nh";
    }
    leaf last-rib-result {
      type uint64;
      description
        "Last RIB batch result";
    }
    leaf last-bfd-state {
      type Bfd-state;
      description
        "State of bfd session";
    }
    leaf last-bfd-time {
      type uint64;
      description
        "Last BFD notification time";
    }
    leaf path-state {
      type Explicit-path-state;
      description
        "explicit path status";
    }
    leaf last-te-time {
      type uint64;
      description
        "Last TE notification time";
    }
    leaf algorithm {
      type uint32;
      description
        "FlexAlgo value, Valid only for ipv6_static";
    }
  }

  grouping IPV6-STATIC-ROUTE-BD {
    description
      "A static route";
    container evt-hist {
      description
        "Event history of topology";
      uses EVT-HIST-INFO;
    }
    leaf vrf-name {
      type string;
      description
        "VRF Name";
    }
    leaf table-id {
      type uint32;
      description
        "Table id of static route";
    }
    leaf afi {
      type uint32;
      description
        "AFI";
    }
    leaf safi {
      type uint32;
      description
        "SAFI";
    }
    leaf best-distance {
      type uint32;
      description
        "Administrative distance of best path";
    }
    leaf last-tdb-time {
      type uint64;
      description
        "Last event occured on the tdb";
    }
    list paths {
      description
        "Path(s) of the route";
      uses IPV6-STATIC-PATH-BD;
    }
  }

  grouping IP-STATIC-NHDB-BFD-STAT-BD {
    description
      "BFD session stats";
    leaf session-up-cnt {
      type uint32;
      description
        "# of state change to up";
    }
    leaf session-down-cnt {
      type uint32;
      description
        "# of state change to down";
    }
  }

  grouping IPV6-STATIC-NHDB-BFD-BD {
    description
      "A static nhdb bfd session";
    container bfd-stat {
      description
        "Stat of bfd session";
      uses IP-STATIC-NHDB-BFD-STAT-BD;
    }
    leaf vrf-name {
      type string;
      description
        "VRF Name";
    }
    leaf table-id {
      type uint32;
      description
        "next-hop bfd table id";
    }
    leaf afi {
      type uint32;
      description
        "AFI";
    }
    leaf safi {
      type uint32;
      description
        "SAFI";
    }
    leaf ifh {
      type uint32;
      description
        "Interface handle";
    }
    leaf bfd-interval {
      type uint32;
      description
        "BFD hello interval";
    }
    leaf bfd-multiplier {
      type uint32;
      description
        "BFD multiplier";
    }
    leaf bfd-multihop {
      type boolean;
      description
        "BFD multihop";
    }
    leaf bfd-state {
      type Bfd-state;
      description
        "State of bfd session";
    }
    leaf bfd-source {
      type Ipv6-static-addr-bd;
      description
        "Multihop session source IP";
    }
  }

  grouping EVT-HIST-ENTRY {
    description
      "Event history Entry";
    leaf evt-timestamp {
      type string;
      description
        "The timestamp of the event";
    }
    leaf evt-name {
      type string;
      description
        "Event name";
    }
    leaf evt-type {
      type uint8;
      description
        "Event type";
    }
    leaf evt-many {
      type boolean;
      description
        "Multiple instance flag";
    }
    leaf evt-sticky {
      type boolean;
      description
        "Sticky flag";
    }
    leaf-list evt-data {
      type uint32;
      description
        "Optional data";
    }
  }

  grouping EVT-HIST-INFO {
    description
      "Per object event history";
    leaf evt-class-name {
      type string;
      description
        "Class name string";
    }
    list evt-entry {
      description
        "Array of event entries";
      uses EVT-HIST-ENTRY;
    }
  }

  grouping IP-STATIC-PATH-BFD-BD {
    description
      "A static bfd";
    leaf enable {
      type boolean;
      description
        "TRUE if bfd is enabled";
    }
  }

  grouping IP-STATIC-PATH-ADDR-BD {
    description
      "Static address path";
    leaf prefix {
      type Ipv6-static-addr-bd;
      description
        "The path's prefix address";
    }
    leaf prefix-len {
      type uint8;
      description
        "The path's prefix length";
    }
    leaf vrf-name {
      type string;
      description
        "VRF Name";
    }
  }

  grouping IPV6-STATIC-NHDB-BD {
    description
      "A static nhdb";
    container evt-hist {
      description
        "Event history of next-hop";
      uses EVT-HIST-INFO;
    }
    leaf vrf-name {
      type string;
      description
        "VRF Name";
    }
    leaf table-id {
      type uint32;
      description
        "next-hop table id";
    }
    leaf afi {
      type uint32;
      description
        "AFI";
    }
    leaf safi {
      type uint32;
      description
        "SAFI";
    }
    leaf state {
      type Nexthop-state;
      description
        "Next-hop address state";
    }
    leaf conn-state {
      type Nexthop-state;
      description
        "Next-hop address connected state";
    }
    leaf ifh {
      type uint32;
      description
        "Interface handleto which RIB resolves this";
    }
    leaf conn-ifh {
      type uint32;
      description
        "Interface handle to which this is connected";
    }
    leaf conn-ref-count {
      type uint32;
      description
        "Number of paths for which conn_state is resolved";
    }
    leaf bfd-interval {
      type uint32;
      description
        "BFD hello interval";
    }
    leaf bfd-multiplier {
      type uint32;
      description
        "BFD multiplier";
    }
    leaf bfd-state {
      type Bfd-state;
      description
        "State of bfd session";
    }
    leaf last-rib-time {
      type uint64;
      description
        "Last RIB notification time";
    }
    leaf last-rib-state {
      type Nexthop-state;
      description
        "Last RIB notification state";
    }
    leaf last-bfd-time {
      type uint64;
      description
        "Last BFD notification time";
    }
    leaf last-bfd-state {
      type Bfd-state;
      description
        "Last BFD notification state";
    }
    list paths {
      description
        "Paths referenced by this nhdb";
      uses IP-STATIC-PATH-ADDR-BD;
    }
    list bfds {
      description
        "Paths bfd state";
      uses IP-STATIC-PATH-BFD-BD;
    }
  }

  grouping IP-STATIC-FRIDB-BD {
    description
      "A static fridb";
    leaf if-name {
      type string;
      description
        "Interface name";
    }
    leaf if-handle {
      type uint32;
      description
        "Interface handle";
    }
    leaf-list tblid-db {
      type uint32;
      description
        "Table ID database";
    }
  }
}
