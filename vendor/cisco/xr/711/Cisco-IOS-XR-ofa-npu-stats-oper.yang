module Cisco-IOS-XR-ofa-npu-stats-oper {
  namespace "http://cisco.com/ns/yang/Cisco-IOS-XR-ofa-npu-stats-oper";
  prefix ofa-npu-stats-oper;

  import Cisco-IOS-XR-types {
    prefix xr;
  }
  import cisco-semver {
    prefix semver;
  }
  include Cisco-IOS-XR-ofa-npu-stats-oper-sub1 {
    revision-date 2019-12-14;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ofa-npu-stats package operational data.
     
     This module contains definitions
     for the following management objects:
       dpa: Stats Data
     
     Copyright (c) 2013-2019 by Cisco Systems, Inc.
     All rights reserved.";

  revision 2019-12-14 {
    description
      "Updated date for npu stats model";
    semver:module-version "1.1.0";
  }
  revision 2019-04-05 {
    description
      "Establish semantic version baseline.";
    semver:module-version "1.0.0";
  }
  revision 2015-11-09 {
    description
      "IOS XR 6.0 revision.";
  }

  typedef Max-trap-s {
    type uint32 {
      range "0..4294967295";
    }
    description
      "Max trap s";
  }

  typedef Max-lc-intf-hand-les {
    type uint32 {
      range "0..4294967295";
    }
    description
      "Max lc intf hand les";
  }

  container dpa {
    config false;
    description
      "Stats Data";
    container stats {
      description
        "Voq or Trap Data";
      container nodes {
        description
          "DPA data for available nodes";
        list node {
          key "node-name";
          description
            "DPA operational data for a particular node";
          container asic-statistics {
            description
              "ASIC statistics table";
            container asic-statistics-detail-for-npu-ids {
              description
                "Detailed ASIC statistics";
              list asic-statistics-detail-for-npu-id {
                key "npu-id";
                description
                  "Detailed ASIC statistics for a particular
                   NPU";
                leaf npu-id {
                  type uint32;
                  description
                    "NPU number";
                }
                uses FIA-EDM-STATS-INFO;
              }
            }
            container asic-statistics-for-npu-ids {
              description
                "ASIC statistics";
              list asic-statistics-for-npu-id {
                key "npu-id";
                description
                  "ASIC statistics for a particular NPU";
                leaf npu-id {
                  type uint32;
                  description
                    "NPU number";
                }
                uses FIA-EDM-STATS-BRIEF-INFO;
              }
            }
          }
          container npu-numbers {
            description
              "Ingress Stats";
            list npu-number {
              key "npu-id";
              description
                "Stats for a particular npu";
              container display {
                description
                  "show npu specific voq or trap stats";
                container trap-ids {
                  description
                    "Trap stats for a particular npu";
                  list trap-id {
                    key "trap-id";
                    description
                      "Filter by specific trap id";
                    leaf trap-id {
                      type Max-trap-s;
                      description
                        "Trap ID";
                    }
                    uses DPA-TRAP-STATS;
                  }
                }
                container interface-handles {
                  description
                    "Voq stats grouped by interface handle";
                  list interface-handle {
                    key "interface-handle";
                    description
                      "Voq stats for a particular interface
                       handle";
                    leaf interface-handle {
                      type Max-lc-intf-hand-les;
                      description
                        "Interface Handle";
                    }
                    uses DPA-VOQ-INTF-PORT;
                  }
                }
                container base-numbers {
                  description
                    "Voq stats grouped by voq base numbers";
                  list base-number {
                    key "base-number";
                    description
                      "Voq Base Number for a particular voq";
                    leaf base-number {
                      type Max-lc-intf-hand-les;
                      description
                        "Interface handle";
                    }
                    uses DPA-VOQ-INTF-PORT;
                  }
                }
              }
              leaf npu-id {
                type uint32;
                description
                  "Npu number";
              }
            }
          }
          leaf node-name {
            type xr:Node-id;
            description
              "Node ID";
          }
        }
      }
    }
  }
}
