module Cisco-IOS-XR-sysadmin-nto-misc-set-hostname {
  namespace "http://www.cisco.com/ns/yang/Cisco-IOS-XR-sysadmin-nto-misc-set-hostname";
  prefix hostname;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR syadmin hostname configuration and cli.
     
     This module contains definitions
     for the following management objects:
     hostname cli and configuration data
     
     Copyright (c) 2017 by Cisco Systems, Inc.
     All rights reserved.
     
     Copyright (c) 2012-2019 by Cisco Systems, Inc.
     All rights reserved.";

  revision 2019-04-15 {
    description
      "Establish semantic version baseline.";
    semver:module-version "1.0.1";
  }
  revision 2017-04-12 {
    description
      "Initial version.";
  }

  container hostname {
    description
      "Set system`s network name";
    leaf name {
      type string {
        length "1..255";
        pattern "[a-zA-Z0-9_.{}+-]+";
      }
    }
  }
}
