module Cisco-IOS-XR-um-access-list-datatypes {
  namespace "http://cisco.com/ns/yang/Cisco-IOS-XR-um-access-list-datatypes";
  prefix um-access-list-datatypes;

  import cisco-semver {
    prefix semver;
  }

  organization
    "Cisco Systems, Inc.";
  contact
    "
     Cisco Systems, Inc.
     Customer Service
     
     Postal: 170 W Tasman Drive
     San Jose, CA 95134
     
     Tel: +1 1800 553-NETS
     
     E-mail: cs-yang@cisco.com</text>
    ";
  description
    "
     This module contains a collection of IOS-XR YANG model derived from CLI.
     
     Copyright (c) 2013-2019 by Cisco Systems, Inc.
     All rights reserved.
    ";

  revision 2019-06-10 {
    description
      "Establish semantic version baseline.";
    semver:module-version "1.0.0";
  }
  revision 2019-04-01 {
    description
      "Initial version";
  }

  typedef ipv4-protocol {
    type union {
      type uint8 {
        range "0..255" {
          description
            "An IPv4 Protocol Number";
        }
      }
      type enumeration {
        enum "ahp" {
          value 51;
          description
            "Authentication Header Protocol";
        }
        enum "eigrp" {
          value 88;
          description
            "Cisco's EIGRP Routing Protocol";
        }
        enum "esp" {
          value 50;
          description
            "Encapsulation Security Payload";
        }
        enum "gre" {
          value 47;
          description
            "Cisco's GRE Tunneling";
        }
        enum "icmp" {
          value 1;
          description
            "Internet Control Message Protocol";
        }
        enum "igmp" {
          value 2;
          description
            "Internet Gateway Message Protocol";
        }
        enum "igrp" {
          value 9;
          description
            "Cisco's IGRP Routing Protocol";
        }
        enum "ipinip" {
          value 4;
          description
            "IP in IP tunneling";
        }
        enum "ipv4" {
          value 512;
          description
            "Any IPv4 Protocol";
        }
        enum "nos" {
          value 94;
          description
            "KA9Q NOS Compatible IP over IP Tunneling";
        }
        enum "ospf" {
          value 89;
          description
            "OSPF Routing Protocol";
        }
        enum "pcp" {
          value 108;
          description
            "Payload Compression Protocol";
        }
        enum "pim" {
          value 103;
          description
            "Protocol Independent Multicast";
        }
        enum "sctp" {
          value 132;
          description
            "Stream Control Transmission Protocol";
        }
        enum "tcp" {
          value 6;
          description
            "Transport Control Protocol";
        }
        enum "udp" {
          value 17;
          description
            "User Datagram Protocol";
        }
      }
    }
  }

  typedef ipv4-port-number {
    type union {
      type ipv4-tcp-port-number;
      type ipv4-udp-port-number;
    }
  }

  typedef ipv4-tcp-port-number {
    type union {
      type uint16 {
        range "0..65535";
      }
      type enumeration {
        enum "echo" {
          value 7;
          description
            "Echo";
        }
        enum "discard" {
          value 9;
          description
            "Discard";
        }
        enum "daytime" {
          value 13;
          description
            "Daytime";
        }
        enum "chargen" {
          value 19;
          description
            "Character generator";
        }
        enum "ftp-data" {
          value 20;
          description
            "FTP data connections (used infrequently)";
        }
        enum "ftp" {
          value 21;
          description
            "File Transfer Protocol";
        }
        enum "ssh" {
          value 22;
          description
            "Secure Shell";
        }
        enum "telnet" {
          value 23;
          description
            "Telnet";
        }
        enum "smtp" {
          value 25;
          description
            "Simple Mail Transport Protocol";
        }
        enum "time" {
          value 37;
          description
            "Time";
        }
        enum "whois" {
          value 43;
          description
            "Nicname";
        }
        enum "tacacs" {
          value 49;
          description
            "TAC Access Control System";
        }
        enum "domain" {
          value 53;
          description
            "Domain Name Service";
        }
        enum "gopher" {
          value 70;
          description
            "Gopher";
        }
        enum "finger" {
          value 79;
          description
            "Finger";
        }
        enum "www" {
          value 80;
          description
            "World Wide Web (HTTP)";
        }
        enum "hostname" {
          value 101;
          description
            "NIC hostname server";
        }
        enum "pop2" {
          value 109;
          description
            "Post Office Protocol v2";
        }
        enum "pop3" {
          value 110;
          description
            "Post Office Protocol v3";
        }
        enum "sunrpc" {
          value 111;
          description
            "Sun Remote Procedure Call";
        }
        enum "ident" {
          value 113;
          description
            "Ident Protocol";
        }
        enum "nntp" {
          value 119;
          description
            "Network News Transport Protocol";
        }
        enum "bgp" {
          value 179;
          description
            "Border Gateway Protocol";
        }
        enum "irc" {
          value 194;
          description
            "Internet Relay Chat";
        }
        enum "pim-auto-rp" {
          value 496;
          description
            "PIM Auto-RP";
        }
        enum "exec" {
          value 512;
          description
            "Exec (rsh)";
        }
        enum "login" {
          value 513;
          description
            "Login (rlogin)";
        }
        enum "cmd" {
          value 514;
          description
            "Remote commands (rcmd)";
        }
        enum "lpd" {
          value 515;
          description
            "Printer service";
        }
        enum "uucp" {
          value 540;
          description
            "Unix-to-Unix Copy Program";
        }
        enum "klogin" {
          value 543;
          description
            "Kerberos login";
        }
        enum "kshell" {
          value 544;
          description
            "Kerberos shell";
        }
        enum "talk" {
          value 517;
          description
            "Talk";
        }
        enum "ldp" {
          value 646;
          description
            "LDP session connection attempts (MPLS)";
        }
      }
    }
  }

  typedef ipv4-udp-port-number {
    type union {
      type uint16 {
        range "0..65535";
      }
      type enumeration {
        enum "biff" {
          value 512;
          description
            "Biff (mail notification, comsat";
        }
        enum "bootpc" {
          value 68;
          description
            "Bootstrap Protocol (BOOTP) client";
        }
        enum "bootps" {
          value 67;
          description
            "Bootstrap Protocol (BOOTP) server";
        }
        enum "discard" {
          value 9;
          description
            "Discard";
        }
        enum "dnsix" {
          value 195;
          description
            "DNSIX security protocol auditing";
        }
        enum "domain" {
          value 53;
          description
            "Domain Name Service (DNS)";
        }
        enum "echo" {
          value 7;
          description
            "Echo";
        }
        enum "isakmp" {
          value 500;
          description
            "Internet Security Association and Key Management Protocol";
        }
        enum "ldp" {
          value 646;
          description
            "LDP hello packets (MPLS)";
        }
        enum "mobile-ip" {
          value 434;
          description
            "Mobile IP registration";
        }
        enum "nameserver" {
          value 42;
          description
            "IEN116 name service (obsolete)";
        }
        enum "netbios-dgm" {
          value 138;
          description
            "NetBios datagram service";
        }
        enum "netbios-ns" {
          value 137;
          description
            "NetBios name service";
        }
        enum "netbios-ss" {
          value 139;
          description
            "NetBios session service";
        }
        enum "ntp" {
          value 123;
          description
            "Network Time Protocol";
        }
        enum "pim-auto-rp" {
          value 496;
          description
            "PIM Auto-RP";
        }
        enum "rip" {
          value 520;
          description
            "Routing Information Protocol (router, in.routed)";
        }
        enum "snmp" {
          value 161;
          description
            "Simple Network Management Protocol";
        }
        enum "snmptrap" {
          value 162;
          description
            "SNMP Traps";
        }
        enum "ssh" {
          value 22;
          description
            "Secure Shell service";
        }
        enum "sunrpc" {
          value 111;
          description
            "Sun Remote Procedure Call";
        }
        enum "syslog" {
          value 514;
          description
            "System Logger";
        }
        enum "tacacs" {
          value 49;
          description
            "TAC Access Control System";
        }
        enum "talk" {
          value 517;
          description
            "Talk";
        }
        enum "tftp" {
          value 69;
          description
            "Trivial File Transfer Protocol";
        }
        enum "time" {
          value 37;
          description
            "Time";
        }
        enum "who" {
          value 513;
          description
            "Who service (rwho)";
        }
        enum "xdmcp" {
          value 177;
          description
            "X Display Manager Control Protocol";
        }
      }
    }
  }

  typedef precedence-value {
    type union {
      type uint8 {
        range "0..7";
      }
      type enumeration {
        enum "critical" {
          value 5;
          description
            "Match packets with critical precedence";
        }
        enum "flash" {
          value 3;
          description
            "Match packets with flash precedence";
        }
        enum "flash-override" {
          value 4;
          description
            "Match packets with flash override precedence";
        }
        enum "immediate" {
          value 2;
          description
            "Match packets with immediate precedence";
        }
        enum "internet" {
          value 6;
          description
            "Match packets with internetwork control precedence";
        }
        enum "network" {
          value 7;
          description
            "Match packets with network control precedence";
        }
        enum "priority" {
          value 1;
          description
            "Match packets with priority precedence";
        }
        enum "routine" {
          value 0;
          description
            "Match packets with routine precedence";
        }
      }
    }
  }

  typedef dscp-value {
    type union {
      type uint8 {
        range "0..63";
      }
      type enumeration {
        enum "af11" {
          value 10;
          description
            "Match packets with AF11 dscp (001010)";
        }
        enum "af12" {
          value 12;
          description
            "Match packets with AF12 dscp (001100)";
        }
        enum "af13" {
          value 14;
          description
            "Match packets with AF13 dscp (001110)";
        }
        enum "af21" {
          value 18;
          description
            "Match packets with AF21 dscp (010010)";
        }
        enum "af22" {
          value 20;
          description
            "Match packets with AF22 dscp (010100)";
        }
        enum "af23" {
          value 22;
          description
            "Match packets with AF23 dscp (010110)";
        }
        enum "af31" {
          value 26;
          description
            "Match packets with AF31 dscp (011010)";
        }
        enum "af32" {
          value 28;
          description
            "Match packets with AF32 dscp (011100)";
        }
        enum "af33" {
          value 30;
          description
            "Match packets with AF33 dscp (011110)";
        }
        enum "af41" {
          value 34;
          description
            "Match packets with AF41 dscp (100010)";
        }
        enum "af42" {
          value 36;
          description
            "Match packets with AF42 dscp (100100)";
        }
        enum "af43" {
          value 38;
          description
            "Match packets with AF43 dscp (100110)";
        }
        enum "cs1" {
          value 8;
          description
            "Match packets with CS1(precedence 1) dscp (001000)";
        }
        enum "cs2" {
          value 16;
          description
            "Match packets with CS2(precedence 2) dscp (010000)";
        }
        enum "cs3" {
          value 24;
          description
            "Match packets with CS3(precedence 3) dscp (011000)";
        }
        enum "cs4" {
          value 32;
          description
            "Match packets with CS4(precedence 4) dscp (100000)";
        }
        enum "cs5" {
          value 40;
          description
            "Match packets with CS5(precedence 5) dscp (101000)";
        }
        enum "cs6" {
          value 48;
          description
            "Match packets with CS6(precedence 6) dscp (110000)";
        }
        enum "cs7" {
          value 56;
          description
            "Match packets with CS7(precedence 7) dscp (111000)";
        }
        enum "default" {
          value 0;
          description
            "Match packets with default DSCP (000000)";
        }
        enum "ef" {
          value 46;
          description
            "Match packets with EF dscp (101110)";
        }
      }
    }
  }

  typedef tcp-bits-type {
    type bits {
      bit fin {
        position 0;
        description
          "Match on the FIN bit (0x01)";
      }
      bit syn {
        position 1;
        description
          "Match on the SYN bit (0x02)";
      }
      bit rst {
        position 2;
        description
          "Match on the RST bit (0x04)";
      }
      bit psh {
        position 3;
        description
          "Match on the PSH bit (0x08)";
      }
      bit ack {
        position 4;
        description
          "Match on the ACK bit (0x10)";
      }
      bit urg {
        position 5;
        description
          "Match on the URG bit (0x20)";
      }
    }
    description
      "acl tcp bits number";
  }

  typedef ipv4-icmp-message-type {
    type enumeration {
      enum "mobile-redirect" {
        value 2162687;
        description
          "Mobile host redirect";
      }
      enum "conversion-error" {
        value 2097151;
        description
          "Datagram conversion";
      }
      enum "traceroute" {
        value 2031615;
        description
          "Traceroute";
      }
      enum "mask-reply" {
        value 1245183;
        description
          "Mask replies";
      }
      enum "mask-request" {
        value 1179647;
        description
          "Mask requests";
      }
      enum "information-reply" {
        value 1114111;
        description
          "Information replies";
      }
      enum "information-request" {
        value 1048575;
        description
          "Information request";
      }
      enum "timestamp-reply" {
        value 983039;
        description
          "Timestamp replies";
      }
      enum "timestamp-request" {
        value 917503;
        description
          "Timestamp requests";
      }
      enum "parameter-problem" {
        value 851967;
        description
          "All parameter problems";
      }
      enum "time-exceeded" {
        value 786431;
        description
          "All time exceeds";
      }
      enum "router-solicitation" {
        value 720895;
        description
          "Router discovery solicitations";
      }
      enum "router-advertisement" {
        value 655359;
        description
          "Router discovery advertisements";
      }
      enum "alternate-address" {
        value 458751;
        description
          "Alternate address";
      }
      enum "echo" {
        value 589823;
        description
          "Echo (ping)";
      }
      enum "redirect" {
        value 393215;
        description
          "All redirects";
      }
      enum "source-quench" {
        value 327679;
        description
          "Source quenches";
      }
      enum "unreachable" {
        value 262143;
        description
          "All unreachables";
      }
      enum "echo-reply" {
        value 65535;
        description
          "Echo reply";
      }
      enum "net-unreachable" {
        value 196608;
        description
          "Net unreachable";
      }
      enum "host-unreachable" {
        value 196609;
        description
          "Host unreachable";
      }
      enum "protocol-unreachable" {
        value 196610;
        description
          "Protocol unreachable";
      }
      enum "port-unreachable" {
        value 196611;
        description
          "Port unreachable";
      }
      enum "packet-too-big" {
        value 196612;
        description
          "Fragmentation needed and DF set";
      }
      enum "source-route-failed" {
        value 196613;
        description
          "Source route failed";
      }
      enum "network-unknown" {
        value 196614;
        description
          "Network unknown";
      }
      enum "host-unknown" {
        value 196615;
        description
          "Host unknown";
      }
      enum "host-isolated" {
        value 196616;
        description
          "Host isolated";
      }
      enum "dod-net-prohibited" {
        value 196617;
        description
          "Net prohibited";
      }
      enum "dod-host-prohibited" {
        value 196618;
        description
          "Host prohibited";
      }
      enum "net-tos-unreachable" {
        value 196620;
        description
          "Network unreachable for TOS";
      }
      enum "host-tos-unreachable" {
        value 196619;
        description
          "Host unreachable for TOS";
      }
      enum "administratively-prohibited" {
        value 196621;
        description
          "Administratively prohibited";
      }
      enum "host-precedence-unreachable" {
        value 196622;
        description
          "Host unreachable for precedence";
      }
      enum "precedence-unreachable" {
        value 196623;
        description
          "Precedence cutoff";
      }
      enum "net-redirect" {
        value 327680;
        description
          "Network redirect";
      }
      enum "host-redirect" {
        value 327681;
        description
          "Host redirect";
      }
      enum "net-tos-redirect" {
        value 327682;
        description
          "Net redirect for TOS";
      }
      enum "host-tos-redirect" {
        value 327683;
        description
          "Host redirect for TOS";
      }
      enum "ttl-exceeded" {
        value 720896;
        description
          "TTL exceeded";
      }
      enum "reassembly-timeout" {
        value 720897;
        description
          "Reassembly timeout";
      }
      enum "general-parameter-problem" {
        value 786432;
        description
          "Parameter problem";
      }
      enum "option-missing" {
        value 786433;
        description
          "Parameter required but not present";
      }
      enum "no-room-for-option" {
        value 786434;
        description
          "Parameter required but no room";
      }
    }
  }

  typedef ipv6-protocol {
    type union {
      type uint8 {
        range "0..255" {
          description
            "An IPv6 Protocol Number";
        }
      }
      type enumeration {
        enum "ahp" {
          value 51;
          description
            "Authentication Header Protocol";
        }
        enum "eigrp" {
          value 88;
          description
            "Cisco's EIGRP Routing Protocol";
        }
        enum "esp" {
          value 50;
          description
            "Encapsulation Security Payload";
        }
        enum "gre" {
          value 47;
          description
            "Cisco's GRE Tunneling";
        }
        enum "icmpv6" {
          value 58;
          description
            "Internet Control Message Protocol";
        }
        enum "igrp" {
          value 9;
          description
            "Cisco's IGRP Routing Protocol";
        }
        enum "ipv6" {
          value 513;
          description
            "Any IPv6 Protocol";
        }
        enum "ospf" {
          value 89;
          description
            "OSPF Routing Protocol";
        }
        enum "pcp" {
          value 108;
          description
            "Payload Compression Protocol";
        }
        enum "pim" {
          value 103;
          description
            "Protocol Independent Multicast";
        }
        enum "sctp" {
          value 132;
          description
            "Stream Control Transmission Protocol";
        }
        enum "tcp" {
          value 6;
          description
            "Transport Control Protocol";
        }
        enum "udp" {
          value 17;
          description
            "User Datagram Protocol";
        }
      }
    }
  }

  typedef ipv6-port-number {
    type union {
      type ipv6-tcp-port-number;
      type ipv6-udp-port-number;
    }
  }

  typedef ipv6-tcp-port-number {
    type union {
      type uint16 {
        range "0..65535";
      }
      type enumeration {
        enum "echo" {
          value 7;
          description
            "Echo";
        }
        enum "discard" {
          value 9;
          description
            "Discard";
        }
        enum "daytime" {
          value 13;
          description
            "Daytime";
        }
        enum "chargen" {
          value 19;
          description
            "Character generator";
        }
        enum "ftp-data" {
          value 20;
          description
            "FTP data connections (used infrequently)";
        }
        enum "ftp" {
          value 21;
          description
            "File Transfer Protocol";
        }
        enum "ssh" {
          value 22;
          description
            "Secure Shell";
        }
        enum "telnet" {
          value 23;
          description
            "Telnet";
        }
        enum "smtp" {
          value 25;
          description
            "Simple Mail Transport Protocol";
        }
        enum "time" {
          value 37;
          description
            "Time";
        }
        enum "whois" {
          value 43;
          description
            "Nicname";
        }
        enum "tacacs" {
          value 49;
          description
            "TAC Access Control System";
        }
        enum "domain" {
          value 53;
          description
            "Domain Name Service";
        }
        enum "gopher" {
          value 70;
          description
            "Gopher";
        }
        enum "finger" {
          value 79;
          description
            "Finger";
        }
        enum "www" {
          value 80;
          description
            "World Wide Web (HTTP)";
        }
        enum "hostname" {
          value 101;
          description
            "NIC hostname server";
        }
        enum "pop2" {
          value 109;
          description
            "Post Office Protocol v2";
        }
        enum "pop3" {
          value 110;
          description
            "Post Office Protocol v3";
        }
        enum "sunrpc" {
          value 111;
          description
            "Sun Remote Procedure Call";
        }
        enum "ident" {
          value 113;
          description
            "Ident Protocol";
        }
        enum "nntp" {
          value 119;
          description
            "Network News Transport Protocol";
        }
        enum "bgp" {
          value 179;
          description
            "Border Gateway Protocol";
        }
        enum "irc" {
          value 194;
          description
            "Internet Relay Chat";
        }
        enum "pim-auto-rp" {
          value 496;
          description
            "PIM Auto-RP";
        }
        enum "exec" {
          value 512;
          description
            "Exec (rsh)";
        }
        enum "login" {
          value 513;
          description
            "Login (rlogin)";
        }
        enum "cmd" {
          value 514;
          description
            "Remote commands (rcmd)";
        }
        enum "lpd" {
          value 515;
          description
            "Printer service";
        }
        enum "uucp" {
          value 540;
          description
            "Unix-to-Unix Copy Program";
        }
        enum "klogin" {
          value 543;
          description
            "Kerberos login";
        }
        enum "kshell" {
          value 544;
          description
            "Kerberos shell";
        }
        enum "talk" {
          value 517;
          description
            "Talk";
        }
      }
    }
  }

  typedef ipv6-udp-port-number {
    type union {
      type uint16 {
        range "0..65535";
      }
      type enumeration {
        enum "biff" {
          value 512;
          description
            "Biff (mail notification, comsat";
        }
        enum "bootpc" {
          value 68;
          description
            "Bootstrap Protocol (BOOTP) client";
        }
        enum "bootps" {
          value 67;
          description
            "Bootstrap Protocol (BOOTP) server";
        }
        enum "discard" {
          value 9;
          description
            "Discard";
        }
        enum "dnsix" {
          value 195;
          description
            "DNSIX security protocol auditing";
        }
        enum "domain" {
          value 53;
          description
            "Domain Name Service (DNS)";
        }
        enum "echo" {
          value 7;
          description
            "Echo";
        }
        enum "isakmp" {
          value 500;
          description
            "Internet Security Association and Key Management Protocol";
        }
        enum "mobile-ip" {
          value 434;
          description
            "Mobile IP registration";
        }
        enum "nameserver" {
          value 42;
          description
            "IEN116 name service (obsolete)";
        }
        enum "netbios-dgm" {
          value 138;
          description
            "NetBios datagram service";
        }
        enum "netbios-ns" {
          value 137;
          description
            "NetBios name service";
        }
        enum "netbios-ss" {
          value 139;
          description
            "NetBios session service";
        }
        enum "ntp" {
          value 123;
          description
            "Network Time Protocol";
        }
        enum "pim-auto-rp" {
          value 496;
          description
            "PIM Auto-RP";
        }
        enum "rip" {
          value 520;
          description
            "Routing Information Protocol (router, in.routed)";
        }
        enum "snmp" {
          value 161;
          description
            "Simple Network Management Protocol";
        }
        enum "snmptrap" {
          value 162;
          description
            "SNMP Traps";
        }
        enum "ssh" {
          value 22;
          description
            "Secure Shell service";
        }
        enum "sunrpc" {
          value 111;
          description
            "Sun Remote Procedure Call";
        }
        enum "syslog" {
          value 514;
          description
            "System Logger";
        }
        enum "tacacs" {
          value 49;
          description
            "TAC Access Control System";
        }
        enum "talk" {
          value 517;
          description
            "Talk";
        }
        enum "tftp" {
          value 69;
          description
            "Trivial File Transfer Protocol";
        }
        enum "time" {
          value 37;
          description
            "Time";
        }
        enum "who" {
          value 513;
          description
            "Who service (rwho)";
        }
        enum "xdmcp" {
          value 177;
          description
            "X Display Manager Control Protocol";
        }
      }
    }
  }

  typedef ipv6-icmp-message-type {
    type enumeration {
      enum "parameter-problem" {
        value 327679;
        description
          "All parameter problems";
      }
      enum "time-exceeded" {
        value 262143;
        description
          "All time exceeds";
      }
      enum "router-solicitation" {
        value 8716288;
        description
          "Router discovery solicitations";
      }
      enum "router-advertisement" {
        value 8781824;
        description
          "Router discovery advertisements";
      }
      enum "echo" {
        value 8388608;
        description
          "Echo (ping)";
      }
      enum "echo-reply" {
        value 8454144;
        description
          "Echo reply";
      }
      enum "port-unreachable" {
        value 65540;
        description
          "Port unreachable";
      }
      enum "packet-too-big" {
        value 131072;
        description
          "Fragmentation needed and DF set";
      }
      enum "administratively-prohibited" {
        value 65537;
        description
          "Administratively prohibited";
      }
      enum "ttl-exceeded" {
        value 196608;
        description
          "TTL exceeded";
      }
      enum "reassembly-timeout" {
        value 196609;
        description
          "Reassembly timeout";
      }
      enum "erroneous-header-field" {
        value 262144;
        description
          "Erroneous header field";
      }
      enum "unrecognized-next-header" {
        value 262145;
        description
          "Unrecognized Next Header type";
      }
      enum "unrecognized-option" {
        value 262146;
        description
          "Unrecognized IPv6 option";
      }
      enum "destination-unreachable" {
        value 131071;
        description
          "Destination Unreachable";
      }
      enum "address-unreachable" {
        value 65539;
        description
          "Address Unreachable";
      }
      enum "beyond-scope-of-source-address" {
        value 65538;
        description
          "Unreachable beyond scope of address";
      }
      enum "group-membership-query" {
        value 8585215;
        description
          "Multicast Listener Query";
      }
      enum "group-membership-report" {
        value 8650751;
        description
          "Multicast Listener report";
      }
      enum "group-membership-termination" {
        value 8716287;
        description
          "Multicast Listener Done";
      }
      enum "neighbor-redirect" {
        value 8978432;
        description
          "Neighbor redirect";
      }
      enum "no-route-to-destination" {
        value 65536;
        description
          "No route to destination";
      }
      enum "node-information-successful-reply" {
        value 9175040;
        description
          "Node information successful reply";
      }
      enum "node-information-request-is-refused" {
        value 9175041;
        description
          "Node information reply rejected";
      }
      enum "router-renumbering" {
        value 9109503;
        description
          "Router renumbering";
      }
      enum "rr-command" {
        value 9043968;
        description
          "Router renumbering command";
      }
      enum "rr-result" {
        value 9043969;
        description
          "Router renumbering result";
      }
      enum "rr-seqnum-reset" {
        value 9044223;
        description
          "Router renumbering seqnum";
      }
      enum "query-subject-is-IPv6-address" {
        value 9109504;
        description
          "Query subject is ipv6 address";
      }
      enum "query-subject-is-domainname" {
        value 9109505;
        description
          "Query subject is domain name";
      }
      enum "query-subject-is-IPv4address" {
        value 9109506;
        description
          "Query subject is ipv4 address";
      }
      enum "nd-ns" {
        value 8847360;
        description
          "Neighbor discovery neighbor solicitations";
      }
      enum "nd-na" {
        value 8912896;
        description
          "Neighbor discovery neighbor advertisements";
      }
      enum "whoareyou-request" {
        value 9175039;
        description
          "Who are you request";
      }
      enum "whoareyou-reply" {
        value 9240575;
        description
          "Who are you reply";
      }
      enum "unknown-query-type" {
        value 9175042;
        description
          "Unknown query type";
      }
    }
  }

  typedef header-bits-type {
    type bits {
      bit routing {
        position 0;
        description
          "Match if routing header is present";
      }
      bit destopts {
        position 1;
        description
          "Match if destination opts header is present";
      }
      bit hop-by-hop {
        position 2;
        description
          "Match if hop-by-hop opts header is present";
      }
      bit fragments {
        position 3;
        description
          "Match if fragment extension header contains a non-zero fragment offset";
      }
      bit authen {
        position 5;
        description
          "Match if authentication header is present";
      }
    }
    description
      "IPv6 hearder bits number";
  }

  typedef vlan-id {
    type union {
      type uint16 {
        range "0..4095" {
          description
            "Vlan Id";
        }
      }
      type string {
        pattern "([0-9]{1,4})-([0-9]{1,4})" {
          description
            "Lower/upper limit of the Vlan Id range (<0-4095>-<0-4095>)";
        }
      }
    }
  }
}
