module Cisco-IOS-XR-sysadmin-obfl-conf {
  namespace "http://www.cisco.com/ns/yang/Cisco-IOS-XR-sysadmin-obfl-conf";
  prefix obflconf;

  import cisco-semver {
    prefix semver;
  }

  organization
    "Cisco Systems Inc.";
  contact
    "Cisco Systems, Inc.
     Customer Service
     
     Postal: 170 West Tasman Drive
     San Jose, CA 95134
     
     Tel: +1 800 553-NETS
     
     E-mail: cs-yang@cisco.com";
  description
    "This module is for setting certain OBFL params.
     
     Copyright (c) 2012-2019 by Cisco Systems, Inc.
     All rights reserved.";

  revision 2019-04-15 {
    description
      "Establish semantic version baseline.";
    semver:module-version "1.0.0";
  }
  revision 2017-07-31 {
    description
      "Changed namespace to Cisco guidelines on naming convention";
  }
  revision 2011-12-03 {
    description
      "Initial revision.";
  }

  grouping hw-module-config-group {
    uses hw-module-obfl-config-group;
  }

  grouping hw-module-obfl-config-group {
    list location {
      key "location";
      leaf location {
        type string;
      }
      container logging {
        container onboard {
          choice onboard_target {
            case target_disable {
              leaf disable {
                type empty;
              }
            }
          }
        }
      }
    }
  }
}
