module Cisco-IOS-XR-freqsync-sat-cfg {
  namespace "http://cisco.com/ns/yang/Cisco-IOS-XR-freqsync-sat-cfg";
  prefix freqsync-sat-cfg;

  import cisco-semver {
    prefix semver;
  }
  import Cisco-IOS-XR-ifmgr-cfg {
    prefix a1;
  }
  import Cisco-IOS-XR-l2-eth-infra-cfg {
    prefix a2;
  }
  import Cisco-IOS-XR-icpe-infra-cfg {
    prefix a3;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR freqsync-sat package configuration.
     
     This YANG module augments the
       Cisco-IOS-XR-ifmgr-cfg,
       Cisco-IOS-XR-l2-eth-infra-cfg,
       Cisco-IOS-XR-icpe-infra-cfg
     modules with configuration data.
     
     Copyright (c) 2013-2019 by Cisco Systems, Inc.
     All rights reserved.";

  revision 2019-04-05 {
    description
      "Establish semantic version baseline.";
    semver:module-version "1.0.1";
  }
  revision 2015-11-09 {
    description
      "IOS XR 6.0 revision.";
  }

  augment "/a1:interface-configurations/a1:interface-configuration/a3:nv-satellite-fabric-link" {
    description
      "This augment extends the configuration data of
       'Cisco-IOS-XR-icpe-infra-cfg'";
    container frequency-synchronization {
      description
        "Frequency Synchronization satellite
         configuration";
      leaf enable {
        type empty;
        description
          "Enable Frequency Synchronization";
      }
    }
  }
}
