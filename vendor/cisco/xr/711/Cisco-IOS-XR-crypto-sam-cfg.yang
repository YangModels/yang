module Cisco-IOS-XR-crypto-sam-cfg {
  namespace "http://cisco.com/ns/yang/Cisco-IOS-XR-crypto-sam-cfg";
  prefix crypto-sam-cfg;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR crypto-sam package configuration.
     
     This module contains definitions
     for the following management objects:
       sam: Software Authentication Manager (SAM) Config
     
     Copyright (c) 2013-2019 by Cisco Systems, Inc.
     All rights reserved.";

  revision 2019-04-05 {
    description
      "Establish semantic version baseline.";
    semver:module-version "1.0.0";
  }
  revision 2017-11-21 {
    description
      "Resolving dependency issue with SAM";
  }
  revision 2015-01-07 {
    description
      "IOS XR 5.3.1 revision.";
  }

  typedef Crypto-sam-action {
    type enumeration {
      enum "proceed" {
        value 1;
        description
          "To respond YES to the SAM prompt";
      }
      enum "terminate" {
        value 2;
        description
          "To respond NO to the SAM prompt";
      }
    }
    description
      "Crypto sam action";
  }

  container sam {
    description
      "Software Authentication Manager (SAM) Config";
    container prompt-interval {
      presence "Indicates a prompt-interval node is configured.";
      description
        "Set prompt interval at reboot time";
      leaf action {
        type Crypto-sam-action;
        mandatory true;
        description
          "Respond to SAM prompt either Proceed/Terminate";
      }
      leaf prompt-time {
        type uint32 {
          range "0..300";
        }
        units "second";
        mandatory true;
        description
          "Prompt time from 0 - 300 seconds";
      }
    }
  }
}
