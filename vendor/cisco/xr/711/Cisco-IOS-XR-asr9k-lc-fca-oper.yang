module Cisco-IOS-XR-asr9k-lc-fca-oper {
  namespace "http://cisco.com/ns/yang/Cisco-IOS-XR-asr9k-lc-fca-oper";
  prefix asr9k-lc-fca-oper;

  import Cisco-IOS-XR-types {
    prefix xr;
  }
  import cisco-semver {
    prefix semver;
  }
  include Cisco-IOS-XR-asr9k-lc-fca-oper-sub2 {
    revision-date 2019-04-05;
  }
  include Cisco-IOS-XR-asr9k-lc-fca-oper-sub1 {
    revision-date 2019-04-05;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR asr9k-lc-fca package operational data.
     
     This module contains definitions
     for the following management objects:
       mpa-internal: Management LAN Operational data space
       mpa: Management LAN Operational data space
     
     Copyright (c) 2013-2019 by Cisco Systems, Inc.
     All rights reserved.";

  revision 2019-04-05 {
    description
      "Establish semantic version baseline.";
    semver:module-version "1.0.1";
  }
  revision 2015-11-09 {
    description
      "IOS XR 6.0 revision.";
  }

  container mpa-internal {
    config false;
    description
      "Management LAN Operational data space";
    container nodes {
      description
        "Table of nodes";
      list node {
        key "node";
        description
          "Number";
        leaf node {
          type xr:Node-id;
          description
            "node number";
        }
        list bay {
          key "number";
          description
            "Number";
          container ifsubsies {
            description
              "Table of Ifsubsys";
            list ifsubsy {
              key "number";
              description
                "Number";
              container mpa-internal-info {
                description
                  "mpa internal info";
                uses LDA-IFSUBSYS-STATE-EDM-INFO;
              }
              leaf number {
                type xr:Hex-integer;
                description
                  "ifsubsys number";
              }
            }
          }
          leaf number {
            type uint32;
            description
              "bay number";
          }
        }
      }
    }
  }
  container mpa {
    config false;
    description
      "Management LAN Operational data space";
    container nodes {
      description
        "Table of nodes";
      list node {
        key "node";
        description
          "Number";
        leaf node {
          type xr:Node-id;
          description
            "node number";
        }
        list bay {
          key "number";
          description
            "Number";
          container mpa-detail-table {
            description
              "Table of Mpa Detail Info";
            container mpa-detail {
              description
                "mpa detail status info";
              uses SPA-BAY-STATUS-INFO;
            }
          }
          leaf number {
            type uint32;
            description
              "bay number";
          }
        }
      }
    }
  }
}
