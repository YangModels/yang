submodule Cisco-IOS-XR-ipv6-nd-oper-sub1 {
  belongs-to Cisco-IOS-XR-ipv6-nd-oper {
    prefix Cisco-IOS-XR-ipv6-nd-oper;
  }

  import ietf-inet-types {
    prefix inet;
  }
  import ietf-yang-types {
    prefix yang;
  }
  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR ipv6-nd package operational data.
     
     Copyright (c) 2013-2019 by Cisco Systems, Inc.
     All rights reserved.";

  revision 2019-11-08 {
    description
      "Modified bag with dns server/searchlist count.
       2019-09-26
         changing dns lifetime range.";
    semver:module-version "1.1.0";
  }
  revision 2019-04-05 {
    description
      "Establish semantic version baseline.";
    semver:module-version "1.0.0";
  }
  revision 2019-02-18 {
    description
      "Fixing yang usability warnings.";
  }
  revision 2015-11-09 {
    description
      "IOS XR 6.0 revision.";
  }

  typedef Ipv6-nd-sh-vr-flags {
    type enumeration {
      enum "no-flags" {
        description
          "None";
      }
      enum "final-ra" {
        description
          "Final RA";
      }
    }
    description
      "IPv6 ND VR Entry Flags Type ";
  }

  typedef Ipv6-nd-sh-vr-state {
    type enumeration {
      enum "deleted" {
        description
          "Delete";
      }
      enum "standby" {
        description
          "Standby";
      }
      enum "active" {
        description
          "Active";
      }
    }
    description
      "IPv6 ND VR Entry State Type ";
  }

  typedef Ipv6-nd-bndl-state {
    type enumeration {
      enum "run" {
        description
          "Running state";
      }
      enum "error" {
        description
          "Error state";
      }
      enum "wait" {
        description
          "Wait state";
      }
    }
    description
      "IPv6 ND Bundle State";
  }

  typedef Ipv6-nd-neighbor-origin {
    type enumeration {
      enum "other" {
        description
          "Other Address";
      }
      enum "static" {
        description
          "Static Address";
      }
      enum "dynamic" {
        description
          "Dynamic Address";
      }
    }
    description
      "IPv6 ND Neighbor Origin Type";
  }

  typedef Ipv6-nd-media-encap {
    type enumeration {
      enum "none" {
        description
          "No encapsulation";
      }
      enum "arpa" {
        description
          "ARPA encapsulation";
      }
      enum "snap" {
        description
          "SNAP encapsulation";
      }
      enum "ieee802-1q" {
        description
          "802_1Q encapsulation";
      }
      enum "srp" {
        description
          "SRP encapsulation";
      }
      enum "srpa" {
        description
          "SRPA encapsulation";
      }
      enum "srpb" {
        description
          "SRPB encapsulation";
      }
      enum "ppp" {
        description
          "PPP encapsulation";
      }
      enum "hdlc" {
        description
          "HDLC encapsulation";
      }
      enum "chdlc" {
        description
          "CHDLC encapsulation";
      }
      enum "dot1q" {
        description
          "DOT1Q encapsulation";
      }
      enum "fr" {
        description
          "FR encapsulation";
      }
      enum "gre" {
        description
          "GRE encapsulation";
      }
    }
    description
      "IPv6 ND Media Encapsulation Type";
  }

  typedef Ipv6-nd-sh-state {
    type enumeration {
      enum "incomplete" {
        description
          "Incomplete";
      }
      enum "reachable" {
        description
          "Reachable";
      }
      enum "stale" {
        description
          "Stale";
      }
      enum "glean" {
        description
          "Glean";
      }
      enum "delay" {
        description
          "Delay";
      }
      enum "probe" {
        description
          "Probe";
      }
      enum "delete" {
        description
          "Delete";
      }
    }
    description
      "IPv6 ND Neighbor Reachability State";
  }

  grouping IPV6-ND-PREFIX-Q {
    description
      "Prefix Queue";
    leaf prefix-address {
      type inet:ipv6-address;
      description
        "IPV6 Prefix address";
    }
    leaf eui64 {
      type inet:ipv6-address;
      description
        "IPv6 Auto generated address";
    }
    leaf valid-life-time {
      type uint32;
      description
        "IPV6 Prefix Valid Life Time";
    }
    leaf preferred-life-time {
      type uint32;
      description
        "IPV6 Prefix Preferred Life Time";
    }
    leaf prefix-len {
      type uint32;
      description
        "IPV6 Prefix Length";
    }
    leaf flags {
      type uint32;
      description
        "IPv6 Address Specific Flags";
    }
    leaf pfx-flags {
      type uint32;
      description
        "Prefix Address Specific Flags";
    }
  }

  grouping IPV6-ND-RA-INFO {
    description
      "RA Info";
    container elapsed-ra-time {
      description
        "elapsedRATime";
      uses BAG-TIMESPEC;
    }
    container reachable-time {
      description
        "common reachabletime";
      uses BAG-TIMESPEC;
    }
    container retrans-time {
      description
        "RA retransmit time";
      uses BAG-TIMESPEC;
    }
    leaf address {
      type inet:ipv6-address;
      description
        "address of type IPV6";
    }
    leaf hops {
      type uint32;
      description
        "number of intermediate devices between source
         and destination";
    }
    leaf flags {
      type uint32;
      description
        "RA flags";
    }
    leaf life-time {
      type uint32;
      description
        "active time";
    }
    leaf mtu {
      type uint32;
      description
        "maximum transmission unit";
    }
    leaf err-msg {
      type boolean;
      description
        "message having the error info";
    }
    leaf vrf-id {
      type uint32;
      description
        "virtual routing and forwarding id";
    }
    leaf u6-tbl-id {
      type uint32;
      description
        "tbl id";
    }
    leaf rib-protoid {
      type uint16;
      description
        "proto id";
    }
    leaf default-router {
      type boolean;
      description
        "router";
    }
    leaf reachability {
      type uint32;
      description
        "reach";
    }
    list prefix-q {
      description
        "Prefix Queue";
      uses IPV6-ND-PREFIX-Q;
    }
  }

  grouping IPV6-ND-SLAAC-INTFS-INFO {
    description
      "Slaac Intfs";
    leaf idb {
      type xr:Interface-name;
      description
        "interface database";
    }
    list ra {
      description
        "slaac db";
      uses IPV6-ND-RA-INFO;
    }
  }

  grouping IPV6-ND-VR-ENTRY {
    description
      "Detailed Info of ND IPv6 Virtual Router entry";
    container local-address {
      description
        "IPV6 Link local address";
      uses IPV6-ND-ADDR;
    }
    leaf link-layer-address {
      type yang:mac-address;
      description
        "IPV6 Link-Layer Address";
    }
    leaf context {
      type uint32;
      description
        "Virtual Router ID";
    }
    leaf state {
      type Ipv6-nd-sh-vr-state;
      description
        "VR state";
    }
    leaf flags {
      type Ipv6-nd-sh-vr-flags;
      description
        "VR Flags";
    }
    leaf vr-gl-addr-ct {
      type uint32;
      description
        "Virtual Global Address Count";
    }
    list vr-global-address {
      description
        "List of ND global addresses";
      uses IPV6-ND-ADDR;
    }
  }

  grouping IPV6-ND-GSPNODE {
    description
      "GSP node info ";
    leaf node-name {
      type xr:Node-id;
      description
        "Node Name";
    }
    leaf total-links {
      type uint32;
      description
        "Number of links on the node";
    }
  }

  grouping IPV6-ND-ADDR {
    description
      "List of IPv6 ND Addresses ";
    leaf ipv6-address {
      type inet:ipv6-address;
      description
        "Address of type IPV6";
    }
    leaf valid-lifetime {
      type uint32;
      description
        "Valid lifetime of a Prefix";
    }
    leaf pref-lifetime {
      type uint32;
      description
        "Preffered lifetime of a Prefix";
    }
    leaf prefix-length {
      type uint32;
      description
        "IPV6 Prefix length";
    }
    leaf flags {
      type uint32;
      description
        "Address flags";
    }
  }

  grouping IPV6-ND-IF-PARAMS {
    description
      "Detailed Info of ND IPv6 Interface";
    leaf is-dad-enabled {
      type boolean;
      description
        "If true, DAD (D.. A.. D..) is enabled otherwise
         it is disabled";
    }
    leaf dad-attempts {
      type uint32;
      description
        "DAD attempt count";
    }
    leaf is-icm-pv6-redirect {
      type boolean;
      description
        "ICMP redirect flag";
    }
    leaf is-dhcp-managed {
      type boolean;
      description
        "Flag used for utilising DHCP";
    }
    leaf is-route-address-managed {
      type boolean;
      description
        "Flag used to manage routable address";
    }
    leaf is-suppressed {
      type boolean;
      description
        "Suppress flag";
    }
    leaf send-unicast-ra {
      type boolean;
      description
        "unicast RA send flag";
    }
    leaf nd-retransmit-interval {
      type uint32;
      description
        "ND retransmit interval in msec";
    }
    leaf nd-min-transmit-interval {
      type uint32;
      description
        "ND router advertisement minimum transmit
         interval in sec";
    }
    leaf nd-max-transmit-interval {
      type uint32;
      description
        "ND router advertisement maximum transmit
         interval in sec";
    }
    leaf nd-advertisement-lifetime {
      type uint32;
      description
        "ND router advertisement life time in sec";
    }
    leaf nd-reachable-time {
      type uint32;
      description
        "Time to reach ND in msec";
    }
    leaf nd-cache-limit {
      type uint32;
      description
        "Completed adjacency limit per interface";
    }
    leaf complete-protocol-count {
      type uint32;
      description
        "Completed PROTO entry Count";
    }
    leaf complete-glean-count {
      type uint32;
      description
        "Completed GLEAN entry count";
    }
    leaf incomplete-protocol-count {
      type uint32;
      description
        "Incomplete PROTO entry count";
    }
    leaf incomplete-glean-count {
      type uint32;
      description
        "Incomplete GLEAN entry count";
    }
    leaf dropped-protocol-req-count {
      type uint32;
      description
        "Dropped PROTO entry request count";
    }
    leaf dropped-glean-req-count {
      type uint32;
      description
        "Dropped GLEAN entry lequest count";
    }
    leaf radns-server-address-count {
      type uint32;
      description
        "RA DNS Server Address Count";
    }
    leaf radns-search-list-count {
      type uint32;
      description
        "RA DNS Search List Count";
    }
  }

  grouping IPV6-ND-IF-ENTRY {
    description
      "Detailed Info of ND IPv6 Interface entry";
    container nd-parameters {
      description
        "ND interface parameters";
      uses IPV6-ND-IF-PARAMS;
    }
    container local-address {
      description
        "IPV6 Link local address";
      uses IPV6-ND-ADDR;
    }
    leaf parent-interface-name {
      type xr:Interface-name;
      description
        "Name of the Parent interface";
    }
    leaf iftype {
      type uint32;
      description
        "Interface type";
    }
    leaf mtu {
      type uint32;
      description
        "MTU";
    }
    leaf etype {
      type uint32;
      description
        "etype field";
    }
    leaf vlan-tag {
      type uint16;
      description
        "vlan tag/id/ucv";
    }
    leaf mac-addr-size {
      type uint32;
      description
        "size of mac address";
    }
    leaf mac-addr {
      type yang:mac-address;
      description
        "media access control address";
    }
    leaf is-interface-enabled {
      type boolean;
      description
        "If true, interface is enabled";
    }
    leaf is-ipv6-enabled {
      type boolean;
      description
        "If true, IPv6 is enabled";
    }
    leaf is-mpls-enabled {
      type boolean;
      description
        "If true, MPLS is enabled";
    }
    leaf-list member-link {
      type uint32;
      description
        "List of member links";
    }
    list global-address {
      description
        "List of ND global addresses";
      uses IPV6-ND-ADDR;
    }
    list member-node {
      description
        "List of member nodes";
      uses IPV6-ND-GSPNODE;
    }
  }

  grouping IPV6-ND-BL-NODE-ENTRY {
    description
      "IPv6 node discovery bundle node information";
    container age {
      description
        "Uptime of node (secs)";
      uses BAG-TIMESPEC;
    }
    leaf group-id {
      type uint32;
      description
        "Group ID";
    }
    leaf process-name {
      type string;
      description
        "Name of the process";
    }
    leaf sent-sequence-number {
      type uint32;
      description
        "Sent sequence number for error detection";
    }
    leaf received-sequence-number {
      type uint32;
      description
        "Received sequence num for error detection";
    }
    leaf state {
      type Ipv6-nd-bndl-state;
      description
        "State";
    }
    leaf state-changes {
      type uint32;
      description
        "change of state";
    }
    leaf sent-packets {
      type uint32;
      description
        "Total packet sends";
    }
    leaf received-packets {
      type uint32;
      description
        "Total packet receives";
    }
  }

  grouping BAG-NBR-ENTRY-SUM {
    description
      "IPv6 ND summary information";
    leaf incomplete-entries {
      type uint32;
      description
        "Total ipv6 neighbhors count which are in INCMP
         state";
    }
    leaf reachable-entries {
      type uint32;
      description
        "Total ipv6 neighbhors count which are in REACH
         state";
    }
    leaf stale-entries {
      type uint32;
      description
        "Total ipv6 neighbhors count which are STALE";
    }
    leaf delayed-entries {
      type uint32;
      description
        "Total ipv6 neighbhors count which are in DELAY
         state";
    }
    leaf probe-entries {
      type uint32;
      description
        "Total ipv6 neighbhors count which are in PROBE
         state";
    }
    leaf deleted-entries {
      type uint32;
      description
        "Total ipv6 neighbhors count which are in DELETE
         state";
    }
    leaf subtotal-neighbor-entries {
      type uint32;
      description
        "Total number of entries";
    }
  }

  grouping IPV6-ND-NEIGHBOR-ENTRY-SUMMARY {
    description
      "IPv6 ND neighbor entry summary";
    container multicast {
      description
        "Multicast neighbor summary";
      uses BAG-NBR-ENTRY-SUM;
    }
    container static {
      description
        "Static neighbor summary";
      uses BAG-NBR-ENTRY-SUM;
    }
    container dynamic {
      description
        "Dynamic neighbor summary";
      uses BAG-NBR-ENTRY-SUM;
    }
    container sync {
      description
        "Sync neighbor summary";
      uses BAG-NBR-ENTRY-SUM;
    }
    container static-sync {
      description
        "StaticSync neighbor summary";
      uses BAG-NBR-ENTRY-SUM;
    }
    container dynamic-sync {
      description
        "DynamicSync neighbor summary";
      uses BAG-NBR-ENTRY-SUM;
    }
    leaf total-neighbor-entries {
      type uint32;
      description
        "Total number of entries";
    }
  }

  grouping BAG-TIMESPEC {
    description
      "Timespec specifying the number of seconds since
       the base time of 00:00:00 GMT, 1 January 1970.";
    leaf seconds {
      type uint32;
      units "second";
      description
        "Number of seconds";
    }
  }

  grouping IPV6-ND-NEIGHBOR-ENTRY {
    description
      "IPv6 ND neighbor entry";
    container last-reached-time {
      description
        "Last time of reachability";
      uses BAG-TIMESPEC;
    }
    leaf reachability-state {
      type Ipv6-nd-sh-state;
      description
        "Current state";
    }
    leaf link-layer-address {
      type yang:mac-address;
      description
        "IPV6 Link-Layer Address";
    }
    leaf encapsulation {
      type Ipv6-nd-media-encap;
      description
        "Preferred media encap type";
    }
    leaf selected-encapsulation {
      type Ipv6-nd-media-encap;
      description
        "Selected media encap";
    }
    leaf origin-encapsulation {
      type Ipv6-nd-neighbor-origin;
      description
        "Neighbor origin";
    }
    leaf interface-name {
      type string;
      description
        "Name of Interface";
    }
    leaf location {
      type xr:Node-id;
      description
        "Location where the neighbor entry exists";
    }
    leaf is-router {
      type boolean;
      description
        "IsRouter";
    }
    leaf serg-flags {
      type uint32;
      description
        "ND serg flags for this entry";
    }
    leaf vrfid {
      type uint32;
      description
        "VRF name for this entry";
    }
  }
}
