//*************  DO-NOT EDIT  **************
//*********** Auto-generated file ********** 

 module cisco-xr-openconfig-platform-deviations {

  prefix  "oc-platformdevs";

  namespace "http://cisco.com/ns/yang/cisco-xr-openconfig-platform-deviations";

  import openconfig-platform { prefix oc-platform; }

  organization "Cisco Systems, Inc.";

  contact
    "Cisco Systems, Inc.
     Customer Service

     Postal: 170 West Tasman Drive
     San Jose, CA 95134

     Tel: +1 800 553-NETS

     E-mail: cs-yang@cisco.com";

  description
    "This module contains a set of deviations for 
 
     openconfig-platform.yang@2018-06-29 

     on Cisco IOS-XR devices.

     Copyright (c) 2017-2019 by Cisco Systems, Inc.
     All rights reserved.";

  revision "2019-10-15" {
    description
      "IOS XR 7.0.12 revision";
  }

  revision "2019-08-22" {
    description
      "Initial revision applicable to IOS-XR 7.0.11";
  }


  deviation /oc-platform:components/oc-platform:component/oc-platform:state/oc-platform:mfg-date {
    deviate not-supported;
  }

  deviation /oc-platform:components/oc-platform:component/oc-platform:state/oc-platform:temperature:avg {
    deviate not-supported;
  }

  deviation /oc-platform:components/oc-platform:component/oc-platform:state/oc-platform:temperature:min {
    deviate not-supported;
  }

  deviation /oc-platform:components/oc-platform:component/oc-platform:state/oc-platform:temperature:max {
    deviate not-supported;
  }

  deviation /oc-platform:components/oc-platform:component/oc-platform:state/oc-platform:temperature:interval {
    deviate not-supported;
  }

  deviation /oc-platform:components/oc-platform:component/oc-platform:state/oc-platform:temperature:min-time {
    deviate not-supported;
  }

  deviation /oc-platform:components/oc-platform:component/oc-platform:state/oc-platform:temperature:max-time {
    deviate not-supported;
  }

  deviation /oc-platform:components/oc-platform:component/oc-platform:properties/oc-platform:property {
    deviate not-supported;
  }


}
//total deviations:8
