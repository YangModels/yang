module Cisco-IOS-XR-sysadmin-vm-mgr {
  namespace "http://www.cisco.com/ns/yang/Cisco-IOS-XR-sysadmin-vm-mgr";
  prefix vmmh;

  import cisco-semver {
    prefix semver;
  }

  organization
    "Cisco Systems Inc.";
  contact
    "Cisco Systems, Inc.
     Customer Service
     
     Postal: 170 West Tasman Drive
     San Jose, CA 95134
     
     Tel: +1 800 553-NETS
     
     E-mail: cs-yang@cisco.com";
  description
    "This module contains a collection of YANG
     definitions for Cisco IOS-XR SysAdmin configuration.
     
     Copyright (c) 2012-2019 by Cisco Systems, Inc.
     All rights reserved.";

  revision 2019-06-12 {
    description
      "Fixed canonical order error for keyword config";
    semver:module-version "1.0.0";
  }
  revision 2019-04-15 {
    description
      "Establish semantic version baseline.";
  }
  revision 2018-07-13 {
    description
      "Removed unused show fields in show vm";
  }
  revision 2017-04-12 {
    description
      "Changed the namespace and module name";
  }
  revision 2016-05-12 {
    description
      "Initial Version";
  }

  container VM {
    config false;
    description
      "VM Info";
    list all-locations {
      key "location";
      leaf location {
        type string;
      }
      list all-uiids {
        key "uiid";
        leaf uiid {
          type string;
          description
            "Unique Immutable ID";
        }
        leaf id {
          type string;
          description
            "ID of the VM";
        }
        leaf status {
          type string;
          description
            "Status of the VM";
        }
        leaf ipaddr {
          type string;
          description
            "CE IP address";
        }
        leaf last_hb_sent {
          type string;
          description
            "Last heartbeat sent";
        }
        leaf last_hb_rec {
          type string;
          description
            "Last heartbeat received";
        }
      }
    }
  }
}
