module Cisco-IOS-XR-segment-routing-srv6-datatypes {
  namespace "http://cisco.com/ns/yang/Cisco-IOS-XR-segment-routing-srv6-datatypes";
  prefix segment-routing-srv6-datatypes;

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of generally useful
     derived YANG data types.
     
     Copyright (c) 2013-2019 by Cisco Systems, Inc.
     All rights reserved.";

  revision 2019-04-05 {
    description
      "Establish semantic version baseline.";
    semver:module-version "1.0.1";
  }
  revision 2015-11-09 {
    description
      "IOS XR 6.0 revision.";
  }

  typedef Srv6-locator-name {
    type xr:Cisco-ios-xr-string {
      length "1..58";
    }
    description
      "Srv6 locator name";
  }

  typedef Srv6sid-holdtime {
    type uint32 {
      range "0..60";
    }
    description
      "Srv6sid holdtime";
  }

  typedef Srv6-locator-len {
    type uint32 {
      range "32..112";
    }
    description
      "Srv6 locator len";
  }

  typedef Srv6-encapsulation-hop-limit-value {
    type uint32 {
      range "1..255";
    }
    description
      "Srv6 encapsulation hop limit value";
  }

  typedef Srv6-encapsulation-hop-limit-option {
    type enumeration {
      enum "count" {
        value 1;
        description
          "Set Value";
      }
    }
    description
      "Srv6 encapsulation hop limit option";
  }
}
