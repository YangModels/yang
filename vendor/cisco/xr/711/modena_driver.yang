module modena_driver {
  namespace "http://www.cisco.com/calvados/calvados_controllers/slice_control/modena";
  prefix modena_driver;

  import modena_driver_types {
    prefix modena-driver-types;
  }

  organization "Cisco Systems, Inc.";

  contact
    "Cisco Systems, Inc.
     Customer Service
    
     Postal: 170 West Tasman Drive
     San Jose, CA 95134
    
     Tel: +1 800 553-NETS
    
     E-mail: cs-yang@cisco.com";

  description 
    "This module contains definitions
     for the Calvados model objects.

     Copyright (c) 2012-2019 by Cisco Systems, Inc.
     All rights reserved.";

  revision "2018-04-09" {
    description "Required changes for ConfD 6.4.5";
  }

  grouping modena_lane_data {
    list modena_lane {
      key "modena_lane_id";
      leaf modena_lane_id {
        type modena-driver-types:modena_lane_id_type;
      }
      leaf is_data_available {
        type boolean;
        default "false";
      }
      leaf oper_mode {
        type string;
      }
    }
  }

  grouping modena_summary_info {
    list modena_summary {
      key "modena_id";
      leaf modena_id {
        type modena-driver-types:modena_id_type;
      }
      leaf is_data_available {
        type boolean;
        default "false";
      }
      leaf mready {
        type boolean;
        default "false";
      }
      leaf mport_ctx_p {
        type string;
      }
      leaf mlevm {
        type string;
      }
      leaf mctrace_err_hdl {
        type string;
      }
      leaf mctrace_evt_hdl {
        type string;
      }
      leaf msignature {
        type string;
      }
      leaf mlpc_ready {
        type boolean;
        default "false";
      }
      leaf mopaque {
        type string;
      }
      leaf mnodeid {
        type string;
      }
      leaf mslice {
        type uint32;
      }
      leaf mport {
        type uint32;
      }
      leaf mdev_addr {
        type uint8;
      }
      leaf mrd_func {
        type string;
      }
      leaf mwr_func {
        type string;
      }
      leaf mnext {
        type string;
      }
    }
  }

  grouping modena_data_show {
    list modena {
      key "modena_id";
      leaf modena_id {
        type modena-driver-types:modena_id_type;
      }
      uses modena_lane_data;
    }
  }
}
