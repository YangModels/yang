module tailf-aaa {
  namespace "http://tail-f.com/ns/aaa/1.1";
  prefix aaa;

  import iana-crypt-hash {
    prefix ianach;
  }

  organization
    "Tail-f Systems";

  contact
    "Cisco Systems, Inc.
     Customer Service
    
     Postal: 170 West Tasman Drive
     San Jose, CA 95134
    
     Tel: +1 800 553-NETS
    
     E-mail: cs-yang@cisco.com";

  description
    "This module defines the Tail-f AAA data model.

     Copyright (c) 2012-2019 by Cisco Systems, Inc.
     All rights reserved.";

  revision "2019-05-04" {
    description "Changed passwdStr typedef to use ianach:crypt-hash instead of
tailf:md5-digest-string.";
  }

  revision "2011-09-22" {
    description "Released as part of ConfD-3.7.";
  }

  revision "2010-06-17" {
    description "Released as part of ConfD-3.3.";
  }

  revision "2010-04-22" {
    description "Released as part of ConfD-3.2.1.";
  }

  revision "2010-03-18" {
    description "Released as part of ConfD-3.2.";
  }

  typedef history {
    type uint64 {
      range "0 .. 8192";
    }
  }

  typedef idle-timeout {
    type uint64 {
      range "0 .. 8192";
    }
  }

  typedef display-level {
    type uint64 {
      range "1 .. 64";
    }
  }

  typedef dataOperationType {
    type enumeration {
      enum r;
      enum rx;
      enum x;
      enum rw;
      enum rwx;
      enum wx;
      enum w;
      enum c;
      enum cr;
      enum cu;
      enum cd;
      enum cx;
      enum cru;
      enum crd;
      enum crx;
      enum cud;
      enum cux;
      enum cdx;
      enum crud;
      enum crux;
      enum crdx;
      enum cudx;
      enum crudx;
      enum ru;
      enum rd;
      enum rud;
      enum rux;
      enum rdx;
      enum u;
      enum ud;
      enum ux;
      enum d;
      enum dx;
    }
  }

  typedef cmdOperationType {
    type enumeration {
      enum r;
      enum rx;
      enum x;
    }
  }

  typedef Action {
    type enumeration {
      enum accept;
      enum reject;
      enum accept_log;
    }
  }

  typedef passwdStr {
    type ianach:crypt-hash;
  }

  typedef levelInt {
    type int32 {
      range "0 .. 15";
    }
  }

  typedef modeStr {
    type union {
      type string;
      type builtinModes;
    }
  }

  typedef builtinModes {
    type enumeration {
      enum exec;
      enum configure;
    }
  }

  grouping session-params {
    leaf complete-on-space {
      type boolean;
    }
    leaf ignore-leading-space {
      type boolean;
    }
    leaf idle-timeout {
      type idle-timeout;
    }
    leaf paginate {
      type boolean;
    }
    leaf history {
      type history;
    }
    leaf autowizard {
      type boolean;
    }
    leaf show-defaults {
      type boolean;
    }
    leaf display-level {
      type display-level;
    }
    leaf prompt1 {
      type string;
    }
    leaf prompt2 {
      type string;
    }
  }
  container aaa {
    container authentication {
      container users {
        list user {
          key "name";
          ordered-by user;
          max-elements "1024";
          leaf name {
            type string;
          }
          leaf uid {
            type uint32;
            default "9000";
          }
          leaf gid {
            type uint32;
            default "100";
          }
          leaf password {
            type passwdStr;
            mandatory true;
          }
          leaf ssh_keydir {
            type string;
            default "/home/sshdir";
          }
          leaf homedir {
            type string;
            default "/home/homedir";
          }
        }
      }
      container groups {
        list group {
          key "name";
          max-elements "32";
          leaf name {
            type string;
          }
          leaf gid {
            type uint32;
            default "100";
          }
          leaf users {
            type string;
            default "%%__system_user__%%";
          }
        }
      }
      container login {
        container group {
          leaf tacacs {
            type empty;
          }
        }
      }
    }
    container authorization {
      container cmdrules {
        list cmdrule {
          key "index";
          leaf index {
            type uint32;
          }
          leaf context {
            type string;
            mandatory true;
          }
          leaf command {
            type string;
            mandatory true;
          }
          leaf group {
            type string;
            mandatory true;
          }
          leaf ops {
            type cmdOperationType;
            mandatory true;
          }
          leaf action {
            type Action;
            mandatory true;
          }
        }
      }
      container datarules {
        list datarule {
          key "index";
          leaf index {
            type uint32;
          }
          leaf namespace {
            type string;
            mandatory true;
          }
          leaf context {
            type string;
            default "*";
          }
          leaf keypath {
            type string;
            mandatory true;
          }
          leaf group {
            type string;
            mandatory true;
          }
          leaf ops {
            type dataOperationType;
            mandatory true;
          }
          leaf action {
            type Action;
            mandatory true;
          }
        }
      }
      container commands {
        container group {
          leaf tacacs {
            type empty;
          }
          leaf none {
            type empty;
          }
        }
      }
    }
    container accounting {
      container commands {
        container group {
          leaf tacacs {
            type empty;
          }
        }
      }
    }
    container ios {
      presence "";
      list level {
        key "nr";
        min-elements 2;
        leaf nr {
          type levelInt;
        }
        leaf secret {
          type passwdStr;
        }
        leaf password {
          type passwdStr;
        }
        leaf prompt {
          type string;
          default "\\h# ";
        }
      }
      list privilege {
        key "mode";
        leaf mode {
          type modeStr;
        }
        list level {
          key "nr";
          min-elements 1;
          max-elements "15";
          leaf nr {
            type levelInt;
          }
          list command {
            key "name";
            leaf name {
              type string;
            }
          }
        }
      }
    }
  }
  list alias {
    key "name";
    leaf name {
      type string;
    }
    leaf expansion {
      type string;
      mandatory true;
    }
  }
  container session {
    uses session-params;
    presence "";
  }
  list user {
    key "name";
    leaf name {
      type string;
    }
    leaf description {
      type string;
    }
    list alias {
      key "name";
      leaf name {
        type string;
      }
      leaf expansion {
        type string;
        mandatory true;
      }
    }
    container session {
      uses session-params;
    }
  }
}
