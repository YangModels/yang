submodule Cisco-IOS-XR-platform-event-history-oper-sub1 {
  belongs-to Cisco-IOS-XR-platform-event-history-oper {
    prefix Cisco-IOS-XR-platform-event-history-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR platform-event-history package operational data.
     
     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  grouping EVENT-HISTORY-ENTRY {
    description
      "Event History Entry";
    leaf time {
      type string;
      description
        "Time of event";
    }
    leaf micro-seconds {
      type uint64;
      units "microsecond";
      description
        "Time Stamp's Micro Seconds";
    }
    leaf event-source {
      type string;
      description
        "Event Source";
    }
    leaf event {
      type string;
      description
        "Event";
    }
    leaf platform-event {
      type string;
      description
        "Platform Event";
    }
    leaf state {
      type string;
      description
        "State";
    }
    leaf event-log {
      type string;
      description
        "Event Log";
    }
    leaf event-discarded {
      type boolean;
      description
        "Event Discarded";
    }
    leaf event-repeat-count {
      type uint32;
      description
        "Number of times event repeated";
    }
  }

  grouping EVENT-HISTORY {
    description
      "Event History List";
    leaf current-state {
      type string;
      description
        "Current State";
    }
    leaf state-entry-time {
      type string;
      description
        "Timestamp of state entry";
    }
    list event-history {
      description
        "Event History List";
      uses EVENT-HISTORY-ENTRY;
    }
  }
}
