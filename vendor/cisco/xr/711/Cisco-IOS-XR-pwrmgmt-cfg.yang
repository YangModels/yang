module Cisco-IOS-XR-pwrmgmt-cfg {
  namespace "http://cisco.com/ns/yang/Cisco-IOS-XR-pwrmgmt-cfg";
  prefix pwrmgmt-cfg;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR pwrmgmt package configuration.
     
     This module contains definitions
     for the following management objects:
       power-management: EnvMon Power Management Config Data
     
     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  typedef Envmon-pwrmgmt-boolean {
    type enumeration {
      enum "false" {
        value 0;
        description
          "Disable";
      }
      enum "true" {
        value 1;
        description
          "Enable";
      }
    }
    description
      "Envmon pwrmgmt boolean";
  }

  container power-management {
    description
      "EnvMon Power Management Config Data";
    leaf extended-temp {
      type Envmon-pwrmgmt-boolean;
      description
        "Config for setting power budget for extended
         temp mode";
    }
    leaf single-feed-mode {
      type Envmon-pwrmgmt-boolean;
      description
        "Config for suppressing alarms for missing feed
         supplies";
    }
    leaf action {
      type Envmon-pwrmgmt-boolean;
      description
        "Cfg for controlling power budget to not exceed
         power capacity";
    }
    leaf red-num-pems {
      type uint32;
      description
        "Number of the redundant PEMS";
    }
  }
}
