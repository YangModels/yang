module Cisco-IOS-XR-man-xml-ttyagent-cfg {

  /*** NAMESPACE / PREFIX DEFINITION ***/

  namespace "http://cisco.com/ns/yang"+
    "/Cisco-IOS-XR-man-xml-ttyagent-cfg";


  prefix "man-xml-ttyagent-cfg";

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR man-xml-ttyagent package configuration.

     This module contains definitions
     for the following management objects:
       xr-xml: XML

     Copyright (c) 2013-2015 by Cisco Systems, Inc.
     All rights reserved.";

  revision "2015-01-07" {
    description
      "IOS XR 5.3.1 revision.";
  }


  grouping SESSION {
    description "Common node of default, ssl, tty";

    container session {
      xr:xr-xml-map "xml_cfg:Session";
      description "Session attributes";
      leaf timeout {
        xr:xr-xml-map "xml_cfg:Timeout";
        type uint32 {
          range "1..1440";
        }
        units "minute";
        description "Timeout in minutes";
      }
    }
  }

  grouping VRF-TABLE {
    description "Common node of default, ssl";

    container vrfs {
      xr:xr-xml-map "xml_cfg:VRFTable";
      description "List of VRFs";

      list vrf {
        xr:xr-xml-map "xml_cfg:VRF";
        key "vrf-name";
        description "A specific VRF";
        leaf ipv6-access-list {
          xr:xr-xml-map "xml_cfg:IPV6AccessList";
          type xr:Cisco-ios-xr-string {
            length "0..32";
          }
          description "Access list name";
        }
        leaf ipv4-access-list {
          xr:xr-xml-map "xml_cfg:IPV4AccessList";
          type xr:Cisco-ios-xr-string {
            length "0..32";
          }
          description "Access list name";
        }
        leaf access-list {
          xr:xr-xml-map "xml_cfg:AccessList";
          type xr:Cisco-ios-xr-string {
            length "0..32";
          }
          description "Access list name";
        }
        leaf shutdown {
          xr:xr-xml-map "xml_cfg:Shutdown";
          type empty;
          description "Shutdown default VRF";
        }
        leaf vrf-name {
          xr:xr-xml-map "xml_cfg:VRFName";
          type xr:Cisco-ios-xr-string {
            length "0..32";
          }
          description "VRF name";
        }
      }
    }
  }

  grouping ITERATION-SIZE {
    description "Common node of default, ssl, tty";
    leaf iteration-size {
      xr:xr-xml-map "xml_cfg:IterationSize";
      type uint32 {
        range "0..100000";
      }
      units "kilobyte";
      default "48";
      description
        "Iterator size, in KBytes, of the XML response.
        Specify 0 to turn off the XML response iterator.";
    }
  }

  grouping STREAMING-SIZE {
    description "Common node of default, ssl, tty";
    leaf streaming-size {
      xr:xr-xml-map "xml_cfg:StreamingSize";
      type uint32 {
        range "1..100000";
      }
      units "kilobyte";
      description "Streaming size, in KBytes, of the XML response.";
    }
  }

  grouping THROTTLE {
    description "Common node of default, ssl, tty";

    container throttle {
      xr:xr-xml-map "xml_cfg:Throttle";
      description "XML agent throttling";
      leaf process-rate {
        xr:xr-xml-map "xml_cfg:ProcessRate";
        type uint32 {
          range "1000..30000";
        }
        description "Process rate in number of XML tags per second";
      }
      leaf memory {
        xr:xr-xml-map "xml_cfg:Memory";
        type uint32 {
          range "100..600";
        }
        units "megabyte";
        default "300";
        description "Size of memory usage, in MBytes, per session.";
      }
    }
  }

  grouping ENABLE {
    description "Common node of default, ssl, tty";
    leaf enable {
      xr:xr-xml-map "xml_cfg:Enable";
      type empty;
      description "Enable specified XML agent";
    }
  }

  container xr-xml {
    xr:xr-xml-map "xml_cfg:XML";
    description "XML";

    container agent {
      xr:xr-xml-map "xml_cfg:Agent";
      description "XML agent";

      container default {
        xr:xr-xml-map "xml_cfg:Default";
        description "XML default dedicated agent";
        leaf ipv6-enable {
          xr:xr-xml-map "xml_cfg:IPV6Enable";
          type boolean;
          description "TRUE to Enable IPV6";
        }
        leaf ipv4-disable {
          xr:xr-xml-map "xml_cfg:IPV4Disable";
          type boolean;
          description "TRUE to disable IPV4";
        }
        uses SESSION;
        uses ITERATION-SIZE;
        uses THROTTLE;
        uses ENABLE;
        uses STREAMING-SIZE;
        uses VRF-TABLE;
      }

      container tty {
        xr:xr-xml-map "xml_cfg:TTY";
        description "XML TTY agent";
        uses SESSION;
        uses ITERATION-SIZE;
        uses THROTTLE;
        uses ENABLE;
        uses STREAMING-SIZE;
      }

      container ssl {
        xr:xr-xml-map "xml_cfg:SSL";
        description "XML SSL agent";
        uses SESSION;
        uses ITERATION-SIZE;
        uses THROTTLE;
        uses ENABLE;
        uses STREAMING-SIZE;
        uses VRF-TABLE;
      }
    }
  }
}
