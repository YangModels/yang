module Cisco-IOS-XR-cdp-cfg {

  /*** NAMESPACE / PREFIX DEFINITION ***/

  namespace "http://cisco.com/ns/yang/Cisco-IOS-XR-cdp-cfg";


  prefix "cdp-cfg";

  /*** LINKAGE (IMPORTS / INCLUDES) ***/

  import Cisco-IOS-XR-types { prefix "xr"; }

  import Cisco-IOS-XR-ifmgr-cfg { prefix "a1"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR cdp package configuration.

     This module contains definitions
     for the following management objects:
       cdp: Global CDP configuration data

     This YANG module augments the
       Cisco-IOS-XR-ifmgr-cfg
     module with configuration data.

     Copyright (c) 2013-2015 by Cisco Systems, Inc.
     All rights reserved.";

  revision "2015-01-07" {
    description
      "IOS XR 5.3.1 revision.";
  }


  container cdp {
    xr:xr-xml-map "cdp_cfg:CDP";
    description "Global CDP configuration data";
    leaf timer {
      xr:xr-xml-map "cdp_cfg:Timer";
      xr:xr-cli-map "timer <number> ";
      type uint32 {
        range "5..255";
      }
      default "60";
      description "Rate at which CDP packets are sent (in sec)";
    }
    leaf advertise-v1-only {
      xr:xr-xml-map "cdp_cfg:AdvertiseV1Only";
      xr:xr-cli-map "advertise v1 ";
      type empty;
      description "Enable v1 only advertisements";
    }
    leaf enable {
      xr:xr-xml-map "cdp_cfg:Enable";
      xr:xr-cli-map "cdp ";
      type boolean;
      default "true";
      description "Enable or disable CDP";
    }
    leaf hold-time {
      xr:xr-xml-map "cdp_cfg:HoldTime";
      xr:xr-cli-map "holdtime <number> ";
      type uint32 {
        range "10..255";
      }
      default "180";
      description
        "Length of time (in sec) that the receiver must
        keep a CDP packet";
    }
    leaf log-adjacency {
      xr:xr-xml-map "cdp_cfg:LogAdjacency";
      xr:xr-cli-map "log adjacency changes ";
      type empty;
      description "Enable logging";
    }
  }

  augment "/a1:interface-configurations/a1:interface-configuration" {

    container cdp {
      xr:xr-xml-map "cdp_interface_cfg:CDP";
      description "Interface specific CDP configuration";
      leaf enable {
        xr:xr-xml-map "cdp_interface_cfg:Enable";
        type empty;
        description "Enable or disable CDP on an interface";
      }
    }
    description
      "This augment extends the configuration data of
      'Cisco-IOS-XR-ifmgr-cfg'";
  }
}
