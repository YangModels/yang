submodule Cisco-IOS-XR-drivers-media-eth-oper-sub1 {

  belongs-to Cisco-IOS-XR-drivers-media-eth-oper {
    prefix Cisco-IOS-XR-drivers-media-eth-oper;
  }

  /*** LINKAGE (IMPORTS / INCLUDES) ***/

  import ietf-yang-types { prefix "yang"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR drivers-media-eth package operational data.

     Copyright (c) 2013-2015 by Cisco Systems, Inc.
     All rights reserved.";

  revision "2015-01-07" {
    description
      "IOS XR 5.3.1 revision.";
  }

  typedef Ethernet-dev-if {
    type enumeration {
      enum no-interface {
        description "no interface";
      }
      enum xgmii {
        description "xgmii";
      }
      enum xaui {
        description "xaui";
      }
      enum ethernet-num-dev-if {
        description "ethernet num dev if";
      }
    }
    description "Ethernet dev if";
  }
  typedef Ethernet-dev {
    type enumeration {
      enum no-device {
        description "no device";
      }
      enum pma-pmd {
        description "pma pmd";
      }
      enum wis {
        description "wis";
      }
      enum pcs {
        description "pcs";
      }
      enum phy-xs {
        description "phy xs";
      }
      enum dte-xs {
        description "dte xs";
      }
      enum ethernet-num-dev {
        description "ethernet num dev";
      }
    }
    description "Ethernet dev";
  }
  typedef Ethernet-bert-pattern {
    type enumeration {
      enum no-test-pattern {
        description "no test pattern";
      }
      enum high-frequency {
        description "high frequency";
      }
      enum low-frequency {
        description "low frequency";
      }
      enum mixed-frequency {
        description "mixed frequency";
      }
      enum continuous-random {
        description "continuous random";
      }
      enum continuous-jitter {
        description "continuous jitter";
      }
      enum long-continuous-random {
        description "long continuous random";
      }
      enum short-continuous-random {
        description "short continuous random";
      }
      enum pseudorandom-seed-a {
        description "pseudorandom seed a";
      }
      enum pseudorandom-seed-b {
        description "pseudorandom seed b";
      }
      enum prbs31 {
        description "prbs31";
      }
      enum square-wave {
        description "square wave";
      }
      enum pseudorandom {
        description "pseudorandom";
      }
      enum ethernet-bert-pattern-types {
        description "ethernet bert pattern types";
      }
    }
    description "Ethernet test patterns (IEEE spec 36A/48A)";
  }
  typedef Ethernet-bert-err-cnt {
    type enumeration {
      enum no-count-type {
        description "no count type";
      }
      enum bit-error-count {
        description "bit error count";
      }
      enum frame-error-count {
        description "frame error count";
      }
      enum block-error-count {
        description "block error count";
      }
      enum ethernet-bert-err-cnt-types {
        description "ethernet bert err cnt types";
      }
    }
    description "Ethernet bert err cnt";
  }
  typedef Ethernet-bert-mask {
    type uint32;
    description "Ethernet bert mask";
  }
  typedef Ether-ains-status {
    type enumeration {
      enum ains-soak-status-none {
        description "AINS Soak timer not running";
      }
      enum ains-soak-status-pending {
        description "AINS Soak timer pending";
      }
      enum ains-soak-status-running {
        description "AINS Soak timer running";
      }
    }
    description "Ether ains status";
  }
  typedef Mac-addr {
    type yang:mac-address;
    description "Mac addr";
  }
  typedef Eth-ctrlr-alarm-state {
    type enumeration {
      enum alarm-not-supported {
        value 0;
        description "Not supported on this interface";
      }
      enum alarm-set {
        value 1;
        description "Alarm set";
      }
      enum alarm-not-set {
        value 2;
        description "Alarm not set";
      }
    }
    description "Ethernet alarm state";
  }
  typedef Ethernet-ipg {
    type enumeration {
      enum standard {
        description "IEEE standard value of 12";
      }
      enum non-standard {
        description "Non-standard value of 16";
      }
    }
    description "Inter packet gap";
  }
  typedef Ether-flowcontrol {
    type enumeration {
      enum no-flowcontrol {
        description "No flow control (disabled)";
      }
      enum egress {
        description "Traffic egress (pause frames ingress)";
      }
      enum ingress {
        description "Traffic ingress (pause frames egress)";
      }
      enum bidirectional {
        description "On both ingress and egress";
      }
    }
    description "Flowcontrol type";
  }
  typedef Ethernet-duplex {
    type enumeration {
      enum ethernet-duplex-invalid {
        description "ethernet duplex invalid";
      }
      enum half-duplex {
        description "half duplex";
      }
      enum full-duplex {
        description "full duplex";
      }
    }
    description "Duplexity";
  }
  typedef Ethernet-speed {
    type enumeration {
      enum ethernet-speed-invalid {
        value 0;
        description "ethernet speed invalid";
      }
      enum ten-mbps {
        value 1;
        description "ten mbps";
      }
      enum hundred-mbps {
        value 2;
        description "hundred mbps";
      }
      enum one-gbps {
        value 3;
        description "one gbps";
      }
      enum ten-gbps {
        value 4;
        description "ten gbps";
      }
      enum forty-gbps {
        value 5;
        description "forty gbps";
      }
      enum hundred-gbps {
        value 6;
        description "hundred gbps";
      }
      enum ethernet-speed-types-count {
        value 7;
        description "ethernet speed types count";
      }
    }
    description "Speed";
  }
  typedef Ether-autoneg-mask {
    type uint32;
    description "Ether autoneg mask";
  }
  typedef Ether-led-state {
    type enumeration {
      enum led-state-unknown {
        description "LED state is unknown";
      }
      enum led-off {
        description "LED is off";
      }
      enum green-on {
        description "LED is green";
      }
      enum green-flashing {
        description "LED is flashing green";
      }
      enum yellow-on {
        description "LED is yellow";
      }
      enum yellow-flashing {
        description "LED is flashing yellow";
      }
      enum red-on {
        description "LED is red";
      }
      enum red-flashing {
        description "LED is flashing red";
      }
    }
    description "Ether led state";
  }
  typedef Ether-link-state {
    type enumeration {
      enum state-undefined {
        description "State undefined";
      }
      enum unknown-state {
        description "Initializing, true state not yet known";
      }
      enum available {
        description "Link or light normal, loopback normal";
      }
      enum not-available {
        description "Link loss or low light, no loopback";
      }
      enum remote-fault {
        description "Remote fault with no detail";
      }
      enum invalid-signal {
        description "Invalid signal, applies only to 10BASE-FB";
      }
      enum remote-jabber {
        description "Remote fault, reason known to be jabber";
      }
      enum link-loss {
        description
          "Remote fault, reason known to be far-end link
          loss";
      }
      enum remote-test {
        description "Remote fault, reason known to be test";
      }
      enum offline {
        description "Offline (applies to auto-negotiation)";
      }
      enum auto-neg-error {
        description "Auto-Negotiation Error";
      }
      enum pmd-link-fault {
        description "PMD/PMA receive link fault";
      }
      enum frame-loss {
        description "WIS loss of frames";
      }
      enum signal-loss {
        description "WIS loss of signal";
      }
      enum link-fault {
        description "PCS receive link fault";
      }
      enum excessive-ber {
        description
          "PCS Bit Error Rate monitor reporting excessive
          error rate";
      }
      enum dxs-link-fault {
        description "DTE XGXS receive link fault";
      }
      enum pxs-link-fault {
        description "PHY XGXS transmit link fault";
      }
      enum security {
        description "Security failure (not a valid part)";
      }
      enum phy-not-present {
        description "The optics for the port are not present";
      }
      enum no-optic-license {
        description "License error (No advanced optical license)";
      }
      enum unsupported-module {
        description "Module is not supported";
      }
      enum dwdm-laser-shut {
        description "DWDM Laser shutdown";
      }
      enum wanphy-laser-shut {
        description "WANPHY Laser shutdown";
      }
      enum incompatible-config {
        description "Incompatible configuration";
      }
      enum system-error {
        description "System error";
      }
      enum wan-framing-error {
        description "WAN Framing Error";
      }
      enum otn-framing-error {
        description "OTN Framing Error";
      }
    }
    description
      "Ethernet link state: IEEE 802.3/802.3ae clause 30
      .5.1.1.4";
  }
  typedef Ethernet-loopback {
    type enumeration {
      enum no-loopback {
        description "Disabled";
      }
      enum internal {
        description "Loopback in the framer";
      }
      enum line {
        description "Loops peer's packets back to them";
      }
      enum external {
        description "tx externally connected to rx";
      }
    }
    description "Loopback type";
  }
  typedef Ether-dom-alarm {
    type enumeration {
      enum no-information {
        description "DOM Alarm information is not available";
      }
      enum alarm-high {
        description "Alarm high";
      }
      enum warning-high {
        description "Warning high";
      }
      enum normal {
        description "Within normal parameters";
      }
      enum warning-low {
        description "Warning low";
      }
      enum alarm-low {
        description "Alarm low";
      }
    }
    description "Ether dom alarm";
  }
  typedef Ether-phy-present {
    type enumeration {
      enum phy-not-present {
        description "No PHY present";
      }
      enum phy-present {
        description "PHY is present";
      }
      enum no-information {
        description "State is unknown";
      }
    }
    description "Ether phy present";
  }
  typedef Ethernet-media {
    type enumeration {
      enum ethernet-other {
        description "IEEE 802.3/802.3ae clause 30.2.5";
      }
      enum ethernet-unknown {
        description
          "Initializing, true state or type not yet known";
      }
      enum ethernet-aui {
        description "No internal MAU, view from AUI";
      }
      enum ethernet-10base5 {
        description "Thick coax MAU";
      }
      enum ethernet-foirl {
        description "FOIRL MAU as specified in 9.9";
      }
      enum ethernet-10base2 {
        description "Thin coax MAU";
      }
      enum ethernet-10broad36 {
        description "Broadband DTE MAU";
      }
      enum ethernet-10base {
        description "UTP MAU, duplexity unknown";
      }
      enum ethernet-10base-thd {
        description "UTP MAU, half duplex";
      }
      enum ethernet-10base-tfd {
        description "UTP MAU, full duplex";
      }
      enum ethernet-10base-fp {
        description "Passive fiber MAU";
      }
      enum ethernet-10base-fb {
        description "Synchronous fiber MAU";
      }
      enum ethernet-10base-fl {
        description "Asynchronous fiber MAU, duplexity unknown";
      }
      enum ethernet-10base-flhd {
        description "Asynchronous fiber MAU, half duplex";
      }
      enum ethernet-10base-flfd {
        description "Asynchronous fiber MAU, full duplex";
      }
      enum ethernet-100base-t4 {
        description "Four-pair Category 3 UTP";
      }
      enum ethernet-100base-tx {
        description "Two-pair Category 5 UTP, duplexity unknown";
      }
      enum ethernet-100base-txhd {
        description "Two-pair Category 5 UTP, half duplex";
      }
      enum ethernet-100base-txfd {
        description "Two-pair Category 5 UTP, full duplex";
      }
      enum ethernet-100base-fx {
        description "X fiber over PMD, duplexity unknown";
      }
      enum ethernet-100base-fxhd {
        description "X fiber over PMD, half duplex";
      }
      enum ethernet-100base-fxfd {
        description "X fiber over PMD, full duplex";
      }
      enum ethernet-100base-ex {
        description "X fiber over PMD (40km), duplexity unknown";
      }
      enum ethernet-100base-exhd {
        description "X fiber over PMD (40km), half duplex";
      }
      enum ethernet-100base-exfd {
        description "X fiber over PMD (40km), full duplex";
      }
      enum ethernet-100base-t2 {
        description "Two-pair Category 3 UTP, duplexity unknown";
      }
      enum ethernet-100base-t2hd {
        description "Two-pair Category 3 UTP, half duplex";
      }
      enum ethernet-100base-t2fd {
        description "Two-pair Category 3 UTP, full duplex";
      }
      enum ethernet-1000base-x {
        description "X PCS/PMA, duplexity unknown";
      }
      enum ethernet-1000base-xhd {
        description "X 1000BASE-XHDX PCS/PMA, half duplex";
      }
      enum ethernet-1000base-xfd {
        description "X PCS/PMA, full duplex";
      }
      enum ethernet-1000base-lx {
        description
          "X fiber over long-wl laser PMD, duplexity
          unknown";
      }
      enum ethernet-1000base-lxhd {
        description "X fiber over long-wl laser PMD, half duplex";
      }
      enum ethernet-1000base-lxfd {
        description "X fiber over long-wl laser PMD, full duplex";
      }
      enum ethernet-1000base-sx {
        description
          "X fiber over short-wl laser PMD, duplexity
          unknown";
      }
      enum ethernet-1000base-sxhd {
        description "X fiber over short-wl laser PMD, half duplex";
      }
      enum ethernet-1000base-sxfd {
        description "X fiber over short-wl laser PMD, full duplex";
      }
      enum ethernet-1000base-cx {
        description
          "X copper over 150-Ohm balanced PMD, duplexity
          unknown";
      }
      enum ethernet-1000base-cxhd {
        description
          "X copper over 150-Ohm balancedPMD, half duplex";
      }
      enum ethernet-1000base-cxfd {
        description
          "X copper over 150-Ohm balancedPMD, full duplex";
      }
      enum ethernet-1000base {
        description
          "Four-pair Category 5 UTP PHY, duplexity unknown";
      }
      enum ethernet-1000base-thd {
        description "Four-pair Category 5 UTP PHY, half duplex";
      }
      enum ethernet-1000base-tfd {
        description "Four-pair Category 5 UTP PHY, full duplex";
      }
      enum ethernet-10gbase-x {
        description "X PCS/PMA ";
      }
      enum ethernet-10gbase-lx4 {
        description "X fiber over 4 lane 1310nm optics";
      }
      enum ethernet-10gbase-r {
        description "R PCS/PMA";
      }
      enum ethernet-10gbase-er {
        description "R fiber over 1550nm optics";
      }
      enum ethernet-10gbase-lr {
        description "R fiber over 1310nm optics";
      }
      enum ethernet-10gbase-sr {
        description "R fiber over 850nm optics";
      }
      enum ethernet-10gbase-w {
        description "W PCS/PMA";
      }
      enum ethernet-10gbase-ew {
        description "W fiber over 1550nm optics";
      }
      enum ethernet-10gbase-lw {
        description "W fiber over 1310nm optics";
      }
      enum ethernet-10gbase-sw {
        description "W fiber over 850nm optics";
      }
      enum ethernet-1000base-zx {
        description "Single-mode fiber over 1550nm optics (Cisco)";
      }
      enum ethernet-1000base-cwdm {
        description "CWDM with unknown wavelength optics";
      }
      enum ethernet-1000base-cwdm-1470 {
        description "CWDM with 1470nm optics";
      }
      enum ethernet-1000base-cwdm-1490 {
        description "CWDM with 1490nm optics";
      }
      enum ethernet-1000base-cwdm-1510 {
        description "CWDM with 1510nm optics";
      }
      enum ethernet-1000base-cwdm-1530 {
        description "CWDM with 1530nm optics";
      }
      enum ethernet-1000base-cwdm-1550 {
        description "CWDM with 1550nm optics";
      }
      enum ethernet-1000base-cwdm-1570 {
        description "CWDM with 1570nm optics";
      }
      enum ethernet-1000base-cwdm-1590 {
        description "CWDM with 1590nm optics";
      }
      enum ethernet-1000base-cwdm-1610 {
        description "CWDM with 1610nm optics";
      }
      enum ethernet-10gbase-zr {
        description "Cisco-defined, over 1550nm optics";
      }
      enum ethernet-10gbase-dwdm {
        description "DWDM optics";
      }
      enum ethernet-100gbase-lr4 {
        description "fiber over 4 lane optics (long reach)";
      }
      enum ethernet-1000base-dwdm {
        description "DWDM optics";
      }
      enum ethernet-1000base-dwdm-1533 {
        description "DWDM with 1533nm optics";
      }
      enum ethernet-1000base-dwdm-1537 {
        description "DWDM with 1537nm optics";
      }
      enum ethernet-1000base-dwdm-1541 {
        description "DWDM with 1541nm optics";
      }
      enum ethernet-1000base-dwdm-1545 {
        description "DWDM with 1545nm optics";
      }
      enum ethernet-1000base-dwdm-1549 {
        description "DWDM with 1549nm optics";
      }
      enum ethernet-1000base-dwdm-1553 {
        description "DWDM with 1553nm optics";
      }
      enum ethernet-1000base-dwdm-1557 {
        description "DWDM with 1557nm optics";
      }
      enum ethernet-1000base-dwdm-1561 {
        description "DWDM with 1561nm optics";
      }
      enum ethernet-40gbase-lr4 {
        description "fiber over 4 lane optics (long reach)";
      }
      enum ethernet-40gbase-er4 {
        description "fiber over 4 lane optics (extended reach)";
      }
      enum ethernet-100gbase-er4 {
        description "fiber over 4 lane optics (extended reach)";
      }
      enum ethernet-1000base-ex {
        description "X fiber over 1310nm optics";
      }
      enum ethernet-1000base-bx10-d {
        description "X fibre (D, 10km)";
      }
      enum ethernet-1000base-bx10-u {
        description "X fibre (U, 10km)";
      }
      enum ethernet-1000base-dwdm-1561-42 {
        description "DWDM with 1561.42nm optics";
      }
      enum ethernet-1000base-dwdm-1560-61 {
        description "DWDM with 1560.61nm optics";
      }
      enum ethernet-1000base-dwdm-1559-79 {
        description "DWDM with 1559.79nm optics";
      }
      enum ethernet-1000base-dwdm-1558-98 {
        description "DWDM with 1558.98nm optics";
      }
      enum ethernet-1000base-dwdm-1558-17 {
        description "DWDM with 1558.17nm optics";
      }
      enum ethernet-1000base-dwdm-1557-36 {
        description "DWDM with 1557.36nm optics";
      }
      enum ethernet-1000base-dwdm-1556-55 {
        description "DWDM with 1556.55nm optics";
      }
      enum ethernet-1000base-dwdm-1555-75 {
        description "DWDM with 1555.75nm optics";
      }
      enum ethernet-1000base-dwdm-1554-94 {
        description "DWDM with 1554.94nm optics";
      }
      enum ethernet-1000base-dwdm-1554-13 {
        description "DWDM with 1554.13nm optics";
      }
      enum ethernet-1000base-dwdm-1553-33 {
        description "DWDM with 1553.33nm optics";
      }
      enum ethernet-1000base-dwdm-1552-52 {
        description "DWDM with 1552.52nm optics";
      }
      enum ethernet-1000base-dwdm-1551-72 {
        description "DWDM with 1551.72nm optics";
      }
      enum ethernet-1000base-dwdm-1550-92 {
        description "DWDM with 1550.92nm optics";
      }
      enum ethernet-1000base-dwdm-1550-12 {
        description "DWDM with 1550.12nm optics";
      }
      enum ethernet-1000base-dwdm-1549-32 {
        description "DWDM with 1549.32nm optics";
      }
      enum ethernet-1000base-dwdm-1548-51 {
        description "DWDM with 1548.51nm optics";
      }
      enum ethernet-1000base-dwdm-1547-72 {
        description "DWDM with 1547.72nm optics";
      }
      enum ethernet-1000base-dwdm-1546-92 {
        description "DWDM with 1546.92nm optics";
      }
      enum ethernet-1000base-dwdm-1546-12 {
        description "DWDM with 1546.12nm optics";
      }
      enum ethernet-1000base-dwdm-1545-32 {
        description "DWDM with 1545.32nm optics";
      }
      enum ethernet-1000base-dwdm-1544-53 {
        description "DWDM with 1544.53nm optics";
      }
      enum ethernet-1000base-dwdm-1543-73 {
        description "DWDM with 1543.73nm optics";
      }
      enum ethernet-1000base-dwdm-1542-94 {
        description "DWDM with 1542.94nm optics";
      }
      enum ethernet-1000base-dwdm-1542-14 {
        description "DWDM with 1542.14nm optics";
      }
      enum ethernet-1000base-dwdm-1541-35 {
        description "DWDM with 1541.35nm optics";
      }
      enum ethernet-1000base-dwdm-1540-56 {
        description "DWDM with 1540.56nm optics";
      }
      enum ethernet-1000base-dwdm-1539-77 {
        description "DWDM with 1539.77nm optics";
      }
      enum ethernet-1000base-dwdm-1538-98 {
        description "DWDM with 1538.98nm optics";
      }
      enum ethernet-1000base-dwdm-1538-19 {
        description "DWDM with 1538.19nm optics";
      }
      enum ethernet-1000base-dwdm-1537-40 {
        description "DWDM with 1537.40nm optics";
      }
      enum ethernet-1000base-dwdm-1536-61 {
        description "DWDM with 1536.61nm optics";
      }
      enum ethernet-1000base-dwdm-1535-82 {
        description "DWDM with 1535.82nm optics";
      }
      enum ethernet-1000base-dwdm-1535-04 {
        description "DWDM with 1535.04nm optics";
      }
      enum ethernet-1000base-dwdm-1534-25 {
        description "DWDM with 1534.25nm optics";
      }
      enum ethernet-1000base-dwdm-1533-47 {
        description "DWDM with 1533.47nm optics";
      }
      enum ethernet-1000base-dwdm-1532-68 {
        description "DWDM with 1532.68nm optics";
      }
      enum ethernet-1000base-dwdm-1531-90 {
        description "DWDM with 1531.90nm optics";
      }
      enum ethernet-1000base-dwdm-1531-12 {
        description "DWDM with 1531.12nm optics";
      }
      enum ethernet-1000base-dwdm-1530-33 {
        description "DWDM with 1530.33nm optics";
      }
      enum ethernet-1000base-dwdm-tunable {
        description "DWDM with tunable optics";
      }
      enum ethernet-10gbase-dwdm-1561-42 {
        description "DWDM with 1561.42nm optics";
      }
      enum ethernet-10gbase-dwdm-1560-61 {
        description "DWDM with 1560.61nm optics";
      }
      enum ethernet-10gbase-dwdm-1559-79 {
        description "DWDM with 1559.79nm optics";
      }
      enum ethernet-10gbase-dwdm-1558-98 {
        description "DWDM with 1558.98nm optics";
      }
      enum ethernet-10gbase-dwdm-1558-17 {
        description "DWDM with 1558.17nm optics";
      }
      enum ethernet-10gbase-dwdm-1557-36 {
        description "DWDM with 1557.36nm optics";
      }
      enum ethernet-10gbase-dwdm-1556-55 {
        description "DWDM with 1556.55nm optics";
      }
      enum ethernet-10gbase-dwdm-1555-75 {
        description "DWDM with 1555.75nm optics";
      }
      enum ethernet-10gbase-dwdm-1554-94 {
        description "DWDM with 1554.94nm optics";
      }
      enum ethernet-10gbase-dwdm-1554-13 {
        description "DWDM with 1554.13nm optics";
      }
      enum ethernet-10gbase-dwdm-1553-33 {
        description "DWDM with 1553.33nm optics";
      }
      enum ethernet-10gbase-dwdm-1552-52 {
        description "DWDM with 1552.52nm optics";
      }
      enum ethernet-10gbase-dwdm-1551-72 {
        description "DWDM with 1551.72nm optics";
      }
      enum ethernet-10gbase-dwdm-1550-92 {
        description "DWDM with 1550.92nm optics";
      }
      enum ethernet-10gbase-dwdm-1550-12 {
        description "DWDM with 1550.12nm optics";
      }
      enum ethernet-10gbase-dwdm-1549-32 {
        description "DWDM with 1549.32nm optics";
      }
      enum ethernet-10gbase-dwdm-1548-51 {
        description "DWDM with 1548.51nm optics";
      }
      enum ethernet-10gbase-dwdm-1547-72 {
        description "DWDM with 1547.72nm optics";
      }
      enum ethernet-10gbase-dwdm-1546-92 {
        description "DWDM with 1546.92nm optics";
      }
      enum ethernet-10gbase-dwdm-1546-12 {
        description "DWDM with 1546.12nm optics";
      }
      enum ethernet-10gbase-dwdm-1545-32 {
        description "DWDM with 1545.32nm optics";
      }
      enum ethernet-10gbase-dwdm-1544-53 {
        description "DWDM with 1544.53nm optics";
      }
      enum ethernet-10gbase-dwdm-1543-73 {
        description "DWDM with 1543.73nm optics";
      }
      enum ethernet-10gbase-dwdm-1542-94 {
        description "DWDM with 1542.94nm optics";
      }
      enum ethernet-10gbase-dwdm-1542-14 {
        description "DWDM with 1542.14nm optics";
      }
      enum ethernet-10gbase-dwdm-1541-35 {
        description "DWDM with 1541.35nm optics";
      }
      enum ethernet-10gbase-dwdm-1540-56 {
        description "DWDM with 1540.56nm optics";
      }
      enum ethernet-10gbase-dwdm-1539-77 {
        description "DWDM with 1539.77nm optics";
      }
      enum ethernet-10gbase-dwdm-1538-98 {
        description "DWDM with 1538.98nm optics";
      }
      enum ethernet-10gbase-dwdm-1538-19 {
        description "DWDM with 1538.19nm optics";
      }
      enum ethernet-10gbase-dwdm-1537-40 {
        description "DWDM with 1537.40nm optics";
      }
      enum ethernet-10gbase-dwdm-1536-61 {
        description "DWDM with 1536.61nm optics";
      }
      enum ethernet-10gbase-dwdm-1535-82 {
        description "DWDM with 1535.82nm optics";
      }
      enum ethernet-10gbase-dwdm-1535-04 {
        description "DWDM with 1535.04nm optics";
      }
      enum ethernet-10gbase-dwdm-1534-25 {
        description "DWDM with 1534.25nm optics";
      }
      enum ethernet-10gbase-dwdm-1533-47 {
        description "DWDM with 1533.47nm optics";
      }
      enum ethernet-10gbase-dwdm-1532-68 {
        description "DWDM with 1532.68nm optics";
      }
      enum ethernet-10gbase-dwdm-1531-90 {
        description "DWDM with 1531.90nm optics";
      }
      enum ethernet-10gbase-dwdm-1531-12 {
        description "DWDM with 1531.12nm optics";
      }
      enum ethernet-10gbase-dwdm-1530-33 {
        description "DWDM with 1530.33nm optics";
      }
      enum ethernet-10gbase-dwdm-tunable {
        description "DWDM with tunable optics";
      }
      enum ethernet-40gbase-dwdm-1561-42 {
        description "DWDM with 1561.42nm optics";
      }
      enum ethernet-40gbase-dwdm-1560-61 {
        description "DWDM with 1560.61nm optics";
      }
      enum ethernet-40gbase-dwdm-1559-79 {
        description "DWDM with 1559.79nm optics";
      }
      enum ethernet-40gbase-dwdm-1558-98 {
        description "DWDM with 1558.98nm optics";
      }
      enum ethernet-40gbase-dwdm-1558-17 {
        description "DWDM with 1558.17nm optics";
      }
      enum ethernet-40gbase-dwdm-1557-36 {
        description "DWDM with 1557.36nm optics";
      }
      enum ethernet-40gbase-dwdm-1556-55 {
        description "DWDM with 1556.55nm optics";
      }
      enum ethernet-40gbase-dwdm-1555-75 {
        description "DWDM with 1555.75nm optics";
      }
      enum ethernet-40gbase-dwdm-1554-94 {
        description "DWDM with 1554.94nm optics";
      }
      enum ethernet-40gbase-dwdm-1554-13 {
        description "DWDM with 1554.13nm optics";
      }
      enum ethernet-40gbase-dwdm-1553-33 {
        description "DWDM with 1553.33nm optics";
      }
      enum ethernet-40gbase-dwdm-1552-52 {
        description "DWDM with 1552.52nm optics";
      }
      enum ethernet-40gbase-dwdm-1551-72 {
        description "DWDM with 1551.72nm optics";
      }
      enum ethernet-40gbase-dwdm-1550-92 {
        description "DWDM with 1550.92nm optics";
      }
      enum ethernet-40gbase-dwdm-1550-12 {
        description "DWDM with 1550.12nm optics";
      }
      enum ethernet-40gbase-dwdm-1549-32 {
        description "DWDM with 1549.32nm optics";
      }
      enum ethernet-40gbase-dwdm-1548-51 {
        description "DWDM with 1548.51nm optics";
      }
      enum ethernet-40gbase-dwdm-1547-72 {
        description "DWDM with 1547.72nm optics";
      }
      enum ethernet-40gbase-dwdm-1546-92 {
        description "DWDM with 1546.92nm optics";
      }
      enum ethernet-40gbase-dwdm-1546-12 {
        description "DWDM with 1546.12nm optics";
      }
      enum ethernet-40gbase-dwdm-1545-32 {
        description "DWDM with 1545.32nm optics";
      }
      enum ethernet-40gbase-dwdm-1544-53 {
        description "DWDM with 1544.53nm optics";
      }
      enum ethernet-40gbase-dwdm-1543-73 {
        description "DWDM with 1543.73nm optics";
      }
      enum ethernet-40gbase-dwdm-1542-94 {
        description "DWDM with 1542.94nm optics";
      }
      enum ethernet-40gbase-dwdm-1542-14 {
        description "DWDM with 1542.14nm optics";
      }
      enum ethernet-40gbase-dwdm-1541-35 {
        description "DWDM with 1541.35nm optics";
      }
      enum ethernet-40gbase-dwdm-1540-56 {
        description "DWDM with 1540.56nm optics";
      }
      enum ethernet-40gbase-dwdm-1539-77 {
        description "DWDM with 1539.77nm optics";
      }
      enum ethernet-40gbase-dwdm-1538-98 {
        description "DWDM with 1538.98nm optics";
      }
      enum ethernet-40gbase-dwdm-1538-19 {
        description "DWDM with 1538.19nm optics";
      }
      enum ethernet-40gbase-dwdm-1537-40 {
        description "DWDM with 1537.40nm optics";
      }
      enum ethernet-40gbase-dwdm-1536-61 {
        description "DWDM with 1536.61nm optics";
      }
      enum ethernet-40gbase-dwdm-1535-82 {
        description "DWDM with 1535.82nm optics";
      }
      enum ethernet-40gbase-dwdm-1535-04 {
        description "DWDM with 1535.04nm optics";
      }
      enum ethernet-40gbase-dwdm-1534-25 {
        description "DWDM with 1534.25nm optics";
      }
      enum ethernet-40gbase-dwdm-1533-47 {
        description "DWDM with 1533.47nm optics";
      }
      enum ethernet-40gbase-dwdm-1532-68 {
        description "DWDM with 1532.68nm optics";
      }
      enum ethernet-40gbase-dwdm-1531-90 {
        description "DWDM with 1531.90nm optics";
      }
      enum ethernet-40gbase-dwdm-1531-12 {
        description "DWDM with 1531.12nm optics";
      }
      enum ethernet-40gbase-dwdm-1530-33 {
        description "DWDM with 1530.33nm optics";
      }
      enum ethernet-40gbase-dwdm-tunable {
        description "DWDM with tunable optics";
      }
      enum ethernet-100gbase-dwdm-1561-42 {
        description "DWDM with 1561.42nm optics";
      }
      enum ethernet-100gbase-dwdm-1560-61 {
        description "DWDM with 1560.61nm optics";
      }
      enum ethernet-100gbase-dwdm-1559-79 {
        description "DWDM with 1559.79nm optics";
      }
      enum ethernet-100gbase-dwdm-1558-98 {
        description "DWDM with 1558.98nm optics";
      }
      enum ethernet-100gbase-dwdm-1558-17 {
        description "DWDM with 1558.17nm optics";
      }
      enum ethernet-100gbase-dwdm-1557-36 {
        description "DWDM with 1557.36nm optics";
      }
      enum ethernet-100gbase-dwdm-1556-55 {
        description "DWDM with 1556.55nm optics";
      }
      enum ethernet-100gbase-dwdm-1555-75 {
        description "DWDM with 1555.75nm optics";
      }
      enum ethernet-100gbase-dwdm-1554-94 {
        description "DWDM with 1554.94nm optics";
      }
      enum ethernet-100gbase-dwdm-1554-13 {
        description "DWDM with 1554.13nm optics";
      }
      enum ethernet-100gbase-dwdm-1553-33 {
        description "DWDM with 1553.33nm optics";
      }
      enum ethernet-100gbase-dwdm-1552-52 {
        description "DWDM with 1552.52nm optics";
      }
      enum ethernet-100gbase-dwdm-1551-72 {
        description "DWDM with 1551.72nm optics";
      }
      enum ethernet-100gbase-dwdm-1550-92 {
        description "DWDM with 1550.92nm optics";
      }
      enum ethernet-100gbase-dwdm-1550-12 {
        description "DWDM with 1550.12nm optics";
      }
      enum ethernet-100gbase-dwdm-1549-32 {
        description "DWDM with 1549.32nm optics";
      }
      enum ethernet-100gbase-dwdm-1548-51 {
        description "DWDM with 1548.51nm optics";
      }
      enum ethernet-100gbase-dwdm-1547-72 {
        description "DWDM with 1547.72nm optics";
      }
      enum ethernet-100gbase-dwdm-1546-92 {
        description "DWDM with 1546.92nm optics";
      }
      enum ethernet-100gbase-dwdm-1546-12 {
        description "DWDM with 1546.12nm optics";
      }
      enum ethernet-100gbase-dwdm-1545-32 {
        description "DWDM with 1545.32nm optics";
      }
      enum ethernet-100gbase-dwdm-1544-53 {
        description "DWDM with 1544.53nm optics";
      }
      enum ethernet-100gbase-dwdm-1543-73 {
        description "DWDM with 1543.73nm optics";
      }
      enum ethernet-100gbase-dwdm-1542-94 {
        description "DWDM with 1542.94nm optics";
      }
      enum ethernet-100gbase-dwdm-1542-14 {
        description "DWDM with 1542.14nm optics";
      }
      enum ethernet-100gbase-dwdm-1541-35 {
        description "DWDM with 1541.35nm optics";
      }
      enum ethernet-100gbase-dwdm-1540-56 {
        description "DWDM with 1540.56nm optics";
      }
      enum ethernet-100gbase-dwdm-1539-77 {
        description "DWDM with 1539.77nm optics";
      }
      enum ethernet-100gbase-dwdm-1538-98 {
        description "DWDM with 1538.98nm optics";
      }
      enum ethernet-100gbase-dwdm-1538-19 {
        description "DWDM with 1538.19nm optics";
      }
      enum ethernet-100gbase-dwdm-1537-40 {
        description "DWDM with 1537.40nm optics";
      }
      enum ethernet-100gbase-dwdm-1536-61 {
        description "DWDM with 1536.61nm optics";
      }
      enum ethernet-100gbase-dwdm-1535-82 {
        description "DWDM with 1535.82nm optics";
      }
      enum ethernet-100gbase-dwdm-1535-04 {
        description "DWDM with 1535.04nm optics";
      }
      enum ethernet-100gbase-dwdm-1534-25 {
        description "DWDM with 1534.25nm optics";
      }
      enum ethernet-100gbase-dwdm-1533-47 {
        description "DWDM with 1533.47nm optics";
      }
      enum ethernet-100gbase-dwdm-1532-68 {
        description "DWDM with 1532.68nm optics";
      }
      enum ethernet-100gbase-dwdm-1531-90 {
        description "DWDM with 1531.90nm optics";
      }
      enum ethernet-100gbase-dwdm-1531-12 {
        description "DWDM with 1531.12nm optics";
      }
      enum ethernet-100gbase-dwdm-1530-33 {
        description "DWDM with 1530.33nm optics";
      }
      enum ethernet-100gbase-dwdm-tunable {
        description "DWDM with tunable optics";
      }
      enum ethernet-40gbase-kr4 {
        description "4 lane copper (backplane)";
      }
      enum ethernet-40gbase-cr4 {
        description "4 lane copper (very short reach)";
      }
      enum ethernet-40gbase-sr4 {
        description "fiber over 4 lane optics (short reach)";
      }
      enum ethernet-40gbase-fr {
        description "serial fiber (2+ km)";
      }
      enum ethernet-100gbase-cr10 {
        description "10 lane copper (very short reach)";
      }
      enum ethernet-100gbase-sr10 {
        description "MMF fiber over 10 lane optics (short reach)";
      }
      enum ethernet-40gbase-csr4 {
        description
          "fiber over 4 lane optics (extended short reach)";
      }
      enum ethernet-10gbase-cwdm {
        description "CWDM optics";
      }
      enum ethernet-10gbase-cwdm-tunable {
        description "CWDM with tunable optics";
      }
      enum ethernet-10gbase-cwdm-1470 {
        description "CWDM with 1470nm optics";
      }
      enum ethernet-10gbase-cwdm-1490 {
        description "CWDM with 1490nm optics";
      }
      enum ethernet-10gbase-cwdm-1510 {
        description "CWDM with 1510nm optics";
      }
      enum ethernet-10gbase-cwdm-1530 {
        description "CWDM with 1530nm optics";
      }
      enum ethernet-10gbase-cwdm-1550 {
        description "CWDM with 1550nm optics";
      }
      enum ethernet-10gbase-cwdm-1570 {
        description "CWDM with 1570nm optics";
      }
      enum ethernet-10gbase-cwdm-1590 {
        description "CWDM with 1590nm optics";
      }
      enum ethernet-10gbase-cwdm-1610 {
        description "CWDM with 1610nm optics";
      }
      enum ethernet-40gbase-cwdm {
        description "CWDM optics";
      }
      enum ethernet-40gbase-cwdm-tunable {
        description "CWDM with tunable optics";
      }
      enum ethernet-40gbase-cwdm-1470 {
        description "CWDM with 1470nm optics";
      }
      enum ethernet-40gbase-cwdm-1490 {
        description "CWDM with 1490nm optics";
      }
      enum ethernet-40gbase-cwdm-1510 {
        description "CWDM with 1510nm optics";
      }
      enum ethernet-40gbase-cwdm-1530 {
        description "CWDM with 1530nm optics";
      }
      enum ethernet-40gbase-cwdm-1550 {
        description "CWDM with 1550nm optics";
      }
      enum ethernet-40gbase-cwdm-1570 {
        description "CWDM with 1570nm optics";
      }
      enum ethernet-40gbase-cwdm-1590 {
        description "CWDM with 1590nm optics";
      }
      enum ethernet-40gbase-cwdm-1610 {
        description "CWDM with 1610nm optics";
      }
      enum ethernet-100gbase-cwdm {
        description "CWDM optics";
      }
      enum ethernet-100gbase-cwdm-tunable {
        description "CWDM with tunable optics";
      }
      enum ethernet-100gbase-cwdm-1470 {
        description "CWDM with 1470nm optics";
      }
      enum ethernet-100gbase-cwdm-1490 {
        description "CWDM with 1490nm optics";
      }
      enum ethernet-100gbase-cwdm-1510 {
        description "CWDM with 1510nm optics";
      }
      enum ethernet-100gbase-cwdm-1530 {
        description "CWDM with 1530nm optics";
      }
      enum ethernet-100gbase-cwdm-1550 {
        description "CWDM with 1550nm optics";
      }
      enum ethernet-100gbase-cwdm-1570 {
        description "CWDM with 1570nm optics";
      }
      enum ethernet-100gbase-cwdm-1590 {
        description "CWDM with 1590nm optics";
      }
      enum ethernet-100gbase-cwdm-1610 {
        description "CWDM with 1610nm optics";
      }
      enum ethernet-40gbase-elpb {
        description "Electrical loopback";
      }
      enum ethernet-100gbase-elpb {
        description "Electrical loopback";
      }
      enum ethernet-100gbase-lr10 {
        description "Fiber over 10 lane optics (long reach)";
      }
      enum ethernet-40gbase {
        description "Four-pair Category 8 STP";
      }
      enum ethernet-100gbase-kp4 {
        description "4 lane copper (backplane)";
      }
      enum ethernet-100gbase-kr4 {
        description "Improved 4 lane copper (backplane)";
      }
      enum ethernet-10gbase-lrm {
        description
          "Multimode fiber with 1310nm optics (long reach)";
      }
      enum ethernet-10gbase-cx4 {
        description "4 lane X copper";
      }
      enum ethernet-10gbase {
        description "Four-pair Category 6+ UTP";
      }
      enum ethernet-10gbase-kx4 {
        description "4 lane X copper (backplane)";
      }
      enum ethernet-10gbase-kr {
        description "Copper (backplane)";
      }
      enum ethernet-10gbase-pr {
        description "Passive optical network";
      }
      enum ethernet-100base-lx {
        description "X fiber over 4 lane 1310nm optics";
      }
      enum ethernet-100base-zx {
        description "Single-mode fiber over 1550nm optics (Cisco)";
      }
      enum ethernet-1000base-bx-d {
        description "X fibre (D)";
      }
      enum ethernet-1000base-bx-u {
        description "X fibre (U)";
      }
      enum ethernet-1000base-bx20-d {
        description "X fibre (D, 20km)";
      }
      enum ethernet-1000base-bx20-u {
        description "X fibre (U, 20km)";
      }
      enum ethernet-1000base-bx40-d {
        description "X fibre (D, 40km)";
      }
      enum ethernet-1000base-bx40-da {
        description "X fibre (D, 40km)";
      }
      enum ethernet-1000base-bx40-u {
        description "X fibre (U, 40km)";
      }
      enum ethernet-1000base-bx80-d {
        description "X fibre (D, 80km)";
      }
      enum ethernet-1000base-bx80-u {
        description "X fibre (U, 80km)";
      }
      enum ethernet-1000base-bx120-d {
        description "X fibre (D, 120km)";
      }
      enum ethernet-1000base-bx120-u {
        description "X fibre (U, 120km)";
      }
      enum ethernet-10gbase-bx-d {
        description "X fibre (D)";
      }
      enum ethernet-10gbase-bx-u {
        description "X fibre (U)";
      }
      enum ethernet-10gbase-bx10-d {
        description "X fibre (D, 10km)";
      }
      enum ethernet-10gbase-bx10-u {
        description "X fibre (U, 10km)";
      }
      enum ethernet-10gbase-bx20-d {
        description "X fibre (D, 20km)";
      }
      enum ethernet-10gbase-bx20-u {
        description "X fibre (U, 20km)";
      }
      enum ethernet-10gbase-bx40-d {
        description "X fibre (D, 40km)";
      }
      enum ethernet-10gbase-bx40-u {
        description "X fibre (U, 40km)";
      }
      enum ethernet-10gbase-bx80-d {
        description "X fibre (D, 80km)";
      }
      enum ethernet-10gbase-bx80-u {
        description "X fibre (U, 80km)";
      }
      enum ethernet-10gbase-bx120-d {
        description "X fibre (D, 120km)";
      }
      enum ethernet-10gbase-bx120-u {
        description "X fibre (U, 120km)";
      }
      enum ethernet-1000base-dr-lx {
        description
          "X fiber over long-wl laser PMD, duplexity
          unknown, dual rate";
      }
      enum ethernet-100gbase-er4l {
        description "fiber over 4 lane optics (25km reach)";
      }
      enum ethernet-base-max {
        description "ethernet base max";
      }
    }
    description
      "Ethernet media types: IEEE 802.3/802.3ae clause
      30.5.1.1.2";
  }
  typedef Ethernet-port-enable {
    type enumeration {
      enum disabled {
        description "Port disabled, both directions";
      }
      enum rx-enabled {
        description "Port enabled rx direction only";
      }
      enum tx-enabled {
        description "Port enabled tx direction only";
      }
      enum enabled {
        description "Port enabled, both directions";
      }
    }
    description "Port admin state";
  }

  grouping ETHERNET-BERT-STATUS-TYPE {
    description "ETHERNET BERT STATUS TYPE";
    leaf bert-state-enabled {
      xr:xr-xml-map "ethernet_show_controller:BERTStateEnabled";
      type boolean;
      description "State";
    }
    leaf data-availability {
      xr:xr-xml-map "ethernet_show_controller:DataAvailability";
      type Ethernet-bert-mask;
      description "Flag indicating available data";
    }
    leaf receive-count {
      xr:xr-xml-map "ethernet_show_controller:ReceiveCount";
      type uint64;
      description "Receive count (if 0x1 set in flag)";
    }
    leaf transmit-count {
      xr:xr-xml-map "ethernet_show_controller:TransmitCount";
      type uint64;
      description "Transmit count (if 0x2 set in flag)";
    }
    leaf receive-errors {
      xr:xr-xml-map "ethernet_show_controller:ReceiveErrors";
      type uint64;
      description "Received errors (if 0x4 set in flag)";
    }
    leaf error-type {
      xr:xr-xml-map "ethernet_show_controller:ErrorType";
      type Ethernet-bert-err-cnt;
      description "Bit, block or frame error";
    }
    leaf test-pattern {
      xr:xr-xml-map "ethernet_show_controller:TestPattern";
      type Ethernet-bert-pattern;
      description "Test pattern";
    }
    leaf device-under-test {
      xr:xr-xml-map "ethernet_show_controller:DeviceUnderTest";
      type Ethernet-dev;
      description "Device being tested";
    }
    leaf interface-device {
      xr:xr-xml-map "ethernet_show_controller:InterfaceDevice";
      type Ethernet-dev-if;
      description "Interface being tested";
    }
  }

  grouping ETH-SHOWCTRL-BERT {
    description "Per port BERT test status information";

    container bert-status {
      description "Current test status";
      uses ETHERNET-BERT-STATUS-TYPE;
    }
    leaf time-left {
      xr:xr-xml-map "ethernet_show_controller:TimeLeft";
      type uint32;
      units "second";
      description "Remaining time for this test in seconds";
    }
    leaf port-bert-interval {
      xr:xr-xml-map "ethernet_show_controller:PortBERTInterval";
      type uint32;
      description "Port BERT interval";
    }
  }

  grouping ETH-CTLR-TRANSPORT-INFO {
    description "ETH CTLR TRANSPORT INFO";
    leaf maintenance-mode-enabled {
      xr:xr-xml-map "ethernet_show_controller:MaintenanceModeEnable"+
        "d";
      type boolean;
      description "Maintenance Mode - TRUE if enabled";
    }
    leaf ains-status {
      xr:xr-xml-map "ethernet_show_controller:AINSStatus";
      type Ether-ains-status;
      description "AINS Soak status";
    }
    leaf total-duration {
      xr:xr-xml-map "ethernet_show_controller:TotalDuration";
      type uint32;
      units "second";
      description "Total duration (seconds) of AINS soak timer";
    }
    leaf remaining-duration {
      xr:xr-xml-map "ethernet_show_controller:RemainingDuration";
      type uint32;
      units "second";
      description "Remaining duration (seconds) of AINS soak timer";
    }
  }

  grouping ETHER-MCAST-MAC-TYPE {
    description "Multicast MAC address";
    leaf mac-address {
      xr:xr-xml-map "ethernet_show_controller:MACAddress";
      type Mac-addr;
      description "MAC address";
    }
    leaf mask {
      xr:xr-xml-map "ethernet_show_controller:Mask";
      type Mac-addr;
      description "Mask for this MAC address";
    }
  }

  grouping ETH-CTRLR-MCAST-MAC-FILTER {
    description "ETH CTRLR MCAST MAC FILTER";
    leaf multicast-promiscuous {
      xr:xr-xml-map "ethernet_show_controller:MulticastPromiscuous";
      type boolean;
      description
        "Whether the port is in multicast promiscuous
        mode";
    }

    list multicast-mac-address {
      description
        "MAC addresses in the multicast ingress
        destination MAC filter";
      uses ETHER-MCAST-MAC-TYPE;
    }
  }

  grouping ETH-CTRLR-UCAST-MAC-FILTER {
    description "ETH CTRLR UCAST MAC FILTER";
    leaf-list unicast-mac-address {
      xr:xr-xml-map "ethernet_show_controller:UnicastMACAddresses";
      type Mac-addr;
      description
        "MAC addresses in the unicast ingress destination
        MAC filter";
    }
  }

  grouping ETH-CTRLR-MAC-INFO {
    description "ETH CTRLR MAC INFO";

    container unicast-mac-filters {
      description "Port unicast MAC filter information";
      uses ETH-CTRLR-UCAST-MAC-FILTER;
    }

    container multicast-mac-filters {
      description "Port multicast MAC filter information";
      uses ETH-CTRLR-MCAST-MAC-FILTER;
    }
    leaf mtu {
      xr:xr-xml-map "ethernet_show_controller:MTU";
      type uint32;
      description "Port operational MTU";
    }
    leaf mru {
      xr:xr-xml-map "ethernet_show_controller:MRU";
      type uint32;
      description "Port operational MRU";
    }
    leaf burned-in-mac-address {
      xr:xr-xml-map "ethernet_show_controller:BurnedInMACAddress";
      type Mac-addr;
      description "Port Burned-In MAC address";
    }
    leaf operational-mac-address {
      xr:xr-xml-map "ethernet_show_controller:OperationalMACAddress";
      type Mac-addr;
      description "Port operational MAC address";
    }
  }

  grouping ETHER-BER-SETTINGS {
    description "ETHER BER SETTINGS";
    leaf signal-degrade-threshold {
      xr:xr-xml-map "ethernet_show_controller:SignalDegradeThreshol"+
        "d";
      type uint32;
      description "BER threshold for signal to degrade";
    }
    leaf signal-degrade-alarm {
      xr:xr-xml-map "ethernet_show_controller:SignalDegradeAlarm";
      type int32;
      description "Report alarm to indicate signal degrade";
    }
    leaf signal-fail-threshold {
      xr:xr-xml-map "ethernet_show_controller:SignalFailThreshold";
      type uint32;
      description "BER threshold for signal to fail";
    }
    leaf signal-fail-alarm {
      xr:xr-xml-map "ethernet_show_controller:SignalFailAlarm";
      type int32;
      description "Report alarm to indicate signal failure";
    }
    leaf signal-remote-fault {
      xr:xr-xml-map "ethernet_show_controller:SignalRemoteFault";
      type int32;
      description "Whether drivers should signal remote faults";
    }
  }

  grouping ETH-BER-MONITORING {
    description "ETH BER MONITORING";

    container settings {
      description "The BER monitoring settings to be applied";
      uses ETHER-BER-SETTINGS;
    }
    leaf supported {
      xr:xr-xml-map "ethernet_show_controller:Supported";
      type int32;
      description "Whether or not BER monitoring is supported";
    }
  }

  grouping ETH-CTRLR-ERROR-COUNTERS {
    description "ETH CTRLR ERROR COUNTERS";
    leaf sync-header-errors {
      xr:xr-xml-map "ethernet_show_controller:SyncHeaderErrors";
      type uint64;
      description "Sync-header error count";
    }
    leaf pcsbip-errors {
      xr:xr-xml-map "ethernet_show_controller:PCSBIPErrors";
      type uint64;
      description "PCS BIP error count";
    }
  }

  grouping ETH-CTRLR-ALARMS {
    description "ETH CTRLR ALARMS";
    leaf received-loss-of-signal-alarm {
      xr:xr-xml-map "ethernet_show_controller:ReceivedLossOfSignalA"+
        "larm";
      type Eth-ctrlr-alarm-state;
      description "Received Loss of Signal";
    }
    leaf pcs-loss-of-block-lock-alarm {
      xr:xr-xml-map "ethernet_show_controller:PCSLossOfBlockLockAla"+
        "rm";
      type Eth-ctrlr-alarm-state;
      description "PCS Loss of Block Lock";
    }
    leaf local-fault-alarm {
      xr:xr-xml-map "ethernet_show_controller:LocalFaultAlarm";
      type Eth-ctrlr-alarm-state;
      description "Local Fault";
    }
    leaf remote-fault-alarm {
      xr:xr-xml-map "ethernet_show_controller:RemoteFaultAlarm";
      type Eth-ctrlr-alarm-state;
      description "Remote Fault";
    }
    leaf sd-ber-alarm {
      xr:xr-xml-map "ethernet_show_controller:SD_BERAlarm";
      type Eth-ctrlr-alarm-state;
      description "SD BER";
    }
    leaf sf-ber-alarm {
      xr:xr-xml-map "ethernet_show_controller:SF_BERAlarm";
      type Eth-ctrlr-alarm-state;
      description "SF BER";
    }
    leaf loss-of-synchronization-data-alarm {
      xr:xr-xml-map "ethernet_show_controller:LossOfSynchronization"+
        "DataAlarm";
      type Eth-ctrlr-alarm-state;
      description "Loss of Synchronization Data";
    }
  }

  grouping ETHER-AUTONEG-TYPE {
    description "Autonegotiation settings";
    leaf autoneg-enabled {
      xr:xr-xml-map "ethernet_show_controller:AutonegEnabled";
      type int32;
      description "TRUE if autonegotiation is enabled";
    }
    leaf mask {
      xr:xr-xml-map "ethernet_show_controller:Mask";
      type Ether-autoneg-mask;
      description
        "Validity mask: 0x1 speed, 0x2 duplex, 0x4
        flowcontrol";
    }
    leaf speed {
      xr:xr-xml-map "ethernet_show_controller:Speed";
      type Ethernet-speed;
      description
        "Restricted speed (if relevant bit is set in
        mask)";
    }
    leaf duplex {
      xr:xr-xml-map "ethernet_show_controller:Duplex";
      type Ethernet-duplex;
      description
        "Restricted duplex (if relevant bit is set in
        mask)";
    }
    leaf flowcontrol {
      xr:xr-xml-map "ethernet_show_controller:Flowcontrol";
      type Ether-flowcontrol;
      description
        "Restricted flowcontrol (if relevant bit is set
        in mask)";
    }
    leaf config-override {
      xr:xr-xml-map "ethernet_show_controller:ConfigOverride";
      type int32;
      description
        "If true, configuration overrides negotiated
        settings.  If false, negotiated settings in
        effect";
    }
  }

  grouping ETH-CTRLR-L1-INFO {
    description "ETH CTRLR L1 INFO";

    container autoneg {
      description "Port autonegotiation configuration settings";
      uses ETHER-AUTONEG-TYPE;
    }

    container current-alarms {
      description "Current alarms";
      uses ETH-CTRLR-ALARMS;
    }

    container previous-alarms {
      description "Previous alarms";
      uses ETH-CTRLR-ALARMS;
    }

    container error-counts {
      description "Statistics for detected errors";
      uses ETH-CTRLR-ERROR-COUNTERS;
    }

    container ber-monitoring {
      description "BER monitoring details";
      uses ETH-BER-MONITORING;
    }
    leaf link-state {
      xr:xr-xml-map "ethernet_show_controller:LinkState";
      type Ether-link-state;
      description "Link state";
    }
    leaf led-state {
      xr:xr-xml-map "ethernet_show_controller:LEDState";
      type Ether-led-state;
      description "State of the LED";
    }
    leaf speed {
      xr:xr-xml-map "ethernet_show_controller:Speed";
      type Ethernet-speed;
      description "Port operational speed";
    }
    leaf duplex {
      xr:xr-xml-map "ethernet_show_controller:Duplex";
      type Ethernet-duplex;
      description "Port operational duplexity";
    }
    leaf flowcontrol {
      xr:xr-xml-map "ethernet_show_controller:Flowcontrol";
      type Ether-flowcontrol;
      description "Port operational flow control";
    }
    leaf ipg {
      xr:xr-xml-map "ethernet_show_controller:IPG";
      type Ethernet-ipg;
      description "Port operational inter-packet-gap";
    }
  }

  grouping ETH-CTRLR-PHY-DOM-ALARMS {
    description "ETH CTRLR PHY DOM ALARMS";
    leaf transceiver-temperature {
      xr:xr-xml-map "ethernet_show_controller:TransceiverTemperatur"+
        "e";
      type Ether-dom-alarm;
      description "Transceiver Temperature Alarm";
    }
    leaf transceiver-voltage {
      xr:xr-xml-map "ethernet_show_controller:TransceiverVoltage";
      type Ether-dom-alarm;
      description "Transceiver Voltage Alarm";
    }
    leaf transmit-laser-power {
      xr:xr-xml-map "ethernet_show_controller:TransmitLaserPower";
      type Ether-dom-alarm;
      description "Transmit Laser Power Alarm";
    }
    leaf received-laser-power {
      xr:xr-xml-map "ethernet_show_controller:ReceivedLaserPower";
      type Ether-dom-alarm;
      description "Received Optical Power Alarm";
    }
    leaf laser-bias-current {
      xr:xr-xml-map "ethernet_show_controller:LaserBiasCurrent";
      type Ether-dom-alarm;
      description "Laser Bias Current Alarm";
    }
  }

  grouping ETH-CTRLR-PHY-DOM-THRESHOLDS {
    description "ETH CTRLR PHY DOM THRESHOLDS";
    leaf transceiver-temperature-alarm-high {
      xr:xr-xml-map "ethernet_show_controller:TransceiverTemperatur"+
        "eAlarmHigh";
      type int32;
      description
        "Transceiver high temperature alarm threshold
        (mDegrees C)";
    }
    leaf transceiver-temperature-warning-high {
      xr:xr-xml-map "ethernet_show_controller:TransceiverTemperatur"+
        "eWarningHigh";
      type int32;
      description
        "Transceiver high temperature warning threshold
        (mDegrees C)";
    }
    leaf transceiver-temperature-warning-low {
      xr:xr-xml-map "ethernet_show_controller:TransceiverTemperatur"+
        "eWarningLow";
      type int32;
      description
        "Transceiver low temperature warning threshold
        (mDegrees C)";
    }
    leaf transceiver-temperature-alarm-low {
      xr:xr-xml-map "ethernet_show_controller:TransceiverTemperatur"+
        "eAlarmLow";
      type int32;
      description
        "Transceiver low temperature alarm threshold
        (mDegrees C)";
    }
    leaf transceiver-voltage-alarm-high {
      xr:xr-xml-map "ethernet_show_controller:TransceiverVoltageAla"+
        "rmHigh";
      type uint32;
      description "Transceiver high voltage alarm threshold (mV)";
    }
    leaf transceiver-voltage-warning-high {
      xr:xr-xml-map "ethernet_show_controller:TransceiverVoltageWar"+
        "ningHigh";
      type uint32;
      description "Transceiver high voltage warning threshold (mV)";
    }
    leaf transceiver-voltage-warning-low {
      xr:xr-xml-map "ethernet_show_controller:TransceiverVoltageWar"+
        "ningLow";
      type uint32;
      description "Transceiver low voltage warning threshold (mV)";
    }
    leaf transceiver-voltage-alarm-low {
      xr:xr-xml-map "ethernet_show_controller:TransceiverVoltageAla"+
        "rmLow";
      type uint32;
      description "Transceiver low voltage alarm threshold (mV)";
    }
    leaf laser-bias-alarm-high {
      xr:xr-xml-map "ethernet_show_controller:LaserBiasAlarmHigh";
      type uint32;
      description "Laser bias high alarm threshold (mA)";
    }
    leaf laser-bias-warning-high {
      xr:xr-xml-map "ethernet_show_controller:LaserBiasWarningHigh";
      type uint32;
      description "Laser bias high warning threshold (mA)";
    }
    leaf laser-bias-warning-low {
      xr:xr-xml-map "ethernet_show_controller:LaserBiasWarningLow";
      type uint32;
      description "Laser bias low warning threshold (mA)";
    }
    leaf laser-bias-alarm-low {
      xr:xr-xml-map "ethernet_show_controller:LaserBiasAlarmLow";
      type uint32;
      description "Laser bias low alarm threshold (mA)";
    }
    leaf optical-transmit-power-alarm-high {
      xr:xr-xml-map "ethernet_show_controller:OpticalTransmitPowerA"+
        "larmHigh";
      type uint32;
      description
        "High optical transmit power alarm threshold (mW)";
    }
    leaf optical-transmit-power-warning-high {
      xr:xr-xml-map "ethernet_show_controller:OpticalTransmitPowerW"+
        "arningHigh";
      type uint32;
      description
        "High optical transmit power warning threshold
        (mW)";
    }
    leaf optical-transmit-power-warning-low {
      xr:xr-xml-map "ethernet_show_controller:OpticalTransmitPowerW"+
        "arningLow";
      type uint32;
      description
        "Low optical transmit power warning threshold
        (mW)";
    }
    leaf optical-transmit-power-alarm-low {
      xr:xr-xml-map "ethernet_show_controller:OpticalTransmitPowerA"+
        "larmLow";
      type uint32;
      description "Low optical transmit power alarm threshold (mW)";
    }
    leaf optical-receive-power-alarm-high {
      xr:xr-xml-map "ethernet_show_controller:OpticalReceivePowerAl"+
        "armHigh";
      type uint32;
      description "High optical receive power alarm threshold (mW)";
    }
    leaf optical-receive-power-warning-high {
      xr:xr-xml-map "ethernet_show_controller:OpticalReceivePowerWa"+
        "rningHigh";
      type uint32;
      description
        "High optical receive power warning threshold
        (mW)";
    }
    leaf optical-receive-power-warning-low {
      xr:xr-xml-map "ethernet_show_controller:OpticalReceivePowerWa"+
        "rningLow";
      type uint32;
      description
        "Low optical receive power warning threshold (mW)";
    }
    leaf optical-receive-power-alarm-low {
      xr:xr-xml-map "ethernet_show_controller:OpticalReceivePowerAl"+
        "armLow";
      type uint32;
      description "Low optical receive power alarm threshold (mW)";
    }
  }

  grouping ETH-CTRLR-PHY-DOM-LANE-ALARMS {
    description "ETH CTRLR PHY DOM LANE ALARMS";
    leaf transmit-laser-power {
      xr:xr-xml-map "ethernet_show_controller:TransmitLaserPower";
      type Ether-dom-alarm;
      description "Transmit Laser Power Alarm";
    }
    leaf received-laser-power {
      xr:xr-xml-map "ethernet_show_controller:ReceivedLaserPower";
      type Ether-dom-alarm;
      description "Received Optical Power Alarm";
    }
    leaf laser-bias-current {
      xr:xr-xml-map "ethernet_show_controller:LaserBiasCurrent";
      type Ether-dom-alarm;
      description "Laser Bias Current Alarm";
    }
  }

  grouping ETH-CTRLR-PHY-LANE-OPT-MON {
    description "ETH CTRLR PHY LANE OPT MON";

    container dig-opt-mon-alarm {
      description "Digital Optical Monitoring alarms";
      uses ETH-CTRLR-PHY-DOM-LANE-ALARMS;
    }
    leaf center-wavelength {
      xr:xr-xml-map "ethernet_show_controller:CenterWavelength";
      type uint32;
      description "Center Wavelength (nm*1000)";
    }
    leaf transmit-laser-power {
      xr:xr-xml-map "ethernet_show_controller:TransmitLaserPower";
      type int32;
      description "Transmit Laser Power (dBm*1000)";
    }
    leaf received-laser-power {
      xr:xr-xml-map "ethernet_show_controller:ReceivedLaserPower";
      type int32;
      description "Received Optical Power (dBm*1000)";
    }
    leaf laser-bias-current {
      xr:xr-xml-map "ethernet_show_controller:LaserBiasCurrent";
      type uint32;
      description "Laser Bias Current (uAmps)";
    }
  }

  grouping ETHER-PHY-DETAILS-TYPE {
    description "ETHER PHY DETAILS TYPE";

    container dig-opt-mon-alarm-thresholds {
      description "Digital Optical Monitoring alarm thresholds";
      uses ETH-CTRLR-PHY-DOM-THRESHOLDS;
    }

    container dig-opt-mon-alarms {
      description "Digital Optical Monitoring alarms";
      uses ETH-CTRLR-PHY-DOM-ALARMS;
    }
    leaf vendor {
      xr:xr-xml-map "ethernet_show_controller:Vendor";
      type string;
      description "Name of the port optics manufacturer";
    }
    leaf vendor-part-number {
      xr:xr-xml-map "ethernet_show_controller:VendorPartNumber";
      type string;
      description "Part number for the port optics";
    }
    leaf vendor-serial-number {
      xr:xr-xml-map "ethernet_show_controller:VendorSerialNumber";
      type string;
      description "Serial number for the port optics";
    }
    leaf transceiver-temperature {
      xr:xr-xml-map "ethernet_show_controller:TransceiverTemperatur"+
        "e";
      type uint32;
      description "The temperature of the transceiver (mDegrees C)";
    }
    leaf transceiver-voltage {
      xr:xr-xml-map "ethernet_show_controller:TransceiverVoltage";
      type uint32;
      description "The input voltage to the transceiver (mV)";
    }
    leaf optics-wavelength {
      xr:xr-xml-map "ethernet_show_controller:OpticsWavelength";
      type uint32;
      description
        "Wavelength of the optics being used in nm *
        10000";
    }

    list lane {
      description
        "Digital Optical Monitoring (per lane
        information)";
      uses ETH-CTRLR-PHY-LANE-OPT-MON;
    }
  }

  grouping ETH-CTRLR-PHY-INFO {
    description "ETH CTRLR PHY INFO";

    container phy-details {
      description "Details about the PHY";
      uses ETHER-PHY-DETAILS-TYPE;
    }
    leaf media-type {
      xr:xr-xml-map "ethernet_show_controller:MediaType";
      type Ethernet-media;
      description "Port media type";
    }
    leaf phy-present {
      xr:xr-xml-map "ethernet_show_controller:PhyPresent";
      type Ether-phy-present;
      description "Presence of PHY";
    }
    leaf loopback {
      xr:xr-xml-map "ethernet_show_controller:Loopback";
      type Ethernet-loopback;
      description "Port operational loopback";
    }
  }

  grouping ETHERNET-CONTROLLER-DRIVER-BAG-V2-TYPE {
    description
      "Ethernet bag for driver state for the show
      controllers command";

    container phy-info {
      description "PHY information";
      uses ETH-CTRLR-PHY-INFO;
    }

    container layer1-info {
      description "Layer 1 information";
      uses ETH-CTRLR-L1-INFO;
    }

    container mac-info {
      description "MAC Layer information";
      uses ETH-CTRLR-MAC-INFO;
    }

    container transport-info {
      description "Transport state information";
      uses ETH-CTLR-TRANSPORT-INFO;
    }
    leaf admin-state {
      xr:xr-xml-map "ethernet_show_controller:AdminState";
      type Ethernet-port-enable;
      description "Port Administrative State";
    }
    leaf oper-state-up {
      xr:xr-xml-map "ethernet_show_controller:OperStateUp";
      type boolean;
      description "Port Operational state - TRUE if up";
    }
  }

  grouping ETHERNET-PORT-STATS-TYPE {
    description "Port stats counters";
    leaf received-total-bytes {
      xr:xr-xml-map "ethernet_show_controller:ReceivedTotalBytes";
      type uint64;
      description "Total octets of all frames";
    }
    leaf received-good-bytes {
      xr:xr-xml-map "ethernet_show_controller:ReceivedGoodBytes";
      type uint64;
      description "Total octets of all good frames";
    }
    leaf received-total-frames {
      xr:xr-xml-map "ethernet_show_controller:ReceivedTotalFrames";
      type uint64;
      description "All frames, good or bad";
    }
    leaf received8021q-frames {
      xr:xr-xml-map "ethernet_show_controller:Received8021QFrames";
      type uint64;
      description "All 802.1Q frames";
    }
    leaf received-pause-frames {
      xr:xr-xml-map "ethernet_show_controller:ReceivedPauseFrames";
      type uint64;
      description "All pause frames";
    }
    leaf received-unknown-opcodes {
      xr:xr-xml-map "ethernet_show_controller:ReceivedUnknownOpcode"+
        "s";
      type uint64;
      description "Unsupported MAC Control frames";
    }
    leaf received-total64-octet-frames {
      xr:xr-xml-map "ethernet_show_controller:ReceivedTotal64OctetF"+
        "rames";
      type uint64;
      description "All 64 Octet Frame Count";
    }
    leaf received-total-octet-frames-from65-to127 {
      xr:xr-xml-map "ethernet_show_controller:ReceivedTotalOctetFra"+
        "mesFrom65To127";
      type uint64;
      description "All 65-127 Octet Frame Count";
    }
    leaf received-total-octet-frames-from128-to255 {
      xr:xr-xml-map "ethernet_show_controller:ReceivedTotalOctetFra"+
        "mesFrom128To255";
      type uint64;
      description "All 128-255 Octet Frame Count";
    }
    leaf received-total-octet-frames-from256-to511 {
      xr:xr-xml-map "ethernet_show_controller:ReceivedTotalOctetFra"+
        "mesFrom256To511";
      type uint64;
      description "All 256-511 Octet Frame Count";
    }
    leaf received-total-octet-frames-from512-to1023 {
      xr:xr-xml-map "ethernet_show_controller:ReceivedTotalOctetFra"+
        "mesFrom512To1023";
      type uint64;
      description "All 512-1023 Octet Frame Count";
    }
    leaf received-total-octet-frames-from1024-to1518 {
      xr:xr-xml-map "ethernet_show_controller:ReceivedTotalOctetFra"+
        "mesFrom1024To1518";
      type uint64;
      description "All 1024-1518 Octet Frame Count";
    }
    leaf received-total-octet-frames-from1519-to-max {
      xr:xr-xml-map "ethernet_show_controller:ReceivedTotalOctetFra"+
        "mesFrom1519ToMax";
      type uint64;
      description "All > 1518 Octet Frame Count";
    }
    leaf received-good-frames {
      xr:xr-xml-map "ethernet_show_controller:ReceivedGoodFrames";
      type uint64;
      description "Received Good Frames";
    }
    leaf received-unicast-frames {
      xr:xr-xml-map "ethernet_show_controller:ReceivedUnicastFrames";
      type uint64;
      description "Received unicast Frames";
    }
    leaf received-multicast-frames {
      xr:xr-xml-map "ethernet_show_controller:ReceivedMulticastFram"+
        "es";
      type uint64;
      description "Received multicast Frames";
    }
    leaf received-broadcast-frames {
      xr:xr-xml-map "ethernet_show_controller:ReceivedBroadcastFram"+
        "es";
      type uint64;
      description "Received broadcast Frames";
    }
    leaf number-of-buffer-overrun-packets-dropped {
      xr:xr-xml-map "ethernet_show_controller:NumberOfBufferOverrun"+
        "PacketsDropped";
      type uint64;
      description "Drops due to buffer overrun";
    }
    leaf number-of-aborted-packets-dropped {
      xr:xr-xml-map "ethernet_show_controller:NumberOfAbortedPacket"+
        "sDropped";
      type uint64;
      description "Drops due to packet abort";
    }
    leaf numberof-invalid-vlan-id-packets-dropped {
      xr:xr-xml-map "ethernet_show_controller:NumberofInvalidVLAN_I"+
        "DPacketsDropped";
      type uint64;
      description "Drops due to invalid VLAN id";
    }
    leaf invalid-dest-mac-drop-packets {
      xr:xr-xml-map "ethernet_show_controller:InvalidDestMACDropPac"+
        "kets";
      type uint64;
      description "Drops due to the destination MAC not matching";
    }
    leaf invalid-encap-drop-packets {
      xr:xr-xml-map "ethernet_show_controller:InvalidEncapDropPacke"+
        "ts";
      type uint64;
      description
        "Drops due to the encapsulation or ether type not
        matching";
    }
    leaf number-of-miscellaneous-packets-dropped {
      xr:xr-xml-map "ethernet_show_controller:NumberOfMiscellaneous"+
        "PacketsDropped";
      type uint64;
      description "Any other drops not counted";
    }
    leaf dropped-giant-packets-greaterthan-mru {
      xr:xr-xml-map "ethernet_show_controller:DroppedGiantPacketsGr"+
        "eaterthanMRU";
      type uint64;
      description "Good frames > MRU, dropped";
    }
    leaf dropped-ether-stats-undersize-pkts {
      xr:xr-xml-map "ethernet_show_controller:DroppedEtherStatsUnde"+
        "rsizePkts";
      type uint64;
      description "Good frames < 64 Octet, dropped";
    }
    leaf dropped-jabbers-packets-greaterthan-mru {
      xr:xr-xml-map "ethernet_show_controller:DroppedJabbersPackets"+
        "GreaterthanMRU";
      type uint64;
      description "Bad Frames > MRU, dropped";
    }
    leaf dropped-ether-stats-fragments {
      xr:xr-xml-map "ethernet_show_controller:DroppedEtherStatsFrag"+
        "ments";
      type uint64;
      description "Bad Frames < 64 Octet, dropped";
    }
    leaf dropped-packets-with-crc-align-errors {
      xr:xr-xml-map "ethernet_show_controller:DroppedPacketsWithCRC"+
        "AlignErrors";
      type uint64;
      description "Frames 64 - MRU with CRC error";
    }
    leaf ether-stats-collisions {
      xr:xr-xml-map "ethernet_show_controller:EtherStatsCollisions";
      type uint64;
      description "All collision events";
    }
    leaf symbol-errors {
      xr:xr-xml-map "ethernet_show_controller:SymbolErrors";
      type uint64;
      description "Symbol errors";
    }
    leaf dropped-miscellaneous-error-packets {
      xr:xr-xml-map "ethernet_show_controller:DroppedMiscellaneousE"+
        "rrorPackets";
      type uint64;
      description "Any other errors not counted";
    }
    leaf rfc2819-ether-stats-oversized-pkts {
      xr:xr-xml-map "ethernet_show_controller:RFC2819EtherStatsOver"+
        "sizedPkts";
      type uint64;
      description "RFC2819 etherStatsOversizedPkts";
    }
    leaf rfc2819-ether-stats-jabbers {
      xr:xr-xml-map "ethernet_show_controller:RFC2819EtherStatsJabb"+
        "ers";
      type uint64;
      description "RFC2819 etherStatsJabbers";
    }
    leaf rfc2819-ether-stats-crc-align-errors {
      xr:xr-xml-map "ethernet_show_controller:RFC2819EtherStatsCRCA"+
        "lignErrors";
      type uint64;
      description "RFC2819 etherStatsCRCAlignErrors";
    }
    leaf rfc3635dot3-stats-alignment-errors {
      xr:xr-xml-map "ethernet_show_controller:RFC3635dot3StatsAlign"+
        "mentErrors";
      type uint64;
      description "RFC3635 dot3StatsAlignmentErrors";
    }
    leaf total-bytes-transmitted {
      xr:xr-xml-map "ethernet_show_controller:TotalBytesTransmitted";
      type uint64;
      description "Total octets of all frames";
    }
    leaf total-good-bytes-transmitted {
      xr:xr-xml-map "ethernet_show_controller:TotalGoodBytesTransmi"+
        "tted";
      type uint64;
      description "Total octets of all good frames";
    }
    leaf total-frames-transmitted {
      xr:xr-xml-map "ethernet_show_controller:TotalFramesTransmitte"+
        "d";
      type uint64;
      description "All frames, good or bad";
    }
    leaf transmitted8021q-frames {
      xr:xr-xml-map "ethernet_show_controller:Transmitted8021QFrame"+
        "s";
      type uint64;
      description "All 802.1Q frames";
    }
    leaf transmitted-total-pause-frames {
      xr:xr-xml-map "ethernet_show_controller:TransmittedTotalPause"+
        "Frames";
      type uint64;
      description "All pause frames";
    }
    leaf transmitted-total64-octet-frames {
      xr:xr-xml-map "ethernet_show_controller:TransmittedTotal64Oct"+
        "etFrames";
      type uint64;
      description "All 64 Octet Frame Count";
    }
    leaf transmitted-total-octet-frames-from65-to127 {
      xr:xr-xml-map "ethernet_show_controller:TransmittedTotalOctet"+
        "FramesFrom65To127";
      type uint64;
      description "All 65-127 Octet Frame Count";
    }
    leaf transmitted-total-octet-frames-from128-to255 {
      xr:xr-xml-map "ethernet_show_controller:TransmittedTotalOctet"+
        "FramesFrom128To255";
      type uint64;
      description "All 128-255 Octet Frame Count";
    }
    leaf transmitted-total-octet-frames-from256-to511 {
      xr:xr-xml-map "ethernet_show_controller:TransmittedTotalOctet"+
        "FramesFrom256To511";
      type uint64;
      description "All 256-511 Octet Frame Count";
    }
    leaf transmitted-total-octet-frames-from512-to1023 {
      xr:xr-xml-map "ethernet_show_controller:TransmittedTotalOctet"+
        "FramesFrom512To1023";
      type uint64;
      description "All 512-1023 Octet Frame Count";
    }
    leaf transmitted-total-octet-frames-from1024-to1518 {
      xr:xr-xml-map "ethernet_show_controller:TransmittedTotalOctet"+
        "FramesFrom1024To1518";
      type uint64;
      description "All 1024-1518 Octet Frame Count";
    }
    leaf transmitted-total-octet-frames-from1518-to-max {
      xr:xr-xml-map "ethernet_show_controller:TransmittedTotalOctet"+
        "FramesFrom1518ToMax";
      type uint64;
      description "All > 1518 Octet Frame Count";
    }
    leaf transmitted-good-frames {
      xr:xr-xml-map "ethernet_show_controller:TransmittedGoodFrames";
      type uint64;
      description "Transmitted Good Frames";
    }
    leaf transmitted-unicast-frames {
      xr:xr-xml-map "ethernet_show_controller:TransmittedUnicastFra"+
        "mes";
      type uint64;
      description "Transmitted unicast Frames";
    }
    leaf transmitted-multicast-frames {
      xr:xr-xml-map "ethernet_show_controller:TransmittedMulticastF"+
        "rames";
      type uint64;
      description "Transmitted multicast Frames";
    }
    leaf transmitted-broadcast-frames {
      xr:xr-xml-map "ethernet_show_controller:TransmittedBroadcastF"+
        "rames";
      type uint64;
      description "Transmitted broadcast Frames";
    }
    leaf buffer-underrun-packet-drops {
      xr:xr-xml-map "ethernet_show_controller:BufferUnderrunPacketD"+
        "rops";
      type uint64;
      description "Drops due to buffer underrun";
    }
    leaf aborted-packet-drops {
      xr:xr-xml-map "ethernet_show_controller:AbortedPacketDrops";
      type uint64;
      description "Drops due to packet abort";
    }
    leaf uncounted-dropped-frames {
      xr:xr-xml-map "ethernet_show_controller:UncountedDroppedFrame"+
        "s";
      type uint64;
      description "Any other drops not counted";
    }
    leaf miscellaneous-output-errors {
      xr:xr-xml-map "ethernet_show_controller:MiscellaneousOutputEr"+
        "rors";
      type uint64;
      description "Any other errors not counted";
    }
  }
}
