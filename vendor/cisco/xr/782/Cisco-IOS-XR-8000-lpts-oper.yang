module Cisco-IOS-XR-8000-lpts-oper {
  namespace "http://cisco.com/ns/yang/Cisco-IOS-XR-8000-lpts-oper";
  prefix xr-8000-lpts-oper;

  import Cisco-IOS-XR-types {
    prefix xr;
  }
  import cisco-semver {
    prefix semver;
  }
  include Cisco-IOS-XR-8000-lpts-oper-sub1 {
    revision-date 2022-05-05;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR 8000-lpts package operational data.
     
     This module contains definitions
     for the following management objects:
       platform-lptsp-ifib: 8000 platform ifib operational data
     
     Copyright (c) 2013-2022 by Cisco Systems, Inc.
     All rights reserved.";

  revision 2022-05-05 {
    description
      "Add is_compressed leaf to grouping PL-PIFIB-SHOW-ENTRY";
    semver:module-version "1.1.0";
  }
  revision 2021-03-30 {
    description
      "LPTS Pre-ifib Oper Yang added.";
    semver:module-version "1.0.0";
  }
  revision 2019-04-05 {
    description
      "Establish semantic version baseline.";
  }
  revision 2015-11-09 {
    description
      "IOS XR 6.0 revision.";
  }

  container platform-lptsp-ifib {
    config false;
    description
      "8000 platform ifib operational data ";
    container nodes {
      description
        "List of nodes with platform specific lpts
         operation data";
      list node {
        key "node-name";
        description
          "Node with platform specific lpts data";
        container polices {
          description
            "policer info for LC";
          list police {
            key "entry";
            description
              "Data for single policer entry";
            leaf entry {
              type xr:Cisco-ios-xr-string;
              description
                "Single Policer entry";
            }
            uses PL-PIFIB-POLICER-INFO;
          }
        }
        container entries {
          description
            "stats for LC";
          list entry {
            key "entry";
            description
              "Data for single pre-ifib entry";
            leaf entry {
              type xr:Cisco-ios-xr-string;
              description
                "Single Pre-ifib entry";
            }
            uses PL-PIFIB-SHOW-ENTRY;
          }
        }
        container og-entries {
          description
            "og entry for LC";
          list og-entry {
            key "entry";
            description
              "Data for single pre-ifib og entry";
            leaf entry {
              type xr:Cisco-ios-xr-string;
              description
                "Single Pre-ifib og entry";
            }
            uses PL-PIFIB-SHOW-OG-ENTRY;
          }
        }
        leaf node-name {
          type xr:Node-id;
          description
            "Node name";
        }
      }
    }
  }
}
