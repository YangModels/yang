module Cisco-IOS-XR-um-performance-mgmt-cfg {
  namespace "http://cisco.com/ns/yang/Cisco-IOS-XR-um-performance-mgmt-cfg";
  prefix um-performance-mgmt-cfg;

  import Cisco-IOS-XR-types {
    prefix xr;
  }
  import ietf-inet-types {
    prefix inet;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR performance-mgmt package configuration.
     
     This YANG module augments the
     modules with configuration data.
     
     Copyright (c) 2021-2022 by Cisco Systems, Inc.
     All rights reserved.";

  revision 2021-07-21 {
    description
      "Initial release";
    semver:module-version "1.0.0";
  }

  container performance-mgmt {
    description
      "Performance Management configuration & operation subcommands";
    container statistics {
      description
        "Configure statistics for data collection";
      container interface {
        description
          "Configure statistics collection for interfaces";
        container basic-counters {
          description
            "Configure data collection for basic counters";
          container templates {
            description
              "Specify template";
            list template {
              key "template-name";
              description
                "Specify template";
              leaf template-name {
                type xr:Cisco-ios-xr-string {
                  length "1..800" {
                    description
                      "Template name";
                  }
                }
                description
                  "Specify template";
              }
              leaf sample-size {
                type uint32 {
                  range "1..60" {
                    description
                      "Number of samples";
                  }
                }
                description
                  "Number of samples to be taken";
              }
              leaf sample-interval {
                type uint32 {
                  range "1..60" {
                    description
                      "Frequency of samples";
                  }
                }
                description
                  "Frequency of sampling in minutes";
              }
              container history-persistent {
                presence "Indicates a history-persistent node is configured.";
                description
                  "Keep history statistics persistently";
              }
              leaf regular-expression {
                type xr:Cisco-ios-xr-string {
                  length "1..32" {
                    description
                      "Regular expression name to be applied";
                  }
                }
                description
                  "Instance filtering by regular expression";
              }
            }
          }
          container default {
            presence "Indicates a default node is configured.";
            description
              "Default template";
            leaf sample-size {
              type uint32 {
                range "1..60" {
                  description
                    "Number of samples";
                }
              }
              description
                "Number of samples to be taken";
            }
            leaf sample-interval {
              type uint32 {
                range "1..60" {
                  description
                    "Frequency of samples";
                }
              }
              description
                "Frequency of sampling in minutes";
            }
            container history-persistent {
              presence "Indicates a history-persistent node is configured.";
              description
                "Keep history statistics persistently";
            }
            leaf regular-expression {
              type xr:Cisco-ios-xr-string {
                length "1..32" {
                  description
                    "Regular expression name to be applied";
                }
              }
              description
                "Instance filtering by regular expression";
            }
          }
        }
        container generic-counters {
          description
            "Configure data collection for generic counters";
          container templates {
            description
              "Specify template";
            list template {
              key "template-name";
              description
                "Specify template";
              leaf template-name {
                type xr:Cisco-ios-xr-string {
                  length "1..800" {
                    description
                      "Template name";
                  }
                }
                description
                  "Specify template";
              }
              leaf sample-size {
                type uint32 {
                  range "1..60" {
                    description
                      "Number of samples";
                  }
                }
                description
                  "Number of samples to be taken";
              }
              leaf sample-interval {
                type uint32 {
                  range "1..60" {
                    description
                      "Frequency of samples";
                  }
                }
                description
                  "Frequency of sampling in minutes";
              }
              container history-persistent {
                presence "Indicates a history-persistent node is configured.";
                description
                  "Keep history statistics persistently";
              }
              leaf regular-expression {
                type xr:Cisco-ios-xr-string {
                  length "1..32" {
                    description
                      "Regular expression name to be applied";
                  }
                }
                description
                  "Instance filtering by regular expression";
              }
              leaf vrf-group {
                type xr:Cisco-ios-xr-string {
                  length "1..32" {
                    description
                      "Regular expression name to be applied";
                  }
                }
                description
                  "Instance filtering by VRF name regular expression";
              }
            }
          }
          container default {
            presence "Indicates a default node is configured.";
            description
              "Default template";
            leaf sample-size {
              type uint32 {
                range "1..60" {
                  description
                    "Number of samples";
                }
              }
              description
                "Number of samples to be taken";
            }
            leaf sample-interval {
              type uint32 {
                range "1..60" {
                  description
                    "Frequency of samples";
                }
              }
              description
                "Frequency of sampling in minutes";
            }
            container history-persistent {
              presence "Indicates a history-persistent node is configured.";
              description
                "Keep history statistics persistently";
            }
            leaf regular-expression {
              type xr:Cisco-ios-xr-string {
                length "1..32" {
                  description
                    "Regular expression name to be applied";
                }
              }
              description
                "Instance filtering by regular expression";
            }
            leaf vrf-group {
              type xr:Cisco-ios-xr-string {
                length "1..32" {
                  description
                    "Regular expression name to be applied";
                }
              }
              description
                "Instance filtering by VRF name regular expression";
            }
          }
        }
        container data-rates {
          description
            "Configure data collection for data rates";
          container templates {
            description
              "Specify template";
            list template {
              key "template-name";
              description
                "Specify template";
              leaf template-name {
                type xr:Cisco-ios-xr-string {
                  length "1..800" {
                    description
                      "Template name";
                  }
                }
                description
                  "Specify template";
              }
              leaf sample-size {
                type uint32 {
                  range "1..60" {
                    description
                      "Number of samples";
                  }
                }
                description
                  "Number of samples to be taken";
              }
              leaf sample-interval {
                type uint32 {
                  range "1..60" {
                    description
                      "Frequency of samples";
                  }
                }
                description
                  "Frequency of sampling in minutes";
              }
              container history-persistent {
                presence "Indicates a history-persistent node is configured.";
                description
                  "Keep history statistics persistenly";
              }
              leaf regular-expression {
                type xr:Cisco-ios-xr-string {
                  length "1..32" {
                    description
                      "Regular expression name to be applied";
                  }
                }
                description
                  "Instance filtering by regular expression";
              }
              leaf vrf-group {
                type xr:Cisco-ios-xr-string {
                  length "1..32" {
                    description
                      "Regular expression name to be applied";
                  }
                }
                description
                  "Instance filtering by VRF name regular expression";
              }
            }
          }
          container default {
            presence "Indicates a default node is configured.";
            description
              "Default template";
            leaf sample-size {
              type uint32 {
                range "1..60" {
                  description
                    "Number of samples";
                }
              }
              description
                "Number of samples to be taken";
            }
            leaf sample-interval {
              type uint32 {
                range "1..60" {
                  description
                    "Frequency of samples";
                }
              }
              description
                "Frequency of sampling in minutes";
            }
            container history-persistent {
              presence "Indicates a history-persistent node is configured.";
              description
                "Keep history statistics persistenly";
            }
            leaf regular-expression {
              type xr:Cisco-ios-xr-string {
                length "1..32" {
                  description
                    "Regular expression name to be applied";
                }
              }
              description
                "Instance filtering by regular expression";
            }
            leaf vrf-group {
              type xr:Cisco-ios-xr-string {
                length "1..32" {
                  description
                    "Regular expression name to be applied";
                }
              }
              description
                "Instance filtering by VRF name regular expression";
            }
          }
        }
      }
      container node {
        description
          "Configure statistics collection for node";
        container memory {
          description
            "Configure data collection for memory";
          container templates {
            description
              "Specify template";
            list template {
              key "template-name";
              description
                "Specify template";
              leaf template-name {
                type xr:Cisco-ios-xr-string {
                  length "1..800" {
                    description
                      "Template name";
                  }
                }
                description
                  "Specify template";
              }
              leaf sample-size {
                type uint32 {
                  range "1..60" {
                    description
                      "Number of samples";
                  }
                }
                description
                  "Number of samples to be taken";
              }
              leaf sample-interval {
                type uint32 {
                  range "1..60" {
                    description
                      "Frequency of samples";
                  }
                }
                description
                  "Frequency of each sample in minutes";
              }
              container history-persistent {
                presence "Indicates a history-persistent node is configured.";
                description
                  "Keep history statistics persistently";
              }
            }
          }
          container default {
            description
              "Default template";
            leaf sample-size {
              type uint32 {
                range "1..60" {
                  description
                    "Number of samples";
                }
              }
              description
                "Number of samples to be taken";
            }
            leaf sample-interval {
              type uint32 {
                range "1..60" {
                  description
                    "Frequency of samples";
                }
              }
              description
                "Frequency of each sample in minutes";
            }
            container history-persistent {
              presence "Indicates a history-persistent node is configured.";
              description
                "Keep history statistics persistently";
            }
          }
        }
        container cpu {
          description
            "Configure data collection for cpu";
          container templates {
            description
              "Specify template";
            list template {
              key "template-name";
              description
                "Specify template";
              leaf template-name {
                type xr:Cisco-ios-xr-string {
                  length "1..800" {
                    description
                      "Template name";
                  }
                }
                description
                  "Specify template";
              }
              leaf sample-size {
                type uint32 {
                  range "1..60" {
                    description
                      "Number of samples";
                  }
                }
                description
                  "Number of samples to be taken";
              }
              leaf sample-interval {
                type uint32 {
                  range "1..60" {
                    description
                      "Frequency of samples";
                  }
                }
                description
                  "Frequency of each sample in minutes";
              }
              container history-persistent {
                presence "Indicates a history-persistent node is configured.";
                description
                  "Keep history statistics persistently";
              }
            }
          }
          container default {
            presence "Indicates a default node is configured.";
            description
              "Default template";
            leaf sample-size {
              type uint32 {
                range "1..60" {
                  description
                    "Number of samples";
                }
              }
              description
                "Number of samples to be taken";
            }
            leaf sample-interval {
              type uint32 {
                range "1..60" {
                  description
                    "Frequency of samples";
                }
              }
              description
                "Frequency of each sample in minutes";
            }
            container history-persistent {
              presence "Indicates a history-persistent node is configured.";
              description
                "Keep history statistics persistently";
            }
          }
        }
        container process {
          description
            "Configure data collection for process";
          container templates {
            description
              "Specify template";
            list template {
              key "template-name";
              description
                "Specify template";
              leaf template-name {
                type xr:Cisco-ios-xr-string {
                  length "1..800" {
                    description
                      "Template name";
                  }
                }
                description
                  "Specify template";
              }
              leaf sample-size {
                type uint32 {
                  range "1..60" {
                    description
                      "Number of samples";
                  }
                }
                description
                  "Number of samples to be taken";
              }
              leaf sample-interval {
                type uint32 {
                  range "1..60" {
                    description
                      "Frequency of samples";
                  }
                }
                description
                  "Frequency of each sample in minutes";
              }
              container history-persistent {
                presence "Indicates a history-persistent node is configured.";
                description
                  "Keep history statistics persistently";
              }
            }
          }
          container default {
            presence "Indicates a default node is configured.";
            description
              "Default template";
            leaf sample-size {
              type uint32 {
                range "1..60" {
                  description
                    "Number of samples";
                }
              }
              description
                "Number of samples to be taken";
            }
            leaf sample-interval {
              type uint32 {
                range "1..60" {
                  description
                    "Frequency of samples";
                }
              }
              description
                "Frequency of each sample in minutes";
            }
            container history-persistent {
              presence "Indicates a history-persistent node is configured.";
              description
                "Keep history statistics persistently";
            }
          }
        }
      }
      container bgp {
        description
          "Configure statistics collection for bgp";
        container templates {
          description
            "Specify template";
          list template {
            key "template-name";
            description
              "Specify template";
            leaf template-name {
              type xr:Cisco-ios-xr-string {
                length "1..800" {
                  description
                    "Template name";
                }
              }
              description
                "Specify template";
            }
            leaf sample-size {
              type uint32 {
                range "1..60" {
                  description
                    "Number of samples";
                }
              }
              description
                "Number of samples to be taken";
            }
            leaf sample-interval {
              type uint32 {
                range "1..60" {
                  description
                    "frequency of samples";
                }
              }
              description
                "Frequency of each sample in minutes";
            }
            container history-persistent {
              presence "Indicates a history-persistent node is configured.";
              description
                "Keep history statistics persistently";
            }
          }
        }
        container default {
          presence "Indicates a default node is configured.";
          description
            "Default template";
          leaf sample-size {
            type uint32 {
              range "1..60" {
                description
                  "Number of samples";
              }
            }
            description
              "Number of samples to be taken";
          }
          leaf sample-interval {
            type uint32 {
              range "1..60" {
                description
                  "frequency of samples";
              }
            }
            description
              "Frequency of each sample in minutes";
          }
          container history-persistent {
            presence "Indicates a history-persistent node is configured.";
            description
              "Keep history statistics persistently";
          }
        }
      }
      container mpls {
        description
          "Configure statistics collection for mpls ";
        container ldp {
          description
            "Configure data collection for a mpls label distribution protocol";
          container templates {
            description
              "Specify template";
            list template {
              key "template-name";
              description
                "Specify template";
              leaf template-name {
                type xr:Cisco-ios-xr-string {
                  length "1..800" {
                    description
                      "Template name";
                  }
                }
                description
                  "Specify template";
              }
              leaf sample-size {
                type uint32 {
                  range "1..60" {
                    description
                      "Number of samples";
                  }
                }
                description
                  "Number of samples to be taken";
              }
              leaf sample-interval {
                type uint32 {
                  range "1..60" {
                    description
                      "Frequency of samples";
                  }
                }
                description
                  "Frequency of each sample in minutes";
              }
              container history-persistent {
                presence "Indicates a history-persistent node is configured.";
                description
                  "Keep history statistics persistently";
              }
              leaf vrf {
                type xr:Cisco-ios-xr-string {
                  length "1..32" {
                    description
                      "VRF name";
                  }
                }
                description
                  "Specify VRF name";
              }
            }
          }
          container default {
            presence "Indicates a default node is configured.";
            description
              "Default template";
            leaf sample-size {
              type uint32 {
                range "1..60" {
                  description
                    "Number of samples";
                }
              }
              description
                "Number of samples to be taken";
            }
            leaf sample-interval {
              type uint32 {
                range "1..60" {
                  description
                    "Frequency of samples";
                }
              }
              description
                "Frequency of each sample in minutes";
            }
            container history-persistent {
              presence "Indicates a history-persistent node is configured.";
              description
                "Keep history statistics persistently";
            }
            leaf vrf {
              type xr:Cisco-ios-xr-string {
                length "1..32" {
                  description
                    "VRF name";
                }
              }
              description
                "Specify VRF name";
            }
          }
        }
      }
      container ospf {
        description
          "Configure statistics collection for OSPF";
        container v2protocol {
          description
            "Configure data collection for v2 protocol";
          container templates {
            description
              "Specify template";
            list template {
              key "template-name";
              description
                "Specify template";
              leaf template-name {
                type xr:Cisco-ios-xr-string {
                  length "1..800" {
                    description
                      "Template name";
                  }
                }
                description
                  "Specify template";
              }
              leaf sample-size {
                type uint32 {
                  range "1..60" {
                    description
                      "Number of samples";
                  }
                }
                description
                  "Number of samples to be taken";
              }
              leaf sample-interval {
                type uint32 {
                  range "1..60" {
                    description
                      "Frequency of samples";
                  }
                }
                description
                  "Frequency of sampling in minutes";
              }
              container history-persistent {
                presence "Indicates a history-persistent node is configured.";
                description
                  "Keep history statistics persistently";
              }
            }
          }
          container default {
            presence "Indicates a default node is configured.";
            description
              "Default template";
            leaf sample-size {
              type uint32 {
                range "1..60" {
                  description
                    "Number of samples";
                }
              }
              description
                "Number of samples to be taken";
            }
            leaf sample-interval {
              type uint32 {
                range "1..60" {
                  description
                    "Frequency of samples";
                }
              }
              description
                "Frequency of sampling in minutes";
            }
            container history-persistent {
              presence "Indicates a history-persistent node is configured.";
              description
                "Keep history statistics persistently";
            }
          }
        }
        container v3protocol {
          description
            "Configure data collection for v3 protocol";
          container templates {
            description
              "Specify template";
            list template {
              key "template-name";
              description
                "Specify template";
              leaf template-name {
                type xr:Cisco-ios-xr-string {
                  length "1..800" {
                    description
                      "Template name";
                  }
                }
                description
                  "Specify template";
              }
              leaf sample-size {
                type uint32 {
                  range "1..60" {
                    description
                      "Number of samples";
                  }
                }
                description
                  "Number of samples to be taken";
              }
              leaf sample-interval {
                type uint32 {
                  range "1..60" {
                    description
                      "Frequency of samples";
                  }
                }
                description
                  "Frequency of sampling in minutes";
              }
              container history-persistent {
                presence "Indicates a history-persistent node is configured.";
                description
                  "Keep history statistics persistently";
              }
            }
          }
          container default {
            presence "Indicates a default node is configured.";
            description
              "Default template";
            leaf sample-size {
              type uint32 {
                range "1..60" {
                  description
                    "Number of samples";
                }
              }
              description
                "Number of samples to be taken";
            }
            leaf sample-interval {
              type uint32 {
                range "1..60" {
                  description
                    "Frequency of samples";
                }
              }
              description
                "Frequency of sampling in minutes";
            }
            container history-persistent {
              presence "Indicates a history-persistent node is configured.";
              description
                "Keep history statistics persistently";
            }
          }
        }
      }
    }
    container thresholds {
      description
        "Configure thresholds for collected data";
      container interface {
        description
          "Configure thresholds for interfaces";
        container basic-counters {
          description
            "Configure threshold attributes for basic counters";
          container templates {
            description
              "Specify template";
            list template {
              key "template-name";
              description
                "Specify template";
              leaf template-name {
                type xr:Cisco-ios-xr-string {
                  length "1..800" {
                    description
                      "Template name";
                  }
                }
                description
                  "Specify template";
              }
              leaf sample-interval {
                type uint32 {
                  range "1..60" {
                    description
                      "Frequency of samples";
                  }
                }
                description
                  "Frequency of sampling in minutes";
              }
              leaf regular-expression {
                type xr:Cisco-ios-xr-string {
                  length "1..32" {
                    description
                      "Regular expression name to be applied";
                  }
                }
                description
                  "Instance filtering by regular expression";
              }
              container in-packets {
                description
                  "Number of inbound packets";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container in-octets {
                description
                  "Number of inbound octets/bytes";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container out-packets {
                description
                  "Number of outbound packets";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container out-octets {
                description
                  "Number of outbound octets/bytes";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container input-total-drops {
                description
                  "Number of inbound correct packets discarded";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container input-queue-drops {
                description
                  "Number of input queue drops";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container input-total-errors {
                description
                  "Number of inbound incorrect packets discarded";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container output-total-drops {
                description
                  "Number of outbound correct packets discarded";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container output-queue-drops {
                description
                  "Number of input queue drops";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container output-total-errors {
                description
                  "Number of outbound incorrect packets discarded";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
            }
          }
          container default {
            presence "Indicates a default node is configured.";
            description
              "Default template";
            leaf sample-interval {
              type uint32 {
                range "1..60" {
                  description
                    "Frequency of samples";
                }
              }
              description
                "Frequency of sampling in minutes";
            }
            leaf regular-expression {
              type xr:Cisco-ios-xr-string {
                length "1..32" {
                  description
                    "Regular expression name to be applied";
                }
              }
              description
                "Instance filtering by regular expression";
            }
            container in-packets {
              description
                "Number of inbound packets";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container in-octets {
              description
                "Number of inbound octets/bytes";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container out-packets {
              description
                "Number of outbound packets";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container out-octets {
              description
                "Number of outbound octets/bytes";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container input-total-drops {
              description
                "Number of inbound correct packets discarded";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container input-queue-drops {
              description
                "Number of input queue drops";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container input-total-errors {
              description
                "Number of inbound incorrect packets discarded";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container output-total-drops {
              description
                "Number of outbound correct packets discarded";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container output-queue-drops {
              description
                "Number of input queue drops";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container output-total-errors {
              description
                "Number of outbound incorrect packets discarded";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
          }
        }
        container generic-counters {
          description
            "Configure threshold attributes for generic counters";
          container templates {
            description
              "Specify template";
            list template {
              key "template-name";
              description
                "Specify template";
              leaf template-name {
                type xr:Cisco-ios-xr-string {
                  length "1..800" {
                    description
                      "Template name";
                  }
                }
                description
                  "Specify template";
              }
              leaf sample-interval {
                type uint32 {
                  range "1..60" {
                    description
                      "Frequency of samples";
                  }
                }
                description
                  "Frequency of sampling in minutes";
              }
              leaf regular-expression {
                type xr:Cisco-ios-xr-string {
                  length "1..32" {
                    description
                      "Regular expression name to be applied";
                  }
                }
                description
                  "Instance filtering by regular expression";
              }
              leaf vrf-group {
                type xr:Cisco-ios-xr-string {
                  length "1..32" {
                    description
                      "Regular expression name to be applied";
                  }
                }
                description
                  "Instance filtering by VRF name regular expression";
              }
              container in-packets {
                description
                  "Number of inbound packets";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container in-octets {
                description
                  "Number of inbound octets/bytes";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container out-packets {
                description
                  "Number of outbound packets";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container out-octets {
                description
                  "Number of outbound octets/bytes";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container in-ucast-pkts {
                description
                  "Number of inbound unicast packets";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container in-multicast-pkts {
                description
                  "Number of inbound multicast packets";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container in-broadcast-pkts {
                description
                  "Number of inbound broadcast packets";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container out-ucast-pkts {
                description
                  "Number of outbound unicast packets";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container out-multicast-pkts {
                description
                  "Number of outbound multicast packets";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container out-broadcast-pkts {
                description
                  "Number of outbound broadcast packets";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container output-total-drops {
                description
                  "Number of outbound correct packets discarded";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container input-total-drops {
                description
                  "Number of inbound correct packets discarded";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container input-queue-drops {
                description
                  "Number of input queue drops";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container input-unknown-proto {
                description
                  "Number of inbound packets discarded with unknown protocol";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container output-total-errors {
                description
                  "Number of outbound incorrect packets discarded";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container output-under-run {
                description
                  "Number of outbound packets with underrun errors";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container input-total-errors {
                description
                  "Number of inbound incorrect packets discarded";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container input-crc {
                description
                  "Number of inbound packets discarded with incorrect CRC";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container input-over-run {
                description
                  "Number of inbound packets with overrun errors";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container input-frame {
                description
                  "Number of inbound packets with framing errors";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
            }
          }
          container default {
            presence "Indicates a default node is configured.";
            description
              "Default template";
            leaf sample-interval {
              type uint32 {
                range "1..60" {
                  description
                    "Frequency of samples";
                }
              }
              description
                "Frequency of sampling in minutes";
            }
            leaf regular-expression {
              type xr:Cisco-ios-xr-string {
                length "1..32" {
                  description
                    "Regular expression name to be applied";
                }
              }
              description
                "Instance filtering by regular expression";
            }
            leaf vrf-group {
              type xr:Cisco-ios-xr-string {
                length "1..32" {
                  description
                    "Regular expression name to be applied";
                }
              }
              description
                "Instance filtering by VRF name regular expression";
            }
            container in-packets {
              description
                "Number of inbound packets";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container in-octets {
              description
                "Number of inbound octets/bytes";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container out-packets {
              description
                "Number of outbound packets";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container out-octets {
              description
                "Number of outbound octets/bytes";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container in-ucast-pkts {
              description
                "Number of inbound unicast packets";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container in-multicast-pkts {
              description
                "Number of inbound multicast packets";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container in-broadcast-pkts {
              description
                "Number of inbound broadcast packets";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container out-ucast-pkts {
              description
                "Number of outbound unicast packets";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container out-multicast-pkts {
              description
                "Number of outbound multicast packets";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container out-broadcast-pkts {
              description
                "Number of outbound broadcast packets";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container output-total-drops {
              description
                "Number of outbound correct packets discarded";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container input-total-drops {
              description
                "Number of inbound correct packets discarded";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container input-queue-drops {
              description
                "Number of input queue drops";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container input-unknown-proto {
              description
                "Number of inbound packets discarded with unknown protocol";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container output-total-errors {
              description
                "Number of outbound incorrect packets discarded";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container output-under-run {
              description
                "Number of outbound packets with underrun errors";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container input-total-errors {
              description
                "Number of inbound incorrect packets discarded";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container input-crc {
              description
                "Number of inbound packets discarded with incorrect CRC";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container input-over-run {
              description
                "Number of inbound packets with overrun errors";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container input-frame {
              description
                "Number of inbound packets with framing errors";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
          }
        }
        container data-rates {
          description
            "Configure threshold attributes for data rates";
          container templates {
            description
              "Specify template";
            list template {
              key "template-name";
              description
                "Specify template";
              leaf template-name {
                type xr:Cisco-ios-xr-string {
                  length "1..800" {
                    description
                      "Template name";
                  }
                }
                description
                  "Specify template";
              }
              leaf sample-interval {
                type uint32 {
                  range "1..60" {
                    description
                      "Frequency of samples";
                  }
                }
                description
                  "Frequency of sampling in minutes";
              }
              leaf regular-expression {
                type xr:Cisco-ios-xr-string {
                  length "1..32" {
                    description
                      "Regular expression name to be applied";
                  }
                }
                description
                  "Instance filtering by regular expression";
              }
              leaf vrf-group {
                type xr:Cisco-ios-xr-string {
                  length "1..32" {
                    description
                      "Regular expression name to be applied";
                  }
                }
                description
                  "Instance filtering by VRF name regular expression";
              }
              container input-data-rate {
                description
                  "Input data rate in kbps";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container output-data-rate {
                description
                  "Output data rate in kbps";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container input-packet-rate {
                description
                  "Number of input packets per second";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container output-packet-rate {
                description
                  "Number of Output packets per second";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container input-peak-rate {
                description
                  "Peak input data rate in kbps";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container output-peak-rate {
                description
                  "Peak output data rate in kbps";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container input-peak-pkts {
                description
                  "Maximum number of input packets per second";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container output-peak-pkts {
                description
                  "Maximum number of output packets per second";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container bandwidth {
                description
                  "Bandwidth in kbps";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
            }
          }
          container default {
            description
              "Default template";
            leaf sample-interval {
              type uint32 {
                range "1..60" {
                  description
                    "Frequency of samples";
                }
              }
              description
                "Frequency of sampling in minutes";
            }
            leaf regular-expression {
              type xr:Cisco-ios-xr-string {
                length "1..32" {
                  description
                    "Regular expression name to be applied";
                }
              }
              description
                "Instance filtering by regular expression";
            }
            leaf vrf-group {
              type xr:Cisco-ios-xr-string {
                length "1..32" {
                  description
                    "Regular expression name to be applied";
                }
              }
              description
                "Instance filtering by VRF name regular expression";
            }
            container input-data-rate {
              description
                "Input data rate in kbps";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container output-data-rate {
              description
                "Output data rate in kbps";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container input-packet-rate {
              description
                "Number of input packets per second";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container output-packet-rate {
              description
                "Number of Output packets per second";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container input-peak-rate {
              description
                "Peak input data rate in kbps";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container output-peak-rate {
              description
                "Peak output data rate in kbps";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container input-peak-pkts {
              description
                "Maximum number of input packets per second";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container output-peak-pkts {
              description
                "Maximum number of output packets per second";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container bandwidth {
              description
                "Bandwidth in kbps";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
          }
        }
      }
      container node {
        description
          "Configure thresholds for node";
        container memory {
          description
            "Configure thresholds for memory";
          container templates {
            description
              "Specify template";
            list template {
              key "template-name";
              description
                "Specify template";
              leaf template-name {
                type xr:Cisco-ios-xr-string {
                  length "1..800" {
                    description
                      "Template name";
                  }
                }
                description
                  "Specify template";
              }
              leaf sample-interval {
                type uint32 {
                  range "1..60" {
                    description
                      "Frequency of samples";
                  }
                }
                description
                  "Frequency of sampling in minutes";
              }
              container curr-memory {
                description
                  "Current memory (Bytes) in use";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container peak-memory {
                description
                  "Maximum memory (KBytes) used";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
            }
          }
          container default {
            presence "Indicates a default node is configured.";
            description
              "Default template";
            leaf sample-interval {
              type uint32 {
                range "1..60" {
                  description
                    "Frequency of samples";
                }
              }
              description
                "Frequency of sampling in minutes";
            }
            container curr-memory {
              description
                "Current memory (Bytes) in use";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container peak-memory {
              description
                "Maximum memory (KBytes) used";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
          }
        }
        container cpu {
          description
            "Configure thresholds for cpu";
          container templates {
            description
              "Specify template";
            list template {
              key "template-name";
              description
                "Specify template";
              leaf template-name {
                type xr:Cisco-ios-xr-string {
                  length "1..800" {
                    description
                      "Template name";
                  }
                }
                description
                  "Specify template";
              }
              leaf sample-interval {
                type uint32 {
                  range "1..60" {
                    description
                      "Frequency of samples";
                  }
                }
                description
                  "Frequency of sampling in minutes";
              }
              container no-processes {
                description
                  "Number of processes";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container average-cpu-used {
                description
                  "Average %CPU utilization";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
            }
          }
          container default {
            presence "Indicates a default node is configured.";
            description
              "Default template";
            leaf sample-interval {
              type uint32 {
                range "1..60" {
                  description
                    "Frequency of samples";
                }
              }
              description
                "Frequency of sampling in minutes";
            }
            container no-processes {
              description
                "Number of processes";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container average-cpu-used {
              description
                "Average %CPU utilization";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
          }
        }
        container process {
          description
            "Configure thresholds for process";
          container templates {
            description
              "Specify template";
            list template {
              key "template-name";
              description
                "Specify template";
              leaf template-name {
                type xr:Cisco-ios-xr-string {
                  length "1..800" {
                    description
                      "Template name";
                  }
                }
                description
                  "Specify template";
              }
              leaf sample-interval {
                type uint32 {
                  range "1..60" {
                    description
                      "Frequency of samples";
                  }
                }
                description
                  "Frequency of sampling in minutes";
              }
              container average-cpuused {
                description
                  "Average %CPU utilization";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container peak-memory {
                description
                  "Max. memory (KBytes) used since startup time";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container num-threads {
                description
                  "Number of threads";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
            }
          }
          container default {
            presence "Indicates a default node is configured.";
            description
              "Default template";
            leaf sample-interval {
              type uint32 {
                range "1..60" {
                  description
                    "Frequency of samples";
                }
              }
              description
                "Frequency of sampling in minutes";
            }
            container average-cpuused {
              description
                "Average %CPU utilization";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container peak-memory {
              description
                "Max. memory (KBytes) used since startup time";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container num-threads {
              description
                "Number of threads";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
          }
        }
      }
      container bgp {
        description
          "Configure thresholds for bgp";
        container templates {
          description
            "Specify template";
          list template {
            key "template-name";
            description
              "Specify template";
            leaf template-name {
              type xr:Cisco-ios-xr-string {
                length "1..800" {
                  description
                    "Template name";
                }
              }
              description
                "Specify template";
            }
            leaf sample-interval {
              type uint32 {
                range "1..60" {
                  description
                    "Frequency of samples";
                }
              }
              description
                "Frequency of sampling in minutes";
            }
            container input-messages {
              description
                "Number of messages received";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container output-messages {
              description
                "Number of messages sent";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container input-update-messages {
              description
                "Number of update messages received";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container output-update-messages {
              description
                "Number of update messages sent";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container conn-established {
              description
                "Number of times the connection was established";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container errors-received {
              description
                "Number of error notifications received";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container errors-sent {
              description
                "Number of error notifications sent";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container connection-drops {
              description
                "Number of times the connection was dropped";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
          }
        }
        container default {
          presence "Indicates a default node is configured.";
          description
            "Default template";
          leaf sample-interval {
            type uint32 {
              range "1..60" {
                description
                  "Frequency of samples";
              }
            }
            description
              "Frequency of sampling in minutes";
          }
          container input-messages {
            description
              "Number of messages received";
            container percent {
              presence "Indicates a percent node is configured.";
              description
                "Specify that threshold value is percent of previous sample";
            }
            container rearm {
              description
                "Specify Rearm parameters (default - always)";
              container toggle {
                must "not(../window)";
                presence "Indicates a toggle node is configured.";
                description
                  "Rearm after the first period when condition is not met";
              }
              leaf window {
                type uint32 {
                  range "1..100" {
                    description
                      "Rearm window size";
                  }
                }
                must "not(../toggle)";
                description
                  "Rearm after the window of sampling periods";
              }
            }
            container eq {
              presence "Indicates the node is configured.";
              description
                "Equal to";
              leaf threshold-value {
                type uint32 {
                  range "0..4294967295" {
                    description
                      "Threshold value";
                  }
                }
                mandatory true;
                description
                  "Threshold value";
              }
            }
            container ne {
              presence "Indicates the node is configured.";
              description
                "Not equal to";
              leaf threshold-value {
                type uint32 {
                  range "0..4294967295" {
                    description
                      "Threshold value";
                  }
                }
                mandatory true;
                description
                  "Threshold value";
              }
            }
            container lt {
              presence "Indicates the node is configured.";
              description
                "Less than";
              leaf threshold-value {
                type uint32 {
                  range "0..4294967295" {
                    description
                      "Threshold value";
                  }
                }
                mandatory true;
                description
                  "Threshold value";
              }
            }
            container le {
              presence "Indicates the node is configured.";
              description
                "Less than or equal to";
              leaf threshold-value {
                type uint32 {
                  range "0..4294967295" {
                    description
                      "Threshold value";
                  }
                }
                mandatory true;
                description
                  "Threshold value";
              }
            }
            container gt {
              presence "Indicates the node is configured.";
              description
                "Greater than";
              leaf threshold-value {
                type uint32 {
                  range "0..4294967295" {
                    description
                      "Threshold value";
                  }
                }
                mandatory true;
                description
                  "Threshold value";
              }
            }
            container ge {
              presence "Indicates the node is configured.";
              description
                "Greater than or equal to";
              leaf threshold-value {
                type uint32 {
                  range "0..4294967295" {
                    description
                      "Threshold value";
                  }
                }
                mandatory true;
                description
                  "Threshold value";
              }
            }
            container rg {
              presence "Indicates the node is configured.";
              description
                "Not in range";
              leaf start-threshold-value {
                type uint32 {
                  range "0..4294967295" {
                    description
                      "Threshold value";
                  }
                }
                mandatory true;
                description
                  "Threshold value";
              }
              leaf end-threshold-value {
                type uint32 {
                  range "0..4294967295" {
                    description
                      "Threshold value";
                  }
                }
                mandatory true;
                description
                  "Threshold value";
              }
            }
          }
          container output-messages {
            description
              "Number of messages sent";
            container percent {
              presence "Indicates a percent node is configured.";
              description
                "Specify that threshold value is percent of previous sample";
            }
            container rearm {
              description
                "Specify Rearm parameters (default - always)";
              container toggle {
                must "not(../window)";
                presence "Indicates a toggle node is configured.";
                description
                  "Rearm after the first period when condition is not met";
              }
              leaf window {
                type uint32 {
                  range "1..100" {
                    description
                      "Rearm window size";
                  }
                }
                must "not(../toggle)";
                description
                  "Rearm after the window of sampling periods";
              }
            }
            container eq {
              presence "Indicates the node is configured.";
              description
                "Equal to";
              leaf threshold-value {
                type uint32 {
                  range "0..4294967295" {
                    description
                      "Threshold value";
                  }
                }
                mandatory true;
                description
                  "Threshold value";
              }
            }
            container ne {
              presence "Indicates the node is configured.";
              description
                "Not equal to";
              leaf threshold-value {
                type uint32 {
                  range "0..4294967295" {
                    description
                      "Threshold value";
                  }
                }
                mandatory true;
                description
                  "Threshold value";
              }
            }
            container lt {
              presence "Indicates the node is configured.";
              description
                "Less than";
              leaf threshold-value {
                type uint32 {
                  range "0..4294967295" {
                    description
                      "Threshold value";
                  }
                }
                mandatory true;
                description
                  "Threshold value";
              }
            }
            container le {
              presence "Indicates the node is configured.";
              description
                "Less than or equal to";
              leaf threshold-value {
                type uint32 {
                  range "0..4294967295" {
                    description
                      "Threshold value";
                  }
                }
                mandatory true;
                description
                  "Threshold value";
              }
            }
            container gt {
              presence "Indicates the node is configured.";
              description
                "Greater than";
              leaf threshold-value {
                type uint32 {
                  range "0..4294967295" {
                    description
                      "Threshold value";
                  }
                }
                mandatory true;
                description
                  "Threshold value";
              }
            }
            container ge {
              presence "Indicates the node is configured.";
              description
                "Greater than or equal to";
              leaf threshold-value {
                type uint32 {
                  range "0..4294967295" {
                    description
                      "Threshold value";
                  }
                }
                mandatory true;
                description
                  "Threshold value";
              }
            }
            container rg {
              presence "Indicates the node is configured.";
              description
                "Not in range";
              leaf start-threshold-value {
                type uint32 {
                  range "0..4294967295" {
                    description
                      "Threshold value";
                  }
                }
                mandatory true;
                description
                  "Threshold value";
              }
              leaf end-threshold-value {
                type uint32 {
                  range "0..4294967295" {
                    description
                      "Threshold value";
                  }
                }
                mandatory true;
                description
                  "Threshold value";
              }
            }
          }
          container input-update-messages {
            description
              "Number of update messages received";
            container percent {
              presence "Indicates a percent node is configured.";
              description
                "Specify that threshold value is percent of previous sample";
            }
            container rearm {
              description
                "Specify Rearm parameters (default - always)";
              container toggle {
                must "not(../window)";
                presence "Indicates a toggle node is configured.";
                description
                  "Rearm after the first period when condition is not met";
              }
              leaf window {
                type uint32 {
                  range "1..100" {
                    description
                      "Rearm window size";
                  }
                }
                must "not(../toggle)";
                description
                  "Rearm after the window of sampling periods";
              }
            }
            container eq {
              presence "Indicates the node is configured.";
              description
                "Equal to";
              leaf threshold-value {
                type uint32 {
                  range "0..4294967295" {
                    description
                      "Threshold value";
                  }
                }
                mandatory true;
                description
                  "Threshold value";
              }
            }
            container ne {
              presence "Indicates the node is configured.";
              description
                "Not equal to";
              leaf threshold-value {
                type uint32 {
                  range "0..4294967295" {
                    description
                      "Threshold value";
                  }
                }
                mandatory true;
                description
                  "Threshold value";
              }
            }
            container lt {
              presence "Indicates the node is configured.";
              description
                "Less than";
              leaf threshold-value {
                type uint32 {
                  range "0..4294967295" {
                    description
                      "Threshold value";
                  }
                }
                mandatory true;
                description
                  "Threshold value";
              }
            }
            container le {
              presence "Indicates the node is configured.";
              description
                "Less than or equal to";
              leaf threshold-value {
                type uint32 {
                  range "0..4294967295" {
                    description
                      "Threshold value";
                  }
                }
                mandatory true;
                description
                  "Threshold value";
              }
            }
            container gt {
              presence "Indicates the node is configured.";
              description
                "Greater than";
              leaf threshold-value {
                type uint32 {
                  range "0..4294967295" {
                    description
                      "Threshold value";
                  }
                }
                mandatory true;
                description
                  "Threshold value";
              }
            }
            container ge {
              presence "Indicates the node is configured.";
              description
                "Greater than or equal to";
              leaf threshold-value {
                type uint32 {
                  range "0..4294967295" {
                    description
                      "Threshold value";
                  }
                }
                mandatory true;
                description
                  "Threshold value";
              }
            }
            container rg {
              presence "Indicates the node is configured.";
              description
                "Not in range";
              leaf start-threshold-value {
                type uint32 {
                  range "0..4294967295" {
                    description
                      "Threshold value";
                  }
                }
                mandatory true;
                description
                  "Threshold value";
              }
              leaf end-threshold-value {
                type uint32 {
                  range "0..4294967295" {
                    description
                      "Threshold value";
                  }
                }
                mandatory true;
                description
                  "Threshold value";
              }
            }
          }
          container output-update-messages {
            description
              "Number of update messages sent";
            container percent {
              presence "Indicates a percent node is configured.";
              description
                "Specify that threshold value is percent of previous sample";
            }
            container rearm {
              description
                "Specify Rearm parameters (default - always)";
              container toggle {
                must "not(../window)";
                presence "Indicates a toggle node is configured.";
                description
                  "Rearm after the first period when condition is not met";
              }
              leaf window {
                type uint32 {
                  range "1..100" {
                    description
                      "Rearm window size";
                  }
                }
                must "not(../toggle)";
                description
                  "Rearm after the window of sampling periods";
              }
            }
            container eq {
              presence "Indicates the node is configured.";
              description
                "Equal to";
              leaf threshold-value {
                type uint32 {
                  range "0..4294967295" {
                    description
                      "Threshold value";
                  }
                }
                mandatory true;
                description
                  "Threshold value";
              }
            }
            container ne {
              presence "Indicates the node is configured.";
              description
                "Not equal to";
              leaf threshold-value {
                type uint32 {
                  range "0..4294967295" {
                    description
                      "Threshold value";
                  }
                }
                mandatory true;
                description
                  "Threshold value";
              }
            }
            container lt {
              presence "Indicates the node is configured.";
              description
                "Less than";
              leaf threshold-value {
                type uint32 {
                  range "0..4294967295" {
                    description
                      "Threshold value";
                  }
                }
                mandatory true;
                description
                  "Threshold value";
              }
            }
            container le {
              presence "Indicates the node is configured.";
              description
                "Less than or equal to";
              leaf threshold-value {
                type uint32 {
                  range "0..4294967295" {
                    description
                      "Threshold value";
                  }
                }
                mandatory true;
                description
                  "Threshold value";
              }
            }
            container gt {
              presence "Indicates the node is configured.";
              description
                "Greater than";
              leaf threshold-value {
                type uint32 {
                  range "0..4294967295" {
                    description
                      "Threshold value";
                  }
                }
                mandatory true;
                description
                  "Threshold value";
              }
            }
            container ge {
              presence "Indicates the node is configured.";
              description
                "Greater than or equal to";
              leaf threshold-value {
                type uint32 {
                  range "0..4294967295" {
                    description
                      "Threshold value";
                  }
                }
                mandatory true;
                description
                  "Threshold value";
              }
            }
            container rg {
              presence "Indicates the node is configured.";
              description
                "Not in range";
              leaf start-threshold-value {
                type uint32 {
                  range "0..4294967295" {
                    description
                      "Threshold value";
                  }
                }
                mandatory true;
                description
                  "Threshold value";
              }
              leaf end-threshold-value {
                type uint32 {
                  range "0..4294967295" {
                    description
                      "Threshold value";
                  }
                }
                mandatory true;
                description
                  "Threshold value";
              }
            }
          }
          container conn-established {
            description
              "Number of times the connection was established";
            container percent {
              presence "Indicates a percent node is configured.";
              description
                "Specify that threshold value is percent of previous sample";
            }
            container rearm {
              description
                "Specify Rearm parameters (default - always)";
              container toggle {
                must "not(../window)";
                presence "Indicates a toggle node is configured.";
                description
                  "Rearm after the first period when condition is not met";
              }
              leaf window {
                type uint32 {
                  range "1..100" {
                    description
                      "Rearm window size";
                  }
                }
                must "not(../toggle)";
                description
                  "Rearm after the window of sampling periods";
              }
            }
            container eq {
              presence "Indicates the node is configured.";
              description
                "Equal to";
              leaf threshold-value {
                type uint32 {
                  range "0..4294967295" {
                    description
                      "Threshold value";
                  }
                }
                mandatory true;
                description
                  "Threshold value";
              }
            }
            container ne {
              presence "Indicates the node is configured.";
              description
                "Not equal to";
              leaf threshold-value {
                type uint32 {
                  range "0..4294967295" {
                    description
                      "Threshold value";
                  }
                }
                mandatory true;
                description
                  "Threshold value";
              }
            }
            container lt {
              presence "Indicates the node is configured.";
              description
                "Less than";
              leaf threshold-value {
                type uint32 {
                  range "0..4294967295" {
                    description
                      "Threshold value";
                  }
                }
                mandatory true;
                description
                  "Threshold value";
              }
            }
            container le {
              presence "Indicates the node is configured.";
              description
                "Less than or equal to";
              leaf threshold-value {
                type uint32 {
                  range "0..4294967295" {
                    description
                      "Threshold value";
                  }
                }
                mandatory true;
                description
                  "Threshold value";
              }
            }
            container gt {
              presence "Indicates the node is configured.";
              description
                "Greater than";
              leaf threshold-value {
                type uint32 {
                  range "0..4294967295" {
                    description
                      "Threshold value";
                  }
                }
                mandatory true;
                description
                  "Threshold value";
              }
            }
            container ge {
              presence "Indicates the node is configured.";
              description
                "Greater than or equal to";
              leaf threshold-value {
                type uint32 {
                  range "0..4294967295" {
                    description
                      "Threshold value";
                  }
                }
                mandatory true;
                description
                  "Threshold value";
              }
            }
            container rg {
              presence "Indicates the node is configured.";
              description
                "Not in range";
              leaf start-threshold-value {
                type uint32 {
                  range "0..4294967295" {
                    description
                      "Threshold value";
                  }
                }
                mandatory true;
                description
                  "Threshold value";
              }
              leaf end-threshold-value {
                type uint32 {
                  range "0..4294967295" {
                    description
                      "Threshold value";
                  }
                }
                mandatory true;
                description
                  "Threshold value";
              }
            }
          }
          container errors-received {
            description
              "Number of error notifications received";
            container percent {
              presence "Indicates a percent node is configured.";
              description
                "Specify that threshold value is percent of previous sample";
            }
            container rearm {
              description
                "Specify Rearm parameters (default - always)";
              container toggle {
                must "not(../window)";
                presence "Indicates a toggle node is configured.";
                description
                  "Rearm after the first period when condition is not met";
              }
              leaf window {
                type uint32 {
                  range "1..100" {
                    description
                      "Rearm window size";
                  }
                }
                must "not(../toggle)";
                description
                  "Rearm after the window of sampling periods";
              }
            }
            container eq {
              presence "Indicates the node is configured.";
              description
                "Equal to";
              leaf threshold-value {
                type uint32 {
                  range "0..4294967295" {
                    description
                      "Threshold value";
                  }
                }
                mandatory true;
                description
                  "Threshold value";
              }
            }
            container ne {
              presence "Indicates the node is configured.";
              description
                "Not equal to";
              leaf threshold-value {
                type uint32 {
                  range "0..4294967295" {
                    description
                      "Threshold value";
                  }
                }
                mandatory true;
                description
                  "Threshold value";
              }
            }
            container lt {
              presence "Indicates the node is configured.";
              description
                "Less than";
              leaf threshold-value {
                type uint32 {
                  range "0..4294967295" {
                    description
                      "Threshold value";
                  }
                }
                mandatory true;
                description
                  "Threshold value";
              }
            }
            container le {
              presence "Indicates the node is configured.";
              description
                "Less than or equal to";
              leaf threshold-value {
                type uint32 {
                  range "0..4294967295" {
                    description
                      "Threshold value";
                  }
                }
                mandatory true;
                description
                  "Threshold value";
              }
            }
            container gt {
              presence "Indicates the node is configured.";
              description
                "Greater than";
              leaf threshold-value {
                type uint32 {
                  range "0..4294967295" {
                    description
                      "Threshold value";
                  }
                }
                mandatory true;
                description
                  "Threshold value";
              }
            }
            container ge {
              presence "Indicates the node is configured.";
              description
                "Greater than or equal to";
              leaf threshold-value {
                type uint32 {
                  range "0..4294967295" {
                    description
                      "Threshold value";
                  }
                }
                mandatory true;
                description
                  "Threshold value";
              }
            }
            container rg {
              presence "Indicates the node is configured.";
              description
                "Not in range";
              leaf start-threshold-value {
                type uint32 {
                  range "0..4294967295" {
                    description
                      "Threshold value";
                  }
                }
                mandatory true;
                description
                  "Threshold value";
              }
              leaf end-threshold-value {
                type uint32 {
                  range "0..4294967295" {
                    description
                      "Threshold value";
                  }
                }
                mandatory true;
                description
                  "Threshold value";
              }
            }
          }
          container errors-sent {
            description
              "Number of error notifications sent";
            container percent {
              presence "Indicates a percent node is configured.";
              description
                "Specify that threshold value is percent of previous sample";
            }
            container rearm {
              description
                "Specify Rearm parameters (default - always)";
              container toggle {
                must "not(../window)";
                presence "Indicates a toggle node is configured.";
                description
                  "Rearm after the first period when condition is not met";
              }
              leaf window {
                type uint32 {
                  range "1..100" {
                    description
                      "Rearm window size";
                  }
                }
                must "not(../toggle)";
                description
                  "Rearm after the window of sampling periods";
              }
            }
            container eq {
              presence "Indicates the node is configured.";
              description
                "Equal to";
              leaf threshold-value {
                type uint32 {
                  range "0..4294967295" {
                    description
                      "Threshold value";
                  }
                }
                mandatory true;
                description
                  "Threshold value";
              }
            }
            container ne {
              presence "Indicates the node is configured.";
              description
                "Not equal to";
              leaf threshold-value {
                type uint32 {
                  range "0..4294967295" {
                    description
                      "Threshold value";
                  }
                }
                mandatory true;
                description
                  "Threshold value";
              }
            }
            container lt {
              presence "Indicates the node is configured.";
              description
                "Less than";
              leaf threshold-value {
                type uint32 {
                  range "0..4294967295" {
                    description
                      "Threshold value";
                  }
                }
                mandatory true;
                description
                  "Threshold value";
              }
            }
            container le {
              presence "Indicates the node is configured.";
              description
                "Less than or equal to";
              leaf threshold-value {
                type uint32 {
                  range "0..4294967295" {
                    description
                      "Threshold value";
                  }
                }
                mandatory true;
                description
                  "Threshold value";
              }
            }
            container gt {
              presence "Indicates the node is configured.";
              description
                "Greater than";
              leaf threshold-value {
                type uint32 {
                  range "0..4294967295" {
                    description
                      "Threshold value";
                  }
                }
                mandatory true;
                description
                  "Threshold value";
              }
            }
            container ge {
              presence "Indicates the node is configured.";
              description
                "Greater than or equal to";
              leaf threshold-value {
                type uint32 {
                  range "0..4294967295" {
                    description
                      "Threshold value";
                  }
                }
                mandatory true;
                description
                  "Threshold value";
              }
            }
            container rg {
              presence "Indicates the node is configured.";
              description
                "Not in range";
              leaf start-threshold-value {
                type uint32 {
                  range "0..4294967295" {
                    description
                      "Threshold value";
                  }
                }
                mandatory true;
                description
                  "Threshold value";
              }
              leaf end-threshold-value {
                type uint32 {
                  range "0..4294967295" {
                    description
                      "Threshold value";
                  }
                }
                mandatory true;
                description
                  "Threshold value";
              }
            }
          }
          container connection-drops {
            description
              "Number of times the connection was dropped";
            container percent {
              presence "Indicates a percent node is configured.";
              description
                "Specify that threshold value is percent of previous sample";
            }
            container rearm {
              description
                "Specify Rearm parameters (default - always)";
              container toggle {
                must "not(../window)";
                presence "Indicates a toggle node is configured.";
                description
                  "Rearm after the first period when condition is not met";
              }
              leaf window {
                type uint32 {
                  range "1..100" {
                    description
                      "Rearm window size";
                  }
                }
                must "not(../toggle)";
                description
                  "Rearm after the window of sampling periods";
              }
            }
            container eq {
              presence "Indicates the node is configured.";
              description
                "Equal to";
              leaf threshold-value {
                type uint32 {
                  range "0..4294967295" {
                    description
                      "Threshold value";
                  }
                }
                mandatory true;
                description
                  "Threshold value";
              }
            }
            container ne {
              presence "Indicates the node is configured.";
              description
                "Not equal to";
              leaf threshold-value {
                type uint32 {
                  range "0..4294967295" {
                    description
                      "Threshold value";
                  }
                }
                mandatory true;
                description
                  "Threshold value";
              }
            }
            container lt {
              presence "Indicates the node is configured.";
              description
                "Less than";
              leaf threshold-value {
                type uint32 {
                  range "0..4294967295" {
                    description
                      "Threshold value";
                  }
                }
                mandatory true;
                description
                  "Threshold value";
              }
            }
            container le {
              presence "Indicates the node is configured.";
              description
                "Less than or equal to";
              leaf threshold-value {
                type uint32 {
                  range "0..4294967295" {
                    description
                      "Threshold value";
                  }
                }
                mandatory true;
                description
                  "Threshold value";
              }
            }
            container gt {
              presence "Indicates the node is configured.";
              description
                "Greater than";
              leaf threshold-value {
                type uint32 {
                  range "0..4294967295" {
                    description
                      "Threshold value";
                  }
                }
                mandatory true;
                description
                  "Threshold value";
              }
            }
            container ge {
              presence "Indicates the node is configured.";
              description
                "Greater than or equal to";
              leaf threshold-value {
                type uint32 {
                  range "0..4294967295" {
                    description
                      "Threshold value";
                  }
                }
                mandatory true;
                description
                  "Threshold value";
              }
            }
            container rg {
              presence "Indicates the node is configured.";
              description
                "Not in range";
              leaf start-threshold-value {
                type uint32 {
                  range "0..4294967295" {
                    description
                      "Threshold value";
                  }
                }
                mandatory true;
                description
                  "Threshold value";
              }
              leaf end-threshold-value {
                type uint32 {
                  range "0..4294967295" {
                    description
                      "Threshold value";
                  }
                }
                mandatory true;
                description
                  "Threshold value";
              }
            }
          }
        }
      }
      container mpls {
        description
          "Configure thresholds for MPLS";
        container ldp {
          description
            "Configure thresholds for mpls label distribution protocol";
          container templates {
            description
              "Specify template";
            list template {
              key "template-name";
              description
                "Specify template";
              leaf template-name {
                type xr:Cisco-ios-xr-string {
                  length "1..800" {
                    description
                      "Template name";
                  }
                }
                description
                  "Specify template";
              }
              leaf sample-interval {
                type uint32 {
                  range "1..60" {
                    description
                      "Frequency of samples";
                  }
                }
                description
                  "Frequency of sampling in minutes";
              }
              container total-msgs-sent {
                description
                  "Total number of messages sent";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container total-msgs-rcvd {
                description
                  "Total number of messages received";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container init-msgs-sent {
                description
                  "Number of Init messages sent";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container init-msgs-rcvd {
                description
                  "Number of Init messages received";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container address-msgs-sent {
                description
                  "Number of Address messages sent";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container address-msgs-rcvd {
                description
                  "Number of Address messages received";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container address-withdraw-msgs-sent {
                description
                  "Number of Address Withdraw messages sent";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container address-withdraw-msgs-rcvd {
                description
                  "Number of Address Withdraw messages received";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container label-mapping-msgs-sent {
                description
                  "Number of Label Mapping messages sent";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container label-mapping-msgs-rcvd {
                description
                  "Number of Label Mapping messages received";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container label-withdraw-msgs-sent {
                description
                  "Number of Label Withdraw messages sent";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container label-withdraw-msgs-rcvd {
                description
                  "Number of Label Withdraw messages received";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container label-release-msgs-sent {
                description
                  "Number of Label Release messages sent";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container label-release-msgs-rcvd {
                description
                  "Number of LAbel Release messages received";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container notification-msgs-sent {
                description
                  "Number of Notification messages sent";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container notification-msgs-rcvd {
                description
                  "Number of Notification messages received";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container keepalive-msgs-sent {
                description
                  "Number of Keepalive messages sent";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container keepalive-msgs-rcvd {
                description
                  "Number of Keepalive messages received";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
            }
          }
          container default {
            presence "Indicates a default node is configured.";
            description
              "Default template";
            leaf sample-interval {
              type uint32 {
                range "1..60" {
                  description
                    "Frequency of samples";
                }
              }
              description
                "Frequency of sampling in minutes";
            }
            container total-msgs-sent {
              description
                "Total number of messages sent";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container total-msgs-rcvd {
              description
                "Total number of messages received";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container init-msgs-sent {
              description
                "Number of Init messages sent";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container init-msgs-rcvd {
              description
                "Number of Init messages received";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container address-msgs-sent {
              description
                "Number of Address messages sent";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container address-msgs-rcvd {
              description
                "Number of Address messages received";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container address-withdraw-msgs-sent {
              description
                "Number of Address Withdraw messages sent";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container address-withdraw-msgs-rcvd {
              description
                "Number of Address Withdraw messages received";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container label-mapping-msgs-sent {
              description
                "Number of Label Mapping messages sent";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container label-mapping-msgs-rcvd {
              description
                "Number of Label Mapping messages received";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container label-withdraw-msgs-sent {
              description
                "Number of Label Withdraw messages sent";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container label-withdraw-msgs-rcvd {
              description
                "Number of Label Withdraw messages received";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container label-release-msgs-sent {
              description
                "Number of Label Release messages sent";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container label-release-msgs-rcvd {
              description
                "Number of LAbel Release messages received";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container notification-msgs-sent {
              description
                "Number of Notification messages sent";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container notification-msgs-rcvd {
              description
                "Number of Notification messages received";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container keepalive-msgs-sent {
              description
                "Number of Keepalive messages sent";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container keepalive-msgs-rcvd {
              description
                "Number of Keepalive messages received";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
          }
        }
      }
      container ospf {
        description
          "Configure thresholds for OSPF";
        container v2protocol {
          description
            "Configure threshold attributes for OSPF v2 Protocol";
          container templates {
            description
              "Specify template";
            list template {
              key "template-name";
              description
                "Specify template";
              leaf template-name {
                type xr:Cisco-ios-xr-string {
                  length "1..800" {
                    description
                      "Template name";
                  }
                }
                description
                  "Specify template";
              }
              leaf sample-interval {
                type uint32 {
                  range "1..60" {
                    description
                      "Frequency of samples";
                  }
                }
                description
                  "Frequency of sampling in minutes";
              }
              container input-packets {
                description
                  "Total number of packets received";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container output-packets {
                description
                  "Total number of packets sent";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container input-hello-packets {
                description
                  "Number of Hello packets received";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container output-hello-packets {
                description
                  "Number of Hello packets sent";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container input-dbds {
                description
                  "Number of DBD packets received";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container input-dbds-lsa {
                description
                  "Number of LSA received in DBD packets";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container output-dbds {
                description
                  "Number of DBD packets sent";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container output-dbds-lsa {
                description
                  "Number of LSA sent in DBD packets";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container input-lsrequests {
                description
                  "Number of LS Requests received";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container input-lsrequests-lsa {
                description
                  "Number of LSA received in LS Requests";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container output-lsrequests {
                description
                  "Number of LS Requests sent";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container output-lsrequests-lsa {
                description
                  "Number of LSA sent in LS Requests";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container input-lsaupdates {
                description
                  "Number of LSA Updates received";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container input-lsaupdates-lsa {
                description
                  "Number of LSA received in LSA Updates";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container output-lsaupdates {
                description
                  "Number of LSA Updates sent";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container output-lsaupdates-lsa {
                description
                  "Number of LSA sent in LSA Updates";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container input-lsaacks {
                description
                  "Number of LSA Acknowledgements received";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container input-lsaacks-lsa {
                description
                  "Number of LSA received in LSA Acknowledgements";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container output-lsaacks {
                description
                  "Number of LSA Acknowledgements sent";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container output-lsaacks-lsa {
                description
                  "Number of LSA sent in LSA Acknowledgements";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container checksum-errors {
                description
                  "Number of packets received with checksum errors";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
            }
          }
          container default {
            presence "Indicates a default node is configured.";
            description
              "Default template";
            leaf sample-interval {
              type uint32 {
                range "1..60" {
                  description
                    "Frequency of samples";
                }
              }
              description
                "Frequency of sampling in minutes";
            }
            container input-packets {
              description
                "Total number of packets received";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container output-packets {
              description
                "Total number of packets sent";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container input-hello-packets {
              description
                "Number of Hello packets received";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container output-hello-packets {
              description
                "Number of Hello packets sent";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container input-dbds {
              description
                "Number of DBD packets received";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container input-dbds-lsa {
              description
                "Number of LSA received in DBD packets";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container output-dbds {
              description
                "Number of DBD packets sent";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container output-dbds-lsa {
              description
                "Number of LSA sent in DBD packets";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container input-lsrequests {
              description
                "Number of LS Requests received";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container input-lsrequests-lsa {
              description
                "Number of LSA received in LS Requests";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container output-lsrequests {
              description
                "Number of LS Requests sent";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container output-lsrequests-lsa {
              description
                "Number of LSA sent in LS Requests";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container input-lsaupdates {
              description
                "Number of LSA Updates received";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container input-lsaupdates-lsa {
              description
                "Number of LSA received in LSA Updates";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container output-lsaupdates {
              description
                "Number of LSA Updates sent";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container output-lsaupdates-lsa {
              description
                "Number of LSA sent in LSA Updates";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container input-lsaacks {
              description
                "Number of LSA Acknowledgements received";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container input-lsaacks-lsa {
              description
                "Number of LSA received in LSA Acknowledgements";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container output-lsaacks {
              description
                "Number of LSA Acknowledgements sent";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container output-lsaacks-lsa {
              description
                "Number of LSA sent in LSA Acknowledgements";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container checksum-errors {
              description
                "Number of packets received with checksum errors";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
          }
        }
        container v3protocol {
          description
            "Configure threshold attributes for OSPF v3 Protocol";
          container templates {
            description
              "Specify template";
            list template {
              key "template-name";
              description
                "Specify template";
              leaf template-name {
                type xr:Cisco-ios-xr-string {
                  length "1..800" {
                    description
                      "Template name";
                  }
                }
                description
                  "Specify template";
              }
              leaf sample-interval {
                type uint32 {
                  range "1..60" {
                    description
                      "Frequency of samples";
                  }
                }
                description
                  "Frequency of sampling in minutes";
              }
              container input-packets {
                description
                  "Total number of packets received";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container output-packets {
                description
                  "Total number of packets sent";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container input-hello-packets {
                description
                  "Number of Hello packets received";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container output-hello-packets {
                description
                  "Number of Hello packets sent";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container input-dbds {
                description
                  "Number of DBD packets received";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container input-dbds-lsa {
                description
                  "Number of LSA received in DBD packets";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container output-dbds {
                description
                  "Number of DBD packets sent";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container output-dbds-lsa {
                description
                  "Number of LSA sent in DBD packets";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container input-lsrequests {
                description
                  "Number of LS Requests received";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container input-lsrequests-lsa {
                description
                  "Number of LSA received in LS Requests";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container output-lsrequests {
                description
                  "Number of LS Requests sent";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container output-lsrequests-lsa {
                description
                  "Number of LSA sent in LS Requests";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container input-lsaupdates {
                description
                  "Number of LSA Updates received";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container input-lsaupdates-lsa {
                description
                  "Number of LSA received in LSA Updates";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container output-lsaupdates {
                description
                  "Number of LSA Updates sent";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container output-lsaupdates-lsa {
                description
                  "Number of LSA sent in LSA Updates";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container input-lsaacks {
                description
                  "Number of LSA Acknowledgements received";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container input-lsaacks-lsa {
                description
                  "Number of LSA received in LSA Acknowledgements";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container output-lsaacks {
                description
                  "Number of LSA Acknowledgements sent";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
              container output-lsaacks-lsa {
                description
                  "Number of LSA sent in LSA Acknowledgements";
                container percent {
                  presence "Indicates a percent node is configured.";
                  description
                    "Specify that threshold value is percent of previous sample";
                }
                container rearm {
                  description
                    "Specify Rearm parameters (default - always)";
                  container toggle {
                    must "not(../window)";
                    presence "Indicates a toggle node is configured.";
                    description
                      "Rearm after the first period when condition is not met";
                  }
                  leaf window {
                    type uint32 {
                      range "1..100" {
                        description
                          "Rearm window size";
                      }
                    }
                    must "not(../toggle)";
                    description
                      "Rearm after the window of sampling periods";
                  }
                }
                container eq {
                  presence "Indicates the node is configured.";
                  description
                    "Equal to";
                  leaf threshold-value {
                    type uint32 {
                      range "0..4294967295" {
                        description
                          "Threshold value";
                      }
                    }
                    mandatory true;
                    description
                      "Threshold value";
                  }
                }
                container ne {
                  presence "Indicates the node is configured.";
                  description
                    "Not equal to";
                  leaf threshold-value {
                    type uint32 {
                      range "0..4294967295" {
                        description
                          "Threshold value";
                      }
                    }
                    mandatory true;
                    description
                      "Threshold value";
                  }
                }
                container lt {
                  presence "Indicates the node is configured.";
                  description
                    "Less than";
                  leaf threshold-value {
                    type uint32 {
                      range "0..4294967295" {
                        description
                          "Threshold value";
                      }
                    }
                    mandatory true;
                    description
                      "Threshold value";
                  }
                }
                container le {
                  presence "Indicates the node is configured.";
                  description
                    "Less than or equal to";
                  leaf threshold-value {
                    type uint32 {
                      range "0..4294967295" {
                        description
                          "Threshold value";
                      }
                    }
                    mandatory true;
                    description
                      "Threshold value";
                  }
                }
                container gt {
                  presence "Indicates the node is configured.";
                  description
                    "Greater than";
                  leaf threshold-value {
                    type uint32 {
                      range "0..4294967295" {
                        description
                          "Threshold value";
                      }
                    }
                    mandatory true;
                    description
                      "Threshold value";
                  }
                }
                container ge {
                  presence "Indicates the node is configured.";
                  description
                    "Greater than or equal to";
                  leaf threshold-value {
                    type uint32 {
                      range "0..4294967295" {
                        description
                          "Threshold value";
                      }
                    }
                    mandatory true;
                    description
                      "Threshold value";
                  }
                }
                container rg {
                  presence "Indicates the node is configured.";
                  description
                    "Not in range";
                  leaf start-threshold-value {
                    type uint32 {
                      range "0..4294967295" {
                        description
                          "Threshold value";
                      }
                    }
                    mandatory true;
                    description
                      "Threshold value";
                  }
                  leaf end-threshold-value {
                    type uint32 {
                      range "0..4294967295" {
                        description
                          "Threshold value";
                      }
                    }
                    mandatory true;
                    description
                      "Threshold value";
                  }
                }
              }
            }
          }
          container default {
            presence "Indicates a default node is configured.";
            description
              "Default template";
            leaf sample-interval {
              type uint32 {
                range "1..60" {
                  description
                    "Frequency of samples";
                }
              }
              description
                "Frequency of sampling in minutes";
            }
            container input-packets {
              description
                "Total number of packets received";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container output-packets {
              description
                "Total number of packets sent";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container input-hello-packets {
              description
                "Number of Hello packets received";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container output-hello-packets {
              description
                "Number of Hello packets sent";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container input-dbds {
              description
                "Number of DBD packets received";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container input-dbds-lsa {
              description
                "Number of LSA received in DBD packets";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container output-dbds {
              description
                "Number of DBD packets sent";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container output-dbds-lsa {
              description
                "Number of LSA sent in DBD packets";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container input-lsrequests {
              description
                "Number of LS Requests received";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container input-lsrequests-lsa {
              description
                "Number of LSA received in LS Requests";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container output-lsrequests {
              description
                "Number of LS Requests sent";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container output-lsrequests-lsa {
              description
                "Number of LSA sent in LS Requests";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container input-lsaupdates {
              description
                "Number of LSA Updates received";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container input-lsaupdates-lsa {
              description
                "Number of LSA received in LSA Updates";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container output-lsaupdates {
              description
                "Number of LSA Updates sent";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container output-lsaupdates-lsa {
              description
                "Number of LSA sent in LSA Updates";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container input-lsaacks {
              description
                "Number of LSA Acknowledgements received";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container input-lsaacks-lsa {
              description
                "Number of LSA received in LSA Acknowledgements";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container output-lsaacks {
              description
                "Number of LSA Acknowledgements sent";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
            container output-lsaacks-lsa {
              description
                "Number of LSA sent in LSA Acknowledgements";
              container percent {
                presence "Indicates a percent node is configured.";
                description
                  "Specify that threshold value is percent of previous sample";
              }
              container rearm {
                description
                  "Specify Rearm parameters (default - always)";
                container toggle {
                  must "not(../window)";
                  presence "Indicates a toggle node is configured.";
                  description
                    "Rearm after the first period when condition is not met";
                }
                leaf window {
                  type uint32 {
                    range "1..100" {
                      description
                        "Rearm window size";
                    }
                  }
                  must "not(../toggle)";
                  description
                    "Rearm after the window of sampling periods";
                }
              }
              container eq {
                presence "Indicates the node is configured.";
                description
                  "Equal to";
                leaf threshold-value {
                  type uint32 {
                    range "0..4294967295" {
                      description
                        "Threshold value";
                    }
                  }
                  mandatory true;
                  description
                    "Threshold value";
                }
              }
              container ne {
                presence "Indicates the node is configured.";
                description
                  "Not equal to";
                leaf threshold-value {
                  type uint32 {
                    range "0..4294967295" {
                      description
                        "Threshold value";
                    }
                  }
                  mandatory true;
                  description
                    "Threshold value";
                }
              }
              container lt {
                presence "Indicates the node is configured.";
                description
                  "Less than";
                leaf threshold-value {
                  type uint32 {
                    range "0..4294967295" {
                      description
                        "Threshold value";
                    }
                  }
                  mandatory true;
                  description
                    "Threshold value";
                }
              }
              container le {
                presence "Indicates the node is configured.";
                description
                  "Less than or equal to";
                leaf threshold-value {
                  type uint32 {
                    range "0..4294967295" {
                      description
                        "Threshold value";
                    }
                  }
                  mandatory true;
                  description
                    "Threshold value";
                }
              }
              container gt {
                presence "Indicates the node is configured.";
                description
                  "Greater than";
                leaf threshold-value {
                  type uint32 {
                    range "0..4294967295" {
                      description
                        "Threshold value";
                    }
                  }
                  mandatory true;
                  description
                    "Threshold value";
                }
              }
              container ge {
                presence "Indicates the node is configured.";
                description
                  "Greater than or equal to";
                leaf threshold-value {
                  type uint32 {
                    range "0..4294967295" {
                      description
                        "Threshold value";
                    }
                  }
                  mandatory true;
                  description
                    "Threshold value";
                }
              }
              container rg {
                presence "Indicates the node is configured.";
                description
                  "Not in range";
                leaf start-threshold-value {
                  type uint32 {
                    range "0..4294967295" {
                      description
                        "Threshold value";
                    }
                  }
                  mandatory true;
                  description
                    "Threshold value";
                }
                leaf end-threshold-value {
                  type uint32 {
                    range "0..4294967295" {
                      description
                        "Threshold value";
                    }
                  }
                  mandatory true;
                  description
                    "Threshold value";
                }
              }
            }
          }
        }
      }
    }
    container apply {
      description
        "Start data collection and/or threshold monitoring";
      container monitor {
        description
          "Start data collection for a monitored instance";
        container interface {
          description
            "Perform monitoring for an interface";
          container basic-counters {
            description
              "Perform monitoring for basic-counters";
            list interface {
              key "interface-name";
              description
                "Perform monitoring for basic-counters";
              leaf interface-name {
                type xr:Interface-name;
                description
                  "Perform monitoring for basic-counters";
              }
              leaf template-name {
                type union {
                  type string {
                    pattern "default" {
                      description
                        "Apply the default template";
                    }
                  }
                  type xr:Cisco-ios-xr-string {
                    length "1..1024" {
                      description
                        "Specify an existing template for data collection";
                    }
                  }
                }
                mandatory true;
                description
                  "Specify an existing template or default template for data collection";
              }
            }
          }
          container generic-counters {
            description
              "Perform monitoring for generic-counters";
            list interface {
              key "interface-name";
              description
                "Perform monitoring for generic-counters";
              leaf interface-name {
                type xr:Interface-name;
                description
                  "Perform monitoring for generic-counters";
              }
              leaf template-name {
                type union {
                  type string {
                    pattern "default" {
                      description
                        "Apply the default template";
                    }
                  }
                  type xr:Cisco-ios-xr-string {
                    length "1..1024" {
                      description
                        "Specify an existing template for data collection";
                    }
                  }
                }
                mandatory true;
                description
                  "Specify an existing template or default template for data collection";
              }
            }
          }
          container data-rates {
            description
              "Perform monitoring for data-rates";
            list interface {
              key "interface-name";
              description
                "Perform monitoring for data-rates";
              leaf interface-name {
                type xr:Interface-name;
                description
                  "Perform monitoring for data-rates";
              }
              leaf template-name {
                type union {
                  type string {
                    pattern "default" {
                      description
                        "Apply the default template";
                    }
                  }
                  type xr:Cisco-ios-xr-string {
                    length "1..1024" {
                      description
                        "Specify an existing template for data collection";
                    }
                  }
                }
                mandatory true;
                description
                  "Specify an existing template or default template for data collection";
              }
            }
          }
        }
        container node {
          description
            "Perform monitoring for node";
          container cpu {
            description
              "Perform collection for CPU";
            container locations {
              description
                "Specify the location to collect from";
              list location {
                key "location-name";
                description
                  "Specify the location to collect from";
                leaf location-name {
                  type xr:Node-id;
                  description
                    "Specify the location to collect from";
                }
                leaf template-name {
                  type union {
                    type string {
                      pattern "default" {
                        description
                          "Apply the default template";
                      }
                    }
                    type xr:Cisco-ios-xr-string {
                      length "1..1024" {
                        description
                          "Specify an existing template for data collection";
                      }
                    }
                  }
                  mandatory true;
                  description
                    "Specify an existing template or default template for data collection";
                }
              }
            }
          }
          container memory {
            description
              "Perform collection for memory";
            container locations {
              description
                "Specify the location to collect from";
              list location {
                key "location-name";
                description
                  "Specify the location to collect from";
                leaf location-name {
                  type xr:Node-id;
                  description
                    "Specify the location to collect from";
                }
                leaf template-name {
                  type union {
                    type string {
                      pattern "default" {
                        description
                          "Apply the default template";
                      }
                    }
                    type xr:Cisco-ios-xr-string {
                      length "1..1024" {
                        description
                          "Specify an existing template for data collection";
                      }
                    }
                  }
                  mandatory true;
                  description
                    "Specify an existing template or default template for data collection";
                }
              }
            }
          }
          container process {
            description
              "Perform collection for process";
            container locations {
              description
                "Specify the location to collect from";
              list location {
                key "location-name";
                description
                  "Specify the location to collect from";
                leaf location-name {
                  type xr:Node-id;
                  description
                    "Specify the location to collect from";
                }
                list process {
                  key "process-id";
                  description
                    "Specify a process";
                  leaf process-id {
                    type uint32 {
                      range "0..4294967295" {
                        description
                          "Enter the process id";
                      }
                    }
                    description
                      "Specify a process";
                  }
                  leaf template-name {
                    type union {
                      type string {
                        pattern "default" {
                          description
                            "Apply the default template";
                        }
                      }
                      type xr:Cisco-ios-xr-string {
                        length "1..1024" {
                          description
                            "Specify an existing template for data collection";
                        }
                      }
                    }
                    mandatory true;
                    description
                      "Specify an existing template or default template for data collection";
                  }
                }
              }
            }
          }
        }
        list bgp {
          key "address";
          description
            "Monitor bgp protocol";
          leaf address {
            type inet:ipv4-address-no-zone;
            description
              "Monitor bgp protocol";
          }
          leaf template-name {
            type union {
              type string {
                pattern "default" {
                  description
                    "Apply the default template";
                }
              }
              type xr:Cisco-ios-xr-string {
                length "1..1024" {
                  description
                    "Specify an existing template for data collection";
                }
              }
            }
            mandatory true;
            description
              "Specify an existing template or default template for data collection";
          }
        }
        container mpls {
          description
            "Perform monitoring for mpls";
          container te-tunnels {
            description
              "Perform monitoring for traffic engineering tunnels";
            list te-tunnel {
              key "interface-name";
              description
                "Perform monitoring for traffic engineering tunnels";
              leaf interface-name {
                type xr:Interface-name;
                description
                  "Perform monitoring for traffic engineering tunnels";
              }
              leaf template-name {
                type union {
                  type string {
                    pattern "default" {
                      description
                        "Apply the default template";
                    }
                  }
                  type xr:Cisco-ios-xr-string {
                    length "1..1024" {
                      description
                        "Specify an existing template for data collection";
                    }
                  }
                }
                mandatory true;
                description
                  "Specify an existing template or default template for data collection";
              }
            }
          }
          container ldps {
            description
              "Perform monitoring for ldp";
            list ldp {
              key "address";
              description
                "Perform monitoring for ldp";
              leaf address {
                type inet:ipv4-address-no-zone;
                description
                  "Perform monitoring for ldp";
              }
              leaf template-name {
                type union {
                  type string {
                    pattern "default" {
                      description
                        "Apply the default template";
                    }
                  }
                  type xr:Cisco-ios-xr-string {
                    length "1..1024" {
                      description
                        "Specify an existing template for data collection";
                    }
                  }
                }
                mandatory true;
                description
                  "Specify an existing template or default template for data collection";
              }
            }
          }
        }
        container ospf {
          description
            "Perform monitoring for OSPF";
          container v2protocols {
            description
              "Perform monitoring for OSPF v2 Protocol";
            list v2protocol {
              key "instance-name";
              description
                "Perform monitoring for OSPF v2 Protocol";
              leaf instance-name {
                type xr:Cisco-ios-xr-string {
                  length "1..800" {
                    description
                      "Select an instance";
                  }
                }
                description
                  "Perform monitoring for OSPF v2 Protocol";
              }
              leaf template-name {
                type union {
                  type string {
                    pattern "default" {
                      description
                        "Apply the default template";
                    }
                  }
                  type xr:Cisco-ios-xr-string {
                    length "1..1024" {
                      description
                        "Specify an existing template for data collection";
                    }
                  }
                }
                mandatory true;
                description
                  "Specify an existing template or default template for data collection";
              }
            }
          }
          container v3protocols {
            description
              "Perform monitoring for OSPF v3 Protocol";
            list v3protocol {
              key "instance-name";
              description
                "Perform monitoring for OSPF v3 Protocol";
              leaf instance-name {
                type xr:Cisco-ios-xr-string {
                  length "1..800" {
                    description
                      "Select an instance";
                  }
                }
                description
                  "Perform monitoring for OSPF v3 Protocol";
              }
              leaf template-name {
                type union {
                  type string {
                    pattern "default" {
                      description
                        "Apply the default template";
                    }
                  }
                  type xr:Cisco-ios-xr-string {
                    length "1..1024" {
                      description
                        "Specify an existing template for data collection";
                    }
                  }
                }
                mandatory true;
                description
                  "Specify an existing template or default template for data collection";
              }
            }
          }
        }
      }
      container statistics {
        description
          "Start periodic collection using a defined a template";
        container interface {
          description
            "Perform data collection for interfaces";
          container basic-counters {
            description
              "Perform statistics collection for basic-counters";
            leaf template-name {
              type union {
                type string {
                  pattern "default" {
                    description
                      "Apply the default template";
                  }
                }
                type xr:Cisco-ios-xr-string {
                  length "1..1024" {
                    description
                      "Specify an existing template for data collection";
                  }
                }
              }
              description
                "Specify an existing template or default template for data collection";
            }
          }
          container generic-counters {
            description
              "Perform statistics collection for generic-counters";
            leaf template-name {
              type union {
                type string {
                  pattern "default" {
                    description
                      "Apply the default template";
                  }
                }
                type xr:Cisco-ios-xr-string {
                  length "1..1024" {
                    description
                      "Specify an existing template for data collection";
                  }
                }
              }
              description
                "Specify an existing template or default template for data collection";
            }
          }
          container data-rates {
            description
              "Perform statistics collection for data-rates";
            leaf template-name {
              type union {
                type string {
                  pattern "default" {
                    description
                      "Apply the default template";
                  }
                }
                type xr:Cisco-ios-xr-string {
                  length "1..1024" {
                    description
                      "Specify an existing template for data collection";
                  }
                }
              }
              description
                "Specify an existing template or default template for data collection";
            }
          }
        }
        container node {
          description
            "Perform collection for node";
          container cpu {
            description
              "Perform collection for CPU";
            container location {
              description
                "Specify the location to collect from";
              container all {
                description
                  "For all nodes in the LR";
                leaf template-name {
                  type union {
                    type string {
                      pattern "default" {
                        description
                          "Apply the default template";
                      }
                    }
                    type xr:Cisco-ios-xr-string {
                      length "1..1024" {
                        description
                          "Specify an existing template for data collection";
                      }
                    }
                  }
                  description
                    "Specify an existing template or default template for data collection";
                }
              }
              list location {
                key "location-id";
                description
                  "Specify the location to collect from";
                leaf location-id {
                  type xr:Node-id;
                  description
                    "Fully qualified location specification";
                }
                leaf template-name {
                  type union {
                    type string {
                      pattern "default" {
                        description
                          "Apply the default template";
                      }
                    }
                    type xr:Cisco-ios-xr-string {
                      length "1..1024" {
                        description
                          "Specify an existing template for data collection";
                      }
                    }
                  }
                  mandatory true;
                  description
                    "Specify an existing template or default template for data collection";
                }
              }
            }
          }
          container memory {
            description
              "Perform collection for memory";
            container location {
              description
                "Specify the location to collect from";
              container all {
                description
                  "For all nodes in the LR";
                leaf template-name {
                  type union {
                    type string {
                      pattern "default" {
                        description
                          "Apply the default template";
                      }
                    }
                    type xr:Cisco-ios-xr-string {
                      length "1..1024" {
                        description
                          "Specify an existing template for data collection";
                      }
                    }
                  }
                  description
                    "Specify an existing template or default template for data collection";
                }
              }
              list location {
                key "location-id";
                description
                  "Specify the location to collect from";
                leaf location-id {
                  type xr:Node-id;
                  description
                    "Fully qualified location specification";
                }
                leaf template-name {
                  type union {
                    type string {
                      pattern "default" {
                        description
                          "Apply the default template";
                      }
                    }
                    type xr:Cisco-ios-xr-string {
                      length "1..1024" {
                        description
                          "Specify an existing template for data collection";
                      }
                    }
                  }
                  mandatory true;
                  description
                    "Specify an existing template or default template for data collection";
                }
              }
            }
          }
          container process {
            description
              "Perform collection for process";
            container location {
              description
                "Specify the location to collect from";
              container all {
                description
                  "For all nodes in the LR";
                leaf template-name {
                  type union {
                    type string {
                      pattern "default" {
                        description
                          "Apply the default template";
                      }
                    }
                    type xr:Cisco-ios-xr-string {
                      length "1..1024" {
                        description
                          "Specify an existing template for data collection";
                      }
                    }
                  }
                  description
                    "Specify an existing template or default template for data collection";
                }
              }
              list location {
                key "location-id";
                description
                  "Specify the location to collect from";
                leaf location-id {
                  type xr:Node-id;
                  description
                    "Fully qualified location specification";
                }
                leaf template-name {
                  type union {
                    type string {
                      pattern "default" {
                        description
                          "Apply the default template";
                      }
                    }
                    type xr:Cisco-ios-xr-string {
                      length "1..1024" {
                        description
                          "Specify an existing template for data collection";
                      }
                    }
                  }
                  mandatory true;
                  description
                    "Specify an existing template or default template for data collection";
                }
              }
            }
          }
        }
        container bgp {
          description
            "Perform data collection for bgp";
          leaf template-name {
            type union {
              type string {
                pattern "default" {
                  description
                    "Apply the default template";
                }
              }
              type xr:Cisco-ios-xr-string {
                length "1..1024" {
                  description
                    "Specify an existing template for data collection";
                }
              }
            }
            description
              "Specify an existing template or default template for data collection";
          }
        }
        container mpls {
          description
            "Perform statistics collection for mpls";
          container ldp {
            description
              "Perform collection for labels distribution protocol";
            leaf template-name {
              type union {
                type string {
                  pattern "default" {
                    description
                      "Apply the default template";
                  }
                }
                type xr:Cisco-ios-xr-string {
                  length "1..1024" {
                    description
                      "Specify an existing template for data collection";
                  }
                }
              }
              description
                "Specify an existing template or default template for data collection";
            }
          }
        }
        container ospf {
          description
            "Perform data collection for OSPF";
          container v2protocol {
            description
              "Perform statistics collection for OSPF v2 protocol data";
            leaf template-name {
              type union {
                type string {
                  pattern "default" {
                    description
                      "Apply the default template";
                  }
                }
                type xr:Cisco-ios-xr-string {
                  length "1..1024" {
                    description
                      "Specify an existing template for data collection";
                  }
                }
              }
              description
                "Specify an existing template or default template for data collection";
            }
          }
          container v3protocol {
            description
              "Perform statistics collection for OSPF v3 protocol data";
            leaf template-name {
              type union {
                type string {
                  pattern "default" {
                    description
                      "Apply the default template";
                  }
                }
                type xr:Cisco-ios-xr-string {
                  length "1..1024" {
                    description
                      "Specify an existing template for data collection";
                  }
                }
              }
              description
                "Specify an existing template or default template for data collection";
            }
          }
        }
      }
      container thresholds {
        description
          "Start threshold monitoring using a defined template";
        container interface {
          description
            "Perform threshold monitoring for interface";
          container basic-counters {
            description
              "Perform threshold checking for basic-counters";
            leaf template-name {
              type union {
                type string {
                  pattern "default" {
                    description
                      "Apply the default template";
                  }
                }
                type xr:Cisco-ios-xr-string {
                  length "1..1024" {
                    description
                      "Specify an existing template for data collection";
                  }
                }
              }
              description
                "Specify an existing template or default template for data collection";
            }
          }
          container generic-counters {
            description
              "Perform threshold checking for generic-counters";
            leaf template-name {
              type union {
                type string {
                  pattern "default" {
                    description
                      "Apply the default template";
                  }
                }
                type xr:Cisco-ios-xr-string {
                  length "1..1024" {
                    description
                      "Specify an existing template for data collection";
                  }
                }
              }
              description
                "Specify an existing template or default template for data collection";
            }
          }
          container data-rates {
            description
              "Perform threshold checking for data-rates";
            leaf template-name {
              type union {
                type string {
                  pattern "default" {
                    description
                      "Apply the default template";
                  }
                }
                type xr:Cisco-ios-xr-string {
                  length "1..1024" {
                    description
                      "Specify an existing template for data collection";
                  }
                }
              }
              description
                "Specify an existing template or default template for data collection";
            }
          }
        }
        container node {
          description
            "Perform threshold monitoring for node";
          container cpu {
            description
              "Perform threshold checking for CPU";
            container location {
              description
                "Specify the location to collect from";
              container all {
                description
                  "For all nodes in the LR";
                leaf template-name {
                  type union {
                    type string {
                      pattern "default" {
                        description
                          "Apply the default template";
                      }
                    }
                    type xr:Cisco-ios-xr-string {
                      length "1..1024" {
                        description
                          "Specify an existing template for data collection";
                      }
                    }
                  }
                  description
                    "Specify an existing template or default template for data collection";
                }
              }
              list location {
                key "location-id";
                description
                  "Specify the location to collect from";
                leaf location-id {
                  type xr:Node-id;
                  description
                    "Fully qualified location specification";
                }
                leaf template-name {
                  type union {
                    type string {
                      pattern "default" {
                        description
                          "Apply the default template";
                      }
                    }
                    type xr:Cisco-ios-xr-string {
                      length "1..1024" {
                        description
                          "Specify an existing template for data collection";
                      }
                    }
                  }
                  mandatory true;
                  description
                    "Specify an existing template or default template for data collection";
                }
              }
            }
          }
          container memory {
            description
              "Perform threshold checking for memory";
            container location {
              description
                "Specify the location to collect from";
              container all {
                description
                  "For all nodes in the LR";
                leaf template-name {
                  type union {
                    type string {
                      pattern "default" {
                        description
                          "Apply the default template";
                      }
                    }
                    type xr:Cisco-ios-xr-string {
                      length "1..1024" {
                        description
                          "Specify an existing template for data collection";
                      }
                    }
                  }
                  description
                    "Specify an existing template or default template for data collection";
                }
              }
              list location {
                key "location-id";
                description
                  "Specify the location to collect from";
                leaf location-id {
                  type xr:Node-id;
                  description
                    "Fully qualified location specification";
                }
                leaf template-name {
                  type union {
                    type string {
                      pattern "default" {
                        description
                          "Apply the default template";
                      }
                    }
                    type xr:Cisco-ios-xr-string {
                      length "1..1024" {
                        description
                          "Specify an existing template for data collection";
                      }
                    }
                  }
                  mandatory true;
                  description
                    "Specify an existing template or default template for data collection";
                }
              }
            }
          }
          container process {
            description
              "Perform threshold checking for process";
            container location {
              description
                "Specify the location to collect from";
              container all {
                description
                  "For all nodes in the LR";
                leaf template-name {
                  type union {
                    type string {
                      pattern "default" {
                        description
                          "Apply the default template";
                      }
                    }
                    type xr:Cisco-ios-xr-string {
                      length "1..1024" {
                        description
                          "Specify an existing template for data collection";
                      }
                    }
                  }
                  description
                    "Specify an existing template or default template for data collection";
                }
              }
              list location {
                key "location-id";
                description
                  "Specify the location to collect from";
                leaf location-id {
                  type xr:Node-id;
                  description
                    "Fully qualified location specification";
                }
                leaf template-name {
                  type union {
                    type string {
                      pattern "default" {
                        description
                          "Apply the default template";
                      }
                    }
                    type xr:Cisco-ios-xr-string {
                      length "1..1024" {
                        description
                          "Specify an existing template for data collection";
                      }
                    }
                  }
                  mandatory true;
                  description
                    "Specify an existing template or default template for data collection";
                }
              }
            }
          }
        }
        container bgp {
          description
            "Perform threshold monitoring for bgp";
          leaf template-name {
            type union {
              type string {
                pattern "default" {
                  description
                    "Apply the default template";
                }
              }
              type xr:Cisco-ios-xr-string {
                length "1..1024" {
                  description
                    "Specify an existing template for data collection";
                }
              }
            }
            description
              "Specify an existing template or default template for data collection";
          }
        }
        container mpls {
          description
            "Perform threshold monitoring for mpls";
          container ldp {
            description
              "Perform threshold checking for ldp counters";
            leaf template-name {
              type union {
                type string {
                  pattern "default" {
                    description
                      "Apply the default template";
                  }
                }
                type xr:Cisco-ios-xr-string {
                  length "1..1024" {
                    description
                      "Specify an existing template for data collection";
                  }
                }
              }
              description
                "Specify an existing template or default template for data collection";
            }
          }
        }
        container ospf {
          description
            "Perform threshold monitoring for OSPF";
          container v2protocol {
            description
              "Perform threshold checking for OSPF v2 Protocol";
            leaf template-name {
              type union {
                type string {
                  pattern "default" {
                    description
                      "Apply the default template";
                  }
                }
                type xr:Cisco-ios-xr-string {
                  length "1..1024" {
                    description
                      "Specify an existing template for data collection";
                  }
                }
              }
              description
                "Specify an existing template or default template for data collection";
            }
          }
          container v3protocol {
            description
              "Perform threshold checking for OSPF v3 Protocol";
            leaf template-name {
              type union {
                type string {
                  pattern "default" {
                    description
                      "Apply the default template";
                  }
                }
                type xr:Cisco-ios-xr-string {
                  length "1..1024" {
                    description
                      "Specify an existing template for data collection";
                  }
                }
              }
              description
                "Specify an existing template or default template for data collection";
            }
          }
        }
      }
    }
    container resources {
      description
        "Resources configuration";
      container tftp-server {
        presence "Indicates a tftp-server node is configured.";
        description
          "Configure tftp server parameters";
        leaf ip-address {
          type inet:ipv4-address-no-zone;
          mandatory true;
          description
            "Tftp server IP address";
        }
        leaf vrf {
          type union {
            type string {
              pattern "default" {
                description
                  "Default VRF";
              }
            }
            type xr:Cisco-ios-xr-string {
              length "1..32" {
                description
                  "Name of VRF";
              }
            }
          }
          description
            "VRF name for TFTP service";
        }
        leaf directory {
          type xr:Cisco-ios-xr-string {
            length "1..800" {
              description
                "Enter the directory name";
            }
          }
          description
            "Directory Name";
        }
      }
      container dump {
        description
          "Configure data dump parameters";
        container local {
          presence "Indicates a local node is configured.";
          description
            "Dump onto local filesystem";
        }
      }
      container memory {
        description
          "Configure memory usage limits";
        leaf max-limit {
          type uint32 {
            range "0..4294967295" {
              description
                "Specify maximum memory limit in Kbytes";
            }
          }
          must "../min-reserved";
          description
            "Maximum limit for memory usage for data buffers";
        }
        leaf min-reserved {
          type uint32 {
            range "0..4294967295" {
              description
                "Specify free memory amount in Kbytes";
            }
          }
          must "../max-limit";
          description
            "Ensure a minimum free memory before allowing a collection request";
        }
      }
    }
    container regular-expressions {
      description
        "Configure regular expression";
      list regular-expression {
        key "regular-expression-name";
        description
          "Configure regular expression";
        leaf regular-expression-name {
          type xr:Cisco-ios-xr-string {
            length "1..32" {
              description
                "Regular expression name";
            }
          }
          description
            "Configure regular expression";
        }
        container indexes {
          description
            "Specify a regular expression index";
          list index {
            key "index-number";
            description
              "Specify a regular expression index";
            leaf index-number {
              type uint32 {
                range "1..100" {
                  description
                    "Index number";
                }
              }
              description
                "Specify a regular expression index";
            }
            leaf regular-expression-string {
              type string {
                length "1..128" {
                  description
                    "Regular expression string to match";
                }
              }
              mandatory true;
              description
                "Regular expression string to match";
            }
          }
        }
      }
    }
  }
}
