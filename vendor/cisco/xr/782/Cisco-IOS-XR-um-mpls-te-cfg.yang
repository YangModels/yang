module Cisco-IOS-XR-um-mpls-te-cfg {
  namespace "http://cisco.com/ns/yang/Cisco-IOS-XR-um-mpls-te-cfg";
  prefix um-mpls-te-cfg;

  import cisco-semver {
    prefix semver;
  }
  import Cisco-IOS-XR-types {
    prefix xr;
  }
  import ietf-inet-types {
    prefix inet;
  }
  import Cisco-IOS-XR-um-snmp-server-cfg {
    prefix a1;
  }
  import Cisco-IOS-XR-um-interface-cfg {
    prefix a2;
  }
  import tailf-common {
    prefix tailf;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR mpls-te package configuration.
     
     This YANG module augments the
     modules with configuration data.
     
     Copyright (c) 2019-2022 by Cisco Systems, Inc.
     All rights reserved.";

  revision 2022-10-21 {
    description
      "Changed path-selection/ignore/overload container as presence
       2022-07-11
         Added missing description statement to nodes
       2022-05-23
         Added container self-ping under tunnel-te
       2022-02-01
         Added signalled-bandwidth and soft-preemption support for auto-backup
       2021-11-17
         Added bfd and path protection support for named tunnels";
    semver:module-version "2.2.0";
  }
  revision 2021-07-15 {
    description
      "Removed presence statement of 2 timers nodes under traffic-eng,
        Removed presence statement of auto-tunnel container
       2021-07-09
          Added bandwidth-protection/maximum-aggregate nodes under backup container";
    semver:module-version "2.1.0";
  }
  revision 2021-04-14 {
    description
      "new container reopt is added under pce
       2021-02-19
           Added presence statement in ospf container and removed presence and
         must statement from area container
       2021-02-15
           Added yang nodes for new mib commands
       2021-01-28
           Added cisco-support task yang nodes
       2021-01-15
           Add mandatory flag in min node under overflow, adjustment-threshold and
         underflow container.
         Added tunnel-mte specific config container.
         Added backoff-timer under mpls->traffic-eng.
       2020-12-03
           Removed leaf hold-backup and containers maxabs, ltrace-buffer and its
         child nodes as these are used internally with cisco-support task.";
    semver:module-version "2.0.0";
  }
  revision 2020-05-26 {
    description
      "- removed pce under the dynamic path-option for interface
       - added s2l-setup under timers
       - added path-error under lsp-status for named-tunnels
       - added redundancy under timers for stateful-client";
  }
  revision 2019-07-08 {
    description
      "- removed augmentation to interface-preconfigure as tunnel logical
         interfaces are not allowed to configure as interface preconfig";
  }
  revision 2019-06-11 {
    description
      "- Split area list node under gmpls/optical-nni/topology/instance/opsf
         into two list nodes
       - Added necessary constraints (must, mandatory) under
         gmpls/../path-option";
  }
  revision 2019-06-10 {
    description
      "Establish semantic version baseline.";
    semver:module-version "1.0.0";
  }
  revision 2019-03-30 {
    description
      "Initial version";
  }

  typedef policy-class-type {
    type enumeration {
      enum "1" {
        value 1;
        description
          "1";
      }
      enum "2" {
        value 2;
        description
          "2";
      }
      enum "3" {
        value 3;
        description
          "3";
      }
      enum "4" {
        value 4;
        description
          "4";
      }
      enum "5" {
        value 5;
        description
          "5";
      }
      enum "6" {
        value 6;
        description
          "6";
      }
      enum "7" {
        value 7;
        description
          "7";
      }
      enum "default" {
        value 8;
        description
          "default value must be set alone";
      }
    }
    description
      "Tunnel policy class Value(s)";
  }

  grouping IF-BODY {
    description
      "Grouping for interface";
    container affinity {
      when "../a2:interface-name[starts-with(text(),'tunnel-te')]" {
        tailf:dependency "../a2:interface-name";
      }
      description
        "Link attributes for links traversed by tunnel";
      container includes {
        description
          "Links with all these attributes are included in path calculation";
        list include1 {
          key "name1";
          description
            "Link is excluded if it has every attribute in this list";
          leaf name1 {
            type xr:Cisco-ios-xr-string {
              length "1..32" {
                description
                  "Link is excluded if it has every attribute in this list";
              }
            }
            description
              "Link is excluded if it has every attribute in this list";
          }
        }
        list include2 {
          key "name1 name2";
          description
            "Link is excluded if it has every attribute in this list";
          leaf name1 {
            type xr:Cisco-ios-xr-string {
              length "1..32" {
                description
                  "Link is excluded if it has every attribute in this list";
              }
            }
            description
              "Link is excluded if it has every attribute in this list";
          }
          leaf name2 {
            type xr:Cisco-ios-xr-string {
              length "1..32" {
                description
                  "Link is excluded if it has every attribute in this list";
              }
            }
            description
              "Link is excluded if it has every attribute in this list";
          }
        }
        list include3 {
          key "name1 name2 name3";
          description
            "Link is excluded if it has every attribute in this list";
          leaf name1 {
            type xr:Cisco-ios-xr-string {
              length "1..32" {
                description
                  "Link is excluded if it has every attribute in this list";
              }
            }
            description
              "Link is excluded if it has every attribute in this list";
          }
          leaf name2 {
            type xr:Cisco-ios-xr-string {
              length "1..32" {
                description
                  "Link is excluded if it has every attribute in this list";
              }
            }
            description
              "Link is excluded if it has every attribute in this list";
          }
          leaf name3 {
            type xr:Cisco-ios-xr-string {
              length "1..32" {
                description
                  "Link is excluded if it has every attribute in this list";
              }
            }
            description
              "Link is excluded if it has every attribute in this list";
          }
        }
        list include4 {
          key "name1 name2 name3 name4";
          description
            "Link is excluded if it has every attribute in this list";
          leaf name1 {
            type xr:Cisco-ios-xr-string {
              length "1..32" {
                description
                  "Link is excluded if it has every attribute in this list";
              }
            }
            description
              "Link is excluded if it has every attribute in this list";
          }
          leaf name2 {
            type xr:Cisco-ios-xr-string {
              length "1..32" {
                description
                  "Link is excluded if it has every attribute in this list";
              }
            }
            description
              "Link is excluded if it has every attribute in this list";
          }
          leaf name3 {
            type xr:Cisco-ios-xr-string {
              length "1..32" {
                description
                  "Link is excluded if it has every attribute in this list";
              }
            }
            description
              "Link is excluded if it has every attribute in this list";
          }
          leaf name4 {
            type xr:Cisco-ios-xr-string {
              length "1..32" {
                description
                  "Link is excluded if it has every attribute in this list";
              }
            }
            description
              "Link is excluded if it has every attribute in this list";
          }
        }
        list include5 {
          key "name1 name2 name3 name4 name5";
          description
            "Link is excluded if it has every attribute in this list";
          leaf name1 {
            type xr:Cisco-ios-xr-string {
              length "1..32" {
                description
                  "Link is excluded if it has every attribute in this list";
              }
            }
            description
              "Link is excluded if it has every attribute in this list";
          }
          leaf name2 {
            type xr:Cisco-ios-xr-string {
              length "1..32" {
                description
                  "Link is excluded if it has every attribute in this list";
              }
            }
            description
              "Link is excluded if it has every attribute in this list";
          }
          leaf name3 {
            type xr:Cisco-ios-xr-string {
              length "1..32" {
                description
                  "Link is excluded if it has every attribute in this list";
              }
            }
            description
              "Link is excluded if it has every attribute in this list";
          }
          leaf name4 {
            type xr:Cisco-ios-xr-string {
              length "1..32" {
                description
                  "Link is excluded if it has every attribute in this list";
              }
            }
            description
              "Link is excluded if it has every attribute in this list";
          }
          leaf name5 {
            type xr:Cisco-ios-xr-string {
              length "1..32" {
                description
                  "Link is excluded if it has every attribute in this list";
              }
            }
            description
              "Link is excluded if it has every attribute in this list";
          }
        }
        list include6 {
          key "name1 name2 name3 name4 name5 name6";
          description
            "Link is excluded if it has every attribute in this list";
          leaf name1 {
            type xr:Cisco-ios-xr-string {
              length "1..32" {
                description
                  "Link is excluded if it has every attribute in this list";
              }
            }
            description
              "Link is excluded if it has every attribute in this list";
          }
          leaf name2 {
            type xr:Cisco-ios-xr-string {
              length "1..32" {
                description
                  "Link is excluded if it has every attribute in this list";
              }
            }
            description
              "Link is excluded if it has every attribute in this list";
          }
          leaf name3 {
            type xr:Cisco-ios-xr-string {
              length "1..32" {
                description
                  "Link is excluded if it has every attribute in this list";
              }
            }
            description
              "Link is excluded if it has every attribute in this list";
          }
          leaf name4 {
            type xr:Cisco-ios-xr-string {
              length "1..32" {
                description
                  "Link is excluded if it has every attribute in this list";
              }
            }
            description
              "Link is excluded if it has every attribute in this list";
          }
          leaf name5 {
            type xr:Cisco-ios-xr-string {
              length "1..32" {
                description
                  "Link is excluded if it has every attribute in this list";
              }
            }
            description
              "Link is excluded if it has every attribute in this list";
          }
          leaf name6 {
            type xr:Cisco-ios-xr-string {
              length "1..32" {
                description
                  "Link is excluded if it has every attribute in this list";
              }
            }
            description
              "Link is excluded if it has every attribute in this list";
          }
        }
        list include7 {
          key "name1 name2 name3 name4 name5 name6 name7";
          description
            "Link is excluded if it has every attribute in this list";
          leaf name1 {
            type xr:Cisco-ios-xr-string {
              length "1..32" {
                description
                  "Link is excluded if it has every attribute in this list";
              }
            }
            description
              "Link is excluded if it has every attribute in this list";
          }
          leaf name2 {
            type xr:Cisco-ios-xr-string {
              length "1..32" {
                description
                  "Link is excluded if it has every attribute in this list";
              }
            }
            description
              "Link is excluded if it has every attribute in this list";
          }
          leaf name3 {
            type xr:Cisco-ios-xr-string {
              length "1..32" {
                description
                  "Link is excluded if it has every attribute in this list";
              }
            }
            description
              "Link is excluded if it has every attribute in this list";
          }
          leaf name4 {
            type xr:Cisco-ios-xr-string {
              length "1..32" {
                description
                  "Link is excluded if it has every attribute in this list";
              }
            }
            description
              "Link is excluded if it has every attribute in this list";
          }
          leaf name5 {
            type xr:Cisco-ios-xr-string {
              length "1..32" {
                description
                  "Link is excluded if it has every attribute in this list";
              }
            }
            description
              "Link is excluded if it has every attribute in this list";
          }
          leaf name6 {
            type xr:Cisco-ios-xr-string {
              length "1..32" {
                description
                  "Link is excluded if it has every attribute in this list";
              }
            }
            description
              "Link is excluded if it has every attribute in this list";
          }
          leaf name7 {
            type xr:Cisco-ios-xr-string {
              length "1..32" {
                description
                  "Link is excluded if it has every attribute in this list";
              }
            }
            description
              "Link is excluded if it has every attribute in this list";
          }
        }
        list include8 {
          key "name1 name2 name3 name4 name5 name6 name7 name8";
          description
            "Link is excluded if it has every attribute in this list";
          leaf name1 {
            type xr:Cisco-ios-xr-string {
              length "1..32" {
                description
                  "Link is excluded if it has every attribute in this list";
              }
            }
            description
              "Link is excluded if it has every attribute in this list";
          }
          leaf name2 {
            type xr:Cisco-ios-xr-string {
              length "1..32" {
                description
                  "Link is excluded if it has every attribute in this list";
              }
            }
            description
              "Link is excluded if it has every attribute in this list";
          }
          leaf name3 {
            type xr:Cisco-ios-xr-string {
              length "1..32" {
                description
                  "Link is excluded if it has every attribute in this list";
              }
            }
            description
              "Link is excluded if it has every attribute in this list";
          }
          leaf name4 {
            type xr:Cisco-ios-xr-string {
              length "1..32" {
                description
                  "Link is excluded if it has every attribute in this list";
              }
            }
            description
              "Link is excluded if it has every attribute in this list";
          }
          leaf name5 {
            type xr:Cisco-ios-xr-string {
              length "1..32" {
                description
                  "Link is excluded if it has every attribute in this list";
              }
            }
            description
              "Link is excluded if it has every attribute in this list";
          }
          leaf name6 {
            type xr:Cisco-ios-xr-string {
              length "1..32" {
                description
                  "Link is excluded if it has every attribute in this list";
              }
            }
            description
              "Link is excluded if it has every attribute in this list";
          }
          leaf name7 {
            type xr:Cisco-ios-xr-string {
              length "1..32" {
                description
                  "Link is excluded if it has every attribute in this list";
              }
            }
            description
              "Link is excluded if it has every attribute in this list";
          }
          leaf name8 {
            type xr:Cisco-ios-xr-string {
              length "1..32" {
                description
                  "Link is excluded if it has every attribute in this list";
              }
            }
            description
              "Link is excluded if it has every attribute in this list";
          }
        }
        list include9 {
          key "name1 name2 name3 name4 name5 name6 name7 name8 name9";
          description
            "Link is excluded if it has every attribute in this list";
          leaf name1 {
            type xr:Cisco-ios-xr-string {
              length "1..32" {
                description
                  "Link is excluded if it has every attribute in this list";
              }
            }
            description
              "Link is excluded if it has every attribute in this list";
          }
          leaf name2 {
            type xr:Cisco-ios-xr-string {
              length "1..32" {
                description
                  "Link is excluded if it has every attribute in this list";
              }
            }
            description
              "Link is excluded if it has every attribute in this list";
          }
          leaf name3 {
            type xr:Cisco-ios-xr-string {
              length "1..32" {
                description
                  "Link is excluded if it has every attribute in this list";
              }
            }
            description
              "Link is excluded if it has every attribute in this list";
          }
          leaf name4 {
            type xr:Cisco-ios-xr-string {
              length "1..32" {
                description
                  "Link is excluded if it has every attribute in this list";
              }
            }
            description
              "Link is excluded if it has every attribute in this list";
          }
          leaf name5 {
            type xr:Cisco-ios-xr-string {
              length "1..32" {
                description
                  "Link is excluded if it has every attribute in this list";
              }
            }
            description
              "Link is excluded if it has every attribute in this list";
          }
          leaf name6 {
            type xr:Cisco-ios-xr-string {
              length "1..32" {
                description
                  "Link is excluded if it has every attribute in this list";
              }
            }
            description
              "Link is excluded if it has every attribute in this list";
          }
          leaf name7 {
            type xr:Cisco-ios-xr-string {
              length "1..32" {
                description
                  "Link is excluded if it has every attribute in this list";
              }
            }
            description
              "Link is excluded if it has every attribute in this list";
          }
          leaf name8 {
            type xr:Cisco-ios-xr-string {
              length "1..32" {
                description
                  "Link is excluded if it has every attribute in this list";
              }
            }
            description
              "Link is excluded if it has every attribute in this list";
          }
          leaf name9 {
            type xr:Cisco-ios-xr-string {
              length "1..32" {
                description
                  "Link is excluded if it has every attribute in this list";
              }
            }
            description
              "Link is excluded if it has every attribute in this list";
          }
        }
        list include10 {
          key "name1 name2 name3 name4 name5 name6 name7 name8 name9 name10";
          description
            "Link is excluded if it has every attribute in this list";
          leaf name1 {
            type xr:Cisco-ios-xr-string {
              length "1..32" {
                description
                  "Link is excluded if it has every attribute in this list";
              }
            }
            description
              "Link is excluded if it has every attribute in this list";
          }
          leaf name2 {
            type xr:Cisco-ios-xr-string {
              length "1..32" {
                description
                  "Link is excluded if it has every attribute in this list";
              }
            }
            description
              "Link is excluded if it has every attribute in this list";
          }
          leaf name3 {
            type xr:Cisco-ios-xr-string {
              length "1..32" {
                description
                  "Link is excluded if it has every attribute in this list";
              }
            }
            description
              "Link is excluded if it has every attribute in this list";
          }
          leaf name4 {
            type xr:Cisco-ios-xr-string {
              length "1..32" {
                description
                  "Link is excluded if it has every attribute in this list";
              }
            }
            description
              "Link is excluded if it has every attribute in this list";
          }
          leaf name5 {
            type xr:Cisco-ios-xr-string {
              length "1..32" {
                description
                  "Link is excluded if it has every attribute in this list";
              }
            }
            description
              "Link is excluded if it has every attribute in this list";
          }
          leaf name6 {
            type xr:Cisco-ios-xr-string {
              length "1..32" {
                description
                  "Link is excluded if it has every attribute in this list";
              }
            }
            description
              "Link is excluded if it has every attribute in this list";
          }
          leaf name7 {
            type xr:Cisco-ios-xr-string {
              length "1..32" {
                description
                  "Link is excluded if it has every attribute in this list";
              }
            }
            description
              "Link is excluded if it has every attribute in this list";
          }
          leaf name8 {
            type xr:Cisco-ios-xr-string {
              length "1..32" {
                description
                  "Link is excluded if it has every attribute in this list";
              }
            }
            description
              "Link is excluded if it has every attribute in this list";
          }
          leaf name9 {
            type xr:Cisco-ios-xr-string {
              length "1..32" {
                description
                  "Link is excluded if it has every attribute in this list";
              }
            }
            description
              "Link is excluded if it has every attribute in this list";
          }
          leaf name10 {
            type xr:Cisco-ios-xr-string {
              length "1..32" {
                description
                  "Link is excluded if it has every attribute in this list";
              }
            }
            description
              "Link is excluded if it has every attribute in this list";
          }
        }
      }
      container include-stricts {
        description
          "Links with exactly all these attributes are included in path calculation";
        list include1 {
          key "name1";
          description
            "Link is excluded if it has every attribute in this list";
          leaf name1 {
            type xr:Cisco-ios-xr-string {
              length "1..32" {
                description
                  "Link is excluded if it has every attribute in this list";
              }
            }
            description
              "Link is excluded if it has every attribute in this list";
          }
        }
        list include2 {
          key "name1 name2";
          description
            "Link is excluded if it has every attribute in this list";
          leaf name1 {
            type xr:Cisco-ios-xr-string {
              length "1..32" {
                description
                  "Link is excluded if it has every attribute in this list";
              }
            }
            description
              "Link is excluded if it has every attribute in this list";
          }
          leaf name2 {
            type xr:Cisco-ios-xr-string {
              length "1..32" {
                description
                  "Link is excluded if it has every attribute in this list";
              }
            }
            description
              "Link is excluded if it has every attribute in this list";
          }
        }
        list include3 {
          key "name1 name2 name3";
          description
            "Link is excluded if it has every attribute in this list";
          leaf name1 {
            type xr:Cisco-ios-xr-string {
              length "1..32" {
                description
                  "Link is excluded if it has every attribute in this list";
              }
            }
            description
              "Link is excluded if it has every attribute in this list";
          }
          leaf name2 {
            type xr:Cisco-ios-xr-string {
              length "1..32" {
                description
                  "Link is excluded if it has every attribute in this list";
              }
            }
            description
              "Link is excluded if it has every attribute in this list";
          }
          leaf name3 {
            type xr:Cisco-ios-xr-string {
              length "1..32" {
                description
                  "Link is excluded if it has every attribute in this list";
              }
            }
            description
              "Link is excluded if it has every attribute in this list";
          }
        }
        list include4 {
          key "name1 name2 name3 name4";
          description
            "Link is excluded if it has every attribute in this list";
          leaf name1 {
            type xr:Cisco-ios-xr-string {
              length "1..32" {
                description
                  "Link is excluded if it has every attribute in this list";
              }
            }
            description
              "Link is excluded if it has every attribute in this list";
          }
          leaf name2 {
            type xr:Cisco-ios-xr-string {
              length "1..32" {
                description
                  "Link is excluded if it has every attribute in this list";
              }
            }
            description
              "Link is excluded if it has every attribute in this list";
          }
          leaf name3 {
            type xr:Cisco-ios-xr-string {
              length "1..32" {
                description
                  "Link is excluded if it has every attribute in this list";
              }
            }
            description
              "Link is excluded if it has every attribute in this list";
          }
          leaf name4 {
            type xr:Cisco-ios-xr-string {
              length "1..32" {
                description
                  "Link is excluded if it has every attribute in this list";
              }
            }
            description
              "Link is excluded if it has every attribute in this list";
          }
        }
        list include5 {
          key "name1 name2 name3 name4 name5";
          description
            "Link is excluded if it has every attribute in this list";
          leaf name1 {
            type xr:Cisco-ios-xr-string {
              length "1..32" {
                description
                  "Link is excluded if it has every attribute in this list";
              }
            }
            description
              "Link is excluded if it has every attribute in this list";
          }
          leaf name2 {
            type xr:Cisco-ios-xr-string {
              length "1..32" {
                description
                  "Link is excluded if it has every attribute in this list";
              }
            }
            description
              "Link is excluded if it has every attribute in this list";
          }
          leaf name3 {
            type xr:Cisco-ios-xr-string {
              length "1..32" {
                description
                  "Link is excluded if it has every attribute in this list";
              }
            }
            description
              "Link is excluded if it has every attribute in this list";
          }
          leaf name4 {
            type xr:Cisco-ios-xr-string {
              length "1..32" {
                description
                  "Link is excluded if it has every attribute in this list";
              }
            }
            description
              "Link is excluded if it has every attribute in this list";
          }
          leaf name5 {
            type xr:Cisco-ios-xr-string {
              length "1..32" {
                description
                  "Link is excluded if it has every attribute in this list";
              }
            }
            description
              "Link is excluded if it has every attribute in this list";
          }
        }
        list include6 {
          key "name1 name2 name3 name4 name5 name6";
          description
            "Link is excluded if it has every attribute in this list";
          leaf name1 {
            type xr:Cisco-ios-xr-string {
              length "1..32" {
                description
                  "Link is excluded if it has every attribute in this list";
              }
            }
            description
              "Link is excluded if it has every attribute in this list";
          }
          leaf name2 {
            type xr:Cisco-ios-xr-string {
              length "1..32" {
                description
                  "Link is excluded if it has every attribute in this list";
              }
            }
            description
              "Link is excluded if it has every attribute in this list";
          }
          leaf name3 {
            type xr:Cisco-ios-xr-string {
              length "1..32" {
                description
                  "Link is excluded if it has every attribute in this list";
              }
            }
            description
              "Link is excluded if it has every attribute in this list";
          }
          leaf name4 {
            type xr:Cisco-ios-xr-string {
              length "1..32" {
                description
                  "Link is excluded if it has every attribute in this list";
              }
            }
            description
              "Link is excluded if it has every attribute in this list";
          }
          leaf name5 {
            type xr:Cisco-ios-xr-string {
              length "1..32" {
                description
                  "Link is excluded if it has every attribute in this list";
              }
            }
            description
              "Link is excluded if it has every attribute in this list";
          }
          leaf name6 {
            type xr:Cisco-ios-xr-string {
              length "1..32" {
                description
                  "Link is excluded if it has every attribute in this list";
              }
            }
            description
              "Link is excluded if it has every attribute in this list";
          }
        }
        list include7 {
          key "name1 name2 name3 name4 name5 name6 name7";
          description
            "Link is excluded if it has every attribute in this list";
          leaf name1 {
            type xr:Cisco-ios-xr-string {
              length "1..32" {
                description
                  "Link is excluded if it has every attribute in this list";
              }
            }
            description
              "Link is excluded if it has every attribute in this list";
          }
          leaf name2 {
            type xr:Cisco-ios-xr-string {
              length "1..32" {
                description
                  "Link is excluded if it has every attribute in this list";
              }
            }
            description
              "Link is excluded if it has every attribute in this list";
          }
          leaf name3 {
            type xr:Cisco-ios-xr-string {
              length "1..32" {
                description
                  "Link is excluded if it has every attribute in this list";
              }
            }
            description
              "Link is excluded if it has every attribute in this list";
          }
          leaf name4 {
            type xr:Cisco-ios-xr-string {
              length "1..32" {
                description
                  "Link is excluded if it has every attribute in this list";
              }
            }
            description
              "Link is excluded if it has every attribute in this list";
          }
          leaf name5 {
            type xr:Cisco-ios-xr-string {
              length "1..32" {
                description
                  "Link is excluded if it has every attribute in this list";
              }
            }
            description
              "Link is excluded if it has every attribute in this list";
          }
          leaf name6 {
            type xr:Cisco-ios-xr-string {
              length "1..32" {
                description
                  "Link is excluded if it has every attribute in this list";
              }
            }
            description
              "Link is excluded if it has every attribute in this list";
          }
          leaf name7 {
            type xr:Cisco-ios-xr-string {
              length "1..32" {
                description
                  "Link is excluded if it has every attribute in this list";
              }
            }
            description
              "Link is excluded if it has every attribute in this list";
          }
        }
        list include8 {
          key "name1 name2 name3 name4 name5 name6 name7 name8";
          description
            "Link is excluded if it has every attribute in this list";
          leaf name1 {
            type xr:Cisco-ios-xr-string {
              length "1..32" {
                description
                  "Link is excluded if it has every attribute in this list";
              }
            }
            description
              "Link is excluded if it has every attribute in this list";
          }
          leaf name2 {
            type xr:Cisco-ios-xr-string {
              length "1..32" {
                description
                  "Link is excluded if it has every attribute in this list";
              }
            }
            description
              "Link is excluded if it has every attribute in this list";
          }
          leaf name3 {
            type xr:Cisco-ios-xr-string {
              length "1..32" {
                description
                  "Link is excluded if it has every attribute in this list";
              }
            }
            description
              "Link is excluded if it has every attribute in this list";
          }
          leaf name4 {
            type xr:Cisco-ios-xr-string {
              length "1..32" {
                description
                  "Link is excluded if it has every attribute in this list";
              }
            }
            description
              "Link is excluded if it has every attribute in this list";
          }
          leaf name5 {
            type xr:Cisco-ios-xr-string {
              length "1..32" {
                description
                  "Link is excluded if it has every attribute in this list";
              }
            }
            description
              "Link is excluded if it has every attribute in this list";
          }
          leaf name6 {
            type xr:Cisco-ios-xr-string {
              length "1..32" {
                description
                  "Link is excluded if it has every attribute in this list";
              }
            }
            description
              "Link is excluded if it has every attribute in this list";
          }
          leaf name7 {
            type xr:Cisco-ios-xr-string {
              length "1..32" {
                description
                  "Link is excluded if it has every attribute in this list";
              }
            }
            description
              "Link is excluded if it has every attribute in this list";
          }
          leaf name8 {
            type xr:Cisco-ios-xr-string {
              length "1..32" {
                description
                  "Link is excluded if it has every attribute in this list";
              }
            }
            description
              "Link is excluded if it has every attribute in this list";
          }
        }
        list include9 {
          key "name1 name2 name3 name4 name5 name6 name7 name8 name9";
          description
            "Link is excluded if it has every attribute in this list";
          leaf name1 {
            type xr:Cisco-ios-xr-string {
              length "1..32" {
                description
                  "Link is excluded if it has every attribute in this list";
              }
            }
            description
              "Link is excluded if it has every attribute in this list";
          }
          leaf name2 {
            type xr:Cisco-ios-xr-string {
              length "1..32" {
                description
                  "Link is excluded if it has every attribute in this list";
              }
            }
            description
              "Link is excluded if it has every attribute in this list";
          }
          leaf name3 {
            type xr:Cisco-ios-xr-string {
              length "1..32" {
                description
                  "Link is excluded if it has every attribute in this list";
              }
            }
            description
              "Link is excluded if it has every attribute in this list";
          }
          leaf name4 {
            type xr:Cisco-ios-xr-string {
              length "1..32" {
                description
                  "Link is excluded if it has every attribute in this list";
              }
            }
            description
              "Link is excluded if it has every attribute in this list";
          }
          leaf name5 {
            type xr:Cisco-ios-xr-string {
              length "1..32" {
                description
                  "Link is excluded if it has every attribute in this list";
              }
            }
            description
              "Link is excluded if it has every attribute in this list";
          }
          leaf name6 {
            type xr:Cisco-ios-xr-string {
              length "1..32" {
                description
                  "Link is excluded if it has every attribute in this list";
              }
            }
            description
              "Link is excluded if it has every attribute in this list";
          }
          leaf name7 {
            type xr:Cisco-ios-xr-string {
              length "1..32" {
                description
                  "Link is excluded if it has every attribute in this list";
              }
            }
            description
              "Link is excluded if it has every attribute in this list";
          }
          leaf name8 {
            type xr:Cisco-ios-xr-string {
              length "1..32" {
                description
                  "Link is excluded if it has every attribute in this list";
              }
            }
            description
              "Link is excluded if it has every attribute in this list";
          }
          leaf name9 {
            type xr:Cisco-ios-xr-string {
              length "1..32" {
                description
                  "Link is excluded if it has every attribute in this list";
              }
            }
            description
              "Link is excluded if it has every attribute in this list";
          }
        }
        list include10 {
          key "name1 name2 name3 name4 name5 name6 name7 name8 name9 name10";
          description
            "Link is excluded if it has every attribute in this list";
          leaf name1 {
            type xr:Cisco-ios-xr-string {
              length "1..32" {
                description
                  "Link is excluded if it has every attribute in this list";
              }
            }
            description
              "Link is excluded if it has every attribute in this list";
          }
          leaf name2 {
            type xr:Cisco-ios-xr-string {
              length "1..32" {
                description
                  "Link is excluded if it has every attribute in this list";
              }
            }
            description
              "Link is excluded if it has every attribute in this list";
          }
          leaf name3 {
            type xr:Cisco-ios-xr-string {
              length "1..32" {
                description
                  "Link is excluded if it has every attribute in this list";
              }
            }
            description
              "Link is excluded if it has every attribute in this list";
          }
          leaf name4 {
            type xr:Cisco-ios-xr-string {
              length "1..32" {
                description
                  "Link is excluded if it has every attribute in this list";
              }
            }
            description
              "Link is excluded if it has every attribute in this list";
          }
          leaf name5 {
            type xr:Cisco-ios-xr-string {
              length "1..32" {
                description
                  "Link is excluded if it has every attribute in this list";
              }
            }
            description
              "Link is excluded if it has every attribute in this list";
          }
          leaf name6 {
            type xr:Cisco-ios-xr-string {
              length "1..32" {
                description
                  "Link is excluded if it has every attribute in this list";
              }
            }
            description
              "Link is excluded if it has every attribute in this list";
          }
          leaf name7 {
            type xr:Cisco-ios-xr-string {
              length "1..32" {
                description
                  "Link is excluded if it has every attribute in this list";
              }
            }
            description
              "Link is excluded if it has every attribute in this list";
          }
          leaf name8 {
            type xr:Cisco-ios-xr-string {
              length "1..32" {
                description
                  "Link is excluded if it has every attribute in this list";
              }
            }
            description
              "Link is excluded if it has every attribute in this list";
          }
          leaf name9 {
            type xr:Cisco-ios-xr-string {
              length "1..32" {
                description
                  "Link is excluded if it has every attribute in this list";
              }
            }
            description
              "Link is excluded if it has every attribute in this list";
          }
          leaf name10 {
            type xr:Cisco-ios-xr-string {
              length "1..32" {
                description
                  "Link is excluded if it has every attribute in this list";
              }
            }
            description
              "Link is excluded if it has every attribute in this list";
          }
        }
      }
      container excludes {
        description
          "Links with all these attributes are excluded from path calculation";
        list exclude1 {
          key "name1";
          description
            "Link is excluded if it has every attribute in this list";
          leaf name1 {
            type xr:Cisco-ios-xr-string {
              length "1..32" {
                description
                  "Link is excluded if it has every attribute in this list";
              }
            }
            description
              "Link is excluded if it has every attribute in this list";
          }
        }
        list exclude2 {
          key "name1 name2";
          description
            "Link is excluded if it has every attribute in this list";
          leaf name1 {
            type xr:Cisco-ios-xr-string {
              length "1..32" {
                description
                  "Link is excluded if it has every attribute in this list";
              }
            }
            description
              "Link is excluded if it has every attribute in this list";
          }
          leaf name2 {
            type xr:Cisco-ios-xr-string {
              length "1..32" {
                description
                  "Link is excluded if it has every attribute in this list";
              }
            }
            description
              "Link is excluded if it has every attribute in this list";
          }
        }
        list exclude3 {
          key "name1 name2 name3";
          description
            "Link is excluded if it has every attribute in this list";
          leaf name1 {
            type xr:Cisco-ios-xr-string {
              length "1..32" {
                description
                  "Link is excluded if it has every attribute in this list";
              }
            }
            description
              "Link is excluded if it has every attribute in this list";
          }
          leaf name2 {
            type xr:Cisco-ios-xr-string {
              length "1..32" {
                description
                  "Link is excluded if it has every attribute in this list";
              }
            }
            description
              "Link is excluded if it has every attribute in this list";
          }
          leaf name3 {
            type xr:Cisco-ios-xr-string {
              length "1..32" {
                description
                  "Link is excluded if it has every attribute in this list";
              }
            }
            description
              "Link is excluded if it has every attribute in this list";
          }
        }
        list exclude4 {
          key "name1 name2 name3 name4";
          description
            "Link is excluded if it has every attribute in this list";
          leaf name1 {
            type xr:Cisco-ios-xr-string {
              length "1..32" {
                description
                  "Link is excluded if it has every attribute in this list";
              }
            }
            description
              "Link is excluded if it has every attribute in this list";
          }
          leaf name2 {
            type xr:Cisco-ios-xr-string {
              length "1..32" {
                description
                  "Link is excluded if it has every attribute in this list";
              }
            }
            description
              "Link is excluded if it has every attribute in this list";
          }
          leaf name3 {
            type xr:Cisco-ios-xr-string {
              length "1..32" {
                description
                  "Link is excluded if it has every attribute in this list";
              }
            }
            description
              "Link is excluded if it has every attribute in this list";
          }
          leaf name4 {
            type xr:Cisco-ios-xr-string {
              length "1..32" {
                description
                  "Link is excluded if it has every attribute in this list";
              }
            }
            description
              "Link is excluded if it has every attribute in this list";
          }
        }
        list exclude5 {
          key "name1 name2 name3 name4 name5";
          description
            "Link is excluded if it has every attribute in this list";
          leaf name1 {
            type xr:Cisco-ios-xr-string {
              length "1..32" {
                description
                  "Link is excluded if it has every attribute in this list";
              }
            }
            description
              "Link is excluded if it has every attribute in this list";
          }
          leaf name2 {
            type xr:Cisco-ios-xr-string {
              length "1..32" {
                description
                  "Link is excluded if it has every attribute in this list";
              }
            }
            description
              "Link is excluded if it has every attribute in this list";
          }
          leaf name3 {
            type xr:Cisco-ios-xr-string {
              length "1..32" {
                description
                  "Link is excluded if it has every attribute in this list";
              }
            }
            description
              "Link is excluded if it has every attribute in this list";
          }
          leaf name4 {
            type xr:Cisco-ios-xr-string {
              length "1..32" {
                description
                  "Link is excluded if it has every attribute in this list";
              }
            }
            description
              "Link is excluded if it has every attribute in this list";
          }
          leaf name5 {
            type xr:Cisco-ios-xr-string {
              length "1..32" {
                description
                  "Link is excluded if it has every attribute in this list";
              }
            }
            description
              "Link is excluded if it has every attribute in this list";
          }
        }
        list exclude6 {
          key "name1 name2 name3 name4 name5 name6";
          description
            "Link is excluded if it has every attribute in this list";
          leaf name1 {
            type xr:Cisco-ios-xr-string {
              length "1..32" {
                description
                  "Link is excluded if it has every attribute in this list";
              }
            }
            description
              "Link is excluded if it has every attribute in this list";
          }
          leaf name2 {
            type xr:Cisco-ios-xr-string {
              length "1..32" {
                description
                  "Link is excluded if it has every attribute in this list";
              }
            }
            description
              "Link is excluded if it has every attribute in this list";
          }
          leaf name3 {
            type xr:Cisco-ios-xr-string {
              length "1..32" {
                description
                  "Link is excluded if it has every attribute in this list";
              }
            }
            description
              "Link is excluded if it has every attribute in this list";
          }
          leaf name4 {
            type xr:Cisco-ios-xr-string {
              length "1..32" {
                description
                  "Link is excluded if it has every attribute in this list";
              }
            }
            description
              "Link is excluded if it has every attribute in this list";
          }
          leaf name5 {
            type xr:Cisco-ios-xr-string {
              length "1..32" {
                description
                  "Link is excluded if it has every attribute in this list";
              }
            }
            description
              "Link is excluded if it has every attribute in this list";
          }
          leaf name6 {
            type xr:Cisco-ios-xr-string {
              length "1..32" {
                description
                  "Link is excluded if it has every attribute in this list";
              }
            }
            description
              "Link is excluded if it has every attribute in this list";
          }
        }
        list exclude7 {
          key "name1 name2 name3 name4 name5 name6 name7";
          description
            "Link is excluded if it has every attribute in this list";
          leaf name1 {
            type xr:Cisco-ios-xr-string {
              length "1..32" {
                description
                  "Link is excluded if it has every attribute in this list";
              }
            }
            description
              "Link is excluded if it has every attribute in this list";
          }
          leaf name2 {
            type xr:Cisco-ios-xr-string {
              length "1..32" {
                description
                  "Link is excluded if it has every attribute in this list";
              }
            }
            description
              "Link is excluded if it has every attribute in this list";
          }
          leaf name3 {
            type xr:Cisco-ios-xr-string {
              length "1..32" {
                description
                  "Link is excluded if it has every attribute in this list";
              }
            }
            description
              "Link is excluded if it has every attribute in this list";
          }
          leaf name4 {
            type xr:Cisco-ios-xr-string {
              length "1..32" {
                description
                  "Link is excluded if it has every attribute in this list";
              }
            }
            description
              "Link is excluded if it has every attribute in this list";
          }
          leaf name5 {
            type xr:Cisco-ios-xr-string {
              length "1..32" {
                description
                  "Link is excluded if it has every attribute in this list";
              }
            }
            description
              "Link is excluded if it has every attribute in this list";
          }
          leaf name6 {
            type xr:Cisco-ios-xr-string {
              length "1..32" {
                description
                  "Link is excluded if it has every attribute in this list";
              }
            }
            description
              "Link is excluded if it has every attribute in this list";
          }
          leaf name7 {
            type xr:Cisco-ios-xr-string {
              length "1..32" {
                description
                  "Link is excluded if it has every attribute in this list";
              }
            }
            description
              "Link is excluded if it has every attribute in this list";
          }
        }
        list exclude8 {
          key "name1 name2 name3 name4 name5 name6 name7 name8";
          description
            "Link is excluded if it has every attribute in this list";
          leaf name1 {
            type xr:Cisco-ios-xr-string {
              length "1..32" {
                description
                  "Link is excluded if it has every attribute in this list";
              }
            }
            description
              "Link is excluded if it has every attribute in this list";
          }
          leaf name2 {
            type xr:Cisco-ios-xr-string {
              length "1..32" {
                description
                  "Link is excluded if it has every attribute in this list";
              }
            }
            description
              "Link is excluded if it has every attribute in this list";
          }
          leaf name3 {
            type xr:Cisco-ios-xr-string {
              length "1..32" {
                description
                  "Link is excluded if it has every attribute in this list";
              }
            }
            description
              "Link is excluded if it has every attribute in this list";
          }
          leaf name4 {
            type xr:Cisco-ios-xr-string {
              length "1..32" {
                description
                  "Link is excluded if it has every attribute in this list";
              }
            }
            description
              "Link is excluded if it has every attribute in this list";
          }
          leaf name5 {
            type xr:Cisco-ios-xr-string {
              length "1..32" {
                description
                  "Link is excluded if it has every attribute in this list";
              }
            }
            description
              "Link is excluded if it has every attribute in this list";
          }
          leaf name6 {
            type xr:Cisco-ios-xr-string {
              length "1..32" {
                description
                  "Link is excluded if it has every attribute in this list";
              }
            }
            description
              "Link is excluded if it has every attribute in this list";
          }
          leaf name7 {
            type xr:Cisco-ios-xr-string {
              length "1..32" {
                description
                  "Link is excluded if it has every attribute in this list";
              }
            }
            description
              "Link is excluded if it has every attribute in this list";
          }
          leaf name8 {
            type xr:Cisco-ios-xr-string {
              length "1..32" {
                description
                  "Link is excluded if it has every attribute in this list";
              }
            }
            description
              "Link is excluded if it has every attribute in this list";
          }
        }
        list exclude9 {
          key "name1 name2 name3 name4 name5 name6 name7 name8 name9";
          description
            "Link is excluded if it has every attribute in this list";
          leaf name1 {
            type xr:Cisco-ios-xr-string {
              length "1..32" {
                description
                  "Link is excluded if it has every attribute in this list";
              }
            }
            description
              "Link is excluded if it has every attribute in this list";
          }
          leaf name2 {
            type xr:Cisco-ios-xr-string {
              length "1..32" {
                description
                  "Link is excluded if it has every attribute in this list";
              }
            }
            description
              "Link is excluded if it has every attribute in this list";
          }
          leaf name3 {
            type xr:Cisco-ios-xr-string {
              length "1..32" {
                description
                  "Link is excluded if it has every attribute in this list";
              }
            }
            description
              "Link is excluded if it has every attribute in this list";
          }
          leaf name4 {
            type xr:Cisco-ios-xr-string {
              length "1..32" {
                description
                  "Link is excluded if it has every attribute in this list";
              }
            }
            description
              "Link is excluded if it has every attribute in this list";
          }
          leaf name5 {
            type xr:Cisco-ios-xr-string {
              length "1..32" {
                description
                  "Link is excluded if it has every attribute in this list";
              }
            }
            description
              "Link is excluded if it has every attribute in this list";
          }
          leaf name6 {
            type xr:Cisco-ios-xr-string {
              length "1..32" {
                description
                  "Link is excluded if it has every attribute in this list";
              }
            }
            description
              "Link is excluded if it has every attribute in this list";
          }
          leaf name7 {
            type xr:Cisco-ios-xr-string {
              length "1..32" {
                description
                  "Link is excluded if it has every attribute in this list";
              }
            }
            description
              "Link is excluded if it has every attribute in this list";
          }
          leaf name8 {
            type xr:Cisco-ios-xr-string {
              length "1..32" {
                description
                  "Link is excluded if it has every attribute in this list";
              }
            }
            description
              "Link is excluded if it has every attribute in this list";
          }
          leaf name9 {
            type xr:Cisco-ios-xr-string {
              length "1..32" {
                description
                  "Link is excluded if it has every attribute in this list";
              }
            }
            description
              "Link is excluded if it has every attribute in this list";
          }
        }
        list exclude10 {
          key "name1 name2 name3 name4 name5 name6 name7 name8 name9 name10";
          description
            "Link is excluded if it has every attribute in this list";
          leaf name1 {
            type xr:Cisco-ios-xr-string {
              length "1..32" {
                description
                  "Link is excluded if it has every attribute in this list";
              }
            }
            description
              "Link is excluded if it has every attribute in this list";
          }
          leaf name2 {
            type xr:Cisco-ios-xr-string {
              length "1..32" {
                description
                  "Link is excluded if it has every attribute in this list";
              }
            }
            description
              "Link is excluded if it has every attribute in this list";
          }
          leaf name3 {
            type xr:Cisco-ios-xr-string {
              length "1..32" {
                description
                  "Link is excluded if it has every attribute in this list";
              }
            }
            description
              "Link is excluded if it has every attribute in this list";
          }
          leaf name4 {
            type xr:Cisco-ios-xr-string {
              length "1..32" {
                description
                  "Link is excluded if it has every attribute in this list";
              }
            }
            description
              "Link is excluded if it has every attribute in this list";
          }
          leaf name5 {
            type xr:Cisco-ios-xr-string {
              length "1..32" {
                description
                  "Link is excluded if it has every attribute in this list";
              }
            }
            description
              "Link is excluded if it has every attribute in this list";
          }
          leaf name6 {
            type xr:Cisco-ios-xr-string {
              length "1..32" {
                description
                  "Link is excluded if it has every attribute in this list";
              }
            }
            description
              "Link is excluded if it has every attribute in this list";
          }
          leaf name7 {
            type xr:Cisco-ios-xr-string {
              length "1..32" {
                description
                  "Link is excluded if it has every attribute in this list";
              }
            }
            description
              "Link is excluded if it has every attribute in this list";
          }
          leaf name8 {
            type xr:Cisco-ios-xr-string {
              length "1..32" {
                description
                  "Link is excluded if it has every attribute in this list";
              }
            }
            description
              "Link is excluded if it has every attribute in this list";
          }
          leaf name9 {
            type xr:Cisco-ios-xr-string {
              length "1..32" {
                description
                  "Link is excluded if it has every attribute in this list";
              }
            }
            description
              "Link is excluded if it has every attribute in this list";
          }
          leaf name10 {
            type xr:Cisco-ios-xr-string {
              length "1..32" {
                description
                  "Link is excluded if it has every attribute in this list";
              }
            }
            description
              "Link is excluded if it has every attribute in this list";
          }
        }
      }
      container exclude-all {
        presence "Indicates a exclude-all node is configured.";
        description
          "Links with any attribute are excluded from path calculation";
      }
      container ignore {
        presence "Indicates a ignore node is configured.";
        description
          "All links are included in path calculation regardless of attributes";
      }
      leaf affinity-attribute-value {
        type uint32 {
          range "0..4294967295" {
            description
              "Affinity attribute value";
          }
        }
        description
          "Affinity attribute value";
      }
      leaf mask {
        type uint32 {
          range "0..4294967295" {
            description
              "Affinity attribute mask value";
          }
        }
        description
          "Affinity attribute mask value";
      }
    }
    container autoroute {
      when "../a2:interface-name[starts-with(text(),'tunnel-te')]" {
        tailf:dependency "../a2:interface-name";
      }
      description
        "Parameters for IGP routing over tunnel";
      container announce {
        presence "Indicates a announce node is configured.";
        description
          "Announce tunnel to IGP";
        container metric {
          description
            "Specify MPLS tunnel metric";
          leaf absolute {
            type uint32 {
              range "1..2147483647" {
                description
                  "Absolute metric";
              }
            }
            description
              "Set metric mode absolute";
          }
          leaf relative {
            type int32 {
              range "-10..10" {
                description
                  "Relative metric";
              }
            }
            description
              "Set metric mode relative";
          }
          leaf constant-metric {
            type uint32 {
              range "1..2147483647" {
                description
                  "Set constant metric";
              }
            }
            description
              "Set constant metric";
          }
        }
        container include-ipv6 {
          presence "Indicates a include-ipv6 node is configured.";
          description
            "Announce tunnel as an IPv6 AA also";
        }
        container exclude-traffic {
          description
            "Exclude the type of traffic that goes through AA";
          container segment-routing {
            presence "Indicates a segment-routing node is configured.";
            description
              "Exclude segment-routing traffic from the autoroute announced tunnel";
          }
        }
      }
      container destinations {
        description
          "Adds static route to destination";
        list destination {
          key "address";
          description
            "Adds static route to destination";
          leaf address {
            type inet:ipv4-address-no-zone;
            description
              "Adds static route to destination";
          }
        }
      }
    }
    container backup-bw {
      when "../a2:interface-name[starts-with(text(),'tunnel-te')]" {
        tailf:dependency "../a2:interface-name";
      }
      must "(bandwidth) or ((pool-type or class-type) and (bandwidth or unlimited))";
      presence "Indicates a backup-bw node is configured.";
      description
        "Fast-reroute backup bandwidth requirement";
      leaf pool-type {
        type enumeration {
          enum "any-pool" {
            value 1;
            description
              "default/any-pool bandwidth";
          }
          enum "global-pool" {
            value 2;
            description
              "global-pool bandwidth";
          }
          enum "sub-pool" {
            value 4;
            description
              "sub-pool bandwidth";
          }
        }
        must "not(../class-type)";
        description
          "Configure pool type for backup bandwidth";
      }
      leaf class-type {
        type enumeration {
          enum "0" {
            value 0;
            description
              "class type 0";
          }
          enum "1" {
            value 1;
            description
              "class type 1";
          }
          enum "any" {
            value 9;
            description
              "any class type";
          }
        }
        must "not(../pool-type)";
        description
          "Specify the bandwidth class type";
      }
      leaf bandwidth {
        type uint32 {
          range "1..4294967295" {
            description
              "Bandwidth requirement in kbps";
          }
        }
        must "not(../unlimited)";
        description
          "Bandwidth requirement in kbps";
      }
      container unlimited {
        must "not(../bandwidth)";
        presence "Indicates a unlimited node is configured.";
        description
          "Unlimited backup bandwidth";
      }
    }
    container signalled-bandwidth {
      when "../a2:interface-name[starts-with(text(),'tunnel-te')]" {
        tailf:dependency "../a2:interface-name";
      }
      must "not(class-type and sub-pool)";
      presence "Indicates a signalled-bandwidth node is configured.";
      description
        "Tunnel bandwidth requirement to be signalled";
      leaf bandwidth {
        type uint32 {
          range "0..4294967295" {
            description
              "Bandwidth requirement in kbps";
          }
        }
        mandatory true;
        description
          "Bandwidth requirement in kbps";
      }
      leaf class-type {
        type uint32 {
          range "0..1" {
            description
              "Class type number";
          }
        }
        description
          "Specify the bandwidth class type";
      }
      container sub-pool {
        when "../bandwidth != 0";
        presence "Indicates a sub-pool node is configured.";
        description
          "Specify sub-pool bandwidth";
      }
    }
    container fast-reroute {
      when "../a2:interface-name[starts-with(text(),'tunnel-te')]" {
        tailf:dependency "../a2:interface-name";
      }
      presence "Indicates a fast-reroute node is configured.";
      description
        "Specify MPLS tunnel can be fast-rerouted";
      container protect {
        description
          "Enable protection request";
        container node {
          presence "Indicates a node node is configured.";
          description
            "Enable node protection request";
        }
        container bandwidth {
          presence "Indicates a bandwidth node is configured.";
          description
            "Enable bandwidth protection request";
        }
      }
    }
    leaf forward-class {
      when "../a2:interface-name[starts-with(text(),'tunnel-te')]" {
        tailf:dependency "../a2:interface-name";
      }
      type uint32 {
        range "0..7" {
          description
            "Forward class for the tunnel (default value 0)";
        }
      }
      description
        "Forward class for the tunnel (default value 0)";
    }
    container forwarding-adjacency {
      when "../a2:interface-name[starts-with(text(),'tunnel-te')]" {
        tailf:dependency "../a2:interface-name";
      }
      presence "Indicates a forwarding-adjacency node is configured.";
      description
        "Enable tunnel as a forwarding-adjacency and enter its submode";
      leaf holdtime {
        type uint32 {
          range "0..20000" {
            description
              "Hold time in ms";
          }
        }
        description
          "Hold time in ms";
      }
      container include-ipv6 {
        presence "Indicates a include-ipv6 node is configured.";
        description
          "Announce tunnel as an IPv6 FA also";
      }
    }
    leaf load-share {
      when "../a2:interface-name[starts-with(text(),'tunnel-te')]" {
        tailf:dependency "../a2:interface-name";
      }
      type uint32 {
        range "1..4294967295" {
          description
            "Loadshare value. Scale is the same as bandwidths.";
        }
      }
      description
        "Specify tunnel load-sharing metric";
    }
    container logging {
      when "../a2:interface-name[starts-with(text(),'tunnel-te')]" {
        tailf:dependency "../a2:interface-name";
      }
      description
        "Per-interface logging configuration";
      container events {
        description
          "Per-interface logging events";
        container lsp-status {
          description
            "Enable interface LSP state change alarms";
          container state {
            presence "Indicates a state node is configured.";
            description
              "Enable interface LSP UP/DOWN change alarms";
          }
          container reoptimize {
            presence "Indicates a reoptimize node is configured.";
            description
              "Enable interface LSP REOPT change alarms";
          }
          container reoptimize-attempts {
            presence "Indicates a reoptimize-attempts node is configured.";
            description
              "Enable interface LSP REOPT attempts change alarms";
          }
          container bw-change {
            presence "Indicates a bw-change node is configured.";
            description
              "Enable interface LSP BANDWIDTH change alarms";
          }
          container reroute {
            presence "Indicates a reroute node is configured.";
            description
              "Enable interface LSP REROUTE change alarms";
          }
          container record-route {
            presence "Indicates a record-route node is configured.";
            description
              "Enable interface LSP RECORD-ROUTE change alarms";
          }
          container switchover {
            presence "Indicates a switchover node is configured.";
            description
              "Enable interface LSP SWITCHOVER change alarms";
          }
          container insufficient-bandwidth {
            presence "Indicates a insufficient-bandwidth node is configured.";
            description
              "Enable Syslog for setup/reopt failure due to bandwidth";
          }
        }
        container pcalc-failure {
          presence "Indicates a pcalc-failure node is configured.";
          description
            "Enable logging for path calculation failures";
        }
        container bfd-status {
          presence "Indicates a bfd-status node is configured.";
          description
            "Enable BFD session state change alarms";
        }
        container all {
          presence "Indicates a all node is configured.";
          description
            "Enable all logging for this tunnel";
        }
      }
    }
    leaf signalled-name {
      when "../a2:interface-name[starts-with(text(),'tunnel-te')]" {
        tailf:dependency "../a2:interface-name";
      }
      type xr:Cisco-ios-xr-string {
        length "1..254" {
          description
            "The name to be included in signaling (max 254 characters)";
        }
      }
      description
        "The signaling name to assign to tunnel";
    }
    container path-options {
      when "../a2:interface-name[starts-with(text(),'tunnel-te')]" {
        tailf:dependency "../a2:interface-name";
      }
      description
        "Primary or fallback path setup option";
      list path-option {
        key "preference";
        description
          "Primary or fallback path setup option";
        leaf preference {
          type uint32 {
            range "1..1000" {
              description
                "Preference for this path option";
            }
          }
          description
            "Preference for this path option";
        }
        container dynamic {
          presence "Indicates a dynamic node is configured.";
          description
            "Setup based on dynamically allocated path";
        }
        container explicit {
          must "identifier or name";
          presence "Indicates a explicit node is configured.";
          description
            "Setup based on preconfigured path";
          leaf identifier {
            type uint32 {
              range "1..65535" {
                description
                  "Specify an IP explicit path by number";
              }
            }
            description
              "Specify an IP explicit path by number";
          }
          leaf name {
            type xr:Cisco-ios-xr-string {
              length "1..1024" {
                description
                  "Specify an IP explicit path by name";
              }
            }
            description
              "Specify an IP explicit path by name";
          }
          container verbatim {
            presence "Indicates a verbatim node is configured.";
            description
              "Do not require topology database for explicit path";
          }
        }
        container ospf {
          presence "Indicates a ospf node is configured.";
          description
            "Limit CSPF to a single OSPF instance and area";
          leaf instance-name {
            type xr:Cisco-ios-xr-string {
              length "1..32" {
                description
                  "OSPF instance name";
              }
            }
            description
              "OSPF instance name";
          }
          container area {
            description
              "OSPF area";
            leaf decimal {
              type uint32 {
                range "0..4294967295" {
                  description
                    "OSPF area ID as a decimal value";
                }
              }
              description
                "OSPF area ID as a decimal value";
            }
            leaf ip-address {
              type inet:ipv4-address-no-zone;
              description
                "OSPF area ID in IP address format";
            }
          }
        }
        container isis {
          presence "Indicates a isis node is configured.";
          description
            "Limit CSPF to a single IS-IS instance and area";
          leaf instance-name {
            type xr:Cisco-ios-xr-string {
              length "1..40" {
                description
                  "IS-IS instance name";
              }
            }
            description
              "IS-IS instance name";
          }
          leaf level {
            type uint32 {
              range "1..2" {
                description
                  "IS-IS level";
              }
            }
            must "../instance-name";
            description
              "IS-IS level";
          }
        }
        container attribute-set {
          description
            "Attribute set for this LSP";
          leaf attribute-set-name {
            type xr:Cisco-ios-xr-string {
              length "1..64" {
                description
                  "Specify attribute-set name (max 64 char)";
              }
            }
            description
              "Specify attribute-set name (max 64 char)";
          }
        }
        container protected-by {
          description
            "Path protection using a specific path-option";
          leaf index {
            type uint32 {
              range "1..1000" {
                description
                  "Index of the protecting path-option";
              }
            }
            description
              "Index of the protecting path-option";
          }
        }
        container lockdown {
          presence "Indicates a lockdown node is configured.";
          description
            "Not a candidate for reoptimization";
          container sticky {
            presence "Indicates a sticky node is configured.";
            description
              "Force tunnel to remain on the same path";
          }
        }
      }
    }
    container priority {
      when "../a2:interface-name[starts-with(text(),'tunnel-te')]" {
        tailf:dependency "../a2:interface-name";
      }
      presence "Indicates a priority node is configured.";
      description
        "Tunnel priority";
      leaf setup-priority {
        type uint32 {
          range "0..7" {
            description
              "Setup Priority";
          }
        }
        mandatory true;
        description
          "Tunnel priority";
      }
      leaf hold-priority {
        type uint32 {
          range "0..7" {
            description
              "Hold Priority";
          }
        }
        mandatory true;
        description
          "Hold Priority";
      }
    }
    container record-route {
      when "../a2:interface-name[starts-with(text(),'tunnel-te')]" {
        tailf:dependency "../a2:interface-name";
      }
      presence "Indicates a record-route node is configured.";
      description
        "Record the route used by the tunnel";
    }
    container binding-sid {
      when "../a2:interface-name[starts-with(text(),'tunnel-te')]" {
        tailf:dependency "../a2:interface-name";
      }
      description
        "Binding Segment Identifier";
      container mpls {
        presence "Indicates a mpls node is configured.";
        description
          "Use MPLS label as binding segment identifier";
        leaf label {
          type uint32 {
            range "16..4015" {
              description
                "MPLS label";
            }
          }
          description
            "Specify label value";
        }
      }
    }
    container policy-class {
      when "../a2:interface-name[starts-with(text(),'tunnel-te')]" {
        tailf:dependency "../a2:interface-name";
      }
      description
        "Specify classs for policy-based tunnel selection";
      container tunnel-policy-class-values {
        description
          "Tunnel policy class Value(s)";
        leaf-list tunnel-policy-class-value {
          type policy-class-type;
          max-elements "7";
          description
            "Tunnel policy class Value(s)";
        }
      }
    }
    container auto-bw {
      when "../a2:interface-name[starts-with(text(),'tunnel-te')]" {
        tailf:dependency "../a2:interface-name";
      }
      presence "Indicates a auto-bw node is configured.";
      description
        "Enable tunnel auto-bandwidth and enter its submode";
      leaf application {
        type uint32 {
          range "5..10080" {
            description
              " Auto-bw application frequency (minutes)";
          }
        }
        description
          "Set the tunnel auto-bw application frequency";
      }
      container bw-limit {
        description
          "Set min/max bandwidth auto-bw can apply on a tunnel";
        leaf min {
          type uint32 {
            range "0..4294967295" {
              description
                "Minimum bandwidth to apply (kbps)";
            }
          }
          description
            "Set minimum bandwidth auto-bw can apply on a tunnel";
        }
        leaf max {
          type uint32 {
            range "0..4294967295" {
              description
                "Maximum bandwidth to apply (kbps)";
            }
          }
          description
            "Set maximum bandwidth auto-bw can apply on a tunnel";
        }
      }
      container collect-bw-only {
        presence "Indicates a collect-bw-only node is configured.";
        description
          "Enable bandwidth collection only, no auto-bw adjustment";
      }
      container adjustment-threshold {
        presence "Indicates a adjustment-threshold node is configured.";
        description
          "Set the bandwidth change threshold to trigger adjustment";
        leaf threshold {
          type uint32 {
            range "1..100" {
              description
                "Bandwidth change percent to trigger adjustment";
            }
          }
          mandatory true;
          description
            "Set the bandwidth change threshold to trigger adjustment";
        }
        leaf min {
          type uint32 {
            range "10..4294967295" {
              description
                "Bandwidth change value to trigger adjustment (kbps)";
            }
          }
          mandatory true;
          description
            "Set the bandwidth change value to trigger adjustment";
        }
      }
      container overflow {
        presence "Indicates a overflow node is configured.";
        description
          "Configuring the tunnel overflow detection";
        leaf threshold {
          type uint32 {
            range "1..100" {
              description
                "Bandwidth change percent to trigger an overflow";
            }
          }
          mandatory true;
          description
            "Set the bandwidth change percent to trigger an overflow";
        }
        leaf min {
          type uint32 {
            range "10..4294967295" {
              description
                "Bandwidth change value to trigger an overflow (kbps)";
            }
          }
          mandatory true;
          description
            "Set the bandwidth change value to trigger an overflow";
        }
        leaf limit {
          type uint32 {
            range "1..10" {
              description
                "Number of consecutive collections exceeding threshold";
            }
          }
          mandatory true;
          description
            "Set the number of consecutive collections exceeding threshold";
        }
      }
      container underflow {
        presence "Indicates a underflow node is configured.";
        description
          "Configuring the tunnel underflow detection";
        leaf threshold {
          type uint32 {
            range "1..100" {
              description
                "Bandwidth change percent to trigger an underflow";
            }
          }
          mandatory true;
          description
            "Set the bandwidth change percent to trigger an underflow";
        }
        leaf min {
          type uint32 {
            range "10..4294967295" {
              description
                "Bandwidth change value to trigger an underflow (kbps)";
            }
          }
          mandatory true;
          description
            "Set the bandwidth change value to trigger an underflow";
        }
        leaf limit {
          type uint32 {
            range "1..10" {
              description
                "Number of consecutive collections exceeding threshold";
            }
          }
          mandatory true;
          description
            "Set the number of consecutive collections exceeding threshold";
        }
      }
      container resignal {
        description
          "Configure the tunnel resignal parameters after going down";
        container last-bandwidth {
          description
            "Configure the tunnel to use last applied bandwidth after going down";
          leaf time-out {
            type uint32 {
              range "1..3600000" {
                description
                  "time-out value to trigger a reset of the requested bandwidth (seconds)";
              }
            }
            description
              "Set the bandwidth resignal time-out value (in seconds) After this time the tunnel will be signaled with the configured bandwidth";
          }
        }
      }
    }
    container path-protection {
      when "../a2:interface-name[starts-with(text(),'tunnel-te')]" {
        tailf:dependency "../a2:interface-name";
      }
      presence "Indicates a path-protection node is configured.";
      description
        "Enable the path protection feature on this tunnel";
      container srlg-diverse {
        presence "Indicates a srlg-diverse node is configured.";
        description
          "Enforce SRLG diversity for protecting LSP";
      }
      container protection-mode {
        description
          "Configure Path Protection mode";
        container non-revertive {
          presence "Indicates a non-revertive node is configured.";
          description
            "Enable Non-Revertive mode";
        }
      }
    }
    container soft-preemption {
      when "../a2:interface-name[starts-with(text(),'tunnel-te')]" {
        tailf:dependency "../a2:interface-name";
      }
      presence "Indicates a soft-preemption node is configured.";
      description
        "Enable the soft-preemption feature on this tunnel";
    }
    container delay-measurement {
      when "../a2:interface-name[starts-with(text(),'tunnel-te')]" {
        tailf:dependency "../a2:interface-name";
      }
      presence "Indicates a delay-measurement node is configured.";
      description
        "Enable the delay-measurement feature on this tunnel";
    }
    container pce {
      when "../a2:interface-name[starts-with(text(),'tunnel-te')]" {
        tailf:dependency "../a2:interface-name";
      }
      description
        "Config PCE parameters";
      container delegation {
        presence "Indicates a delegation node is configured.";
        description
          "Enable PCE delegation";
      }
      container reopt {
        must "../delegation";
        presence "Indicates a reopt node is configured.";
        description
          "Enable local reopt for PCE delegation";
      }
    }
    container path-selection {
      when "../a2:interface-name[starts-with(text(),'tunnel-te')]" {
        tailf:dependency "../a2:interface-name";
      }
      description
        "Path Selection Configuration";
      container metric {
        must "igp or te or delay";
        presence "Indicates a metric node is configured.";
        description
          "Metric Type for path calculation";
        container igp {
          presence "Indicates a igp node is configured.";
          description
            "Use IGP metric";
        }
        container te {
          presence "Indicates a te node is configured.";
          description
            "Use TE metric";
        }
        container delay {
          presence "Indicates a delay node is configured.";
          description
            "Use delay metric";
        }
      }
      container tiebreaker {
        must "min-fill or max-fill or random";
        presence "Indicates a tiebreaker node is configured.";
        description
          "Equal cost multipath tiebreaker for path calculation (default: min-fill).";
        container min-fill {
          presence "Indicates a min-fill node is configured.";
          description
            "Prefer the path with the least-utilized links";
        }
        container max-fill {
          presence "Indicates a max-fill node is configured.";
          description
            "Prefer the path with the most-utilized links";
        }
        container random {
          presence "Indicates a random node is configured.";
          description
            "Prefer a path with links utilized randomly";
        }
      }
      leaf hop-limit {
        type uint32 {
          range "1..255" {
            description
              "Hop limit";
          }
        }
        description
          "Hop limit configuration";
      }
      leaf cost-limit {
        type uint32 {
          range "1..4294967295" {
            description
              "Cost limit";
          }
        }
        description
          "Cost limit configuration";
      }
      leaf delay-limit {
        type uint32 {
          range "1..4294967295" {
            description
              "Delay limit in usec";
          }
        }
        description
          "Delay limit configuration";
      }
    }
    container bidirectional {
      when "../a2:interface-name[starts-with(text(),'tunnel-te')]" {
        tailf:dependency "../a2:interface-name";
      }
      presence "Indicates a bidirectional node is configured.";
      description
        "Configure bidirectional LSPs";
      container association {
        description
          "Specify association parameters";
        container id {
          presence "Indicates a id node is configured.";
          description
            "Unique association ID";
          leaf association-id {
            type uint32 {
              range "0..65535" {
                description
                  "Association ID";
              }
            }
            mandatory true;
            description
              "Unique association ID";
          }
          leaf source-address {
            type inet:ipv4-address-no-zone;
            mandatory true;
            description
              "Source IP address";
          }
          leaf global-id {
            type uint32 {
              range "0..4294967295" {
                description
                  "Global ID";
              }
            }
            description
              "Global ID for association global source";
          }
        }
        container type {
          description
            "Association type";
          container co-routed {
            presence "Indicates a co-routed node is configured.";
            description
              "Co-routed LSPs (with bidirectional CSPF)";
            container fault-oam {
              presence "Indicates a fault-oam node is configured.";
              description
                "Enable fault OAM";
            }
            container wrap-protection {
              presence "Indicates a wrap-protection node is configured.";
              description
                "Enable LSP Wrap protection feature";
            }
            container signaling {
              description
                "Signaling configuration";
              container protection-object {
                description
                  "RSVP Protection Object signaling";
                container disable {
                  presence "Indicates a disable node is configured.";
                  description
                    "Disable signaling of RSVP Protection Object";
                }
              }
            }
          }
        }
      }
    }
    container bfd {
      when "../a2:interface-name[starts-with(text(),'tunnel-te')]" {
        tailf:dependency "../a2:interface-name";
      }
      presence "Indicates a bfd node is configured.";
      description
        "Configure BFD parameters";
      container fast-detect {
        presence "Indicates a fast-detect node is configured.";
        description
          "Enable BFD fast detection";
        container sbfd {
          presence "Indicates a sbfd node is configured.";
          description
            "Enable SBFD";
        }
      }
      leaf minimum-interval {
        type uint32 {
          range "3..30000" {
            description
              "Hello interval in milliseconds (default 100), lower bound is 50ms for non-GAL BFD sessions";
          }
        }
        description
          "Hello interval";
      }
      leaf multiplier {
        type uint32 {
          range "3..10" {
            description
              "Detect multiplier (default 3)";
          }
        }
        description
          "Detect multiplier";
      }
      leaf bringup-timeout {
        type uint32 {
          range "10..3600" {
            description
              "Wait for session to come up in seconds (default 60)";
          }
        }
        description
          "Timeout before BFD session bring up on new LSP is aborted";
      }
      container lsp-ping {
        description
          "Configure periodic LSP ping";
        leaf interval {
          type uint32 {
            range "60..3600" {
              description
                "Periodic LSP Ping interval in seconds (default 120)";
            }
          }
          description
            "Periodic LSP ping interval";
        }
        container disable {
          presence "Indicates a disable node is configured.";
          description
            "Disable periodic LSP Ping";
        }
      }
      container dampening {
        description
          "Configure dampening intervals to bring tunnel up";
        leaf initial-wait {
          type uint32 {
            range "1..518400000" {
              description
                "Delay in milliseconds (default 16000)";
            }
          }
          description
            "Initial delay before bringing up the tunnel";
        }
        leaf maximum-wait {
          type uint32 {
            range "1..518400000" {
              description
                "Delay in milliseconds (default 600000)";
            }
          }
          description
            "Maximum delay bringing up the tunnel";
        }
        leaf secondary-wait {
          type uint32 {
            range "1..518400000" {
              description
                "Delay in milliseconds (default 20000)";
            }
          }
          description
            "Secondary delay bringing up the tunnel";
        }
      }
      container encap-mode {
        description
          "BFD encap mode (default IP)";
        container gal {
          presence "Indicates a gal node is configured.";
          description
            "GAL encap mode";
        }
      }
    }
    container working-lsp {
      when "../a2:interface-name[starts-with(text(),'tunnel-tp')]" {
        tailf:dependency "../a2:interface-name";
      }
      description
        "Working LSP";
      leaf in-label {
        type uint32 {
          range "16..1048575" {
            description
              "Specify an unused MPLS label";
          }
        }
        description
          "Incoming MPLS label";
      }
      leaf out-label {
        type uint32 {
          range "16..1048575" {
            description
              "MPLS label";
          }
        }
        description
          "Outgoing MPLS label";
      }
      leaf out-link {
        type uint32 {
          range "1..65535" {
            description
              "Link ID";
          }
        }
        must "../out-label";
        description
          "Outgoing TP link ID";
      }
      leaf lsp-number {
        type uint32 {
          range "0..65535" {
            description
              "LSP ID";
          }
        }
        description
          "LSP Identifier";
      }
      container lockout {
        presence "Indicates a lockout node is configured.";
        description
          "Lockout working LSP";
      }
    }
    leaf destination {
      when "../a2:interface-name[starts-with(text(),'tunnel-te')]" {
        tailf:dependency "../a2:interface-name";
      }
      type inet:ipv4-address-no-zone;
      description
        "Specify tunnel destination";
    }
    container tunnel-mte {
      when "../a2:interface-name[starts-with(text(),'tunnel-mte')]" {
        tailf:dependency "../a2:interface-name";
      }
      description
        "Configuratoin specific for tunnel-mte interface";
      container destinations {
        description
          "Specify a destination to an endpoint of the tunnel";
        list destination {
          key "address";
          description
            "Specify a destination to an endpoint of the tunnel";
          leaf address {
            type inet:ipv4-address-no-zone;
            description
              "Specify a destination to an endpoint of the tunnel";
          }
          container path-options {
            description
              "Primary or fallback path setup option";
            list path-option {
              must "dynamic or explicit/identifier or explicit/name";
              key "path-option-id";
              description
                "Primary or fallback path setup option";
              leaf path-option-id {
                type uint32 {
                  range "1..1000" {
                    description
                      "Preference for this path option";
                  }
                }
                description
                  "Primary or fallback path setup option";
              }
              container dynamic {
                presence "Indicates a dynamic node is configured.";
                description
                  "Setup based on dynamically allocated path";
              }
              container explicit {
                description
                  "Setup based on preconfigured path";
                leaf identifier {
                  type uint32 {
                    range "1..65535" {
                      description
                        "Specify an IP explicit path by number";
                    }
                  }
                  must "not(../name)";
                  description
                    "Specify an IP explicit path by number";
                }
                leaf name {
                  type xr:Cisco-ios-xr-string {
                    length "1..800" {
                      description
                        "Specify an IP explicit path by name";
                    }
                  }
                  must "not(../identifier)";
                  description
                    "Specify an IP explicit path by name";
                }
              }
              container lockdown {
                must "../dynamic or ../explicit/identifier or ../explicit/name";
                presence "Indicates a lockdown node is configured.";
                description
                  "Not a candidate for reoptimization";
              }
              container verbatim {
                must "../explicit/identifier or ../explicit/name";
                presence "Indicates a verbatim node is configured.";
                description
                  "Do not require topology database for explicit path";
              }
            }
          }
          container logging {
            description
              "Per-destination logging configuration";
            container events {
              description
                "Per-destination logging events";
              container sub-lsp {
                description
                  "Enable destination sub-lsp state change alarms";
                container state {
                  presence "Indicates a state node is configured.";
                  description
                    "Enable destination sub-lsp UP/DOWN change alarms";
                }
                container reroute {
                  presence "Indicates a reroute node is configured.";
                  description
                    "Enable destination sub-lsp REROUTE change alarms";
                }
                container insufficient-bandwidth {
                  presence "Indicates a insufficient-bandwidth node is configured.";
                  description
                    "Enable Syslog for setup/reopt failure due to bandwidth";
                }
                container pcalc-failure {
                  presence "Indicates a pcalc-failure node is configured.";
                  description
                    "Enable logging for path calculation failures";
                }
              }
            }
          }
          container disable {
            presence "Indicates a disable node is configured.";
            description
              "Disable the given destination";
          }
        }
      }
      container priority {
        presence "Indicates a priority node is configured.";
        description
          "Tunnel priority";
        leaf setup-priority {
          type uint32 {
            range "0..7" {
              description
                "Setup Priority";
            }
          }
          mandatory true;
          description
            "Tunnel priority";
        }
        leaf hold-priority {
          type uint32 {
            range "0..7" {
              description
                "Hold Priority";
            }
          }
          mandatory true;
          description
            "Hold Priority";
        }
      }
      container logging {
        description
          "Per-interface logging configuration";
        container events {
          description
            "Per-interface logging events";
          container lsp-status {
            description
              "Enable interface LSP state change alarms";
            container state {
              presence "Indicates a state node is configured.";
              description
                "Enable interface LSP UP/DOWN change alarms";
            }
            container reoptimize-attempts {
              presence "Indicates a reoptimize-attempts node is configured.";
              description
                "Enable interface LSP REOPT attempts change alarms";
            }
            container reoptimize {
              presence "Indicates a reoptimize node is configured.";
              description
                "Enable interface LSP REOPT change alarms";
            }
            container reroute {
              presence "Indicates a reroute node is configured.";
              description
                "Enable interface LSP REROUTE change alarms";
            }
            container insufficient-bandwidth {
              presence "Indicates a insufficient-bandwidth node is configured.";
              description
                "Enable Syslog for setup/reopt failure due to bandwidth";
            }
            container bw-change {
              presence "Indicates a bw-change node is configured.";
              description
                "Enable interface LSP BANDWIDTH change notification";
            }
          }
          container pcalc-failure {
            presence "Indicates a pcalc-failure node is configured.";
            description
              "Enable logging for path calculation failures";
          }
          container sub-lsp-status {
            description
              "Enable all sub-LSP state change alarms";
            container state {
              presence "Indicates a state node is configured.";
              description
                "Enable all sub-LSP UP/DOWN change alarms";
            }
          }
          container all {
            presence "Indicates a all node is configured.";
            description
              "Enable all logging for this tunnel";
          }
        }
      }
      leaf signalled-name {
        type xr:Cisco-ios-xr-string {
          length "1..254" {
            description
              "The name to be included in signaling (max 64 characters)";
          }
        }
        description
          "The signaling name to assign to tunnel";
      }
      container signalled-bandwidth {
        presence "Indicates a signalled-bandwidth node is configured.";
        description
          "Tunnel bandwidth requirement to be signalled";
        leaf bandwidth {
          type uint32 {
            range "0..4294967295" {
              description
                "Bandwidth requirement in kbps";
            }
          }
          mandatory true;
          description
            "Bandwidth requirement in kbps";
        }
        leaf class-type {
          type uint32 {
            range "0..1" {
              description
                "Class type number";
            }
          }
          must "not(../sub-pool)";
          description
            "Specify the bandwidth class type";
        }
        container sub-pool {
          when "../bandwidth != 0";
          must "not(../class-type)";
          presence "Indicates a sub-pool node is configured.";
          description
            "Specify sub-pool bandwidth";
        }
      }
      container fast-reroute {
        presence "Indicates a fast-reroute node is configured.";
        description
          "Specify MPLS tunnel can be fast-rerouted";
      }
      container record-route {
        presence "Indicates a record-route node is configured.";
        description
          "Record the route used by the tunnel";
      }
      container affinity {
        description
          "Link attributes for links traversed by tunnel";
        container includes {
          description
            "Links with all these attributes are included in path calculation";
          list include1 {
            key "name1";
            description
              "Link is excluded if it has every attribute in this list";
            leaf name1 {
              type xr:Cisco-ios-xr-string {
                length "1..32" {
                  description
                    "Link is excluded if it has every attribute in this list";
                }
              }
              description
                "Link is excluded if it has every attribute in this list";
            }
          }
          list include2 {
            key "name1 name2";
            description
              "Link is excluded if it has every attribute in this list";
            leaf name1 {
              type xr:Cisco-ios-xr-string {
                length "1..32" {
                  description
                    "Link is excluded if it has every attribute in this list";
                }
              }
              description
                "Link is excluded if it has every attribute in this list";
            }
            leaf name2 {
              type xr:Cisco-ios-xr-string {
                length "1..32" {
                  description
                    "Link is excluded if it has every attribute in this list";
                }
              }
              description
                "Link is excluded if it has every attribute in this list";
            }
          }
          list include3 {
            key "name1 name2 name3";
            description
              "Link is excluded if it has every attribute in this list";
            leaf name1 {
              type xr:Cisco-ios-xr-string {
                length "1..32" {
                  description
                    "Link is excluded if it has every attribute in this list";
                }
              }
              description
                "Link is excluded if it has every attribute in this list";
            }
            leaf name2 {
              type xr:Cisco-ios-xr-string {
                length "1..32" {
                  description
                    "Link is excluded if it has every attribute in this list";
                }
              }
              description
                "Link is excluded if it has every attribute in this list";
            }
            leaf name3 {
              type xr:Cisco-ios-xr-string {
                length "1..32" {
                  description
                    "Link is excluded if it has every attribute in this list";
                }
              }
              description
                "Link is excluded if it has every attribute in this list";
            }
          }
          list include4 {
            key "name1 name2 name3 name4";
            description
              "Link is excluded if it has every attribute in this list";
            leaf name1 {
              type xr:Cisco-ios-xr-string {
                length "1..32" {
                  description
                    "Link is excluded if it has every attribute in this list";
                }
              }
              description
                "Link is excluded if it has every attribute in this list";
            }
            leaf name2 {
              type xr:Cisco-ios-xr-string {
                length "1..32" {
                  description
                    "Link is excluded if it has every attribute in this list";
                }
              }
              description
                "Link is excluded if it has every attribute in this list";
            }
            leaf name3 {
              type xr:Cisco-ios-xr-string {
                length "1..32" {
                  description
                    "Link is excluded if it has every attribute in this list";
                }
              }
              description
                "Link is excluded if it has every attribute in this list";
            }
            leaf name4 {
              type xr:Cisco-ios-xr-string {
                length "1..32" {
                  description
                    "Link is excluded if it has every attribute in this list";
                }
              }
              description
                "Link is excluded if it has every attribute in this list";
            }
          }
          list include5 {
            key "name1 name2 name3 name4 name5";
            description
              "Link is excluded if it has every attribute in this list";
            leaf name1 {
              type xr:Cisco-ios-xr-string {
                length "1..32" {
                  description
                    "Link is excluded if it has every attribute in this list";
                }
              }
              description
                "Link is excluded if it has every attribute in this list";
            }
            leaf name2 {
              type xr:Cisco-ios-xr-string {
                length "1..32" {
                  description
                    "Link is excluded if it has every attribute in this list";
                }
              }
              description
                "Link is excluded if it has every attribute in this list";
            }
            leaf name3 {
              type xr:Cisco-ios-xr-string {
                length "1..32" {
                  description
                    "Link is excluded if it has every attribute in this list";
                }
              }
              description
                "Link is excluded if it has every attribute in this list";
            }
            leaf name4 {
              type xr:Cisco-ios-xr-string {
                length "1..32" {
                  description
                    "Link is excluded if it has every attribute in this list";
                }
              }
              description
                "Link is excluded if it has every attribute in this list";
            }
            leaf name5 {
              type xr:Cisco-ios-xr-string {
                length "1..32" {
                  description
                    "Link is excluded if it has every attribute in this list";
                }
              }
              description
                "Link is excluded if it has every attribute in this list";
            }
          }
          list include6 {
            key "name1 name2 name3 name4 name5 name6";
            description
              "Link is excluded if it has every attribute in this list";
            leaf name1 {
              type xr:Cisco-ios-xr-string {
                length "1..32" {
                  description
                    "Link is excluded if it has every attribute in this list";
                }
              }
              description
                "Link is excluded if it has every attribute in this list";
            }
            leaf name2 {
              type xr:Cisco-ios-xr-string {
                length "1..32" {
                  description
                    "Link is excluded if it has every attribute in this list";
                }
              }
              description
                "Link is excluded if it has every attribute in this list";
            }
            leaf name3 {
              type xr:Cisco-ios-xr-string {
                length "1..32" {
                  description
                    "Link is excluded if it has every attribute in this list";
                }
              }
              description
                "Link is excluded if it has every attribute in this list";
            }
            leaf name4 {
              type xr:Cisco-ios-xr-string {
                length "1..32" {
                  description
                    "Link is excluded if it has every attribute in this list";
                }
              }
              description
                "Link is excluded if it has every attribute in this list";
            }
            leaf name5 {
              type xr:Cisco-ios-xr-string {
                length "1..32" {
                  description
                    "Link is excluded if it has every attribute in this list";
                }
              }
              description
                "Link is excluded if it has every attribute in this list";
            }
            leaf name6 {
              type xr:Cisco-ios-xr-string {
                length "1..32" {
                  description
                    "Link is excluded if it has every attribute in this list";
                }
              }
              description
                "Link is excluded if it has every attribute in this list";
            }
          }
          list include7 {
            key "name1 name2 name3 name4 name5 name6 name7";
            description
              "Link is excluded if it has every attribute in this list";
            leaf name1 {
              type xr:Cisco-ios-xr-string {
                length "1..32" {
                  description
                    "Link is excluded if it has every attribute in this list";
                }
              }
              description
                "Link is excluded if it has every attribute in this list";
            }
            leaf name2 {
              type xr:Cisco-ios-xr-string {
                length "1..32" {
                  description
                    "Link is excluded if it has every attribute in this list";
                }
              }
              description
                "Link is excluded if it has every attribute in this list";
            }
            leaf name3 {
              type xr:Cisco-ios-xr-string {
                length "1..32" {
                  description
                    "Link is excluded if it has every attribute in this list";
                }
              }
              description
                "Link is excluded if it has every attribute in this list";
            }
            leaf name4 {
              type xr:Cisco-ios-xr-string {
                length "1..32" {
                  description
                    "Link is excluded if it has every attribute in this list";
                }
              }
              description
                "Link is excluded if it has every attribute in this list";
            }
            leaf name5 {
              type xr:Cisco-ios-xr-string {
                length "1..32" {
                  description
                    "Link is excluded if it has every attribute in this list";
                }
              }
              description
                "Link is excluded if it has every attribute in this list";
            }
            leaf name6 {
              type xr:Cisco-ios-xr-string {
                length "1..32" {
                  description
                    "Link is excluded if it has every attribute in this list";
                }
              }
              description
                "Link is excluded if it has every attribute in this list";
            }
            leaf name7 {
              type xr:Cisco-ios-xr-string {
                length "1..32" {
                  description
                    "Link is excluded if it has every attribute in this list";
                }
              }
              description
                "Link is excluded if it has every attribute in this list";
            }
          }
          list include8 {
            key "name1 name2 name3 name4 name5 name6 name7 name8";
            description
              "Link is excluded if it has every attribute in this list";
            leaf name1 {
              type xr:Cisco-ios-xr-string {
                length "1..32" {
                  description
                    "Link is excluded if it has every attribute in this list";
                }
              }
              description
                "Link is excluded if it has every attribute in this list";
            }
            leaf name2 {
              type xr:Cisco-ios-xr-string {
                length "1..32" {
                  description
                    "Link is excluded if it has every attribute in this list";
                }
              }
              description
                "Link is excluded if it has every attribute in this list";
            }
            leaf name3 {
              type xr:Cisco-ios-xr-string {
                length "1..32" {
                  description
                    "Link is excluded if it has every attribute in this list";
                }
              }
              description
                "Link is excluded if it has every attribute in this list";
            }
            leaf name4 {
              type xr:Cisco-ios-xr-string {
                length "1..32" {
                  description
                    "Link is excluded if it has every attribute in this list";
                }
              }
              description
                "Link is excluded if it has every attribute in this list";
            }
            leaf name5 {
              type xr:Cisco-ios-xr-string {
                length "1..32" {
                  description
                    "Link is excluded if it has every attribute in this list";
                }
              }
              description
                "Link is excluded if it has every attribute in this list";
            }
            leaf name6 {
              type xr:Cisco-ios-xr-string {
                length "1..32" {
                  description
                    "Link is excluded if it has every attribute in this list";
                }
              }
              description
                "Link is excluded if it has every attribute in this list";
            }
            leaf name7 {
              type xr:Cisco-ios-xr-string {
                length "1..32" {
                  description
                    "Link is excluded if it has every attribute in this list";
                }
              }
              description
                "Link is excluded if it has every attribute in this list";
            }
            leaf name8 {
              type xr:Cisco-ios-xr-string {
                length "1..32" {
                  description
                    "Link is excluded if it has every attribute in this list";
                }
              }
              description
                "Link is excluded if it has every attribute in this list";
            }
          }
          list include9 {
            key "name1 name2 name3 name4 name5 name6 name7 name8 name9";
            description
              "Link is excluded if it has every attribute in this list";
            leaf name1 {
              type xr:Cisco-ios-xr-string {
                length "1..32" {
                  description
                    "Link is excluded if it has every attribute in this list";
                }
              }
              description
                "Link is excluded if it has every attribute in this list";
            }
            leaf name2 {
              type xr:Cisco-ios-xr-string {
                length "1..32" {
                  description
                    "Link is excluded if it has every attribute in this list";
                }
              }
              description
                "Link is excluded if it has every attribute in this list";
            }
            leaf name3 {
              type xr:Cisco-ios-xr-string {
                length "1..32" {
                  description
                    "Link is excluded if it has every attribute in this list";
                }
              }
              description
                "Link is excluded if it has every attribute in this list";
            }
            leaf name4 {
              type xr:Cisco-ios-xr-string {
                length "1..32" {
                  description
                    "Link is excluded if it has every attribute in this list";
                }
              }
              description
                "Link is excluded if it has every attribute in this list";
            }
            leaf name5 {
              type xr:Cisco-ios-xr-string {
                length "1..32" {
                  description
                    "Link is excluded if it has every attribute in this list";
                }
              }
              description
                "Link is excluded if it has every attribute in this list";
            }
            leaf name6 {
              type xr:Cisco-ios-xr-string {
                length "1..32" {
                  description
                    "Link is excluded if it has every attribute in this list";
                }
              }
              description
                "Link is excluded if it has every attribute in this list";
            }
            leaf name7 {
              type xr:Cisco-ios-xr-string {
                length "1..32" {
                  description
                    "Link is excluded if it has every attribute in this list";
                }
              }
              description
                "Link is excluded if it has every attribute in this list";
            }
            leaf name8 {
              type xr:Cisco-ios-xr-string {
                length "1..32" {
                  description
                    "Link is excluded if it has every attribute in this list";
                }
              }
              description
                "Link is excluded if it has every attribute in this list";
            }
            leaf name9 {
              type xr:Cisco-ios-xr-string {
                length "1..32" {
                  description
                    "Link is excluded if it has every attribute in this list";
                }
              }
              description
                "Link is excluded if it has every attribute in this list";
            }
          }
          list include10 {
            key "name1 name2 name3 name4 name5 name6 name7 name8 name9 name10";
            description
              "Link is excluded if it has every attribute in this list";
            leaf name1 {
              type xr:Cisco-ios-xr-string {
                length "1..32" {
                  description
                    "Link is excluded if it has every attribute in this list";
                }
              }
              description
                "Link is excluded if it has every attribute in this list";
            }
            leaf name2 {
              type xr:Cisco-ios-xr-string {
                length "1..32" {
                  description
                    "Link is excluded if it has every attribute in this list";
                }
              }
              description
                "Link is excluded if it has every attribute in this list";
            }
            leaf name3 {
              type xr:Cisco-ios-xr-string {
                length "1..32" {
                  description
                    "Link is excluded if it has every attribute in this list";
                }
              }
              description
                "Link is excluded if it has every attribute in this list";
            }
            leaf name4 {
              type xr:Cisco-ios-xr-string {
                length "1..32" {
                  description
                    "Link is excluded if it has every attribute in this list";
                }
              }
              description
                "Link is excluded if it has every attribute in this list";
            }
            leaf name5 {
              type xr:Cisco-ios-xr-string {
                length "1..32" {
                  description
                    "Link is excluded if it has every attribute in this list";
                }
              }
              description
                "Link is excluded if it has every attribute in this list";
            }
            leaf name6 {
              type xr:Cisco-ios-xr-string {
                length "1..32" {
                  description
                    "Link is excluded if it has every attribute in this list";
                }
              }
              description
                "Link is excluded if it has every attribute in this list";
            }
            leaf name7 {
              type xr:Cisco-ios-xr-string {
                length "1..32" {
                  description
                    "Link is excluded if it has every attribute in this list";
                }
              }
              description
                "Link is excluded if it has every attribute in this list";
            }
            leaf name8 {
              type xr:Cisco-ios-xr-string {
                length "1..32" {
                  description
                    "Link is excluded if it has every attribute in this list";
                }
              }
              description
                "Link is excluded if it has every attribute in this list";
            }
            leaf name9 {
              type xr:Cisco-ios-xr-string {
                length "1..32" {
                  description
                    "Link is excluded if it has every attribute in this list";
                }
              }
              description
                "Link is excluded if it has every attribute in this list";
            }
            leaf name10 {
              type xr:Cisco-ios-xr-string {
                length "1..32" {
                  description
                    "Link is excluded if it has every attribute in this list";
                }
              }
              description
                "Link is excluded if it has every attribute in this list";
            }
          }
        }
        container include-stricts {
          description
            "Links with exactly all these attributes are included in path calculation";
          list include1 {
            key "name1";
            description
              "Link is excluded if it has every attribute in this list";
            leaf name1 {
              type xr:Cisco-ios-xr-string {
                length "1..32" {
                  description
                    "Link is excluded if it has every attribute in this list";
                }
              }
              description
                "Link is excluded if it has every attribute in this list";
            }
          }
          list include2 {
            key "name1 name2";
            description
              "Link is excluded if it has every attribute in this list";
            leaf name1 {
              type xr:Cisco-ios-xr-string {
                length "1..32" {
                  description
                    "Link is excluded if it has every attribute in this list";
                }
              }
              description
                "Link is excluded if it has every attribute in this list";
            }
            leaf name2 {
              type xr:Cisco-ios-xr-string {
                length "1..32" {
                  description
                    "Link is excluded if it has every attribute in this list";
                }
              }
              description
                "Link is excluded if it has every attribute in this list";
            }
          }
          list include3 {
            key "name1 name2 name3";
            description
              "Link is excluded if it has every attribute in this list";
            leaf name1 {
              type xr:Cisco-ios-xr-string {
                length "1..32" {
                  description
                    "Link is excluded if it has every attribute in this list";
                }
              }
              description
                "Link is excluded if it has every attribute in this list";
            }
            leaf name2 {
              type xr:Cisco-ios-xr-string {
                length "1..32" {
                  description
                    "Link is excluded if it has every attribute in this list";
                }
              }
              description
                "Link is excluded if it has every attribute in this list";
            }
            leaf name3 {
              type xr:Cisco-ios-xr-string {
                length "1..32" {
                  description
                    "Link is excluded if it has every attribute in this list";
                }
              }
              description
                "Link is excluded if it has every attribute in this list";
            }
          }
          list include4 {
            key "name1 name2 name3 name4";
            description
              "Link is excluded if it has every attribute in this list";
            leaf name1 {
              type xr:Cisco-ios-xr-string {
                length "1..32" {
                  description
                    "Link is excluded if it has every attribute in this list";
                }
              }
              description
                "Link is excluded if it has every attribute in this list";
            }
            leaf name2 {
              type xr:Cisco-ios-xr-string {
                length "1..32" {
                  description
                    "Link is excluded if it has every attribute in this list";
                }
              }
              description
                "Link is excluded if it has every attribute in this list";
            }
            leaf name3 {
              type xr:Cisco-ios-xr-string {
                length "1..32" {
                  description
                    "Link is excluded if it has every attribute in this list";
                }
              }
              description
                "Link is excluded if it has every attribute in this list";
            }
            leaf name4 {
              type xr:Cisco-ios-xr-string {
                length "1..32" {
                  description
                    "Link is excluded if it has every attribute in this list";
                }
              }
              description
                "Link is excluded if it has every attribute in this list";
            }
          }
          list include5 {
            key "name1 name2 name3 name4 name5";
            description
              "Link is excluded if it has every attribute in this list";
            leaf name1 {
              type xr:Cisco-ios-xr-string {
                length "1..32" {
                  description
                    "Link is excluded if it has every attribute in this list";
                }
              }
              description
                "Link is excluded if it has every attribute in this list";
            }
            leaf name2 {
              type xr:Cisco-ios-xr-string {
                length "1..32" {
                  description
                    "Link is excluded if it has every attribute in this list";
                }
              }
              description
                "Link is excluded if it has every attribute in this list";
            }
            leaf name3 {
              type xr:Cisco-ios-xr-string {
                length "1..32" {
                  description
                    "Link is excluded if it has every attribute in this list";
                }
              }
              description
                "Link is excluded if it has every attribute in this list";
            }
            leaf name4 {
              type xr:Cisco-ios-xr-string {
                length "1..32" {
                  description
                    "Link is excluded if it has every attribute in this list";
                }
              }
              description
                "Link is excluded if it has every attribute in this list";
            }
            leaf name5 {
              type xr:Cisco-ios-xr-string {
                length "1..32" {
                  description
                    "Link is excluded if it has every attribute in this list";
                }
              }
              description
                "Link is excluded if it has every attribute in this list";
            }
          }
          list include6 {
            key "name1 name2 name3 name4 name5 name6";
            description
              "Link is excluded if it has every attribute in this list";
            leaf name1 {
              type xr:Cisco-ios-xr-string {
                length "1..32" {
                  description
                    "Link is excluded if it has every attribute in this list";
                }
              }
              description
                "Link is excluded if it has every attribute in this list";
            }
            leaf name2 {
              type xr:Cisco-ios-xr-string {
                length "1..32" {
                  description
                    "Link is excluded if it has every attribute in this list";
                }
              }
              description
                "Link is excluded if it has every attribute in this list";
            }
            leaf name3 {
              type xr:Cisco-ios-xr-string {
                length "1..32" {
                  description
                    "Link is excluded if it has every attribute in this list";
                }
              }
              description
                "Link is excluded if it has every attribute in this list";
            }
            leaf name4 {
              type xr:Cisco-ios-xr-string {
                length "1..32" {
                  description
                    "Link is excluded if it has every attribute in this list";
                }
              }
              description
                "Link is excluded if it has every attribute in this list";
            }
            leaf name5 {
              type xr:Cisco-ios-xr-string {
                length "1..32" {
                  description
                    "Link is excluded if it has every attribute in this list";
                }
              }
              description
                "Link is excluded if it has every attribute in this list";
            }
            leaf name6 {
              type xr:Cisco-ios-xr-string {
                length "1..32" {
                  description
                    "Link is excluded if it has every attribute in this list";
                }
              }
              description
                "Link is excluded if it has every attribute in this list";
            }
          }
          list include7 {
            key "name1 name2 name3 name4 name5 name6 name7";
            description
              "Link is excluded if it has every attribute in this list";
            leaf name1 {
              type xr:Cisco-ios-xr-string {
                length "1..32" {
                  description
                    "Link is excluded if it has every attribute in this list";
                }
              }
              description
                "Link is excluded if it has every attribute in this list";
            }
            leaf name2 {
              type xr:Cisco-ios-xr-string {
                length "1..32" {
                  description
                    "Link is excluded if it has every attribute in this list";
                }
              }
              description
                "Link is excluded if it has every attribute in this list";
            }
            leaf name3 {
              type xr:Cisco-ios-xr-string {
                length "1..32" {
                  description
                    "Link is excluded if it has every attribute in this list";
                }
              }
              description
                "Link is excluded if it has every attribute in this list";
            }
            leaf name4 {
              type xr:Cisco-ios-xr-string {
                length "1..32" {
                  description
                    "Link is excluded if it has every attribute in this list";
                }
              }
              description
                "Link is excluded if it has every attribute in this list";
            }
            leaf name5 {
              type xr:Cisco-ios-xr-string {
                length "1..32" {
                  description
                    "Link is excluded if it has every attribute in this list";
                }
              }
              description
                "Link is excluded if it has every attribute in this list";
            }
            leaf name6 {
              type xr:Cisco-ios-xr-string {
                length "1..32" {
                  description
                    "Link is excluded if it has every attribute in this list";
                }
              }
              description
                "Link is excluded if it has every attribute in this list";
            }
            leaf name7 {
              type xr:Cisco-ios-xr-string {
                length "1..32" {
                  description
                    "Link is excluded if it has every attribute in this list";
                }
              }
              description
                "Link is excluded if it has every attribute in this list";
            }
          }
          list include8 {
            key "name1 name2 name3 name4 name5 name6 name7 name8";
            description
              "Link is excluded if it has every attribute in this list";
            leaf name1 {
              type xr:Cisco-ios-xr-string {
                length "1..32" {
                  description
                    "Link is excluded if it has every attribute in this list";
                }
              }
              description
                "Link is excluded if it has every attribute in this list";
            }
            leaf name2 {
              type xr:Cisco-ios-xr-string {
                length "1..32" {
                  description
                    "Link is excluded if it has every attribute in this list";
                }
              }
              description
                "Link is excluded if it has every attribute in this list";
            }
            leaf name3 {
              type xr:Cisco-ios-xr-string {
                length "1..32" {
                  description
                    "Link is excluded if it has every attribute in this list";
                }
              }
              description
                "Link is excluded if it has every attribute in this list";
            }
            leaf name4 {
              type xr:Cisco-ios-xr-string {
                length "1..32" {
                  description
                    "Link is excluded if it has every attribute in this list";
                }
              }
              description
                "Link is excluded if it has every attribute in this list";
            }
            leaf name5 {
              type xr:Cisco-ios-xr-string {
                length "1..32" {
                  description
                    "Link is excluded if it has every attribute in this list";
                }
              }
              description
                "Link is excluded if it has every attribute in this list";
            }
            leaf name6 {
              type xr:Cisco-ios-xr-string {
                length "1..32" {
                  description
                    "Link is excluded if it has every attribute in this list";
                }
              }
              description
                "Link is excluded if it has every attribute in this list";
            }
            leaf name7 {
              type xr:Cisco-ios-xr-string {
                length "1..32" {
                  description
                    "Link is excluded if it has every attribute in this list";
                }
              }
              description
                "Link is excluded if it has every attribute in this list";
            }
            leaf name8 {
              type xr:Cisco-ios-xr-string {
                length "1..32" {
                  description
                    "Link is excluded if it has every attribute in this list";
                }
              }
              description
                "Link is excluded if it has every attribute in this list";
            }
          }
          list include9 {
            key "name1 name2 name3 name4 name5 name6 name7 name8 name9";
            description
              "Link is excluded if it has every attribute in this list";
            leaf name1 {
              type xr:Cisco-ios-xr-string {
                length "1..32" {
                  description
                    "Link is excluded if it has every attribute in this list";
                }
              }
              description
                "Link is excluded if it has every attribute in this list";
            }
            leaf name2 {
              type xr:Cisco-ios-xr-string {
                length "1..32" {
                  description
                    "Link is excluded if it has every attribute in this list";
                }
              }
              description
                "Link is excluded if it has every attribute in this list";
            }
            leaf name3 {
              type xr:Cisco-ios-xr-string {
                length "1..32" {
                  description
                    "Link is excluded if it has every attribute in this list";
                }
              }
              description
                "Link is excluded if it has every attribute in this list";
            }
            leaf name4 {
              type xr:Cisco-ios-xr-string {
                length "1..32" {
                  description
                    "Link is excluded if it has every attribute in this list";
                }
              }
              description
                "Link is excluded if it has every attribute in this list";
            }
            leaf name5 {
              type xr:Cisco-ios-xr-string {
                length "1..32" {
                  description
                    "Link is excluded if it has every attribute in this list";
                }
              }
              description
                "Link is excluded if it has every attribute in this list";
            }
            leaf name6 {
              type xr:Cisco-ios-xr-string {
                length "1..32" {
                  description
                    "Link is excluded if it has every attribute in this list";
                }
              }
              description
                "Link is excluded if it has every attribute in this list";
            }
            leaf name7 {
              type xr:Cisco-ios-xr-string {
                length "1..32" {
                  description
                    "Link is excluded if it has every attribute in this list";
                }
              }
              description
                "Link is excluded if it has every attribute in this list";
            }
            leaf name8 {
              type xr:Cisco-ios-xr-string {
                length "1..32" {
                  description
                    "Link is excluded if it has every attribute in this list";
                }
              }
              description
                "Link is excluded if it has every attribute in this list";
            }
            leaf name9 {
              type xr:Cisco-ios-xr-string {
                length "1..32" {
                  description
                    "Link is excluded if it has every attribute in this list";
                }
              }
              description
                "Link is excluded if it has every attribute in this list";
            }
          }
          list include10 {
            key "name1 name2 name3 name4 name5 name6 name7 name8 name9 name10";
            description
              "Link is excluded if it has every attribute in this list";
            leaf name1 {
              type xr:Cisco-ios-xr-string {
                length "1..32" {
                  description
                    "Link is excluded if it has every attribute in this list";
                }
              }
              description
                "Link is excluded if it has every attribute in this list";
            }
            leaf name2 {
              type xr:Cisco-ios-xr-string {
                length "1..32" {
                  description
                    "Link is excluded if it has every attribute in this list";
                }
              }
              description
                "Link is excluded if it has every attribute in this list";
            }
            leaf name3 {
              type xr:Cisco-ios-xr-string {
                length "1..32" {
                  description
                    "Link is excluded if it has every attribute in this list";
                }
              }
              description
                "Link is excluded if it has every attribute in this list";
            }
            leaf name4 {
              type xr:Cisco-ios-xr-string {
                length "1..32" {
                  description
                    "Link is excluded if it has every attribute in this list";
                }
              }
              description
                "Link is excluded if it has every attribute in this list";
            }
            leaf name5 {
              type xr:Cisco-ios-xr-string {
                length "1..32" {
                  description
                    "Link is excluded if it has every attribute in this list";
                }
              }
              description
                "Link is excluded if it has every attribute in this list";
            }
            leaf name6 {
              type xr:Cisco-ios-xr-string {
                length "1..32" {
                  description
                    "Link is excluded if it has every attribute in this list";
                }
              }
              description
                "Link is excluded if it has every attribute in this list";
            }
            leaf name7 {
              type xr:Cisco-ios-xr-string {
                length "1..32" {
                  description
                    "Link is excluded if it has every attribute in this list";
                }
              }
              description
                "Link is excluded if it has every attribute in this list";
            }
            leaf name8 {
              type xr:Cisco-ios-xr-string {
                length "1..32" {
                  description
                    "Link is excluded if it has every attribute in this list";
                }
              }
              description
                "Link is excluded if it has every attribute in this list";
            }
            leaf name9 {
              type xr:Cisco-ios-xr-string {
                length "1..32" {
                  description
                    "Link is excluded if it has every attribute in this list";
                }
              }
              description
                "Link is excluded if it has every attribute in this list";
            }
            leaf name10 {
              type xr:Cisco-ios-xr-string {
                length "1..32" {
                  description
                    "Link is excluded if it has every attribute in this list";
                }
              }
              description
                "Link is excluded if it has every attribute in this list";
            }
          }
        }
        container excludes {
          description
            "Links with all these attributes are excluded from path calculation";
          list exclude1 {
            key "name1";
            description
              "Link is excluded if it has every attribute in this list";
            leaf name1 {
              type xr:Cisco-ios-xr-string {
                length "1..32" {
                  description
                    "Link is excluded if it has every attribute in this list";
                }
              }
              description
                "Link is excluded if it has every attribute in this list";
            }
          }
          list exclude2 {
            key "name1 name2";
            description
              "Link is excluded if it has every attribute in this list";
            leaf name1 {
              type xr:Cisco-ios-xr-string {
                length "1..32" {
                  description
                    "Link is excluded if it has every attribute in this list";
                }
              }
              description
                "Link is excluded if it has every attribute in this list";
            }
            leaf name2 {
              type xr:Cisco-ios-xr-string {
                length "1..32" {
                  description
                    "Link is excluded if it has every attribute in this list";
                }
              }
              description
                "Link is excluded if it has every attribute in this list";
            }
          }
          list exclude3 {
            key "name1 name2 name3";
            description
              "Link is excluded if it has every attribute in this list";
            leaf name1 {
              type xr:Cisco-ios-xr-string {
                length "1..32" {
                  description
                    "Link is excluded if it has every attribute in this list";
                }
              }
              description
                "Link is excluded if it has every attribute in this list";
            }
            leaf name2 {
              type xr:Cisco-ios-xr-string {
                length "1..32" {
                  description
                    "Link is excluded if it has every attribute in this list";
                }
              }
              description
                "Link is excluded if it has every attribute in this list";
            }
            leaf name3 {
              type xr:Cisco-ios-xr-string {
                length "1..32" {
                  description
                    "Link is excluded if it has every attribute in this list";
                }
              }
              description
                "Link is excluded if it has every attribute in this list";
            }
          }
          list exclude4 {
            key "name1 name2 name3 name4";
            description
              "Link is excluded if it has every attribute in this list";
            leaf name1 {
              type xr:Cisco-ios-xr-string {
                length "1..32" {
                  description
                    "Link is excluded if it has every attribute in this list";
                }
              }
              description
                "Link is excluded if it has every attribute in this list";
            }
            leaf name2 {
              type xr:Cisco-ios-xr-string {
                length "1..32" {
                  description
                    "Link is excluded if it has every attribute in this list";
                }
              }
              description
                "Link is excluded if it has every attribute in this list";
            }
            leaf name3 {
              type xr:Cisco-ios-xr-string {
                length "1..32" {
                  description
                    "Link is excluded if it has every attribute in this list";
                }
              }
              description
                "Link is excluded if it has every attribute in this list";
            }
            leaf name4 {
              type xr:Cisco-ios-xr-string {
                length "1..32" {
                  description
                    "Link is excluded if it has every attribute in this list";
                }
              }
              description
                "Link is excluded if it has every attribute in this list";
            }
          }
          list exclude5 {
            key "name1 name2 name3 name4 name5";
            description
              "Link is excluded if it has every attribute in this list";
            leaf name1 {
              type xr:Cisco-ios-xr-string {
                length "1..32" {
                  description
                    "Link is excluded if it has every attribute in this list";
                }
              }
              description
                "Link is excluded if it has every attribute in this list";
            }
            leaf name2 {
              type xr:Cisco-ios-xr-string {
                length "1..32" {
                  description
                    "Link is excluded if it has every attribute in this list";
                }
              }
              description
                "Link is excluded if it has every attribute in this list";
            }
            leaf name3 {
              type xr:Cisco-ios-xr-string {
                length "1..32" {
                  description
                    "Link is excluded if it has every attribute in this list";
                }
              }
              description
                "Link is excluded if it has every attribute in this list";
            }
            leaf name4 {
              type xr:Cisco-ios-xr-string {
                length "1..32" {
                  description
                    "Link is excluded if it has every attribute in this list";
                }
              }
              description
                "Link is excluded if it has every attribute in this list";
            }
            leaf name5 {
              type xr:Cisco-ios-xr-string {
                length "1..32" {
                  description
                    "Link is excluded if it has every attribute in this list";
                }
              }
              description
                "Link is excluded if it has every attribute in this list";
            }
          }
          list exclude6 {
            key "name1 name2 name3 name4 name5 name6";
            description
              "Link is excluded if it has every attribute in this list";
            leaf name1 {
              type xr:Cisco-ios-xr-string {
                length "1..32" {
                  description
                    "Link is excluded if it has every attribute in this list";
                }
              }
              description
                "Link is excluded if it has every attribute in this list";
            }
            leaf name2 {
              type xr:Cisco-ios-xr-string {
                length "1..32" {
                  description
                    "Link is excluded if it has every attribute in this list";
                }
              }
              description
                "Link is excluded if it has every attribute in this list";
            }
            leaf name3 {
              type xr:Cisco-ios-xr-string {
                length "1..32" {
                  description
                    "Link is excluded if it has every attribute in this list";
                }
              }
              description
                "Link is excluded if it has every attribute in this list";
            }
            leaf name4 {
              type xr:Cisco-ios-xr-string {
                length "1..32" {
                  description
                    "Link is excluded if it has every attribute in this list";
                }
              }
              description
                "Link is excluded if it has every attribute in this list";
            }
            leaf name5 {
              type xr:Cisco-ios-xr-string {
                length "1..32" {
                  description
                    "Link is excluded if it has every attribute in this list";
                }
              }
              description
                "Link is excluded if it has every attribute in this list";
            }
            leaf name6 {
              type xr:Cisco-ios-xr-string {
                length "1..32" {
                  description
                    "Link is excluded if it has every attribute in this list";
                }
              }
              description
                "Link is excluded if it has every attribute in this list";
            }
          }
          list exclude7 {
            key "name1 name2 name3 name4 name5 name6 name7";
            description
              "Link is excluded if it has every attribute in this list";
            leaf name1 {
              type xr:Cisco-ios-xr-string {
                length "1..32" {
                  description
                    "Link is excluded if it has every attribute in this list";
                }
              }
              description
                "Link is excluded if it has every attribute in this list";
            }
            leaf name2 {
              type xr:Cisco-ios-xr-string {
                length "1..32" {
                  description
                    "Link is excluded if it has every attribute in this list";
                }
              }
              description
                "Link is excluded if it has every attribute in this list";
            }
            leaf name3 {
              type xr:Cisco-ios-xr-string {
                length "1..32" {
                  description
                    "Link is excluded if it has every attribute in this list";
                }
              }
              description
                "Link is excluded if it has every attribute in this list";
            }
            leaf name4 {
              type xr:Cisco-ios-xr-string {
                length "1..32" {
                  description
                    "Link is excluded if it has every attribute in this list";
                }
              }
              description
                "Link is excluded if it has every attribute in this list";
            }
            leaf name5 {
              type xr:Cisco-ios-xr-string {
                length "1..32" {
                  description
                    "Link is excluded if it has every attribute in this list";
                }
              }
              description
                "Link is excluded if it has every attribute in this list";
            }
            leaf name6 {
              type xr:Cisco-ios-xr-string {
                length "1..32" {
                  description
                    "Link is excluded if it has every attribute in this list";
                }
              }
              description
                "Link is excluded if it has every attribute in this list";
            }
            leaf name7 {
              type xr:Cisco-ios-xr-string {
                length "1..32" {
                  description
                    "Link is excluded if it has every attribute in this list";
                }
              }
              description
                "Link is excluded if it has every attribute in this list";
            }
          }
          list exclude8 {
            key "name1 name2 name3 name4 name5 name6 name7 name8";
            description
              "Link is excluded if it has every attribute in this list";
            leaf name1 {
              type xr:Cisco-ios-xr-string {
                length "1..32" {
                  description
                    "Link is excluded if it has every attribute in this list";
                }
              }
              description
                "Link is excluded if it has every attribute in this list";
            }
            leaf name2 {
              type xr:Cisco-ios-xr-string {
                length "1..32" {
                  description
                    "Link is excluded if it has every attribute in this list";
                }
              }
              description
                "Link is excluded if it has every attribute in this list";
            }
            leaf name3 {
              type xr:Cisco-ios-xr-string {
                length "1..32" {
                  description
                    "Link is excluded if it has every attribute in this list";
                }
              }
              description
                "Link is excluded if it has every attribute in this list";
            }
            leaf name4 {
              type xr:Cisco-ios-xr-string {
                length "1..32" {
                  description
                    "Link is excluded if it has every attribute in this list";
                }
              }
              description
                "Link is excluded if it has every attribute in this list";
            }
            leaf name5 {
              type xr:Cisco-ios-xr-string {
                length "1..32" {
                  description
                    "Link is excluded if it has every attribute in this list";
                }
              }
              description
                "Link is excluded if it has every attribute in this list";
            }
            leaf name6 {
              type xr:Cisco-ios-xr-string {
                length "1..32" {
                  description
                    "Link is excluded if it has every attribute in this list";
                }
              }
              description
                "Link is excluded if it has every attribute in this list";
            }
            leaf name7 {
              type xr:Cisco-ios-xr-string {
                length "1..32" {
                  description
                    "Link is excluded if it has every attribute in this list";
                }
              }
              description
                "Link is excluded if it has every attribute in this list";
            }
            leaf name8 {
              type xr:Cisco-ios-xr-string {
                length "1..32" {
                  description
                    "Link is excluded if it has every attribute in this list";
                }
              }
              description
                "Link is excluded if it has every attribute in this list";
            }
          }
          list exclude9 {
            key "name1 name2 name3 name4 name5 name6 name7 name8 name9";
            description
              "Link is excluded if it has every attribute in this list";
            leaf name1 {
              type xr:Cisco-ios-xr-string {
                length "1..32" {
                  description
                    "Link is excluded if it has every attribute in this list";
                }
              }
              description
                "Link is excluded if it has every attribute in this list";
            }
            leaf name2 {
              type xr:Cisco-ios-xr-string {
                length "1..32" {
                  description
                    "Link is excluded if it has every attribute in this list";
                }
              }
              description
                "Link is excluded if it has every attribute in this list";
            }
            leaf name3 {
              type xr:Cisco-ios-xr-string {
                length "1..32" {
                  description
                    "Link is excluded if it has every attribute in this list";
                }
              }
              description
                "Link is excluded if it has every attribute in this list";
            }
            leaf name4 {
              type xr:Cisco-ios-xr-string {
                length "1..32" {
                  description
                    "Link is excluded if it has every attribute in this list";
                }
              }
              description
                "Link is excluded if it has every attribute in this list";
            }
            leaf name5 {
              type xr:Cisco-ios-xr-string {
                length "1..32" {
                  description
                    "Link is excluded if it has every attribute in this list";
                }
              }
              description
                "Link is excluded if it has every attribute in this list";
            }
            leaf name6 {
              type xr:Cisco-ios-xr-string {
                length "1..32" {
                  description
                    "Link is excluded if it has every attribute in this list";
                }
              }
              description
                "Link is excluded if it has every attribute in this list";
            }
            leaf name7 {
              type xr:Cisco-ios-xr-string {
                length "1..32" {
                  description
                    "Link is excluded if it has every attribute in this list";
                }
              }
              description
                "Link is excluded if it has every attribute in this list";
            }
            leaf name8 {
              type xr:Cisco-ios-xr-string {
                length "1..32" {
                  description
                    "Link is excluded if it has every attribute in this list";
                }
              }
              description
                "Link is excluded if it has every attribute in this list";
            }
            leaf name9 {
              type xr:Cisco-ios-xr-string {
                length "1..32" {
                  description
                    "Link is excluded if it has every attribute in this list";
                }
              }
              description
                "Link is excluded if it has every attribute in this list";
            }
          }
          list exclude10 {
            key "name1 name2 name3 name4 name5 name6 name7 name8 name9 name10";
            description
              "Link is excluded if it has every attribute in this list";
            leaf name1 {
              type xr:Cisco-ios-xr-string {
                length "1..32" {
                  description
                    "Link is excluded if it has every attribute in this list";
                }
              }
              description
                "Link is excluded if it has every attribute in this list";
            }
            leaf name2 {
              type xr:Cisco-ios-xr-string {
                length "1..32" {
                  description
                    "Link is excluded if it has every attribute in this list";
                }
              }
              description
                "Link is excluded if it has every attribute in this list";
            }
            leaf name3 {
              type xr:Cisco-ios-xr-string {
                length "1..32" {
                  description
                    "Link is excluded if it has every attribute in this list";
                }
              }
              description
                "Link is excluded if it has every attribute in this list";
            }
            leaf name4 {
              type xr:Cisco-ios-xr-string {
                length "1..32" {
                  description
                    "Link is excluded if it has every attribute in this list";
                }
              }
              description
                "Link is excluded if it has every attribute in this list";
            }
            leaf name5 {
              type xr:Cisco-ios-xr-string {
                length "1..32" {
                  description
                    "Link is excluded if it has every attribute in this list";
                }
              }
              description
                "Link is excluded if it has every attribute in this list";
            }
            leaf name6 {
              type xr:Cisco-ios-xr-string {
                length "1..32" {
                  description
                    "Link is excluded if it has every attribute in this list";
                }
              }
              description
                "Link is excluded if it has every attribute in this list";
            }
            leaf name7 {
              type xr:Cisco-ios-xr-string {
                length "1..32" {
                  description
                    "Link is excluded if it has every attribute in this list";
                }
              }
              description
                "Link is excluded if it has every attribute in this list";
            }
            leaf name8 {
              type xr:Cisco-ios-xr-string {
                length "1..32" {
                  description
                    "Link is excluded if it has every attribute in this list";
                }
              }
              description
                "Link is excluded if it has every attribute in this list";
            }
            leaf name9 {
              type xr:Cisco-ios-xr-string {
                length "1..32" {
                  description
                    "Link is excluded if it has every attribute in this list";
                }
              }
              description
                "Link is excluded if it has every attribute in this list";
            }
            leaf name10 {
              type xr:Cisco-ios-xr-string {
                length "1..32" {
                  description
                    "Link is excluded if it has every attribute in this list";
                }
              }
              description
                "Link is excluded if it has every attribute in this list";
            }
          }
        }
        container exclude-all {
          presence "Indicates a exclude-all node is configured.";
          description
            "Links with any attribute are excluded from path calculation";
        }
        container ignore {
          presence "Indicates a ignore node is configured.";
          description
            "All links are included in path calculation regardless of attributes";
        }
        leaf affinity-attribute-value {
          type uint32 {
            range "0..4294967295" {
              description
                "Affinity attribute value";
            }
          }
          must "../mask";
          description
            "Affinity attribute value";
        }
        leaf mask {
          type uint32 {
            range "0..4294967295" {
              description
                "Affinity attribute mask value";
            }
          }
          must "../affinity-attribute-value";
          description
            "Affinity attribute mask value";
        }
      }
      container path-selection {
        description
          "Path Selection Configuration";
        container metric {
          description
            "Metric Type for path calculation";
          container igp {
            must "not(../te or ../delay)";
            presence "Indicates a igp node is configured.";
            description
              "Use IGP metric";
          }
          container te {
            must "not(../igp or ../delay)";
            presence "Indicates a te node is configured.";
            description
              "Use TE metric";
          }
          container delay {
            must "not(../igp or ../te)";
            presence "Indicates a delay node is configured.";
            description
              "Use delay metric";
          }
        }
      }
    }
  }

  augment "/a2:interfaces/a2:interface" {
    description
      "This augment extends active nodes configuration";
    uses IF-BODY;
  }
  augment "/a1:snmp-server-mibs" {
    description
      "This augment extends snmp-server-mibs nodes
       configuration";
    container mplstemib {
      description
        "TE-MIB configuration commands";
      container cache {
        description
          "Modify MIB cache properties";
        container timers {
          description
            "Modify MIB cache timers";
          leaf garbage-collect {
            type uint32 {
              range "0..3600" {
                description
                  "Cache garbage collect time in seconds (0 immediately purges deleted OIDs from cache)";
              }
            }
            description
              "Modify MIB cache garbage collect timer";
          }
          leaf refresh {
            type uint32 {
              range "0..600" {
                description
                  "Cache refresh time in seconds";
              }
            }
            description
              "Modify MIB cache refresh timer";
          }
        }
      }
    }
    container mplsp2mpmib {
      description
        "p2mp mib configuration commands";
      container cache {
        description
          "Modify MIB cache properties";
        leaf timer {
          type uint32 {
            range "0..600" {
              description
                "Cache time in seconds";
            }
          }
          description
            "Modify MIB cache timer";
        }
      }
    }
    container frrmib {
      description
        "frr mib configuration commands";
      container cache {
        description
          "Modify MIB cache properties";
        leaf timer {
          type uint32 {
            range "0..600" {
              description
                "Cache time in seconds";
            }
          }
          description
            "Modify MIB chache timer";
        }
      }
    }
    container cmplsteextmib {
      description
        "cmplsteext mib configuration commands";
      container cache {
        description
          "Modify MIB cache properties";
        leaf timer {
          type uint32 {
            range "0..600" {
              description
                "Cache time in seconds";
            }
          }
          description
            "Modify MIB chache timer";
        }
      }
    }
    container cmplsteextstdmib {
      description
        "cmplsteextstd mib configuration commands";
      container cache {
        description
          "Modify MIB cache properties";
        leaf timer {
          type uint32 {
            range "0..600" {
              description
                "Cache time in seconds";
            }
          }
          description
            "Modify MIB chache timer";
        }
      }
    }
  }
  augment "/a1:snmp-server/a1:traps" {
    description
      "This augment extends snmp-server traps nodes
       configuration";
    container mpls {
      description
        "Enable SNMP MPLS traps";
      container traffic-eng {
        description
          "Enable MPLS TE traps";
        container cisco {
          presence "Indicates a cisco node is configured.";
          description
            "MPLS TE tunnel traps in Cisco format (default ietf)";
        }
        container cisco-ext {
          description
            "cisco_ext";
          container bringup-fail {
            presence "Indicates a bringup-fail node is configured.";
            description
              "Enable MPLS TE tunnel bringup-fail trap";
          }
          container insuff-bw {
            presence "Indicates a insuff-bw node is configured.";
            description
              "Enable MPLS TE tunnel insufficient bandwidth trap";
          }
          container preempt {
            presence "Indicates a preempt node is configured.";
            description
              "Enable MPLS TE tunnel preempt trap";
          }
          container reroute-pending {
            presence "Indicates a reroute-pending node is configured.";
            description
              "Enable MPLS TE tunnel reroute-pending trap";
          }
          container reroute-pending-clear {
            presence "Indicates a reroute-pending-clear node is configured.";
            description
              "Enable MPLS TE tunnel reroute-pending trap";
          }
        }
        container down {
          presence "Indicates a down node is configured.";
          description
            "Enable MPLS TE tunnel down traps";
        }
        container p2mp {
          description
            "Enable MPLS TE tunnel p2mp traps";
          container down {
            presence "Indicates a down node is configured.";
            description
              "Enable MPLS TE P2MP tunnel destination down traps";
          }
          container up {
            presence "Indicates a up node is configured.";
            description
              "Enable MPLS TE P2MP tunnel destination up traps";
          }
        }
        container reoptimize {
          presence "Indicates a reoptimize node is configured.";
          description
            "Enable MPLS TE tunnel reoptimize traps";
        }
        container reroute {
          presence "Indicates a reroute node is configured.";
          description
            "Enable MPLS TE tunnel reroute traps";
        }
        container up {
          presence "Indicates a up node is configured.";
          description
            "Enable MPLS TE tunnel up traps";
        }
      }
      container frr {
        description
          "Enable MPLS FRR traps";
        container all {
          presence "Indicates a all node is configured.";
          description
            "Enable all MPLS FRR MIB traps";
        }
        container protected {
          presence "Indicates a protected node is configured.";
          description
            "Enable MPLS FRR tunnel protected traps";
        }
        container unprotected {
          presence "Indicates a unprotected node is configured.";
          description
            "Enable MPLS FRR tunnel unprotected traps";
        }
      }
    }
  }
  container mpls {
    description
      "Global MPLS configuration subcommands";
    container traffic-eng {
      presence "Indicates a traffic-eng node is configured.";
      description
        "Go into the MPLS-TE submode";
      container link-management {
        description
          "MPLS Link Manager subcommands";
        container timers {
          description
            "MPLS Link Manager Timer subcommands";
          leaf bandwidth-hold {
            type uint32 {
              range "1..300" {
                description
                  "Bandwidth hold timer value (seconds)";
              }
            }
            description
              "Bandwidth hold timer";
          }
          leaf periodic-flooding {
            type uint32 {
              range "0..3600" {
                description
                  "Periodic flooding value (seconds), minimum 30 seconds";
              }
            }
            description
              "Periodic flooding timer";
          }
          container preemption-delay {
            description
              "Delay LSP preemption";
            leaf bundle-capacity {
              type uint32 {
                range "0..300" {
                  description
                    "Bundle capacity change preemption timer value (seconds)";
                }
              }
              description
                "Bundle capacity change preemption delay timer";
            }
          }
        }
      }
      container reoptimize {
        description
          "MPLS TE Reoptimize config";
        leaf reoptimize-value {
          type uint32 {
            range "0..604800" {
              description
                "Reoptimize timers frequency (secs)";
            }
          }
          description
            "Reoptimize timers frequency (secs)";
        }
        container timers {
          description
            "Reoptimization timers";
          container delay {
            description
              "Delay reoptimization action";
            leaf cleanup {
              type uint32 {
                range "0..300" {
                  description
                    "Seconds to delay cleanup of reoptimized LSP";
                }
              }
              description
                "Delay cleanup of reoptimized LSP";
            }
            leaf after-frr {
              type uint32 {
                range "0..120" {
                  description
                    "Seconds to delay re-opt initiation of tunnel after an FRR event";
                }
              }
              description
                "Delay LSP reoptimization in the event of FRR";
            }
            leaf installation {
              type uint32 {
                range "0..3600" {
                  description
                    "Seconds to delay replacement of tunnel LSP";
                }
              }
              description
                "Delay replacement of current LSP by reoptimized LSP";
            }
            leaf after-affinity-failure {
              type uint32 {
                range "1..604800" {
                  description
                    "Seconds to delay reoptimizing current LSP";
                }
              }
              description
                "Delay reoptimizing current LSP after path affinity failure";
            }
            leaf path-protection {
              type uint32 {
                range "0..604800" {
                  description
                    "Seconds between path protection switchover event and tunnel re-optimization. Set to 0 to disable";
                }
              }
              description
                "Time between path protection switchover event and tunnel re-optimization";
            }
          }
        }
        container events {
          description
            "Event-based reoptimization";
          container link-up {
            presence "Indicates a link-up node is configured.";
            description
              "Trigger reoptimization on topology link-up events";
          }
        }
        container load-balance {
          presence "Indicates a load-balance node is configured.";
          description
            "Load balance bandwidth during reoptimization";
        }
        container disable {
          description
            "disable reoptimization";
          container affinity-failure {
            presence "Indicates a affinity-failure node is configured.";
            description
              "disable reoptimization on affinity failure";
          }
        }
      }
      container bfd {
        description
          "Configure parameters for BFD over TE";
        leaf minimum-interval {
          type uint32 {
            range "15..200" {
              description
                "Hello interval in milliseconds (default 15)";
            }
          }
          description
            "Hello interval for BFD over Link";
        }
        leaf multiplier {
          type uint32 {
            range "2..10" {
              description
                "Detect multiplier (default 3)";
            }
          }
          description
            "Detect multiplier for BFD over Link";
        }
        container lsp {
          description
            "Configure parameters for BFD over LSP";
          container tail {
            description
              "Tail end configuration";
            leaf minimum-interval {
              type uint32 {
                range "50..30000" {
                  description
                    "Hello interval in milliseconds (default 100)";
                }
              }
              description
                "Hello interval";
            }
            leaf multiplier {
              type uint32 {
                range "3..10" {
                  description
                    "Detect multiplier (default 3)";
                }
              }
              description
                "Detect multiplier";
            }
          }
          container head {
            description
              "Head end configuration";
            container down-action {
              description
                "Action to take for FRR enabled tunnel when BFD session down";
              container resetup {
                presence "Indicates a resetup node is configured.";
                description
                  "Teardown and resetup when received BFD session down event";
              }
              container reoptimize {
                description
                  "Reoptimize when received BFD session down event (default)";
                leaf timeout {
                  type uint32 {
                    range "120..4294967295" {
                      description
                        "Reoptmization timeout in seconds (default 300)";
                    }
                  }
                  description
                    "Timeout and teardown if failed to reoptimize";
                }
              }
            }
          }
        }
      }
      container interfaces {
        description
          "Enable MPLS-TE on an interface";
        list interface {
          key "interface-name";
          description
            "Enable MPLS-TE on an interface";
          leaf interface-name {
            type xr:Interface-name;
            description
              "Enable MPLS-TE on an interface";
          }
          leaf admin-weight {
            type uint32 {
              range "0..4294967295" {
                description
                  "Administrative weight for the interface";
              }
            }
            description
              "Set administrative weight for the interface";
          }
          container bfd {
            description
              "Configure BFD parameters";
            container fast-detect {
              presence "Indicates a fast-detect node is configured.";
              description
                "Enable Fast detection";
            }
          }
          container fault-oam {
            description
              "Enable fault-oam features";
            container lockout {
              presence "Indicates a lockout node is configured.";
              description
                "Enable Flex LSP lockout protection";
            }
          }
          leaf attribute-flags {
            type xr:Hex-integer;
            description
              "Set user defined interface attribute flags";
          }
          container attribute-names {
            description
              "Specify one or more attribute names";
            leaf-list attribute-name {
              type xr:Cisco-ios-xr-string {
                length "1..32" {
                  description
                    "User defined attribute name";
                }
              }
              max-elements "32";
              description
                "Specify one or more attribute names";
            }
            container indexes {
              description
                "Specify the entry index";
              list index {
                key "index-number";
                description
                  "Specify the entry index";
                leaf index-number {
                  type uint32 {
                    range "1..8" {
                      description
                        "Index number";
                    }
                  }
                  description
                    "Specify the entry index";
                }
                leaf-list attribute-names {
                  type xr:Cisco-ios-xr-string {
                    length "1..32" {
                      description
                        "User defined attribute name";
                    }
                  }
                  min-elements 1;
                  max-elements "32";
                  description
                    "Specify one or more attribute names";
                }
              }
            }
          }
          container flooding {
            description
              "Set flooding parameters";
            container thresholds {
              description
                "Set flooding thresholds";
              container ups {
                description
                  "Set thresholds for increased resource allocation in %";
                leaf-list up {
                  type uint32 {
                    range "0..100" {
                      description
                        "Thresholds in increasing order";
                    }
                  }
                  max-elements "14";
                  description
                    "Set thresholds for increased resource allocation in %";
                }
              }
              container downs {
                description
                  "Set thresholds for decreased resource allocation in %";
                leaf-list down {
                  type uint32 {
                    range "0..100" {
                      description
                        "Thresholds in decreasing order";
                    }
                  }
                  max-elements "14";
                  description
                    "Set thresholds for decreased resource allocation in %";
                }
              }
            }
          }
          container backup-path {
            description
              "Configure an MPLS TE backup for this interface";
            container tunnel-te {
              description
                "Tunnel interface";
              container tunnel-interfaces {
                description
                  "Tunnel interface number";
                list tunnel-interface {
                  key "tunnel-interface-number";
                  description
                    "Tunnel interface number";
                  leaf tunnel-interface-number {
                    type uint32 {
                      range "0..65535" {
                        description
                          "Tunnel interface number";
                      }
                    }
                    description
                      "Tunnel interface number";
                  }
                }
              }
              container backup-tunnels {
                description
                  "Backup Tunnel Name";
                list backup-tunnel {
                  key "backup-tunnel-name";
                  description
                    "Backup Tunnel Name";
                  leaf backup-tunnel-name {
                    type xr:Cisco-ios-xr-string {
                      length "1..54" {
                        description
                          "Backup Tunnel Name";
                      }
                    }
                    description
                      "Backup Tunnel Name";
                  }
                }
              }
            }
          }
          container auto-tunnel {
            description
              "Auto-tunnel configuration";
            container backup {
              presence "Indicates a backup node is configured.";
              description
                "Enable the auto-tunnel backup feature on an interface";
              container nhop-only {
                presence "Indicates a nhop-only node is configured.";
                description
                  "Allow only next hop backup tunnels";
              }
              leaf attribute-set {
                type xr:Cisco-ios-xr-string {
                  length "1..64" {
                    description
                      "Specify attribute-set name (max 64 char)";
                  }
                }
                description
                  "Attribute-set name of type auto-backup";
              }
              container exclude {
                description
                  "Restrict auto-tunnel backup path based on specific criteria.";
                container srlg {
                  presence "Indicates a srlg node is configured.";
                  description
                    "Backup requires SRLG exclusion from protected interface";
                  container preferred {
                    must "not(../weighted)";
                    presence "Indicates a preferred node is configured.";
                    description
                      "SRLG exclusion is preferred but not mandatory";
                  }
                  container weighted {
                    must "not(../preferred)";
                    presence "Indicates a weighted node is configured.";
                    description
                      "If SRLG is shared admin weight of the SRLG is added to link metric";
                  }
                }
              }
              container bandwidth-protection {
                description
                  "Add protected auto-backup for LSPs requesting bandwidth protection";
                leaf maximum-aggregate {
                  type uint32 {
                    range "1..4294967295" {
                      description
                        "Bandwidth requirement in kbps";
                    }
                  }
                  description
                    "Aggregated maximum amount of bandwidth that the auto-backup can protect";
                }
              }
            }
          }
        }
      }
      container ds-te {
        description
          "Diff-Serv Traffic-Engineering Parameters";
        container bc-model {
          description
            "Diff-Serv Traffic-Engineering Bandwidth Constraints Model";
          container mam {
            presence "Indicates a mam node is configured.";
            description
              "Maximum Allocation Bandwidth Constraints Model";
          }
        }
        container mode {
          description
            "Diff-Serv Traffic-Engineering Mode";
          container ietf {
            presence "Indicates a ietf node is configured.";
            description
              "IETF Standard Mode";
          }
        }
        container te-classes {
          description
            "enter the DS-TE te-class map configuration mode";
          list te-class {
            must "(class-type and priority) or unused";
            key "class-number";
            description
              "Specify TE-Class parameters";
            leaf class-number {
              type uint32 {
                range "0..7";
              }
              description
                "DS-TE class number";
            }
            leaf class-type {
              type uint32 {
                range "0..1" {
                  description
                    "Class type number";
                }
              }
              must "not(../unused)";
              description
                "Class type";
            }
            leaf priority {
              type uint32 {
                range "0..7" {
                  description
                    "Class-type priority";
                }
              }
              description
                "Class priority";
            }
            container unused {
              must "not(../class-type)";
              presence "Indicates a unused node is configured.";
              description
                "Mark the TE-class as unused";
            }
          }
        }
      }
      container logging {
        description
          "MPLS Traffic-Eng. logging configuration";
        container events {
          description
            "Global logging events";
          container frr-protection {
            must "not(primary-lsp and backup-tunnel)";
            presence "Indicates a frr-protection node is configured.";
            description
              "Enable protection change Syslog";
            container primary-lsp {
              must "not(ready-state and active-state)";
              presence "Indicates a primary-lsp node is configured.";
              description
                "Enable logging for primary LSP(s)";
              container ready-state {
                presence "Indicates a ready-state node is configured.";
                description
                  "Enable logging when FRR backup is assigned or unassigned";
              }
              container active-state {
                presence "Indicates a active-state node is configured.";
                description
                  "Enable logging when FRR backup is triggered";
              }
            }
            container backup-tunnel {
              presence "Indicates a backup-tunnel node is configured.";
              description
                "Enable logging for backup tunnel(s)";
            }
          }
          container preemption {
            presence "Indicates a preemption node is configured.";
            description
              "Enable Tunnel Preemption alarms";
          }
          container role {
            description
              "Enable all logging for a tunnel role";
            container head {
              presence "Indicates a head node is configured.";
              description
                "Enable all logging for head";
            }
            container mid {
              presence "Indicates a mid node is configured.";
              description
                "Enable all logging for mid";
            }
            container tail {
              presence "Indicates a tail node is configured.";
              description
                "Enable all logging for tail";
            }
          }
          container nsr {
            presence "Indicates a nsr node is configured.";
            description
              "Enable NSR Status Logging";
          }
          container issu {
            presence "Indicates a issu node is configured.";
            description
              "Enable ISSU Status Logging";
          }
          container all {
            presence "Indicates a all node is configured.";
            description
              "Enable all logging for all events";
          }
        }
      }
      container timers {
        description
          "Traffic Engineering timers";
        container loose-path {
          description
            "Control the LSP terminating outside the headend area";
          leaf retry-period {
            type uint32 {
              range "30..600" {
                description
                  "Seconds to retry signalling of loose path tunnels after path errors";
              }
            }
            description
              "Period in seconds between retries after path errors";
          }
        }
        container s2l-setup {
          description
            "Control the LSP headend";
          leaf retry-timer {
            type uint32 {
              range "30..600" {
                description
                  "Seconds to retry signalling after path timeout";
              }
            }
            description
              "Timeout period in seconds before head end retries path";
          }
        }
        container backoff-timer {
          description
            "Control the LSP signaling requests on the same path";
          leaf initial-interval {
            type uint32 {
              range "0..600" {
                description
                  "In seconds";
              }
            }
            must "../final-interval";
            description
              "The initial interval in seconds that the timer will start with. The default value is 3(s). Timer is disabled when this value and the final-interval are both set to 0";
          }
          leaf final-interval {
            type uint32 {
              range "0..600" {
                description
                  "In seconds";
              }
            }
            must "../initial-interval";
            description
              "The final interval in seconds that the timer will cap at. The default value is 300(s). Timer is disabled when this value and the initial-interval are both set to 0";
          }
        }
      }
      container topology {
        description
          "Topology Database Configuration";
        container holddown {
          description
            "Topology Database hold down timers";
          leaf sigerr {
            type uint32 {
              range "0..300" {
                description
                  "Hold down time in seconds";
              }
            }
            description
              "Link hold down time for signalling errors";
          }
        }
      }
      container flooding {
        description
          "Configure MPLS-TE flooding";
        container threshold {
          description
            "Configure MPLS-TE flooding thresholds";
          leaf up {
            type uint32 {
              range "0..100" {
                description
                  "Upward flooding threshold as percentage of total link bandwidth change";
              }
            }
            description
              "Upward flooding threshold";
          }
          leaf down {
            type uint32 {
              range "0..100" {
                description
                  "Downward flooding threshold as percentage of total link bandwidth change";
              }
            }
            must "../up";
            description
              "Downward flooding threshold";
          }
        }
      }
      container named-tunnels {
        presence "Indicates a named-tunnels node is configured.";
        description
          "Named Tunnels";
        container tunnel-tes {
          description
            "Traffic Engineering Tunnel";
          list tunnel-te {
            key "tunnel-name";
            description
              "Traffic Engineering Tunnel";
            leaf tunnel-name {
              type xr:Cisco-ios-xr-string {
                length "1..1024" {
                  description
                    "Tunnel Name";
                }
              }
              description
                "Traffic Engineering Tunnel";
            }
            leaf destination {
              type inet:ipv4-address-no-zone;
              description
                "Specify tunnel destination";
            }
            container shutdown {
              presence "Indicates a shutdown node is configured.";
              description
                "shutdown the given tunnel";
            }
            container soft-preemption {
              presence "Indicates a soft-preemption node is configured.";
              description
                "Enable the soft-preemption feature on this tunnel";
            }
            container delay-measurement {
              presence "Indicates a delay-measurement node is configured.";
              description
                "Enable the delay-measurement feature on this tunnel";
            }
            container record-route {
              presence "Indicates a record-route node is configured.";
              description
                "Record the route used by the tunnel";
            }
            container logging {
              description
                "Per-interface logging configuration";
              container events {
                description
                  "Per-interface logging events";
                container lsp-status {
                  description
                    "Enable interface LSP state change alarms";
                  container state {
                    presence "Indicates a state node is configured.";
                    description
                      "Enable interface LSP UP/DOWN change alarms";
                  }
                  container reoptimize {
                    presence "Indicates a reoptimize node is configured.";
                    description
                      "Enable interface LSP REOPT change alarms";
                  }
                  container reoptimize-attempts {
                    presence "Indicates a reoptimize-attempts node is configured.";
                    description
                      "Enable interface LSP REOPT attempts change alarms";
                  }
                  container bw-change {
                    presence "Indicates a bw-change node is configured.";
                    description
                      "Enable interface LSP BANDWIDTH change alarms";
                  }
                  container reroute {
                    presence "Indicates a reroute node is configured.";
                    description
                      "Enable interface LSP REROUTE change alarms";
                  }
                  container record-route {
                    presence "Indicates a record-route node is configured.";
                    description
                      "Enable interface LSP RECORD-ROUTE change alarms";
                  }
                  container switchover {
                    presence "Indicates a switchover node is configured.";
                    description
                      "Enable interface LSP SWITCHOVER change alarms";
                  }
                  container insufficient-bandwidth {
                    presence "Indicates a insufficient-bandwidth node is configured.";
                    description
                      "Enable Syslog for setup/reopt failure due to bandwidth";
                  }
                  container path-error {
                    presence "Indicates a path-error node is configured.";
                    description
                      "Enable Syslog for failures due to path error";
                  }
                }
                container pcalc-failure {
                  presence "Indicates a pcalc-failure node is configured.";
                  description
                    "Enable logging for path calculation failures";
                }
                container all {
                  presence "Indicates a all node is configured.";
                  description
                    "Enable all logging for this tunnel";
                }
              }
            }
            container fast-reroute {
              presence "Indicates a fast-reroute node is configured.";
              description
                "Specify MPLS tunnel can be fast-rerouted";
              container protect {
                description
                  "Enable protection request";
                container node {
                  presence "Indicates a node node is configured.";
                  description
                    "Enable node protection request";
                }
                container bandwidth {
                  presence "Indicates a bandwidth node is configured.";
                  description
                    "Enable bandwidth protection request";
                }
              }
            }
            container affinity {
              description
                "Link attributes for links traversed by tunnel";
              container includes {
                description
                  "Links with all these attributes are included in path calculation";
                list include1 {
                  key "name1";
                  description
                    "Links with all these attributes are included in path calculation";
                  leaf name1 {
                    type xr:Cisco-ios-xr-string {
                      length "1..32" {
                        description
                          "Attribute or affinity name";
                      }
                    }
                    description
                      "Attribute or affinity name";
                  }
                }
                list include2 {
                  key "name1 name2";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                }
                list include3 {
                  key "name1 name2 name3";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                }
                list include4 {
                  key "name1 name2 name3 name4";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                }
                list include5 {
                  key "name1 name2 name3 name4 name5";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                }
                list include6 {
                  key "name1 name2 name3 name4 name5 name6";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                  leaf name6 {
                    type xr:Cisco-ios-xr-string {
                      length "1..32" {
                        description
                          "Attribute or affinity name";
                      }
                    }
                    description
                      "Attribute or affinity name";
                  }
                }
                list include7 {
                  key "name1 name2 name3 name4 name5 name6 name7";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                  leaf name6 {
                    type xr:Cisco-ios-xr-string {
                      length "1..32" {
                        description
                          "Attribute or affinity name";
                      }
                    }
                    description
                      "Attribute or affinity name";
                  }
                  leaf name7 {
                    type xr:Cisco-ios-xr-string {
                      length "1..32" {
                        description
                          "Attribute or affinity name";
                      }
                    }
                    description
                      "Attribute or affinity name";
                  }
                }
                list include8 {
                  key "name1 name2 name3 name4 name5 name6 name7 name8";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                  leaf name6 {
                    type xr:Cisco-ios-xr-string {
                      length "1..32" {
                        description
                          "Attribute or affinity name";
                      }
                    }
                    description
                      "Attribute or affinity name";
                  }
                  leaf name7 {
                    type xr:Cisco-ios-xr-string {
                      length "1..32" {
                        description
                          "Attribute or affinity name";
                      }
                    }
                    description
                      "Attribute or affinity name";
                  }
                  leaf name8 {
                    type xr:Cisco-ios-xr-string {
                      length "1..32" {
                        description
                          "Attribute or affinity name";
                      }
                    }
                    description
                      "Attribute or affinity name";
                  }
                }
                list include9 {
                  key "name1 name2 name3 name4 name5 name6 name7 name8 name9";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                  leaf name6 {
                    type xr:Cisco-ios-xr-string {
                      length "1..32" {
                        description
                          "Attribute or affinity name";
                      }
                    }
                    description
                      "Attribute or affinity name";
                  }
                  leaf name7 {
                    type xr:Cisco-ios-xr-string {
                      length "1..32" {
                        description
                          "Attribute or affinity name";
                      }
                    }
                    description
                      "Attribute or affinity name";
                  }
                  leaf name8 {
                    type xr:Cisco-ios-xr-string {
                      length "1..32" {
                        description
                          "Attribute or affinity name";
                      }
                    }
                    description
                      "Attribute or affinity name";
                  }
                  leaf name9 {
                    type xr:Cisco-ios-xr-string {
                      length "1..32" {
                        description
                          "Attribute or affinity name";
                      }
                    }
                    description
                      "Attribute or affinity name";
                  }
                }
                list include10 {
                  key "name1 name2 name3 name4 name5 name6 name7 name8 name9 name10";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                  leaf name6 {
                    type xr:Cisco-ios-xr-string {
                      length "1..32" {
                        description
                          "Attribute or affinity name";
                      }
                    }
                    description
                      "Attribute or affinity name";
                  }
                  leaf name7 {
                    type xr:Cisco-ios-xr-string {
                      length "1..32" {
                        description
                          "Attribute or affinity name";
                      }
                    }
                    description
                      "Attribute or affinity name";
                  }
                  leaf name8 {
                    type xr:Cisco-ios-xr-string {
                      length "1..32" {
                        description
                          "Attribute or affinity name";
                      }
                    }
                    description
                      "Attribute or affinity name";
                  }
                  leaf name9 {
                    type xr:Cisco-ios-xr-string {
                      length "1..32" {
                        description
                          "Attribute or affinity name";
                      }
                    }
                    description
                      "Attribute or affinity name";
                  }
                  leaf name10 {
                    type xr:Cisco-ios-xr-string {
                      length "1..32" {
                        description
                          "Attribute or affinity name";
                      }
                    }
                    description
                      "Attribute or affinity name";
                  }
                }
              }
              container include-stricts {
                description
                  "Links with exactly all these attributes are included in path calculation";
                list include1 {
                  key "name1";
                  description
                    "Links with all these attributes are included in path calculation";
                  leaf name1 {
                    type xr:Cisco-ios-xr-string {
                      length "1..32" {
                        description
                          "Attribute or affinity name";
                      }
                    }
                    description
                      "Attribute or affinity name";
                  }
                }
                list include2 {
                  key "name1 name2";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                }
                list include3 {
                  key "name1 name2 name3";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                }
                list include4 {
                  key "name1 name2 name3 name4";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                }
                list include5 {
                  key "name1 name2 name3 name4 name5";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                }
                list include6 {
                  key "name1 name2 name3 name4 name5 name6";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                  leaf name6 {
                    type xr:Cisco-ios-xr-string {
                      length "1..32" {
                        description
                          "Attribute or affinity name";
                      }
                    }
                    description
                      "Attribute or affinity name";
                  }
                }
                list include7 {
                  key "name1 name2 name3 name4 name5 name6 name7";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                  leaf name6 {
                    type xr:Cisco-ios-xr-string {
                      length "1..32" {
                        description
                          "Attribute or affinity name";
                      }
                    }
                    description
                      "Attribute or affinity name";
                  }
                  leaf name7 {
                    type xr:Cisco-ios-xr-string {
                      length "1..32" {
                        description
                          "Attribute or affinity name";
                      }
                    }
                    description
                      "Attribute or affinity name";
                  }
                }
                list include8 {
                  key "name1 name2 name3 name4 name5 name6 name7 name8";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                  leaf name6 {
                    type xr:Cisco-ios-xr-string {
                      length "1..32" {
                        description
                          "Attribute or affinity name";
                      }
                    }
                    description
                      "Attribute or affinity name";
                  }
                  leaf name7 {
                    type xr:Cisco-ios-xr-string {
                      length "1..32" {
                        description
                          "Attribute or affinity name";
                      }
                    }
                    description
                      "Attribute or affinity name";
                  }
                  leaf name8 {
                    type xr:Cisco-ios-xr-string {
                      length "1..32" {
                        description
                          "Attribute or affinity name";
                      }
                    }
                    description
                      "Attribute or affinity name";
                  }
                }
                list include9 {
                  key "name1 name2 name3 name4 name5 name6 name7 name8 name9";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                  leaf name6 {
                    type xr:Cisco-ios-xr-string {
                      length "1..32" {
                        description
                          "Attribute or affinity name";
                      }
                    }
                    description
                      "Attribute or affinity name";
                  }
                  leaf name7 {
                    type xr:Cisco-ios-xr-string {
                      length "1..32" {
                        description
                          "Attribute or affinity name";
                      }
                    }
                    description
                      "Attribute or affinity name";
                  }
                  leaf name8 {
                    type xr:Cisco-ios-xr-string {
                      length "1..32" {
                        description
                          "Attribute or affinity name";
                      }
                    }
                    description
                      "Attribute or affinity name";
                  }
                  leaf name9 {
                    type xr:Cisco-ios-xr-string {
                      length "1..32" {
                        description
                          "Attribute or affinity name";
                      }
                    }
                    description
                      "Attribute or affinity name";
                  }
                }
                list include10 {
                  key "name1 name2 name3 name4 name5 name6 name7 name8 name9 name10";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                  leaf name6 {
                    type xr:Cisco-ios-xr-string {
                      length "1..32" {
                        description
                          "Attribute or affinity name";
                      }
                    }
                    description
                      "Attribute or affinity name";
                  }
                  leaf name7 {
                    type xr:Cisco-ios-xr-string {
                      length "1..32" {
                        description
                          "Attribute or affinity name";
                      }
                    }
                    description
                      "Attribute or affinity name";
                  }
                  leaf name8 {
                    type xr:Cisco-ios-xr-string {
                      length "1..32" {
                        description
                          "Attribute or affinity name";
                      }
                    }
                    description
                      "Attribute or affinity name";
                  }
                  leaf name9 {
                    type xr:Cisco-ios-xr-string {
                      length "1..32" {
                        description
                          "Attribute or affinity name";
                      }
                    }
                    description
                      "Attribute or affinity name";
                  }
                  leaf name10 {
                    type xr:Cisco-ios-xr-string {
                      length "1..32" {
                        description
                          "Attribute or affinity name";
                      }
                    }
                    description
                      "Attribute or affinity name";
                  }
                }
              }
              container excludes {
                description
                  "Links with all these attributes are excluded from path calculation";
                list exclude1 {
                  key "name1";
                  description
                    "Links with all these attributes are included in path calculation";
                  leaf name1 {
                    type xr:Cisco-ios-xr-string {
                      length "1..32" {
                        description
                          "Attribute or affinity name";
                      }
                    }
                    description
                      "Attribute or affinity name";
                  }
                }
                list exclude2 {
                  key "name1 name2";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                }
                list exclude3 {
                  key "name1 name2 name3";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                }
                list exclude4 {
                  key "name1 name2 name3 name4";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                }
                list exclude5 {
                  key "name1 name2 name3 name4 name5";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                }
                list exclude6 {
                  key "name1 name2 name3 name4 name5 name6";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                  leaf name6 {
                    type xr:Cisco-ios-xr-string {
                      length "1..32" {
                        description
                          "Attribute or affinity name";
                      }
                    }
                    description
                      "Attribute or affinity name";
                  }
                }
                list exclude7 {
                  key "name1 name2 name3 name4 name5 name6 name7";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                  leaf name6 {
                    type xr:Cisco-ios-xr-string {
                      length "1..32" {
                        description
                          "Attribute or affinity name";
                      }
                    }
                    description
                      "Attribute or affinity name";
                  }
                  leaf name7 {
                    type xr:Cisco-ios-xr-string {
                      length "1..32" {
                        description
                          "Attribute or affinity name";
                      }
                    }
                    description
                      "Attribute or affinity name";
                  }
                }
                list exclude8 {
                  key "name1 name2 name3 name4 name5 name6 name7 name8";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                  leaf name6 {
                    type xr:Cisco-ios-xr-string {
                      length "1..32" {
                        description
                          "Attribute or affinity name";
                      }
                    }
                    description
                      "Attribute or affinity name";
                  }
                  leaf name7 {
                    type xr:Cisco-ios-xr-string {
                      length "1..32" {
                        description
                          "Attribute or affinity name";
                      }
                    }
                    description
                      "Attribute or affinity name";
                  }
                  leaf name8 {
                    type xr:Cisco-ios-xr-string {
                      length "1..32" {
                        description
                          "Attribute or affinity name";
                      }
                    }
                    description
                      "Attribute or affinity name";
                  }
                }
                list exclude9 {
                  key "name1 name2 name3 name4 name5 name6 name7 name8 name9";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                  leaf name6 {
                    type xr:Cisco-ios-xr-string {
                      length "1..32" {
                        description
                          "Attribute or affinity name";
                      }
                    }
                    description
                      "Attribute or affinity name";
                  }
                  leaf name7 {
                    type xr:Cisco-ios-xr-string {
                      length "1..32" {
                        description
                          "Attribute or affinity name";
                      }
                    }
                    description
                      "Attribute or affinity name";
                  }
                  leaf name8 {
                    type xr:Cisco-ios-xr-string {
                      length "1..32" {
                        description
                          "Attribute or affinity name";
                      }
                    }
                    description
                      "Attribute or affinity name";
                  }
                  leaf name9 {
                    type xr:Cisco-ios-xr-string {
                      length "1..32" {
                        description
                          "Attribute or affinity name";
                      }
                    }
                    description
                      "Attribute or affinity name";
                  }
                }
                list exclude10 {
                  key "name1 name2 name3 name4 name5 name6 name7 name8 name9 name10";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                  leaf name6 {
                    type xr:Cisco-ios-xr-string {
                      length "1..32" {
                        description
                          "Attribute or affinity name";
                      }
                    }
                    description
                      "Attribute or affinity name";
                  }
                  leaf name7 {
                    type xr:Cisco-ios-xr-string {
                      length "1..32" {
                        description
                          "Attribute or affinity name";
                      }
                    }
                    description
                      "Attribute or affinity name";
                  }
                  leaf name8 {
                    type xr:Cisco-ios-xr-string {
                      length "1..32" {
                        description
                          "Attribute or affinity name";
                      }
                    }
                    description
                      "Attribute or affinity name";
                  }
                  leaf name9 {
                    type xr:Cisco-ios-xr-string {
                      length "1..32" {
                        description
                          "Attribute or affinity name";
                      }
                    }
                    description
                      "Attribute or affinity name";
                  }
                  leaf name10 {
                    type xr:Cisco-ios-xr-string {
                      length "1..32" {
                        description
                          "Attribute or affinity name";
                      }
                    }
                    description
                      "Attribute or affinity name";
                  }
                }
              }
              container ignore {
                presence "Indicates a ignore node is configured.";
                description
                  "All links are included in path calculation regardless of attributes";
              }
              container exclude-all {
                presence "Indicates a exclude-all node is configured.";
                description
                  "Links with any attribute are excluded from path calculation";
              }
              leaf affinity-attribute-value {
                type uint32 {
                  range "0..4294967295" {
                    description
                      "Affinity attribute value";
                  }
                }
                description
                  "Affinity attribute value";
              }
              leaf mask {
                type uint32 {
                  range "0..4294967295" {
                    description
                      "Affinity attribute mask value";
                  }
                }
                description
                  "Affinity attribute mask value";
              }
            }
            container priority {
              presence "Indicates a priority node is configured.";
              description
                "Tunnel priority";
              leaf setup-priority {
                type uint32 {
                  range "0..7" {
                    description
                      "Setup Priority";
                  }
                }
                mandatory true;
                description
                  "Tunnel priority";
              }
              leaf hold-priority {
                type uint32 {
                  range "0..7" {
                    description
                      "Hold Priority";
                  }
                }
                mandatory true;
                description
                  "Hold Priority";
              }
            }
            container signalled-bandwidth {
              must "not(class-type and sub-pool)";
              presence "Indicates a signalled-bandwidth node is configured.";
              description
                "Tunnel bandwidth requirement to be signalled";
              leaf bandwidth {
                type uint32 {
                  range "0..4294967295" {
                    description
                      "Bandwidth requirement in kbps";
                  }
                }
                mandatory true;
                description
                  "Bandwidth requirement in kbps";
              }
              leaf class-type {
                type uint32 {
                  range "0..1" {
                    description
                      "Class type number";
                  }
                }
                description
                  "Specify the bandwidth class type";
              }
              container sub-pool {
                when "../bandwidth != 0";
                presence "Indicates a sub-pool node is configured.";
                description
                  "Specify sub-pool bandwidth";
              }
            }
            leaf forward-class {
              type uint32 {
                range "0..7" {
                  description
                    "Forward class for the tunnel (default value 0)";
                }
              }
              description
                "Specify tunnel forward class for policy based routing";
            }
            leaf load-share {
              type uint32 {
                range "1..4294967295" {
                  description
                    "Loadshare value. Scale is the same as bandwidths.";
                }
              }
              description
                "Specify tunnel load-sharing metric";
            }
            container path-selection {
              description
                "Enter path selection configuration submode";
              container metric {
                description
                  "Metric Type for path calculation";
                container igp {
                  presence "Indicates a igp node is configured.";
                  description
                    "Use IGP metric";
                }
                container te {
                  presence "Indicates a te node is configured.";
                  description
                    "Use TE metric";
                }
                container delay {
                  presence "Indicates a delay node is configured.";
                  description
                    "Use delay metric";
                }
              }
              container tiebreaker {
                description
                  "Equal cost multipath tiebreaker for path calculation (default: min-fill).";
                container min-fill {
                  presence "Indicates a min-fill node is configured.";
                  description
                    "Prefer the path with the least-utilized links";
                }
                container max-fill {
                  presence "Indicates a max-fill node is configured.";
                  description
                    "Prefer the path with the most-utilized links";
                }
                container random {
                  presence "Indicates a random node is configured.";
                  description
                    "Prefer a path with links utilized randomly";
                }
              }
              leaf delay-limit {
                type uint32 {
                  range "1..4294967295" {
                    description
                      "Delay limit in usec";
                  }
                }
                description
                  "Delay limit configuration";
              }
            }
            container forwarding-adjacency {
              presence "Indicates a forwarding-adjacency node is configured.";
              description
                "Enable a forwarding-adjacency and enter its submode";
              leaf holdtime {
                type uint32 {
                  range "0..20000" {
                    description
                      "Hold time in ms";
                  }
                }
                description
                  "Hold time in ms";
              }
              container include-ipv6 {
                presence "Indicates a include-ipv6 node is configured.";
                description
                  "Announce tunnel as an IPv6 FA also";
              }
            }
            container autoroute {
              description
                "Parameters for IGP routing over tunnel";
              container announce {
                presence "Indicates a announce node is configured.";
                description
                  "Announce tunnel to IGP";
                container metric {
                  must "constant or absolute or relative";
                  presence "Indicates a metric node is configured.";
                  description
                    "Specify MPLS tunnel metric";
                  leaf absolute {
                    type uint32 {
                      range "1..2147483647" {
                        description
                          "Absolute metric";
                      }
                    }
                    description
                      "Set metric mode absolute";
                  }
                  leaf relative {
                    type int32 {
                      range "-10..10" {
                        description
                          "Relative metric";
                      }
                    }
                    description
                      "Set metric mode relative";
                  }
                  leaf constant {
                    type uint32 {
                      range "1..2147483647" {
                        description
                          "Set constant metric";
                      }
                    }
                    description
                      "Set constant metric";
                  }
                }
                container include-ipv6 {
                  presence "Indicates a include-ipv6 node is configured.";
                  description
                    "Announce tunnel as an IPv6 AA also";
                }
                container exclude-traffic {
                  description
                    "Exclude the type of traffic that goes through AA";
                  container segment-routing {
                    presence "Indicates a segment-routing node is configured.";
                    description
                      "Exclude segment-routing traffic from the autoroute announced tunnel";
                  }
                }
              }
              container destinations {
                description
                  "Adds static route to destination";
                list destination {
                  key "address";
                  description
                    "Adds static route to destination";
                  leaf address {
                    type inet:ipv4-address-no-zone;
                    description
                      "Adds static route to destination";
                  }
                }
              }
            }
            container auto-bw {
              presence "Indicates a auto-bw node is configured.";
              description
                "Enable tunnel auto-bandwidth and enter its submode";
              leaf application {
                type uint32 {
                  range "5..10080" {
                    description
                      " Auto-bw application frequency (minutes)";
                  }
                }
                description
                  "Set the tunnel auto-bw application frequency";
              }
              container bw-limit {
                presence "Indicates a bw-limit node is configured.";
                description
                  "Set min/max bandwidth auto-bw can apply on a tunnel";
                leaf min {
                  type uint32 {
                    range "0..4294967295" {
                      description
                        "Minimum bandwidth to apply (kbps)";
                    }
                  }
                  mandatory true;
                  description
                    "Set minimum bandwidth auto-bw can apply on a tunnel";
                }
                leaf max {
                  type uint32 {
                    range "0..4294967295" {
                      description
                        "Maximum bandwidth to apply (kbps)";
                    }
                  }
                  mandatory true;
                  description
                    "Set maximum bandwidth auto-bw can apply on a tunnel";
                }
              }
              container collect-bw-only {
                presence "Indicates a collect-bw-only node is configured.";
                description
                  "Enable bandwidth collection only, no auto-bw adjustment";
              }
              container adjustment-threshold {
                presence "Indicates a adjustment-threshold node is configured.";
                description
                  "Set the bandwidth change threshold to trigger adjustment";
                leaf bandwidth-change-percent {
                  type uint32 {
                    range "1..100" {
                      description
                        "Bandwidth change percent to trigger adjustment";
                    }
                  }
                  mandatory true;
                  description
                    "Set the bandwidth change threshold to trigger adjustment";
                }
                leaf min {
                  type uint32 {
                    range "10..4294967295" {
                      description
                        "Bandwidth change value to trigger adjustment (kbps)";
                    }
                  }
                  description
                    "Set the bandwidth change value to trigger adjustment";
                }
              }
              container overflow {
                description
                  "Configuring the tunnel overflow detection";
                container threshold {
                  presence "Indicates a threshold node is configured.";
                  description
                    "Set the bandwidth change percent to trigger an overflow";
                  leaf bandwidth-change-percent {
                    type uint32 {
                      range "1..100" {
                        description
                          "Bandwidth change percent to trigger an overflow";
                      }
                    }
                    mandatory true;
                    description
                      "Set the bandwidth change percent to trigger an overflow";
                  }
                  leaf min {
                    type uint32 {
                      range "10..4294967295" {
                        description
                          "Bandwidth change value to trigger an overflow (kbps)";
                      }
                    }
                    mandatory true;
                    description
                      "Set the bandwidth change value to trigger an overflow";
                  }
                  leaf limit {
                    type uint32 {
                      range "1..10" {
                        description
                          "Number of consecutive collections exceeding threshold";
                      }
                    }
                    mandatory true;
                    description
                      "Set the number of consecutive collections exceeding threshold";
                  }
                }
              }
              container underflow {
                description
                  "Configuring the tunnel underflow detection";
                container threshold {
                  presence "Indicates a threshold node is configured.";
                  description
                    "Set the bandwidth change percent to trigger an underflow";
                  leaf bandwidth-change-percent {
                    type uint32 {
                      range "1..100" {
                        description
                          "Bandwidth change percent to trigger an underflow";
                      }
                    }
                    mandatory true;
                    description
                      "Set the bandwidth change percent to trigger an underflow";
                  }
                  leaf min {
                    type uint32 {
                      range "10..4294967295" {
                        description
                          "Bandwidth change value to trigger an underflow (kbps)";
                      }
                    }
                    mandatory true;
                    description
                      "Set the bandwidth change value to trigger an underflow";
                  }
                  leaf limit {
                    type uint32 {
                      range "1..10" {
                        description
                          "Number of consecutive collections exceeding threshold";
                      }
                    }
                    mandatory true;
                    description
                      "Set the number of consecutive collections exceeding threshold";
                  }
                }
              }
              container resignal {
                description
                  "Configure the tunnel resignal parameters after going down";
                container last-bandwidth {
                  description
                    "Configure the tunnel to use last applied bandwidth after going down";
                  leaf time-out {
                    type uint32 {
                      range "1..3600000" {
                        description
                          "time-out value to trigger a reset of the requested bandwidth (seconds)";
                      }
                    }
                    description
                      "Set the bandwidth resignal time-out value (in seconds) After this time the tunnel will be signaled with the configured bandwidth";
                  }
                }
              }
              container auto-capacity {
                presence "Indicates a auto-capacity node is configured.";
                description
                  "Enable auto-capacity and enter its submode";
                leaf min-clones {
                  type uint32 {
                    range "0..63" {
                      description
                        "Range of auto-capacity min clones (default 0)";
                    }
                  }
                  description
                    "Lower limit on the number of clones that can be created for a given tunnel";
                }
                leaf max-clones {
                  type uint32 {
                    range "0..63" {
                      description
                        "Range of auto-capacity max clones (default 63)";
                    }
                  }
                  description
                    "Upper limit on the number of clones that can be created for a given tunnel";
                }
                leaf split-bandwidth {
                  type uint32 {
                    range "0..4294967295" {
                      description
                        "Bandwidth in kbps";
                    }
                  }
                  description
                    "Split bandwidth in kbps";
                }
                leaf merge-bandwidth {
                  type uint32 {
                    range "0..4294967295" {
                      description
                        "Bandwidth in kbps";
                    }
                  }
                  description
                    "Merge bandwidth in kbps";
                }
                leaf nominal-bandwidth {
                  type uint32 {
                    range "0..4294967295" {
                      description
                        "Bandwidth in kbps";
                    }
                  }
                  description
                    "Bandwidth in kbps used to compute the number of tunnels when merging or splitting ";
                }
              }
            }
            container bfd {
              presence "Indicates a bfd node is configured.";
              description
                "Configure BFD parameters";
              container fast-detect {
                presence "Indicates a fast-detect node is configured.";
                description
                  "Enable BFD fast detection";
                container sbfd {
                  presence "Indicates a sbfd node is configured.";
                  description
                    "Enable Seamless BFD";
                }
              }
              leaf minimum-interval {
                type uint32 {
                  range "3..30000" {
                    description
                      "Hello interval in milliseconds (default 100),lower bound is 50ms for BFD sessions for named tunnels ";
                  }
                }
                description
                  "Hello interval";
              }
              leaf multiplier {
                type uint32 {
                  range "3..10" {
                    description
                      "Number of consecutive misses before declaring failure  (default 3)";
                  }
                }
                description
                  "Number of consecutive misses before declaring failure ";
              }
            }
            container path-protection {
              presence "Indicates a path-protection node is configured.";
              description
                "Enable the path protection feature on this named tunnel";
              container srlg-diverse {
                presence "Indicates a srlg-diverse node is configured.";
                description
                  "Enforce SRLG diversity for protecting LSP";
              }
            }
            container path-options {
              description
                "Primary or fallback path setup option";
              list path-option {
                key "path-setup-name";
                description
                  "Primary or fallback path setup option";
                leaf path-setup-name {
                  type xr:Cisco-ios-xr-string {
                    length "1..1024" {
                      description
                        "Path setup name";
                    }
                  }
                  description
                    "Primary or fallback path setup option";
                }
                leaf preference {
                  type uint32 {
                    range "0..255" {
                      description
                        "Lower value is more preferred path option";
                    }
                  }
                  description
                    "Specify the preference of the path-option.";
                }
                container computation {
                  description
                    "Specify the computation method for the path";
                  container dynamic {
                    presence "Indicates a dynamic node is configured.";
                    description
                      "Dyanmic path computation";
                  }
                  leaf explicit {
                    type xr:Cisco-ios-xr-string {
                      length "1..1024" {
                        description
                          "Name of the explicit path";
                      }
                    }
                    description
                      "Computation based on the preconfigured path";
                  }
                }
              }
            }
            leaf load-interval {
              type uint32 {
                range "0|30|60|90|120|150|180|210|240|270|300|330|360|390|420|450|480|510|540|570|600" {
                  description
                    "Number of seconds: 0 disables load calculation";
                }
              }
              description
                "Specify interval for load calculation for the named tunnel";
            }
            container self-ping {
              presence "Indicates a self-ping node is configured.";
              description
                "Enable self-ping and enter its submode";
              leaf max-count {
                type uint32 {
                  range "1..180" {
                    description
                      "Range of maximum number of self-ping probes (default 60)";
                  }
                }
                description
                  "Number of self-ping probes <1-180> (default 60)";
              }
            }
          }
        }
      }
      container affinity-maps {
        description
          "Affinity Map Configuration";
        list affinity-map {
          key "attribute-name";
          description
            "Affinity Map Configuration";
          leaf attribute-name {
            type xr:Cisco-ios-xr-string {
              length "1..32" {
                description
                  "Name of the explicit path";
              }
            }
            must "(../attribute-value and not(../bit-position)) or (../bit-position and not(../attribute-value))";
            description
              "Affinity attribute name";
          }
          leaf attribute-value {
            type uint32 {
              range "1..2147483648" {
                description
                  "Affinity attribute value";
              }
            }
            description
              "Affinity Map Configuration";
          }
          leaf bit-position {
            type uint32 {
              range "0..255" {
                description
                  "Bit Position";
              }
            }
            description
              "Bit Position for Affinity attribute value";
          }
        }
      }
      container signalling {
        description
          "Signalling options";
        container advertise {
          description
            "Label advertising options";
          container explicit-null {
            presence "Indicates a explicit-null node is configured.";
            description
              "Enable explicit-null advertising to PHOP";
          }
        }
      }
      container router-id {
        description
          "Router ID";
        list secondary {
          key "router-id";
          description
            "Configure secondary TE Router ID to be used locally (not advertised)";
          leaf router-id {
            type inet:ipv4-address-no-zone;
            description
              "Configure secondary TE Router ID to be used locally (not advertised)";
          }
        }
      }
      container fast-reroute {
        description
          "Fast-reroute config parameters";
        container timers {
          description
            "Configure fast-reroute timer";
          leaf hold-backup {
            type uint32 {
              range "0..604800" {
                description
                  "Seconds before backup declared UP (0 disables hold-timer)";
              }
            }
            description
              "Hold timer for backup UP event";
          }
          leaf promotion {
            type uint32 {
              range "0..604800" {
                description
                  "Seconds between promotions (0 disables promotion)";
              }
            }
            description
              "Configure how often we scan for LSP backup promotion";
          }
        }
      }
      container gmpls {
        description
          "GMPLS submode";
        container optical-uni {
          description
            "GMPLS-UNI submode";
          container controllers {
            description
              "Configure GMPLS-UNI on a link";
            list controller {
              key "controller-name";
              description
                "Configure GMPLS-UNI on a link";
              leaf controller-name {
                type xr:Interface-name;
                description
                  "Configure GMPLS-UNI on a link";
              }
              container switching-type {
                description
                  "Specify switching type";
                container dcsc {
                  presence "Indicates a dcsc node is configured.";
                  description
                    "Data channel switch capable";
                }
                container lsc {
                  presence "Indicates a lsc node is configured.";
                  description
                    "Lambda switch capable";
                }
                container fsc {
                  presence "Indicates a fsc node is configured.";
                  description
                    "Fiber switch capable";
                }
              }
              leaf mtu {
                type uint32 {
                  range "64..65535" {
                    description
                      "MTU size in bytes";
                  }
                }
                description
                  "Set the MTU on a controller";
              }
              container logging {
                description
                  "Per-controller logging configuration";
                container discovered-srlgs {
                  presence "Indicates a discovered-srlgs node is configured.";
                  description
                    "Enable logging for discovered SRLGs on this link";
                }
              }
              container announce {
                description
                  "Announce discovered tunnel properties to system";
                container srlgs {
                  presence "Indicates a srlgs node is configured.";
                  description
                    "Announce discovered SRLGs to system";
                }
              }
              container tunnel-properties {
                presence "Indicates a tunnel-properties node is configured.";
                description
                  "Configure GMPLS-UNI tunnel head properties";
                container destination {
                  description
                    "Specify tunnel destination";
                  container ipv4 {
                    description
                      "Specify an IPv4 destination";
                    leaf unicast {
                      type inet:ipv4-address-no-zone;
                      description
                        "Specify an IPv4 unicast destination";
                    }
                  }
                }
                leaf g-pid {
                  type uint32 {
                    range "0..255" {
                      description
                        "GPID value";
                    }
                  }
                  description
                    "Specify generalized payload type";
                }
                container encoding-type {
                  description
                    "Specify LSP encoding type";
                  container ethernet-type1 {
                    presence "Indicates a ethernet-type1 node is configured.";
                    description
                      "Ethernet Private Line Type 1";
                  }
                  container ethernet-type2 {
                    presence "Indicates a ethernet-type2 node is configured.";
                    description
                      "Ethernet Private Line Type 1";
                  }
                  container lambda {
                    presence "Indicates a lambda node is configured.";
                    description
                      "Lambda Photonic";
                  }
                  container fiber {
                    presence "Indicates a fiber node is configured.";
                    description
                      "Fiber";
                  }
                }
                container path-options {
                  description
                    "Configure a GMPLS-UNI path-option";
                  list path-option {
                    must "no-ero or explicit";
                    key "preference";
                    description
                      "Configure a GMPLS-UNI path-option";
                    leaf preference {
                      type uint32 {
                        range "1..1000" {
                          description
                            "Preference for this path option";
                        }
                      }
                      description
                        "Configure a GMPLS-UNI path-option";
                    }
                    container no-ero {
                      must "../lockdown";
                      presence "Indicates a no-ero node is configured.";
                      description
                        "No path configuration";
                    }
                    container explicit {
                      description
                        "Setup based on preconfigured path";
                      container identifier {
                        must "not(../name) and ../../lockdown and ../../verbatim";
                        presence "Indicates a identifier node is configured.";
                        description
                          "Specify an explicit path by number";
                        leaf explicit-path-number {
                          type uint32 {
                            range "1..65535" {
                              description
                                "Explicit path number";
                            }
                          }
                          mandatory true;
                          description
                            "Specify an explicit path by number";
                        }
                      }
                      container name {
                        must "not(../identifier) and ../../lockdown and ../../verbatim";
                        presence "Indicates a name node is configured.";
                        description
                          "Specify an explicit path by name";
                        leaf explicit-path-name {
                          type xr:Cisco-ios-xr-string {
                            length "1..1024" {
                              description
                                "Explicit path name";
                            }
                          }
                          mandatory true;
                          description
                            "Specify an explicit path by name";
                        }
                      }
                    }
                    leaf xro-attribute-set {
                      type xr:Cisco-ios-xr-string {
                        length "1..64" {
                          description
                            "Specify attribute-set name (max 64 char)";
                        }
                      }
                      description
                        "Attribute-set containing path exclusions";
                    }
                    container signaled-label {
                      description
                        "Specify a fixed upstream label to be used";
                      container dwdm {
                        description
                          "DWDM label (RFC 6205), 50GHz channel-spacing";
                        leaf wavelength {
                          type uint32 {
                            range "1..89" {
                              description
                                "DWDM channel number (ITU), 50GHz channel-spacing";
                            }
                          }
                          description
                            "DWDM wavelength";
                        }
                      }
                    }
                    container lockdown {
                      presence "Indicates a lockdown node is configured.";
                      description
                        "Not a candidate for reoptimization";
                    }
                    container verbatim {
                      presence "Indicates a verbatim node is configured.";
                      description
                        "Use explicit path to construct ERO directly";
                    }
                  }
                }
                container priority {
                  presence "Indicates a priority node is configured.";
                  description
                    "Tunnel priority";
                  leaf setup-priority {
                    type uint32 {
                      range "0..7" {
                        description
                          "Setup Priority";
                      }
                    }
                    mandatory true;
                    description
                      "Tunnel priority";
                  }
                  leaf hold-priority {
                    type uint32 {
                      range "0..7" {
                        description
                          "Hold Priority";
                      }
                    }
                    mandatory true;
                    description
                      "Hold Priority";
                  }
                }
                container record-route {
                  presence "Indicates a record-route node is configured.";
                  description
                    "Record the route used by the tunnel";
                }
                leaf signalled-name {
                  type xr:Cisco-ios-xr-string {
                    length "1..254" {
                      description
                        "The name to be included in signaling (max 254 characters)";
                    }
                  }
                  description
                    "The signaling name to assign to the tunnel";
                }
                container record {
                  description
                    "Request recording of tunnel properties during signaling";
                  container srlg {
                    presence "Indicates a srlg node is configured.";
                    description
                      "SRLG recording";
                  }
                }
                leaf tunnel-id {
                  type uint32 {
                    range "0..65535" {
                      description
                        "Tunnel ID";
                    }
                  }
                  description
                    "GMPLS-UNI tunnel id";
                }
                container logging {
                  description
                    "Per-tunnel logging configuration";
                  container events {
                    description
                      "Per-tunnel logging events";
                    container lsp-status {
                      description
                        "Enable interface LSP state change alarms";
                      container state {
                        presence "Indicates a state node is configured.";
                        description
                          "Enable interface LSP UP/DOWN change alarms";
                      }
                    }
                  }
                }
                container protection {
                  description
                    "Protection";
                  leaf attribute-set {
                    type xr:Cisco-ios-xr-string {
                      length "1..64" {
                        description
                          "Specify attribute-set name (max 32 characters)";
                      }
                    }
                    description
                      "Protection attribute set";
                  }
                }
              }
            }
          }
          container timers {
            description
              "Configure GMPLS-UNI timers";
            container path-option {
              description
                "Path-option timers";
              container holddown {
                presence "Indicates a holddown node is configured.";
                description
                  "Path-option holddown timer limits";
                leaf minimum {
                  type uint32 {
                    range "5..3600" {
                      description
                        "Minimum path-option holddown time (seconds)";
                    }
                  }
                  mandatory true;
                  description
                    "Path-option holddown timer limits";
                }
                leaf maximum {
                  type uint32 {
                    range "5..3600" {
                      description
                        "Maximum path-option holddown time (seconds)";
                    }
                  }
                  mandatory true;
                  description
                    "Maximum path-option holddown time (seconds)";
                }
              }
            }
          }
        }
        container optical-nni {
          presence "Indicates a optical-nni node is configured.";
          description
            "GMPLS-NNI submode";
          container path-selection {
            description
              "Path Selection Configuration";
            container metric {
              description
                "Metric Type Configuration";
              container te-metric {
                presence "Indicates a te-metric node is configured.";
                description
                  "Use TE metric";
              }
              container delay {
                presence "Indicates a delay node is configured.";
                description
                  "Use delay metric";
              }
            }
          }
          container controller {
            description
              "Configure GMPLS-NNI tunnel";
            list odu-group-te {
              key "tunnel-id";
              description
                "Odu-Group-Te controller(s)";
              leaf tunnel-id {
                type uint32 {
                  range "0..64535" {
                    description
                      "Enter the Tunnel ID";
                  }
                }
                description
                  "Enter the Tunnel ID";
              }
              container logging {
                description
                  "Per-interface logging configuration";
                container events {
                  description
                    "Per-interface logging events";
                  container lsp-status {
                    description
                      "Enable interface LSP state change alarms";
                    container state {
                      presence "Indicates a state node is configured.";
                      description
                        "Enable tunnel oper-state change notification";
                    }
                    container signalling-state {
                      presence "Indicates a signalling-state node is configured.";
                      description
                        "Enable all sub-LSP state change notification";
                    }
                    container insufficient-bandwidth {
                      presence "Indicates a insufficient-bandwidth node is configured.";
                      description
                        "Enable Syslog for setup failure due to bandwidth";
                    }
                    container cross-connect {
                      presence "Indicates a cross-connect node is configured.";
                      description
                        "Enable Static X-connects change notification";
                    }
                    container switch-over {
                      presence "Indicates a switch-over node is configured.";
                      description
                        "Enable Active LSP change notification";
                    }
                    container path-change {
                      presence "Indicates a path-change node is configured.";
                      description
                        "Enable Path-change notification";
                    }
                    container homepath-state {
                      presence "Indicates a homepath-state node is configured.";
                      description
                        "Enable Homepath state change notification";
                    }
                  }
                }
              }
              container path-selection {
                description
                  "Path Selection Configuration";
                container metric {
                  description
                    "Metric Type Configuration";
                  container te-metric {
                    presence "Indicates a te-metric node is configured.";
                    description
                      "Use TE metric";
                  }
                  container delay {
                    presence "Indicates a delay node is configured.";
                    description
                      "Use delay metric";
                  }
                }
              }
              container destination {
                description
                  "Specify tunnel destination";
                container ipv4 {
                  description
                    "Specify an IPv4 destination";
                  leaf unicast {
                    type inet:ipv4-address-no-zone;
                    description
                      "Specify an IPv4 unicast destination";
                  }
                  container unnumbered {
                    presence "Indicates a unnumbered node is configured.";
                    description
                      "Enter Router-id (A.B.C.D)";
                    leaf address {
                      type inet:ipv4-address-no-zone;
                      mandatory true;
                      description
                        "Enter Router-id (A.B.C.D)";
                    }
                    leaf interface-ifindex {
                      type uint32 {
                        range "0..4294967295" {
                          description
                            "Enter the destination IF-index";
                        }
                      }
                      description
                        "Specify terminated interface index assigned by destination node";
                    }
                  }
                }
              }
              leaf signalled-name {
                type xr:Cisco-ios-xr-string {
                  length "1..254" {
                    description
                      "The name to be included in signaling (max 254 characters)";
                  }
                }
                description
                  "The signaling name to assign to the tunnel";
              }
              container protection-switching {
                description
                  "Protection-switching specific commands";
                container lockout {
                  description
                    "Lockout tunnel controller to prevent switch over";
                  container working {
                    presence "Indicates a working node is configured.";
                    description
                      "Lockout working path";
                  }
                }
              }
              container record-route {
                presence "Indicates a record-route node is configured.";
                description
                  "Records the route used by the tunnel";
              }
              container announce-srlg {
                presence "Indicates a announce-srlg node is configured.";
                description
                  "Announce the srlg on termination interface";
              }
              container shutdown {
                presence "Indicates a shutdown node is configured.";
                description
                  "Shuts down LSP/Tunnel";
                container lsp-type {
                  description
                    "Lists the Lsp Types";
                  container current {
                    presence "Indicates a current node is configured.";
                    description
                      "Shuts down the Current/Working LSP";
                  }
                  container standby {
                    presence "Indicates a standby node is configured.";
                    description
                      "Shuts down the Protect/Standby LSP";
                  }
                  container restore {
                    presence "Indicates a restore node is configured.";
                    description
                      "Shuts down the Restore LSP";
                  }
                }
              }
              container signalled-bandwidth {
                description
                  "Set the signaled B/W of the tunnel";
                container odu0 {
                  presence "Indicates a odu0 node is configured.";
                  description
                    "Signalled Bandwidth for ODU0";
                }
                container odu1 {
                  presence "Indicates a odu1 node is configured.";
                  description
                    "Signalled Bandwidth for ODU1";
                }
                container odu1e {
                  presence "Indicates a odu1e node is configured.";
                  description
                    "Signalled Bandwidth for ODU1e";
                }
                container odu1f {
                  presence "Indicates a odu1f node is configured.";
                  description
                    "Signalled Bandwidth for ODU1f";
                }
                container odu2 {
                  presence "Indicates a odu2 node is configured.";
                  description
                    "Signalled Bandwidth for ODU2";
                }
                container odu2e {
                  presence "Indicates a odu2e node is configured.";
                  description
                    "Signalled Bandwidth for ODU2e";
                }
                container odu2f {
                  presence "Indicates a odu2f node is configured.";
                  description
                    "Signalled Bandwidth for ODU2f";
                }
                container odu3 {
                  presence "Indicates a odu3 node is configured.";
                  description
                    "Signalled Bandwidth for ODU3";
                }
                container odu3e1 {
                  presence "Indicates a odu3e1 node is configured.";
                  description
                    "Signalled Bandwidth for ODU3e1";
                }
                container odu3e2 {
                  presence "Indicates a odu3e2 node is configured.";
                  description
                    "Signalled Bandwidth for ODU3e2";
                }
                container odu4 {
                  presence "Indicates a odu4 node is configured.";
                  description
                    "Signalled Bandwidth for ODU4";
                }
                container oduflex {
                  description
                    "Signalled Bandwidth for ODUFlex";
                  leaf bitrate {
                    type uint32 {
                      range "1..104136740" {
                        description
                          "Enter the bitrate for ODUFlex in kbps";
                      }
                    }
                    description
                      "Set bit-rate for ODUFlex in kbps";
                  }
                  container framing-type {
                    description
                      "Set the framing type for ODUFlex";
                    container cbr {
                      presence "Indicates a cbr node is configured.";
                      description
                        "Set framing type as CBR for ODU Flex";
                    }
                    container gfp-f-fixed {
                      presence "Indicates a gfp-f-fixed node is configured.";
                      description
                        "Set framing type as GFP-F-Fixed for ODU Flex";
                    }
                  }
                }
              }
              container path-options {
                description
                  "Path setup option";
                list path-option {
                  must "dynamic or explicit";
                  key "preference";
                  description
                    "Path setup option";
                  leaf preference {
                    type uint32 {
                      range "1..1000" {
                        description
                          "Preference for this path option";
                      }
                    }
                    description
                      "Path setup option";
                  }
                  container dynamic {
                    must "../lockdown";
                    presence "Indicates a dynamic node is configured.";
                    description
                      "Setup based on dynamically allocated path";
                  }
                  container explicit {
                    description
                      "Setup based on preconfigured path";
                    container identifier {
                      must "not(../name) and ../../lockdown";
                      presence "Indicates a identifier node is configured.";
                      description
                        "Specify an IP explicit path by number";
                      leaf explicit-path-number {
                        type uint32 {
                          range "1..65535" {
                            description
                              "Specify an IP explicit path by number";
                          }
                        }
                        mandatory true;
                        description
                          "Specify an IP explicit path by number";
                      }
                    }
                    container name {
                      must "not(../identifier) and ../../lockdown";
                      presence "Indicates a name node is configured.";
                      description
                        "Specify an IP explicit path by name";
                      leaf explicit-path-name {
                        type xr:Cisco-ios-xr-string {
                          length "1..1024" {
                            description
                              "Specify an IP explicit path by name";
                          }
                        }
                        mandatory true;
                        description
                          "Specify an IP explicit path by name";
                      }
                    }
                  }
                  leaf attribute-set {
                    type xr:Cisco-ios-xr-string {
                      length "1..64" {
                        description
                          "Specify attribute-set name (max 64 char)";
                      }
                    }
                    description
                      "Attribute set for this LSP";
                  }
                  leaf xro-attribute-set {
                    type xr:Cisco-ios-xr-string {
                      length "1..64" {
                        description
                          "Specify attribute-set name (max 64 char)";
                      }
                    }
                    description
                      "Attribute-set containing path exclusions";
                  }
                  container lockdown {
                    presence "Indicates a lockdown node is configured.";
                    description
                      "Path-option is not a candidate for reoptimization";
                  }
                  container protected-by {
                    description
                      "Path protection using explicit protecting path";
                    container none {
                      must "not(../explicit-protecting-path)";
                      presence "Indicates a none node is configured.";
                      description
                        "No path protection";
                    }
                    leaf explicit-protecting-path {
                      type uint32 {
                        range "1..1000" {
                          description
                            "Explicit protecting path option preference level (index)";
                        }
                      }
                      must "not(../none)";
                      description
                        "Explicit protecting path option preference level (index)";
                    }
                  }
                  leaf restored-from {
                    type uint32 {
                      range "1..1000" {
                        description
                          "Restore path option preference level (index)";
                      }
                    }
                    description
                      "Path restoration option";
                  }
                }
              }
              container static-uni {
                description
                  "Set the static UNI endpoints of the NNI Tunnel";
                container ingress-port {
                  description
                    "Specify an ingress-port";
                  container controller {
                    must "not(../../local-termination)";
                    presence "Indicates a controller node is configured.";
                    description
                      "Specify an ingress-port controller";
                    leaf controller-name {
                      type xr:Interface-name;
                      mandatory true;
                      description
                        "Ingress-port controller name";
                    }
                    container egress-port {
                      presence "Indicates a egress-port node is configured.";
                      description
                        "Specify an egress-port";
                      leaf unnumbered {
                        type uint32 {
                          range "0..4294967295" {
                            description
                              "Enter the tail-end customer port IF index";
                          }
                        }
                        mandatory true;
                        description
                          "Specify tail-end customer port IF index";
                      }
                    }
                    container remote-termination {
                      presence "Indicates a remote-termination node is configured.";
                      description
                        "Remote termination for egress";
                      leaf unnumbered {
                        type uint32 {
                          range "0..4294967295" {
                            description
                              "Enter the tail-end customer port IF index";
                          }
                        }
                        mandatory true;
                        description
                          "Specify tail-end customer port IF index";
                      }
                    }
                  }
                }
                container local-termination {
                  must "not(../ingress-port/controller)";
                  presence "Indicates a local-termination node is configured.";
                  description
                    "Local termination for ingress";
                  leaf interface-name {
                    type xr:Interface-name;
                    mandatory true;
                    description
                      "Ingress Interface";
                  }
                  container egress-port {
                    presence "Indicates a egress-port node is configured.";
                    description
                      "Specify an egress-port";
                    leaf unnumbered {
                      type uint32 {
                        range "0..4294967295" {
                          description
                            "Enter the tail-end customer port IF index";
                        }
                      }
                      mandatory true;
                      description
                        "Specify tail-end customer port IF index";
                    }
                  }
                  container remote-termination {
                    presence "Indicates a remote-termination node is configured.";
                    description
                      "Remote termination for egress";
                    leaf unnumbered {
                      type uint32 {
                        range "0..4294967295" {
                          description
                            "Enter the tail-end customer port IF index";
                        }
                      }
                      mandatory true;
                      description
                        "Specify tail-end customer port IF index";
                    }
                  }
                }
              }
              container path-protection {
                description
                  "Path protection";
                leaf attribute-set {
                  type xr:Cisco-ios-xr-string {
                    length "1..64" {
                      description
                        "Specify attribute-set name (max 32 characters)";
                    }
                  }
                  description
                    "Path protection attribute set";
                }
              }
              leaf payload {
                type enumeration {
                  enum "Unkonwn" {
                    value 0;
                    description
                      "Payload is unknown";
                  }
                  enum "bmp" {
                    value 50;
                    description
                      "bmp for payload";
                  }
                  enum "gfp-f" {
                    value 54;
                    description
                      "gfp-f for payload";
                  }
                  enum "gmp" {
                    value 55;
                    description
                      "gmp for payload";
                  }
                  enum "gfp-f-ext" {
                    value 70;
                    description
                      "gfp-f-extended for payload";
                  }
                }
                description
                  "gpid as mapping";
              }
            }
          }
          container topology {
            description
              "GMPLS NNI topology instance";
            container instance {
              description
                "GMPLS NNI topology instance";
              list ospf {
                must "areas";
                key "instance-name";
                description
                  "OSPF instance";
                leaf instance-name {
                  type xr:Cisco-ios-xr-string {
                    length "1..40" {
                      description
                        "Name for this OSPF instance";
                    }
                  }
                  description
                    "OSPF instance";
                }
                container areas {
                  description
                    "Specify the OSPF area to flood link into";
                  list area-decimal {
                    key "area-id";
                    description
                      "Specify the OSPF area to flood link into";
                    leaf area-id {
                      type uint32 {
                        range "0..4294967295";
                      }
                      description
                        "Specify the OSPF area ID as a decimal value";
                    }
                    container controllers {
                      description
                        "Configure GMPLS-NNI on a link";
                      list controller {
                        key "controller-id";
                        description
                          "Configure GMPLS-NNI on a link";
                        leaf controller-id {
                          type xr:Interface-name;
                          description
                            "Configure GMPLS-NNI on a link";
                        }
                        leaf admin-weight {
                          type uint32 {
                            range "0..65535" {
                              description
                                "Admin weight value";
                            }
                          }
                          description
                            "Contoller admin weight";
                        }
                        container affinity-names {
                          description
                            "Specify one or more color for the Contoller";
                          leaf-list affinity-name {
                            type xr:Cisco-ios-xr-string {
                              length "1..32" {
                                description
                                  "User defined affinity-name";
                              }
                            }
                            max-elements "32";
                            description
                              "Specify one or more color for the Contoller";
                          }
                        }
                        leaf delay {
                          type uint32 {
                            range "1..16777215" {
                              description
                                "TE link delay value in micro-sec";
                            }
                          }
                          description
                            "TE link delay";
                        }
                        container tti-mode {
                          description
                            "TTI Mode to carry TE Link Id,default is otu_sm";
                          container otu-sm {
                            presence "Indicates a otu-sm node is configured.";
                            description
                              "Section Monitoring for OTU";
                          }
                          container odu-pm {
                            presence "Indicates a odu-pm node is configured.";
                            description
                              "Path Monitoring for ODU";
                          }
                          leaf odu-tcm {
                            type uint32 {
                              range "1..6" {
                                description
                                  "Enter the Tandem Connection Monitoring ID";
                              }
                            }
                            description
                              "Tandem Connection Monitoring for ODU";
                          }
                        }
                      }
                    }
                  }
                  list area-address {
                    key "area-id";
                    description
                      "Specify the OSPF area to flood link into";
                    leaf area-id {
                      type inet:ipv4-address-no-zone;
                      description
                        "Specify the OSPF area ID in IP address format";
                    }
                    container controllers {
                      description
                        "Configure GMPLS-NNI on a link";
                      list controller {
                        key "controller-id";
                        description
                          "Configure GMPLS-NNI on a link";
                        leaf controller-id {
                          type xr:Interface-name;
                          description
                            "Configure GMPLS-NNI on a link";
                        }
                        leaf admin-weight {
                          type uint32 {
                            range "0..65535" {
                              description
                                "Admin weight value";
                            }
                          }
                          description
                            "Contoller admin weight";
                        }
                        container affinity-names {
                          description
                            "Specify one or more color for the Contoller";
                          leaf-list affinity-name {
                            type xr:Cisco-ios-xr-string {
                              length "1..32" {
                                description
                                  "User defined affinity-name";
                              }
                            }
                            max-elements "32";
                            description
                              "Specify one or more color for the Contoller";
                          }
                        }
                        leaf delay {
                          type uint32 {
                            range "1..16777215" {
                              description
                                "TE link delay value in micro-sec";
                            }
                          }
                          description
                            "TE link delay";
                        }
                        container tti-mode {
                          description
                            "TTI Mode to carry TE Link Id,default is otu_sm";
                          container otu-sm {
                            presence "Indicates a otu-sm node is configured.";
                            description
                              "Section Monitoring for OTU";
                          }
                          container odu-pm {
                            presence "Indicates a odu-pm node is configured.";
                            description
                              "Path Monitoring for ODU";
                          }
                          leaf odu-tcm {
                            type uint32 {
                              range "1..6" {
                                description
                                  "Enter the Tandem Connection Monitoring ID";
                              }
                            }
                            description
                              "Tandem Connection Monitoring for ODU";
                          }
                        }
                      }
                    }
                  }
                }
              }
            }
          }
        }
      }
      container maxabs {
        must "(tunnels and not(destinations or p2mp-tunnels)) or (destinations and not(tunnels or p2mp-tunnels)) or (p2mp-tunnels and not(tunnels or destinations))";
        presence "Indicates a maxabs node is configured.";
        description
          "Maximum number of Traffic engineering attribute";
        leaf tunnels {
          type uint32 {
            range "1..65536" {
              description
                "Desired Maximum Number";
            }
          }
          description
            "All MPLS Traffic Engineering Tunnels";
        }
        leaf destinations {
          type uint32 {
            range "1..65536" {
              description
                "Desired Maximum Number";
            }
          }
          description
            "All MPLS Traffic Engineering Destinations";
        }
        leaf p2mp-tunnels {
          type uint32 {
            range "1..65536" {
              description
                "Desired Maximum Number";
            }
          }
          description
            "P2MP MPLS Traffic Engineering Tunnels";
        }
      }
      container route-priority {
        description
          "Set route-priorities for tunnel labels";
        container role {
          description
            "Set route-priorities for tunnel roles";
          container head {
            description
              "Set route-priorities for tunnel heads";
            container primary {
              description
                "Set route-priorities for non-backup tunnels";
              leaf queue {
                type uint32 {
                  range "0..12" {
                    description
                      "LSD queue value (the lower value is the higher priority queue)";
                  }
                }
                description
                  "Set route-priority queue value";
              }
            }
            container backup {
              description
                "Set route-priorities for backup tunnels";
              leaf queue {
                type uint32 {
                  range "0..12" {
                    description
                      "LSD queue value (the lower value is the higher priority queue)";
                  }
                }
                description
                  "Set route-priority queue value";
              }
            }
          }
          container middle {
            description
              "Set route-priorities for tunnel midpoints";
            leaf queue {
              type uint32 {
                range "0..12" {
                  description
                    "LSD queue value (the lower value is the higher priority queue)";
                }
              }
              description
                "Set route-priority queue value";
            }
          }
        }
      }
      container load-share {
        description
          "Load-share configuration";
        container unequal {
          presence "Indicates a unequal node is configured.";
          description
            "Enable unequal load-sharing across TE tunnels to the same destination";
        }
      }
      container auto-bw {
        description
          "Auto-bandwidth configuration";
        container collect {
          description
            "Auto-bandwidth collection parameters";
          leaf frequency {
            type uint32 {
              range "1..10080" {
                description
                  "Auto-bandwidth collection frequency in minutes";
              }
            }
            description
              "Auto-bandwidth collection frequency parameter";
          }
        }
      }
      container soft-preemption {
        presence "Indicates a soft-preemption node is configured.";
        description
          "Enable soft-preemption";
        leaf timeout {
          type uint32 {
            range "1..300" {
              description
                "Timeout for soft-preempted LSP in seconds: default 60";
            }
          }
          description
            "Specify a timeout for soft-preempted LSP";
        }
        container frr-rewrite {
          presence "Indicates a frr-rewrite node is configured.";
          description
            "Move the traffic on the FRR backup tunnel";
        }
      }
      container preemption-graceful {
        description
          "Enable graceful preemption";
        container bw-reduction {
          presence "Indicates a bw-reduction node is configured.";
          description
            "Enable graceful preemption when there is a bandwidth reduction";
        }
      }
      container srlg {
        presence "Indicates a srlg node is configured.";
        description
          "Traffic Engineering SRLG submode";
        leaf admin-weight {
          type uint32 {
            range "0..4294967295" {
              description
                "Value added to link admin-weight during SRLG-aware path computation";
            }
          }
          description
            "Default administrative weight for all SRLGs, default is 1";
        }
        container names {
          description
            "SRLG Name";
          list name {
            key "srlg-name";
            description
              "SRLG Name";
            leaf srlg-name {
              type xr:Cisco-ios-xr-string {
                length "1..64" {
                  description
                    "SRLG Name";
                }
              }
              description
                "SRLG Name";
            }
            leaf admin-weight {
              type uint32 {
                range "0..4294967295" {
                  description
                    "Value added to link admin-weight during SRLG-aware path computation";
                }
              }
              description
                "Administrative weight: default inherited from the global admin-weight";
            }
            container static {
              description
                "Configure static SRLG under name";
              container ipv4 {
                description
                  "IPv4 address";
                list address {
                  key "local-address";
                  description
                    "IPv4 address of local end-point of the link";
                  leaf local-address {
                    type inet:ipv4-address-no-zone;
                    description
                      "IPv4 address of local end-point of the link";
                  }
                  container next-hop {
                    description
                      "Next hop of the link";
                    container ipv4 {
                      description
                        "IPv4 address";
                      leaf address {
                        type inet:ipv4-address-no-zone;
                        description
                          "IPv4 address of remote end-point of the link";
                      }
                    }
                  }
                }
              }
            }
          }
        }
      }
      container mib {
        description
          "MPLS-TE MIB properties";
        container midstats {
          description
            "Midpoint LSP traffic stats collection";
          container disable {
            presence "Indicates a disable node is configured.";
            description
              "Disables MIB midpoint LSP traffic stats collection";
          }
        }
      }
      container fault-oam {
        presence "Indicates a fault-oam node is configured.";
        description
          "Enable fault OAM functionality for bi-directional tunnels";
      }
      container hw-oor {
        description
          "Config submode for NPU OOR handling in MPLS-TE";
        container green {
          description
            "Config submode for handling NPU OOR in normal/green state";
          container action {
            description
              "Action to take in the HW-OOR state";
            container flood {
              description
                "Flooding parameters in the HW-OOR state";
              container te-metric {
                description
                  "Change the TE metric for the link in HW-OOR state";
                leaf penalty {
                  type uint32 {
                    range "0..16777215" {
                      description
                        "Value added to link metric when in HW-OOR state";
                    }
                  }
                  description
                    "Add a penalty to the TE metric of the link in HW-OOR state. Default is 0";
                }
              }
              leaf available-bw {
                type uint32 {
                  range "0..100" {
                    description
                      "Percentage of available BW when the link is in HW-OOR state";
                  }
                }
                description
                  "Specify the percentage of available BW for the link in HW-OOR state. Default is to flood 100% of the available bandwidth";
              }
            }
            container node-protection {
              description
                "Configure the FRR node-protection action in this HW-OOR state";
              container disable {
                presence "Indicates a disable node is configured.";
                description
                  "Disable FRR node-protection backups for the LSPs that use the interface in HW-OOR";
              }
            }
            container accept {
              description
                "Configure the accepted operations in this HW-OOR state";
              container reopt-lsp {
                presence "Indicates a reopt-lsp node is configured.";
                description
                  "Accept the reopt LSP sharing the same link in HW-OOR state as the current LSP";
              }
            }
            container admit {
              description
                "Configure the admission operations in this HW-OOR state";
              leaf lsp-min-bw {
                type uint32 {
                  range "0..4294967295" {
                    description
                      "Minimim bandwidth (in kbps)  of accepted LSPs, default is 0";
                  }
                }
                description
                  "Accept LSPs that are at least equal to the specified bandwidth";
              }
            }
          }
          leaf recovery-duration {
            type uint32 {
              range "0..10080" {
                description
                  "Number of minutes for the recovery in Green state, default is 0";
              }
            }
            description
              "Configure how long the actions are taken in HW-OOR Green state after recovery";
          }
        }
        container yellow {
          description
            "Config submode for handling NPU OOR in minor/yellow state";
          container action {
            description
              "Action to take in the HW-OOR state";
            container flood {
              description
                "Flooding parameters in the HW-OOR state";
              container te-metric {
                description
                  "Change the TE metric for the link in HW-OOR state";
                leaf penalty {
                  type uint32 {
                    range "0..16777215" {
                      description
                        "Value added to link metric when in HW-OOR state";
                    }
                  }
                  description
                    "Add a penalty to the TE metric of the link in HW-OOR state. Default is 0";
                }
              }
              leaf available-bw {
                type uint32 {
                  range "0..100" {
                    description
                      "Percentage of available BW when the link is in HW-OOR state";
                  }
                }
                description
                  "Specify the percentage of available BW for the link in HW-OOR state. Default is to flood 100% of the available bandwidth";
              }
            }
            container node-protection {
              description
                "Configure the FRR node-protection action in this HW-OOR state";
              container disable {
                presence "Indicates a disable node is configured.";
                description
                  "Disable FRR node-protection backups for the LSPs that use the interface in HW-OOR";
              }
            }
            container accept {
              description
                "Configure the accepted operations in this HW-OOR state";
              container reopt-lsp {
                presence "Indicates a reopt-lsp node is configured.";
                description
                  "Accept the reopt LSP sharing the same link in HW-OOR state as the current LSP";
              }
            }
            container admit {
              description
                "Configure the admission operations in this HW-OOR state";
              leaf lsp-min-bw {
                type uint32 {
                  range "0..4294967295" {
                    description
                      "Minimim bandwidth (in kbps)  of accepted LSPs, default is 0";
                  }
                }
                description
                  "Accept LSPs that are at least equal to the specified bandwidth";
              }
            }
          }
          leaf recovery-duration {
            type uint32 {
              range "0..10080" {
                description
                  "Number of minutes for the recovery in Green state, default is 0";
              }
            }
            description
              "Configure how long the actions are taken in HW-OOR Green state after recovery";
          }
        }
        container red {
          description
            "Config submode for handling NPU OOR in major/red state";
          container action {
            description
              "Action to take in the HW-OOR state";
            container flood {
              description
                "Flooding parameters in the HW-OOR state";
              container te-metric {
                description
                  "Change the TE metric for the link in HW-OOR state";
                leaf penalty {
                  type uint32 {
                    range "0..16777215" {
                      description
                        "Value added to link metric when in HW-OOR state";
                    }
                  }
                  description
                    "Add a penalty to the TE metric of the link in HW-OOR state. Default is 0";
                }
              }
              leaf available-bw {
                type uint32 {
                  range "0..100" {
                    description
                      "Percentage of available BW when the link is in HW-OOR state";
                  }
                }
                description
                  "Specify the percentage of available BW for the link in HW-OOR state. Default is to flood 100% of the available bandwidth";
              }
            }
            container node-protection {
              description
                "Configure the FRR node-protection action in this HW-OOR state";
              container disable {
                presence "Indicates a disable node is configured.";
                description
                  "Disable FRR node-protection backups for the LSPs that use the interface in HW-OOR";
              }
            }
            container accept {
              description
                "Configure the accepted operations in this HW-OOR state";
              container reopt-lsp {
                presence "Indicates a reopt-lsp node is configured.";
                description
                  "Accept the reopt LSP sharing the same link in HW-OOR state as the current LSP";
              }
            }
            container admit {
              description
                "Configure the admission operations in this HW-OOR state";
              leaf lsp-min-bw {
                type uint32 {
                  range "0..4294967295" {
                    description
                      "Minimim bandwidth (in kbps)  of accepted LSPs, default is 0";
                  }
                }
                description
                  "Accept LSPs that are at least equal to the specified bandwidth";
              }
            }
          }
          leaf recovery-duration {
            type uint32 {
              range "0..10080" {
                description
                  "Number of minutes for the recovery in Green state, default is 0";
              }
            }
            description
              "Configure how long the actions are taken in HW-OOR Green state after recovery";
          }
        }
      }
      container lsp-oor {
        description
          "Config submode for LSP OOR handling in MPLS-TE";
        container yellow {
          description
            "Config submode for LSP OOR in minor/yellow state";
          container transit-all {
            description
              "Limit for all transit or midpoint LSPs";
            leaf threshold {
              type uint32 {
                range "0..4294967295" {
                  description
                    "Threshold for all transit LSPs. Default is unlimited";
                }
              }
              description
                "Threshold for all transit LSPs";
            }
          }
          container transit-unprotected {
            description
              "Limit for unprotected transit or midpoint LSPs";
            leaf threshold {
              type uint32 {
                range "0..4294967295" {
                  description
                    "Threshold for unprotected transit LSPs; Default is unlimited";
                }
              }
              description
                "Threshold for unprotected transit LSPs";
            }
          }
        }
        container red {
          description
            "Config submode for LSP OOR in major/red state";
          container transit-all {
            description
              "Limit for all transit or midpoint LSPs";
            leaf threshold {
              type uint32 {
                range "0..4294967295" {
                  description
                    "Threshold for all transit LSPs. Default is unlimited";
                }
              }
              description
                "Threshold for all transit LSPs";
            }
          }
          container transit-unprotected {
            description
              "Limit for unprotected transit or midpoint LSPs";
            leaf threshold {
              type uint32 {
                range "0..4294967295" {
                  description
                    "Threshold for unprotected transit LSPs; Default is unlimited";
                }
              }
              description
                "Threshold for unprotected transit LSPs";
            }
          }
        }
      }
      container pce {
        description
          "MPLS Traffic Engineering PCE functionality";
        leaf keepalive {
          type uint32 {
            range "0..255" {
              description
                "Keepalive interval in sec";
            }
          }
          description
            "Keepalive interval in sec";
        }
        leaf deadtimer {
          type uint32 {
            range "0..255" {
              description
                "Keepalive dead interval in sec";
            }
          }
          description
            "Keepalive dead in sec";
        }
        container tolerance {
          description
            "Tolerance for session parameters proposed by peers";
          leaf keepalive {
            type uint32 {
              range "0..255" {
                description
                  "Keepalive interval in sec";
              }
            }
            description
              "Minimum acceptable peer proposed keepalive";
          }
        }
        leaf request-timeout {
          type uint32 {
            range "5..100" {
              description
                "Request timeout in seconds";
            }
          }
          description
            "Timeout period for pending request";
        }
        leaf reoptimize {
          type uint32 {
            range "60..604800" {
              description
                "Reoptimization period in seconds";
            }
          }
          description
            "Reoptimization period for PCE-based paths";
        }
        leaf speaker-entity-id {
          type xr:Cisco-ios-xr-string {
            length "1..256" {
              description
                "Identifying name for the speaker with max 256 characters";
            }
          }
          description
            "PCE speaker entity identifier";
        }
        container logging {
          description
            "Log PCE info";
          container events {
            description
              "Log events info";
            container peer-status {
              presence "Indicates a peer-status node is configured.";
              description
                "Log peer status changes";
            }
          }
        }
        container password {
          description
            "Configure global password for MD5 authentication";
          leaf encrypted {
            type xr:Proprietary-password;
            description
              "Specifies an ENCRYPTED password will follow";
          }
        }
        leaf keychain {
          type xr:Cisco-ios-xr-string {
            length "1..32" {
              description
                "Name of the key chain - maximum 32 characters";
            }
          }
          description
            "Configure keychain based authentication for PCE";
        }
        container stateful-client {
          presence "Indicates a stateful-client node is configured.";
          description
            "Enter the stateful PCE client configuration submode";
          container instantiation {
            presence "Indicates a instantiation node is configured.";
            description
              "Enable stateful instantiate capability";
          }
          container report {
            presence "Indicates a report node is configured.";
            description
              "Report all statically configured tunnels";
          }
          container fast-repair {
            presence "Indicates a fast-repair node is configured.";
            description
              "Enable head-end to react to path failures";
          }
          container cisco-extension {
            presence "Indicates a cisco-extension node is configured.";
            description
              "Enable processing of PCEP Cisco extension";
          }
          container autoroute-announce {
            presence "Indicates a autoroute-announce node is configured.";
            description
              "Enable autoroute announce for PCE tunnels";
          }
          container timers {
            description
              "Stateful client timers";
            leaf state-timeout {
              type uint32 {
                range "0..3600" {
                  description
                    "Cleanup time in seconds";
                }
              }
              description
                "State timeout for LSPs without delegation in seconds, zero means immediate removal, default is 180 seconds";
            }
            leaf redelegation-timeout {
              type uint32 {
                range "0..3600" {
                  description
                    "Time in seconds";
                }
              }
              description
                "Redelegation timeout for LSPs after session failure in seconds, zero means immediate drop delegation, default is 180seconds";
            }
            container redundancy {
              description
                "PCE Redundancy configuration";
              container pcc-centric {
                presence "Indicates a pcc-centric node is configured.";
                description
                  "Enable PCC centric model";
              }
            }
          }
        }
        container peer {
          description
            "PCE peer related configuration";
          container source {
            description
              "Peer source";
            leaf ipv4 {
              type inet:ipv4-address-no-zone;
              description
                "IPv4 address";
            }
          }
          container ipv4s {
            description
              "IPv4 address";
            list ipv4 {
              key "address";
              description
                "IPv4 address";
              leaf address {
                type inet:ipv4-address-no-zone;
                description
                  "IPv4 address";
              }
              container password {
                description
                  "Configure password for MD5 authentication";
                leaf encrypted {
                  type xr:Proprietary-password;
                  description
                    "Specifies an ENCRYPTED password will follow";
                }
              }
              leaf keychain {
                type xr:Cisco-ios-xr-string {
                  length "1..32" {
                    description
                      "Name of the key chain - maximum 32 characters";
                  }
                }
                description
                  "Configure keychain based authentication for PCC";
              }
              leaf precedence {
                type uint32 {
                  range "0..255" {
                    description
                      "PCE server precedence order (low precedence corresponds to high priority)";
                  }
                }
                description
                  "PCE Peer Precedence";
              }
            }
          }
        }
      }
      container auto-tunnel {
        description
          "Automatically created tunnel configuration";
        container backup {
          description
            "Enter the auto-tunnel backup configuration submode";
          container affinity {
            description
              "Affinity for auto-tunnel backup tunnels";
            container ignore {
              presence "Indicates a ignore node is configured.";
              description
                "Ignore link affinites for PCALC for auto-backup tunnels";
            }
          }
          container tunnel-id {
            description
              "Specify Tunnel ID range (modify may result auto-tunnel delete)";
            leaf min {
              type uint32 {
                range "0..65535" {
                  description
                    "Minimum value of tunnel ID for auto-tunnel backups";
                }
              }
              description
                "Minimum tunnel ID for auto-tunnel backups";
            }
            leaf max {
              type uint32 {
                range "0..65535" {
                  description
                    "Maximum value of tunnel ID for auto-tunnel backups";
                }
              }
              description
                "Maximum tunnel ID for auto-tunnel backups";
            }
          }
          container timers {
            description
              "Auto-tunnel backups related timers";
            container removal {
              description
                "Auto-tunnel backups removal timers";
              leaf unused {
                type uint32 {
                  range "0..10080" {
                    description
                      "Auto-tunnel backup unused timeout in minutes (0=never timeout)";
                  }
                }
                description
                  "Auto-tunnel backups unused removal timer";
              }
            }
          }
        }
        container mesh {
          description
            "Enter the auto-tunnel mesh configuration submode";
          container tunnel-id {
            description
              "Specify Tunnel ID range (modify may result auto-tunnel delete)";
            leaf min {
              type uint32 {
                range "0..65535" {
                  description
                    "Minimum value of tunnel ID for auto-tunnel mesh";
                }
              }
              description
                "Minimum tunnel ID for auto-tunnel mesh";
            }
            leaf max {
              type uint32 {
                range "0..65535" {
                  description
                    "Maximum value of tunnel ID for auto-tunnel mesh";
                }
              }
              description
                "Maximum tunnel ID for auto-tunnel mesh";
            }
          }
          container timers {
            description
              "Auto-tunnel mesh related timers";
            container removal {
              description
                "Auto-tunnel mesh removal timers";
              leaf unused {
                type uint32 {
                  range "0..10080" {
                    description
                      "Auto-tunnel mesh unused timeout in minutes (0=never timeout)";
                  }
                }
                description
                  "Auto-tunnel mesh unused removal timer";
              }
            }
          }
          container groups {
            description
              "Enter the auto-tunnel mesh group configuration submode";
            list group {
              key "group-id";
              description
                "Enter the auto-tunnel mesh group configuration submode";
              leaf group-id {
                type uint32 {
                  range "0..4294967295" {
                    description
                      "Auto-tunnel mesh group ID";
                  }
                }
                description
                  "Enter the auto-tunnel mesh group configuration submode";
              }
              leaf attribute-set {
                type xr:Cisco-ios-xr-string {
                  length "1..64" {
                    description
                      "Specify attribute-set name (max 64 char)";
                  }
                }
                description
                  "Attribute-set name of type auto-mesh";
              }
              leaf destination-list {
                type xr:Cisco-ios-xr-string {
                  length "1..64" {
                    description
                      "Specify destination-list (prefix-list) (max 32 char)";
                  }
                }
                description
                  "Destination-list (prefix-list) name";
              }
              container disable {
                presence "Indicates a disable node is configured.";
                description
                  "Disable the mesh group";
              }
              container onehop {
                presence "Indicates a onehop node is configured.";
                description
                  "Automatically create tunnel to all next-hops";
              }
            }
          }
        }
        container p2mp {
          description
            "Enter the auto-tunnel P2MP configuration submode";
          container tunnel-id {
            description
              "Specify Tunnel ID range (modify may result auto-tunnel delete)";
            leaf min {
              type uint32 {
                range "0..65535" {
                  description
                    "Minimum value of tunnel ID for auto-tunnel P2MP";
                }
              }
              description
                "Minimum tunnel ID for auto-tunnel P2MP";
            }
            leaf max {
              type uint32 {
                range "0..65535" {
                  description
                    "Maximum value of tunnel ID for auto-tunnel P2MP";
                }
              }
              description
                "Maximum tunnel ID for auto-tunnel P2MP";
            }
          }
        }
        container p2p {
          description
            "Enter the auto-tunnel p2p configuration submode";
          container tunnel-id {
            description
              "Specify Tunnel ID range (modify may result auto-tunnel delete)";
            leaf min-id {
              type uint32 {
                range "0..65535" {
                  description
                    "Minimum value of tunnel ID for auto-tunnel p2p";
                }
              }
              description
                "Minimum tunnel ID for auto-tunnel p2p";
            }
            leaf max {
              type uint32 {
                range "0..65535" {
                  description
                    "Maximum value of tunnel ID for auto-tunnel p2p";
                }
              }
              description
                "Maximum tunnel ID for auto-tunnel p2p";
            }
          }
        }
        container pcc {
          description
            "Enter the auto-tunnel stateful PCE client configuration submode";
          container tunnel-id {
            description
              "Specify Tunnel ID range (modify may result auto-tunnel delete)";
            leaf min {
              type uint32 {
                range "0..65535" {
                  description
                    "Minimum tunnel ID value for stateful PCE client auto-tunnels";
                }
              }
              description
                "Minimum tunnel ID for stateful PCE client auto-tunnels";
            }
            leaf max {
              type uint32 {
                range "0..65535" {
                  description
                    "Maximum tunnel ID value for stateful PCE client auto-tunnels";
                }
              }
              description
                "Maximum tunnel ID for stateful PCE client auto-tunnels";
            }
          }
        }
      }
      container attribute-set {
        description
          "Specify attribute set";
        container auto-meshes {
          description
            "Attribute-set of auto mesh type";
          list auto-mesh {
            key "attribute-set-name";
            description
              "Attribute-set of auto mesh type";
            leaf attribute-set-name {
              type xr:Cisco-ios-xr-string {
                length "1..64" {
                  description
                    "Specify attribute-set name (maximum 64 characters)";
                }
              }
              description
                "Attribute-set of auto mesh type";
            }
            container policy-class {
              description
                "Specify class for policy-based tunnel selection";
              container tunnel-policy-classes {
                description
                  "Tunnel policy class";
                leaf-list tunnel-policy-class {
                  type policy-class-type;
                  max-elements "7";
                  description
                    "Tunnel policy class";
                }
              }
            }
            container priority {
              presence "Indicates a priority node is configured.";
              description
                "Tunnel priority";
              leaf setup-priority {
                type uint32 {
                  range "0..7" {
                    description
                      "Setup Priority";
                  }
                }
                mandatory true;
                description
                  "Tunnel priority";
              }
              leaf hold-priority {
                type uint32 {
                  range "0..7" {
                    description
                      "Hold Priority";
                  }
                }
                mandatory true;
                description
                  "Hold Priority";
              }
            }
            container signalled-bandwidth {
              presence "Indicates a signalled-bandwidth node is configured.";
              description
                "Tunnel bandwidth requirement to be signalled";
              leaf bandwidth {
                type uint32 {
                  range "0..4294967295" {
                    description
                      "Bandwidth requirement in kbps";
                  }
                }
                mandatory true;
                description
                  "Tunnel bandwidth requirement to be signalled";
              }
              leaf class-type {
                type uint32 {
                  range "0..1" {
                    description
                      "Class type number";
                  }
                }
                description
                  "Specify the bandwidth class type";
              }
            }
            container affinity {
              description
                "Link attributes for links traversed by tunnel";
              leaf affinity-attribute {
                type uint32 {
                  range "0..4294967295" {
                    description
                      "Affinity value";
                  }
                }
                description
                  "Link attributes for links traversed by tunnel";
              }
              leaf mask {
                type uint32 {
                  range "0..4294967295" {
                    description
                      "Affinity mask value";
                  }
                }
                description
                  "Affinity mask value";
              }
              container includes {
                description
                  "Links with all these attributes are included in path calculation";
                list include1 {
                  key "name1";
                  description
                    "Links with all these attributes are included in path calculation";
                  leaf name1 {
                    type xr:Cisco-ios-xr-string {
                      length "1..32" {
                        description
                          "Attribute or affinity name";
                      }
                    }
                    description
                      "Attribute or affinity name";
                  }
                }
                list include2 {
                  key "name1 name2";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                }
                list include3 {
                  key "name1 name2 name3";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                }
                list include4 {
                  key "name1 name2 name3 name4";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                }
                list include5 {
                  key "name1 name2 name3 name4 name5";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                }
                list include6 {
                  key "name1 name2 name3 name4 name5 name6";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                  leaf name6 {
                    type xr:Cisco-ios-xr-string {
                      length "1..32" {
                        description
                          "Attribute or affinity name";
                      }
                    }
                    description
                      "Attribute or affinity name";
                  }
                }
                list include7 {
                  key "name1 name2 name3 name4 name5 name6 name7";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                  leaf name6 {
                    type xr:Cisco-ios-xr-string {
                      length "1..32" {
                        description
                          "Attribute or affinity name";
                      }
                    }
                    description
                      "Attribute or affinity name";
                  }
                  leaf name7 {
                    type xr:Cisco-ios-xr-string {
                      length "1..32" {
                        description
                          "Attribute or affinity name";
                      }
                    }
                    description
                      "Attribute or affinity name";
                  }
                }
                list include8 {
                  key "name1 name2 name3 name4 name5 name6 name7 name8";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                  leaf name6 {
                    type xr:Cisco-ios-xr-string {
                      length "1..32" {
                        description
                          "Attribute or affinity name";
                      }
                    }
                    description
                      "Attribute or affinity name";
                  }
                  leaf name7 {
                    type xr:Cisco-ios-xr-string {
                      length "1..32" {
                        description
                          "Attribute or affinity name";
                      }
                    }
                    description
                      "Attribute or affinity name";
                  }
                  leaf name8 {
                    type xr:Cisco-ios-xr-string {
                      length "1..32" {
                        description
                          "Attribute or affinity name";
                      }
                    }
                    description
                      "Attribute or affinity name";
                  }
                }
                list include9 {
                  key "name1 name2 name3 name4 name5 name6 name7 name8 name9";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                  leaf name6 {
                    type xr:Cisco-ios-xr-string {
                      length "1..32" {
                        description
                          "Attribute or affinity name";
                      }
                    }
                    description
                      "Attribute or affinity name";
                  }
                  leaf name7 {
                    type xr:Cisco-ios-xr-string {
                      length "1..32" {
                        description
                          "Attribute or affinity name";
                      }
                    }
                    description
                      "Attribute or affinity name";
                  }
                  leaf name8 {
                    type xr:Cisco-ios-xr-string {
                      length "1..32" {
                        description
                          "Attribute or affinity name";
                      }
                    }
                    description
                      "Attribute or affinity name";
                  }
                  leaf name9 {
                    type xr:Cisco-ios-xr-string {
                      length "1..32" {
                        description
                          "Attribute or affinity name";
                      }
                    }
                    description
                      "Attribute or affinity name";
                  }
                }
                list include10 {
                  key "name1 name2 name3 name4 name5 name6 name7 name8 name9 name10";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                  leaf name6 {
                    type xr:Cisco-ios-xr-string {
                      length "1..32" {
                        description
                          "Attribute or affinity name";
                      }
                    }
                    description
                      "Attribute or affinity name";
                  }
                  leaf name7 {
                    type xr:Cisco-ios-xr-string {
                      length "1..32" {
                        description
                          "Attribute or affinity name";
                      }
                    }
                    description
                      "Attribute or affinity name";
                  }
                  leaf name8 {
                    type xr:Cisco-ios-xr-string {
                      length "1..32" {
                        description
                          "Attribute or affinity name";
                      }
                    }
                    description
                      "Attribute or affinity name";
                  }
                  leaf name9 {
                    type xr:Cisco-ios-xr-string {
                      length "1..32" {
                        description
                          "Attribute or affinity name";
                      }
                    }
                    description
                      "Attribute or affinity name";
                  }
                  leaf name10 {
                    type xr:Cisco-ios-xr-string {
                      length "1..32" {
                        description
                          "Attribute or affinity name";
                      }
                    }
                    description
                      "Attribute or affinity name";
                  }
                }
              }
              container include-stricts {
                description
                  "Links with exactly all these attributes are included in path calculation";
                list include1 {
                  key "name1";
                  description
                    "Links with all these attributes are included in path calculation";
                  leaf name1 {
                    type xr:Cisco-ios-xr-string {
                      length "1..32" {
                        description
                          "Attribute or affinity name";
                      }
                    }
                    description
                      "Attribute or affinity name";
                  }
                }
                list include2 {
                  key "name1 name2";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                }
                list include3 {
                  key "name1 name2 name3";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                }
                list include4 {
                  key "name1 name2 name3 name4";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                }
                list include5 {
                  key "name1 name2 name3 name4 name5";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                }
                list include6 {
                  key "name1 name2 name3 name4 name5 name6";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                  leaf name6 {
                    type xr:Cisco-ios-xr-string {
                      length "1..32" {
                        description
                          "Attribute or affinity name";
                      }
                    }
                    description
                      "Attribute or affinity name";
                  }
                }
                list include7 {
                  key "name1 name2 name3 name4 name5 name6 name7";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                  leaf name6 {
                    type xr:Cisco-ios-xr-string {
                      length "1..32" {
                        description
                          "Attribute or affinity name";
                      }
                    }
                    description
                      "Attribute or affinity name";
                  }
                  leaf name7 {
                    type xr:Cisco-ios-xr-string {
                      length "1..32" {
                        description
                          "Attribute or affinity name";
                      }
                    }
                    description
                      "Attribute or affinity name";
                  }
                }
                list include8 {
                  key "name1 name2 name3 name4 name5 name6 name7 name8";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                  leaf name6 {
                    type xr:Cisco-ios-xr-string {
                      length "1..32" {
                        description
                          "Attribute or affinity name";
                      }
                    }
                    description
                      "Attribute or affinity name";
                  }
                  leaf name7 {
                    type xr:Cisco-ios-xr-string {
                      length "1..32" {
                        description
                          "Attribute or affinity name";
                      }
                    }
                    description
                      "Attribute or affinity name";
                  }
                  leaf name8 {
                    type xr:Cisco-ios-xr-string {
                      length "1..32" {
                        description
                          "Attribute or affinity name";
                      }
                    }
                    description
                      "Attribute or affinity name";
                  }
                }
                list include9 {
                  key "name1 name2 name3 name4 name5 name6 name7 name8 name9";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                  leaf name6 {
                    type xr:Cisco-ios-xr-string {
                      length "1..32" {
                        description
                          "Attribute or affinity name";
                      }
                    }
                    description
                      "Attribute or affinity name";
                  }
                  leaf name7 {
                    type xr:Cisco-ios-xr-string {
                      length "1..32" {
                        description
                          "Attribute or affinity name";
                      }
                    }
                    description
                      "Attribute or affinity name";
                  }
                  leaf name8 {
                    type xr:Cisco-ios-xr-string {
                      length "1..32" {
                        description
                          "Attribute or affinity name";
                      }
                    }
                    description
                      "Attribute or affinity name";
                  }
                  leaf name9 {
                    type xr:Cisco-ios-xr-string {
                      length "1..32" {
                        description
                          "Attribute or affinity name";
                      }
                    }
                    description
                      "Attribute or affinity name";
                  }
                }
                list include10 {
                  key "name1 name2 name3 name4 name5 name6 name7 name8 name9 name10";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                  leaf name6 {
                    type xr:Cisco-ios-xr-string {
                      length "1..32" {
                        description
                          "Attribute or affinity name";
                      }
                    }
                    description
                      "Attribute or affinity name";
                  }
                  leaf name7 {
                    type xr:Cisco-ios-xr-string {
                      length "1..32" {
                        description
                          "Attribute or affinity name";
                      }
                    }
                    description
                      "Attribute or affinity name";
                  }
                  leaf name8 {
                    type xr:Cisco-ios-xr-string {
                      length "1..32" {
                        description
                          "Attribute or affinity name";
                      }
                    }
                    description
                      "Attribute or affinity name";
                  }
                  leaf name9 {
                    type xr:Cisco-ios-xr-string {
                      length "1..32" {
                        description
                          "Attribute or affinity name";
                      }
                    }
                    description
                      "Attribute or affinity name";
                  }
                  leaf name10 {
                    type xr:Cisco-ios-xr-string {
                      length "1..32" {
                        description
                          "Attribute or affinity name";
                      }
                    }
                    description
                      "Attribute or affinity name";
                  }
                }
              }
              container excludes {
                description
                  "Links with all these attributes are excluded from path calculation";
                list exclude1 {
                  key "name1";
                  description
                    "Links with all these attributes are included in path calculation";
                  leaf name1 {
                    type xr:Cisco-ios-xr-string {
                      length "1..32" {
                        description
                          "Attribute or affinity name";
                      }
                    }
                    description
                      "Attribute or affinity name";
                  }
                }
                list exclude2 {
                  key "name1 name2";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                }
                list exclude3 {
                  key "name1 name2 name3";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                }
                list exclude4 {
                  key "name1 name2 name3 name4";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                }
                list exclude5 {
                  key "name1 name2 name3 name4 name5";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                }
                list exclude6 {
                  key "name1 name2 name3 name4 name5 name6";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                  leaf name6 {
                    type xr:Cisco-ios-xr-string {
                      length "1..32" {
                        description
                          "Attribute or affinity name";
                      }
                    }
                    description
                      "Attribute or affinity name";
                  }
                }
                list exclude7 {
                  key "name1 name2 name3 name4 name5 name6 name7";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                  leaf name6 {
                    type xr:Cisco-ios-xr-string {
                      length "1..32" {
                        description
                          "Attribute or affinity name";
                      }
                    }
                    description
                      "Attribute or affinity name";
                  }
                  leaf name7 {
                    type xr:Cisco-ios-xr-string {
                      length "1..32" {
                        description
                          "Attribute or affinity name";
                      }
                    }
                    description
                      "Attribute or affinity name";
                  }
                }
                list exclude8 {
                  key "name1 name2 name3 name4 name5 name6 name7 name8";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                  leaf name6 {
                    type xr:Cisco-ios-xr-string {
                      length "1..32" {
                        description
                          "Attribute or affinity name";
                      }
                    }
                    description
                      "Attribute or affinity name";
                  }
                  leaf name7 {
                    type xr:Cisco-ios-xr-string {
                      length "1..32" {
                        description
                          "Attribute or affinity name";
                      }
                    }
                    description
                      "Attribute or affinity name";
                  }
                  leaf name8 {
                    type xr:Cisco-ios-xr-string {
                      length "1..32" {
                        description
                          "Attribute or affinity name";
                      }
                    }
                    description
                      "Attribute or affinity name";
                  }
                }
                list exclude9 {
                  key "name1 name2 name3 name4 name5 name6 name7 name8 name9";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                  leaf name6 {
                    type xr:Cisco-ios-xr-string {
                      length "1..32" {
                        description
                          "Attribute or affinity name";
                      }
                    }
                    description
                      "Attribute or affinity name";
                  }
                  leaf name7 {
                    type xr:Cisco-ios-xr-string {
                      length "1..32" {
                        description
                          "Attribute or affinity name";
                      }
                    }
                    description
                      "Attribute or affinity name";
                  }
                  leaf name8 {
                    type xr:Cisco-ios-xr-string {
                      length "1..32" {
                        description
                          "Attribute or affinity name";
                      }
                    }
                    description
                      "Attribute or affinity name";
                  }
                  leaf name9 {
                    type xr:Cisco-ios-xr-string {
                      length "1..32" {
                        description
                          "Attribute or affinity name";
                      }
                    }
                    description
                      "Attribute or affinity name";
                  }
                }
                list exclude10 {
                  key "name1 name2 name3 name4 name5 name6 name7 name8 name9 name10";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                  leaf name6 {
                    type xr:Cisco-ios-xr-string {
                      length "1..32" {
                        description
                          "Attribute or affinity name";
                      }
                    }
                    description
                      "Attribute or affinity name";
                  }
                  leaf name7 {
                    type xr:Cisco-ios-xr-string {
                      length "1..32" {
                        description
                          "Attribute or affinity name";
                      }
                    }
                    description
                      "Attribute or affinity name";
                  }
                  leaf name8 {
                    type xr:Cisco-ios-xr-string {
                      length "1..32" {
                        description
                          "Attribute or affinity name";
                      }
                    }
                    description
                      "Attribute or affinity name";
                  }
                  leaf name9 {
                    type xr:Cisco-ios-xr-string {
                      length "1..32" {
                        description
                          "Attribute or affinity name";
                      }
                    }
                    description
                      "Attribute or affinity name";
                  }
                  leaf name10 {
                    type xr:Cisco-ios-xr-string {
                      length "1..32" {
                        description
                          "Attribute or affinity name";
                      }
                    }
                    description
                      "Attribute or affinity name";
                  }
                }
              }
              container ignore {
                presence "Indicates a ignore node is configured.";
                description
                  "All links are included in path calculation regardless of attributes";
              }
              container exclude-all {
                presence "Indicates a exclude-all node is configured.";
                description
                  "Links with any attribute are excluded from path calculation";
              }
            }
            container auto-bw {
              description
                "Enable tunnel auto-bandwidth";
              container collect-bw-only {
                presence "Indicates a collect-bw-only node is configured.";
                description
                  "Enable bandwidth collection only, no auto-bw adjustment";
              }
            }
            container fast-reroute {
              presence "Indicates a fast-reroute node is configured.";
              description
                "Specify MPLS tunnel can be fast-rerouted";
              container protect {
                description
                  "Enable protection request";
                container node {
                  presence "Indicates a node node is configured.";
                  description
                    "Enable node protection request";
                }
                container bandwidth {
                  presence "Indicates a bandwidth node is configured.";
                  description
                    "Enable bandwidth protection request";
                }
              }
            }
            container record-route {
              presence "Indicates a record-route node is configured.";
              description
                "Record the route used by the tunnel";
            }
            container autoroute {
              description
                "Parameters for IGP routing over tunnel";
              container announce {
                presence "Indicates a announce node is configured.";
                description
                  "Announce tunnel to IGP";
              }
            }
            container logging {
              description
                "Per-interface logging configuration";
              container events {
                description
                  "Per-interface logging events";
                container lsp-status {
                  description
                    "Enable interface LSP state change alarms";
                  container state {
                    presence "Indicates a state node is configured.";
                    description
                      "Enable interface LSP UP/DOWN change alarms";
                  }
                  container reoptimize {
                    presence "Indicates a reoptimize node is configured.";
                    description
                      "Enable interface LSP REOPT change alarms";
                  }
                  container reoptimize-attempts {
                    presence "Indicates a reoptimize-attempts node is configured.";
                    description
                      "Enable interface LSP REOPT attempts change alarms";
                  }
                  container bw-change {
                    presence "Indicates a bw-change node is configured.";
                    description
                      "Enable interface LSP BANDWIDTH change alarms";
                  }
                  container reroute {
                    presence "Indicates a reroute node is configured.";
                    description
                      "Enable interface LSP REROUTE change alarms";
                  }
                  container insufficient-bandwidth {
                    presence "Indicates a insufficient-bandwidth node is configured.";
                    description
                      "Enable Syslog for setup/reopt failure due to bandwidth";
                  }
                }
                container pcalc-failure {
                  presence "Indicates a pcalc-failure node is configured.";
                  description
                    "Enable logging for path calculation failures";
                }
              }
            }
            container soft-preemption {
              presence "Indicates a soft-preemption node is configured.";
              description
                "Enable the soft-preemption feature on this tunnel";
            }
            leaf bandwidth {
              type uint32 {
                range "0..4294967295" {
                  description
                    "bandwidth in kbps";
                }
              }
              description
                "Set the bandwidth of an interface";
            }
            leaf forward-class {
              type uint32 {
                range "0..7" {
                  description
                    "Forward class for the tunnel. Default: feature not enabled";
                }
              }
              description
                "Forward class for the tunnel. Default: feature not enabled";
            }
            leaf load-share {
              type uint32 {
                range "1..4294967295" {
                  description
                    "Loadshare value. Scale is the same as bandwidths.";
                }
              }
              description
                "Specify tunnel load-sharing metric";
            }
            container path-selection {
              presence "Indicates a path-selection node is configured.";
              description
                "Specify path selection";
            }
          }
        }
        container auto-backups {
          description
            "Attribute-set of auto-backup type";
          list auto-backup {
            key "attribute-set-name";
            description
              "Attribute-set of auto-backup type";
            leaf attribute-set-name {
              type xr:Cisco-ios-xr-string {
                length "1..64" {
                  description
                    "Specify attribute-set name (maximum 64 characters)";
                }
              }
              description
                "Attribute-set of auto-backup type";
            }
            container policy-class {
              description
                "Specify class for policy-based tunnel selection";
              container tunnel-policy-classes {
                description
                  "Tunnel policy class";
                leaf-list tunnel-policy-class {
                  type policy-class-type;
                  max-elements "7";
                  description
                    "Tunnel policy class";
                }
              }
            }
            container priority {
              presence "Indicates a priority node is configured.";
              description
                "Tunnel priority";
              leaf setup-priority {
                type uint32 {
                  range "0..7" {
                    description
                      "Setup Priority";
                  }
                }
                mandatory true;
                description
                  "Tunnel priority";
              }
              leaf hold-priority {
                type uint32 {
                  range "0..7" {
                    description
                      "Hold Priority";
                  }
                }
                mandatory true;
                description
                  "Hold Priority";
              }
            }
            container signalled-bandwidth {
              presence "Indicates a signalled-bandwidth node is configured.";
              description
                "Tunnel bandwidth requirement to be signalled";
              leaf bandwidth {
                type uint32 {
                  range "0..4294967295" {
                    description
                      "Bandwidth requirement in kbps";
                  }
                }
                mandatory true;
                description
                  "Tunnel bandwidth requirement to be signalled";
              }
              leaf class-type {
                type uint32 {
                  range "0..1" {
                    description
                      "Class type number";
                  }
                }
                description
                  "Specify the bandwidth class type";
              }
            }
            container affinity {
              description
                "Link attributes for links traversed by tunnel";
              leaf affinity-attribute {
                type uint32 {
                  range "0..4294967295" {
                    description
                      "Affinity value";
                  }
                }
                description
                  "Link attributes for links traversed by tunnel";
              }
              leaf mask {
                type uint32 {
                  range "0..4294967295" {
                    description
                      "Affinity mask value";
                  }
                }
                description
                  "Affinity mask value";
              }
              container includes {
                description
                  "Links with all these attributes are included in path calculation";
                list include1 {
                  key "name1";
                  description
                    "Links with all these attributes are included in path calculation";
                  leaf name1 {
                    type xr:Cisco-ios-xr-string {
                      length "1..32" {
                        description
                          "Attribute or affinity name";
                      }
                    }
                    description
                      "Attribute or affinity name";
                  }
                }
                list include2 {
                  key "name1 name2";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                }
                list include3 {
                  key "name1 name2 name3";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                }
                list include4 {
                  key "name1 name2 name3 name4";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                }
                list include5 {
                  key "name1 name2 name3 name4 name5";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                }
                list include6 {
                  key "name1 name2 name3 name4 name5 name6";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                  leaf name6 {
                    type xr:Cisco-ios-xr-string {
                      length "1..32" {
                        description
                          "Attribute or affinity name";
                      }
                    }
                    description
                      "Attribute or affinity name";
                  }
                }
                list include7 {
                  key "name1 name2 name3 name4 name5 name6 name7";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                  leaf name6 {
                    type xr:Cisco-ios-xr-string {
                      length "1..32" {
                        description
                          "Attribute or affinity name";
                      }
                    }
                    description
                      "Attribute or affinity name";
                  }
                  leaf name7 {
                    type xr:Cisco-ios-xr-string {
                      length "1..32" {
                        description
                          "Attribute or affinity name";
                      }
                    }
                    description
                      "Attribute or affinity name";
                  }
                }
                list include8 {
                  key "name1 name2 name3 name4 name5 name6 name7 name8";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                  leaf name6 {
                    type xr:Cisco-ios-xr-string {
                      length "1..32" {
                        description
                          "Attribute or affinity name";
                      }
                    }
                    description
                      "Attribute or affinity name";
                  }
                  leaf name7 {
                    type xr:Cisco-ios-xr-string {
                      length "1..32" {
                        description
                          "Attribute or affinity name";
                      }
                    }
                    description
                      "Attribute or affinity name";
                  }
                  leaf name8 {
                    type xr:Cisco-ios-xr-string {
                      length "1..32" {
                        description
                          "Attribute or affinity name";
                      }
                    }
                    description
                      "Attribute or affinity name";
                  }
                }
                list include9 {
                  key "name1 name2 name3 name4 name5 name6 name7 name8 name9";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name7 {
                    type xr:Cisco-ios-xr-string {
                      length "1..32" {
                        description
                          "Attribute or affinity name";
                      }
                    }
                    description
                      "Attribute or affinity name";
                  }
                  leaf name8 {
                    type xr:Cisco-ios-xr-string {
                      length "1..32" {
                        description
                          "Attribute or affinity name";
                      }
                    }
                    description
                      "Attribute or affinity name";
                  }
                  leaf name6 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                  leaf name9 {
                    type xr:Cisco-ios-xr-string {
                      length "1..32" {
                        description
                          "Attribute or affinity name";
                      }
                    }
                    description
                      "Attribute or affinity name";
                  }
                }
                list include10 {
                  key "name1 name2 name3 name4 name5 name6 name7 name8 name9 name10";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                  leaf name6 {
                    type xr:Cisco-ios-xr-string {
                      length "1..32" {
                        description
                          "Attribute or affinity name";
                      }
                    }
                    description
                      "Attribute or affinity name";
                  }
                  leaf name7 {
                    type xr:Cisco-ios-xr-string {
                      length "1..32" {
                        description
                          "Attribute or affinity name";
                      }
                    }
                    description
                      "Attribute or affinity name";
                  }
                  leaf name8 {
                    type xr:Cisco-ios-xr-string {
                      length "1..32" {
                        description
                          "Attribute or affinity name";
                      }
                    }
                    description
                      "Attribute or affinity name";
                  }
                  leaf name9 {
                    type xr:Cisco-ios-xr-string {
                      length "1..32" {
                        description
                          "Attribute or affinity name";
                      }
                    }
                    description
                      "Attribute or affinity name";
                  }
                  leaf name10 {
                    type xr:Cisco-ios-xr-string {
                      length "1..32" {
                        description
                          "Attribute or affinity name";
                      }
                    }
                    description
                      "Attribute or affinity name";
                  }
                }
              }
              container include-stricts {
                description
                  "Links with exactly all these attributes are included in path calculation";
                list include1 {
                  key "name1";
                  description
                    "Links with all these attributes are included in path calculation";
                  leaf name1 {
                    type xr:Cisco-ios-xr-string {
                      length "1..32" {
                        description
                          "Attribute or affinity name";
                      }
                    }
                    description
                      "Attribute or affinity name";
                  }
                }
                list include2 {
                  key "name1 name2";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                }
                list include3 {
                  key "name1 name2 name3";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                }
                list include4 {
                  key "name1 name2 name3 name4";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                }
                list include5 {
                  key "name1 name2 name3 name4 name5";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                }
                list include6 {
                  key "name1 name2 name3 name4 name5 name6";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                  leaf name6 {
                    type xr:Cisco-ios-xr-string {
                      length "1..32" {
                        description
                          "Attribute or affinity name";
                      }
                    }
                    description
                      "Attribute or affinity name";
                  }
                }
                list include7 {
                  key "name1 name2 name3 name4 name5 name6 name7";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                  leaf name6 {
                    type xr:Cisco-ios-xr-string {
                      length "1..32" {
                        description
                          "Attribute or affinity name";
                      }
                    }
                    description
                      "Attribute or affinity name";
                  }
                  leaf name7 {
                    type xr:Cisco-ios-xr-string {
                      length "1..32" {
                        description
                          "Attribute or affinity name";
                      }
                    }
                    description
                      "Attribute or affinity name";
                  }
                }
                list include8 {
                  key "name1 name2 name3 name4 name5 name6 name7 name8";
                  description
                    "Links with all these attributes are included in path calculation";
                  leaf name1 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                  leaf name6 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name7 {
                    type xr:Cisco-ios-xr-string {
                      length "1..32" {
                        description
                          "Attribute or affinity name";
                      }
                    }
                    description
                      "Attribute or affinity name";
                  }
                  leaf name8 {
                    type xr:Cisco-ios-xr-string {
                      length "1..32" {
                        description
                          "Attribute or affinity name";
                      }
                    }
                    description
                      "Attribute or affinity name";
                  }
                }
                list include9 {
                  key "name1 name2 name3 name4 name5 name6 name7 name8 name9";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name7 {
                    type xr:Cisco-ios-xr-string {
                      length "1..32" {
                        description
                          "Attribute or affinity name";
                      }
                    }
                    description
                      "Attribute or affinity name";
                  }
                  leaf name8 {
                    type xr:Cisco-ios-xr-string {
                      length "1..32" {
                        description
                          "Attribute or affinity name";
                      }
                    }
                    description
                      "Attribute or affinity name";
                  }
                  leaf name6 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                  leaf name9 {
                    type xr:Cisco-ios-xr-string {
                      length "1..32" {
                        description
                          "Attribute or affinity name";
                      }
                    }
                    description
                      "Attribute or affinity name";
                  }
                }
                list include10 {
                  key "name1 name2 name3 name4 name5 name6 name7 name8 name9 name10";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                  leaf name6 {
                    type xr:Cisco-ios-xr-string {
                      length "1..32" {
                        description
                          "Attribute or affinity name";
                      }
                    }
                    description
                      "Attribute or affinity name";
                  }
                  leaf name7 {
                    type xr:Cisco-ios-xr-string {
                      length "1..32" {
                        description
                          "Attribute or affinity name";
                      }
                    }
                    description
                      "Attribute or affinity name";
                  }
                  leaf name8 {
                    type xr:Cisco-ios-xr-string {
                      length "1..32" {
                        description
                          "Attribute or affinity name";
                      }
                    }
                    description
                      "Attribute or affinity name";
                  }
                  leaf name9 {
                    type xr:Cisco-ios-xr-string {
                      length "1..32" {
                        description
                          "Attribute or affinity name";
                      }
                    }
                    description
                      "Attribute or affinity name";
                  }
                  leaf name10 {
                    type xr:Cisco-ios-xr-string {
                      length "1..32" {
                        description
                          "Attribute or affinity name";
                      }
                    }
                    description
                      "Attribute or affinity name";
                  }
                }
              }
              container excludes {
                description
                  "Links with all these attributes are excluded from path calculation";
                list exclude1 {
                  key "name1";
                  description
                    "Links with all these attributes are included in path calculation";
                  leaf name1 {
                    type xr:Cisco-ios-xr-string {
                      length "1..32" {
                        description
                          "Attribute or affinity name";
                      }
                    }
                    description
                      "Attribute or affinity name";
                  }
                }
                list exclude2 {
                  key "name1 name2";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                }
                list exclude3 {
                  key "name1 name2 name3";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                }
                list exclude4 {
                  key "name1 name2 name3 name4";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                }
                list exclude5 {
                  key "name1 name2 name3 name4 name5";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                }
                list exclude6 {
                  key "name1 name2 name3 name4 name5 name6";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                  leaf name6 {
                    type xr:Cisco-ios-xr-string {
                      length "1..32" {
                        description
                          "Attribute or affinity name";
                      }
                    }
                    description
                      "Attribute or affinity name";
                  }
                }
                list exclude7 {
                  key "name1 name2 name3 name4 name5 name6 name7";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                  leaf name6 {
                    type xr:Cisco-ios-xr-string {
                      length "1..32" {
                        description
                          "Attribute or affinity name";
                      }
                    }
                    description
                      "Attribute or affinity name";
                  }
                  leaf name7 {
                    type xr:Cisco-ios-xr-string {
                      length "1..32" {
                        description
                          "Attribute or affinity name";
                      }
                    }
                    description
                      "Attribute or affinity name";
                  }
                }
                list exclude8 {
                  key "name1 name2 name3 name4 name5 name6 name7 name8";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                  leaf name6 {
                    type xr:Cisco-ios-xr-string {
                      length "1..32" {
                        description
                          "Attribute or affinity name";
                      }
                    }
                    description
                      "Attribute or affinity name";
                  }
                  leaf name7 {
                    type xr:Cisco-ios-xr-string {
                      length "1..32" {
                        description
                          "Attribute or affinity name";
                      }
                    }
                    description
                      "Attribute or affinity name";
                  }
                  leaf name8 {
                    type xr:Cisco-ios-xr-string {
                      length "1..32" {
                        description
                          "Attribute or affinity name";
                      }
                    }
                    description
                      "Attribute or affinity name";
                  }
                }
                list exclude9 {
                  key "name1 name2 name3 name4 name5 name6 name7 name8 name9";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                  leaf name6 {
                    type xr:Cisco-ios-xr-string {
                      length "1..32" {
                        description
                          "Attribute or affinity name";
                      }
                    }
                    description
                      "Attribute or affinity name";
                  }
                  leaf name7 {
                    type xr:Cisco-ios-xr-string {
                      length "1..32" {
                        description
                          "Attribute or affinity name";
                      }
                    }
                    description
                      "Attribute or affinity name";
                  }
                  leaf name8 {
                    type xr:Cisco-ios-xr-string {
                      length "1..32" {
                        description
                          "Attribute or affinity name";
                      }
                    }
                    description
                      "Attribute or affinity name";
                  }
                  leaf name9 {
                    type xr:Cisco-ios-xr-string {
                      length "1..32" {
                        description
                          "Attribute or affinity name";
                      }
                    }
                    description
                      "Attribute or affinity name";
                  }
                }
                list exclude10 {
                  key "name1 name2 name3 name4 name5 name6 name7 name8 name9 name10";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                  leaf name6 {
                    type xr:Cisco-ios-xr-string {
                      length "1..32" {
                        description
                          "Attribute or affinity name";
                      }
                    }
                    description
                      "Attribute or affinity name";
                  }
                  leaf name7 {
                    type xr:Cisco-ios-xr-string {
                      length "1..32" {
                        description
                          "Attribute or affinity name";
                      }
                    }
                    description
                      "Attribute or affinity name";
                  }
                  leaf name8 {
                    type xr:Cisco-ios-xr-string {
                      length "1..32" {
                        description
                          "Attribute or affinity name";
                      }
                    }
                    description
                      "Attribute or affinity name";
                  }
                  leaf name9 {
                    type xr:Cisco-ios-xr-string {
                      length "1..32" {
                        description
                          "Attribute or affinity name";
                      }
                    }
                    description
                      "Attribute or affinity name";
                  }
                  leaf name10 {
                    type xr:Cisco-ios-xr-string {
                      length "1..32" {
                        description
                          "Attribute or affinity name";
                      }
                    }
                    description
                      "Attribute or affinity name";
                  }
                }
              }
              container ignore {
                presence "Indicates a ignore node is configured.";
                description
                  "All links are included in path calculation regardless of attributes";
              }
              container exclude-all {
                presence "Indicates a exclude-all node is configured.";
                description
                  "Links with any attribute are excluded from path calculation";
              }
            }
            container record-route {
              presence "Indicates a record-route node is configured.";
              description
                "Record the route used by the tunnel";
            }
            container logging {
              description
                "Per-interface logging configuration";
              container events {
                description
                  "Per-interface logging events";
                container lsp-status {
                  description
                    "Enable interface LSP state change alarms";
                  container state {
                    presence "Indicates a state node is configured.";
                    description
                      "Enable interface LSP UP/DOWN change alarms";
                  }
                  container reoptimize {
                    presence "Indicates a reoptimize node is configured.";
                    description
                      "Enable interface LSP REOPT change alarms";
                  }
                  container reoptimize-attempts {
                    presence "Indicates a reoptimize-attempts node is configured.";
                    description
                      "Enable interface LSP REOPT attempts change alarms";
                  }
                  container bw-change {
                    presence "Indicates a bw-change node is configured.";
                    description
                      "Enable interface LSP BANDWIDTH change alarms";
                  }
                }
              }
            }
            container soft-preemption {
              presence "Indicates a soft-preemption node is configured.";
              description
                "Enable the soft-preemption feature on this tunnel";
            }
            container signalled-name {
              presence "Indicates a signalled-name node is configured.";
              description
                "The signaling name to assign to tunnel";
              leaf name {
                type xr:Cisco-ios-xr-string {
                  length "1..64" {
                    description
                      "Signalled name (max 64 characters)";
                  }
                }
                mandatory true;
                description
                  "The signaling name to assign to tunnel";
              }
              container append {
                description
                  "Append other parameters to signalled name";
                container source {
                  must "address or name";
                  presence "Indicates a source node is configured.";
                  description
                    "Append source to signalled name";
                  container address {
                    presence "Indicates a address node is configured.";
                    description
                      "Append source address to signalled name";
                  }
                  container name {
                    presence "Indicates a name node is configured.";
                    description
                      "Append source name to signalled name";
                  }
                }
                container protected-link {
                  must "address or name";
                  presence "Indicates a protected-link node is configured.";
                  description
                    "Append protected-link to signalled name";
                  container address {
                    presence "Indicates a address node is configured.";
                    description
                      "Append protected-link address to signalled name";
                  }
                  container name {
                    presence "Indicates a name node is configured.";
                    description
                      "Append protected-link name to signalled name";
                  }
                }
                container merge-point-address {
                  presence "Indicates a merge-point-address node is configured.";
                  description
                    "Append merge-point address to signalled name";
                }
              }
            }
            container path-selection {
              presence "Indicates a path-selection node is configured.";
              description
                "Specify path selection";
            }
          }
        }
        container path-options {
          description
            "Attribute-set of a path option";
          list path-option {
            key "attribute-set-name";
            description
              "Attribute-set of a path option";
            leaf attribute-set-name {
              type xr:Cisco-ios-xr-string {
                length "1..64" {
                  description
                    "Specify attribute-set name (maximum 64 characters)";
                }
              }
              description
                "Attribute-set of a path option";
            }
            container signalled-bandwidth {
              presence "Indicates a signalled-bandwidth node is configured.";
              description
                "Tunnel bandwidth requirement to be signalled";
              leaf bandwidth {
                type uint32 {
                  range "0..4294967295" {
                    description
                      "Bandwidth requirement in kbps";
                  }
                }
                mandatory true;
                description
                  "Tunnel bandwidth requirement to be signalled";
              }
              leaf class-type {
                type uint32 {
                  range "0..1" {
                    description
                      "Class type number";
                  }
                }
                description
                  "Specify the bandwidth class type";
              }
            }
            container affinity {
              description
                "Link attributes for links traversed by tunnel";
              leaf affinity-attribute {
                type uint32 {
                  range "0..4294967295" {
                    description
                      "Affinity value";
                  }
                }
                description
                  "Link attributes for links traversed by tunnel";
              }
              leaf mask {
                type uint32 {
                  range "0..4294967295" {
                    description
                      "Affinity mask value";
                  }
                }
                description
                  "Affinity mask value";
              }
              container includes {
                description
                  "Links with all these attributes are included in path calculation";
                list include1 {
                  key "name1";
                  description
                    "Links with all these attributes are included in path calculation";
                  leaf name1 {
                    type xr:Cisco-ios-xr-string {
                      length "1..32" {
                        description
                          "Attribute or affinity name";
                      }
                    }
                    description
                      "Attribute or affinity name";
                  }
                }
                list include2 {
                  key "name1 name2";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                }
                list include3 {
                  key "name1 name2 name3";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                }
                list include4 {
                  key "name1 name2 name3 name4";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                }
                list include5 {
                  key "name1 name2 name3 name4 name5";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                }
                list include6 {
                  key "name1 name2 name3 name4 name5 name6";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                  leaf name6 {
                    type xr:Cisco-ios-xr-string {
                      length "1..32" {
                        description
                          "Attribute or affinity name";
                      }
                    }
                    description
                      "Attribute or affinity name";
                  }
                }
                list include7 {
                  key "name1 name2 name3 name4 name5 name6 name7";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                  leaf name6 {
                    type xr:Cisco-ios-xr-string {
                      length "1..32" {
                        description
                          "Attribute or affinity name";
                      }
                    }
                    description
                      "Attribute or affinity name";
                  }
                  leaf name7 {
                    type xr:Cisco-ios-xr-string {
                      length "1..32" {
                        description
                          "Attribute or affinity name";
                      }
                    }
                    description
                      "Attribute or affinity name";
                  }
                }
                list include8 {
                  key "name1 name2 name3 name4 name5 name6 name7 name8";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                  leaf name6 {
                    type xr:Cisco-ios-xr-string {
                      length "1..32" {
                        description
                          "Attribute or affinity name";
                      }
                    }
                    description
                      "Attribute or affinity name";
                  }
                  leaf name7 {
                    type xr:Cisco-ios-xr-string {
                      length "1..32" {
                        description
                          "Attribute or affinity name";
                      }
                    }
                    description
                      "Attribute or affinity name";
                  }
                  leaf name8 {
                    type xr:Cisco-ios-xr-string {
                      length "1..32" {
                        description
                          "Attribute or affinity name";
                      }
                    }
                    description
                      "Attribute or affinity name";
                  }
                }
                list include9 {
                  key "name1 name2 name3 name4 name5 name6 name7 name8 name9";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                  leaf name6 {
                    type xr:Cisco-ios-xr-string {
                      length "1..32" {
                        description
                          "Attribute or affinity name";
                      }
                    }
                    description
                      "Attribute or affinity name";
                  }
                  leaf name7 {
                    type xr:Cisco-ios-xr-string {
                      length "1..32" {
                        description
                          "Attribute or affinity name";
                      }
                    }
                    description
                      "Attribute or affinity name";
                  }
                  leaf name8 {
                    type xr:Cisco-ios-xr-string {
                      length "1..32" {
                        description
                          "Attribute or affinity name";
                      }
                    }
                    description
                      "Attribute or affinity name";
                  }
                  leaf name9 {
                    type xr:Cisco-ios-xr-string {
                      length "1..32" {
                        description
                          "Attribute or affinity name";
                      }
                    }
                    description
                      "Attribute or affinity name";
                  }
                }
                list include10 {
                  key "name1 name2 name3 name4 name5 name6 name7 name8 name9 name10";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                  leaf name6 {
                    type xr:Cisco-ios-xr-string {
                      length "1..32" {
                        description
                          "Attribute or affinity name";
                      }
                    }
                    description
                      "Attribute or affinity name";
                  }
                  leaf name7 {
                    type xr:Cisco-ios-xr-string {
                      length "1..32" {
                        description
                          "Attribute or affinity name";
                      }
                    }
                    description
                      "Attribute or affinity name";
                  }
                  leaf name8 {
                    type xr:Cisco-ios-xr-string {
                      length "1..32" {
                        description
                          "Attribute or affinity name";
                      }
                    }
                    description
                      "Attribute or affinity name";
                  }
                  leaf name9 {
                    type xr:Cisco-ios-xr-string {
                      length "1..32" {
                        description
                          "Attribute or affinity name";
                      }
                    }
                    description
                      "Attribute or affinity name";
                  }
                  leaf name10 {
                    type xr:Cisco-ios-xr-string {
                      length "1..32" {
                        description
                          "Attribute or affinity name";
                      }
                    }
                    description
                      "Attribute or affinity name";
                  }
                }
              }
              container include-stricts {
                description
                  "Links with exactly all these attributes are included in path calculation";
                list include1 {
                  key "name1";
                  description
                    "Links with all these attributes are included in path calculation";
                  leaf name1 {
                    type xr:Cisco-ios-xr-string {
                      length "1..32" {
                        description
                          "Attribute or affinity name";
                      }
                    }
                    description
                      "Attribute or affinity name";
                  }
                }
                list include2 {
                  key "name1 name2";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                }
                list include3 {
                  key "name1 name2 name3";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                }
                list include4 {
                  key "name1 name2 name3 name4";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                }
                list include5 {
                  key "name1 name2 name3 name4 name5";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                }
                list include6 {
                  key "name1 name2 name3 name4 name5 name6";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                  leaf name6 {
                    type xr:Cisco-ios-xr-string {
                      length "1..32" {
                        description
                          "Attribute or affinity name";
                      }
                    }
                    description
                      "Attribute or affinity name";
                  }
                }
                list include7 {
                  key "name1 name2 name3 name4 name5 name6 name7";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                  leaf name6 {
                    type xr:Cisco-ios-xr-string {
                      length "1..32" {
                        description
                          "Attribute or affinity name";
                      }
                    }
                    description
                      "Attribute or affinity name";
                  }
                  leaf name7 {
                    type xr:Cisco-ios-xr-string {
                      length "1..32" {
                        description
                          "Attribute or affinity name";
                      }
                    }
                    description
                      "Attribute or affinity name";
                  }
                }
                list include8 {
                  key "name1 name2 name3 name4 name5 name6 name7 name8";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                  leaf name6 {
                    type xr:Cisco-ios-xr-string {
                      length "1..32" {
                        description
                          "Attribute or affinity name";
                      }
                    }
                    description
                      "Attribute or affinity name";
                  }
                  leaf name7 {
                    type xr:Cisco-ios-xr-string {
                      length "1..32" {
                        description
                          "Attribute or affinity name";
                      }
                    }
                    description
                      "Attribute or affinity name";
                  }
                  leaf name8 {
                    type xr:Cisco-ios-xr-string {
                      length "1..32" {
                        description
                          "Attribute or affinity name";
                      }
                    }
                    description
                      "Attribute or affinity name";
                  }
                }
                list include9 {
                  key "name1 name2 name3 name4 name5 name6 name7 name8 name9";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                  leaf name6 {
                    type xr:Cisco-ios-xr-string {
                      length "1..32" {
                        description
                          "Attribute or affinity name";
                      }
                    }
                    description
                      "Attribute or affinity name";
                  }
                  leaf name7 {
                    type xr:Cisco-ios-xr-string {
                      length "1..32" {
                        description
                          "Attribute or affinity name";
                      }
                    }
                    description
                      "Attribute or affinity name";
                  }
                  leaf name8 {
                    type xr:Cisco-ios-xr-string {
                      length "1..32" {
                        description
                          "Attribute or affinity name";
                      }
                    }
                    description
                      "Attribute or affinity name";
                  }
                  leaf name9 {
                    type xr:Cisco-ios-xr-string {
                      length "1..32" {
                        description
                          "Attribute or affinity name";
                      }
                    }
                    description
                      "Attribute or affinity name";
                  }
                }
                list include10 {
                  key "name1 name2 name3 name4 name5 name6 name7 name8 name9 name10";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                  leaf name6 {
                    type xr:Cisco-ios-xr-string {
                      length "1..32" {
                        description
                          "Attribute or affinity name";
                      }
                    }
                    description
                      "Attribute or affinity name";
                  }
                  leaf name7 {
                    type xr:Cisco-ios-xr-string {
                      length "1..32" {
                        description
                          "Attribute or affinity name";
                      }
                    }
                    description
                      "Attribute or affinity name";
                  }
                  leaf name8 {
                    type xr:Cisco-ios-xr-string {
                      length "1..32" {
                        description
                          "Attribute or affinity name";
                      }
                    }
                    description
                      "Attribute or affinity name";
                  }
                  leaf name9 {
                    type xr:Cisco-ios-xr-string {
                      length "1..32" {
                        description
                          "Attribute or affinity name";
                      }
                    }
                    description
                      "Attribute or affinity name";
                  }
                  leaf name10 {
                    type xr:Cisco-ios-xr-string {
                      length "1..32" {
                        description
                          "Attribute or affinity name";
                      }
                    }
                    description
                      "Attribute or affinity name";
                  }
                }
              }
              container excludes {
                description
                  "Links with all these attributes are excluded from path calculation";
                list exclude1 {
                  key "name1";
                  description
                    "Links with all these attributes are included in path calculation";
                  leaf name1 {
                    type xr:Cisco-ios-xr-string {
                      length "1..32" {
                        description
                          "Attribute or affinity name";
                      }
                    }
                    description
                      "Attribute or affinity name";
                  }
                }
                list exclude2 {
                  key "name1 name2";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                }
                list exclude3 {
                  key "name1 name2 name3";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                }
                list exclude4 {
                  key "name1 name2 name3 name4";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                }
                list exclude5 {
                  key "name1 name2 name3 name4 name5";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                }
                list exclude6 {
                  key "name1 name2 name3 name4 name5 name6";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                  leaf name6 {
                    type xr:Cisco-ios-xr-string {
                      length "1..32" {
                        description
                          "Attribute or affinity name";
                      }
                    }
                    description
                      "Attribute or affinity name";
                  }
                }
                list exclude7 {
                  key "name1 name2 name3 name4 name5 name6 name7";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                  leaf name6 {
                    type xr:Cisco-ios-xr-string {
                      length "1..32" {
                        description
                          "Attribute or affinity name";
                      }
                    }
                    description
                      "Attribute or affinity name";
                  }
                  leaf name7 {
                    type xr:Cisco-ios-xr-string {
                      length "1..32" {
                        description
                          "Attribute or affinity name";
                      }
                    }
                    description
                      "Attribute or affinity name";
                  }
                }
                list exclude8 {
                  key "name1 name2 name3 name4 name5 name6 name7 name8";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                  leaf name6 {
                    type xr:Cisco-ios-xr-string {
                      length "1..32" {
                        description
                          "Attribute or affinity name";
                      }
                    }
                    description
                      "Attribute or affinity name";
                  }
                  leaf name7 {
                    type xr:Cisco-ios-xr-string {
                      length "1..32" {
                        description
                          "Attribute or affinity name";
                      }
                    }
                    description
                      "Attribute or affinity name";
                  }
                  leaf name8 {
                    type xr:Cisco-ios-xr-string {
                      length "1..32" {
                        description
                          "Attribute or affinity name";
                      }
                    }
                    description
                      "Attribute or affinity name";
                  }
                }
                list exclude9 {
                  key "name1 name2 name3 name4 name5 name6 name7 name8 name9";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                  leaf name6 {
                    type xr:Cisco-ios-xr-string {
                      length "1..32" {
                        description
                          "Attribute or affinity name";
                      }
                    }
                    description
                      "Attribute or affinity name";
                  }
                  leaf name7 {
                    type xr:Cisco-ios-xr-string {
                      length "1..32" {
                        description
                          "Attribute or affinity name";
                      }
                    }
                    description
                      "Attribute or affinity name";
                  }
                  leaf name8 {
                    type xr:Cisco-ios-xr-string {
                      length "1..32" {
                        description
                          "Attribute or affinity name";
                      }
                    }
                    description
                      "Attribute or affinity name";
                  }
                  leaf name9 {
                    type xr:Cisco-ios-xr-string {
                      length "1..32" {
                        description
                          "Attribute or affinity name";
                      }
                    }
                    description
                      "Attribute or affinity name";
                  }
                }
                list exclude10 {
                  key "name1 name2 name3 name4 name5 name6 name7 name8 name9 name10";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                  leaf name6 {
                    type xr:Cisco-ios-xr-string {
                      length "1..32" {
                        description
                          "Attribute or affinity name";
                      }
                    }
                    description
                      "Attribute or affinity name";
                  }
                  leaf name7 {
                    type xr:Cisco-ios-xr-string {
                      length "1..32" {
                        description
                          "Attribute or affinity name";
                      }
                    }
                    description
                      "Attribute or affinity name";
                  }
                  leaf name8 {
                    type xr:Cisco-ios-xr-string {
                      length "1..32" {
                        description
                          "Attribute or affinity name";
                      }
                    }
                    description
                      "Attribute or affinity name";
                  }
                  leaf name9 {
                    type xr:Cisco-ios-xr-string {
                      length "1..32" {
                        description
                          "Attribute or affinity name";
                      }
                    }
                    description
                      "Attribute or affinity name";
                  }
                  leaf name10 {
                    type xr:Cisco-ios-xr-string {
                      length "1..32" {
                        description
                          "Attribute or affinity name";
                      }
                    }
                    description
                      "Attribute or affinity name";
                  }
                }
              }
              container ignore {
                presence "Indicates a ignore node is configured.";
                description
                  "All links are included in path calculation regardless of attributes";
              }
              container exclude-all {
                presence "Indicates a exclude-all node is configured.";
                description
                  "Links with any attribute are excluded from path calculation";
              }
            }
            container path-selection {
              presence "Indicates a path-selection node is configured.";
              description
                "Specify path selection";
              leaf cost-limit {
                type uint32 {
                  range "1..4294967295" {
                    description
                      "Cost limit";
                  }
                }
                description
                  "Cost limit configuration";
              }
              leaf exclude {
                type xr:Cisco-ios-xr-string {
                  length "1..64" {
                    description
                      "Exclude address list name";
                  }
                }
                description
                  "Path Exclusion Configuration";
              }
              leaf delay-limit {
                type uint32 {
                  range "1..4294967295" {
                    description
                      "Delay limit in usec";
                  }
                }
                description
                  "Delay limit configuration";
              }
            }
            container pce {
              presence "Indicates a pce node is configured.";
              description
                "Specify PCE Configuration";
              container disjoint-path {
                description
                  "Disjoint Path Configuration";
                leaf source {
                  type inet:ipv4-address-no-zone;
                  description
                    "Source address";
                }
                container type {
                  must "link or node or srlg";
                  presence "Indicates a type node is configured.";
                  description
                    "Disjointness type";
                  container link {
                    presence "Indicates a link node is configured.";
                    description
                      "Link Disjointness";
                  }
                  container node {
                    presence "Indicates a node node is configured.";
                    description
                      "Node Disjointness";
                  }
                  container srlg {
                    presence "Indicates a srlg node is configured.";
                    description
                      "SRLG Disjointness";
                  }
                }
                leaf group-id {
                  type uint32 {
                    range "1..4294967295" {
                      description
                        "Enter group-id";
                    }
                  }
                  description
                    "Enter group-id";
                }
              }
            }
            container bfd-reverse-path {
              description
                "Specify bfd reverse path";
              leaf binding-label {
                type uint32 {
                  range "0..1048575" {
                    description
                      "MPLS binding-label value";
                  }
                }
                description
                  "Specify reverse path binding-label";
              }
            }
          }
        }
        container xros {
          description
            "An XRO attribute-set";
          list xro {
            key "attribute-set-name";
            description
              "An XRO attribute-set";
            leaf attribute-set-name {
              type xr:Cisco-ios-xr-string {
                length "1..64" {
                  description
                    "Specify attribute-set name (maximum 64 characters)";
                }
              }
              description
                "An XRO attribute-set";
            }
            container exclude {
              description
                "Specify exclusions for path diversity";
              container strict {
                description
                  "Specified condition must be met";
                container lsps {
                  description
                    "Specify path-diversity from another LSP";
                  list lsp-no-lsp-id {
                    key "source destination tunnel-id extended-tunnel-id";
                    description
                      "Specify path-diversity from another LSP";
                    leaf source {
                      type inet:ipv4-address-no-zone;
                      description
                        "The source of the LSP from which a diverse path is required";
                    }
                    leaf destination {
                      type inet:ipv4-address-no-zone;
                      description
                        "The destination of the LSP from which a diverse path is required";
                    }
                    leaf tunnel-id {
                      type uint32 {
                        range "0..65535" {
                          description
                            "The LSP's tunnel-id";
                        }
                      }
                      description
                        "The tunnel-id of the LSP from which a diverse path is required";
                    }
                    leaf extended-tunnel-id {
                      type inet:ipv4-address-no-zone;
                      description
                        "The extended tunnel-id of the LSP from which a diverse path is required";
                    }
                  }
                  list lsp {
                    key "source destination tunnel-id extended-tunnel-id lsp-id";
                    description
                      "LSP details";
                    leaf source {
                      type inet:ipv4-address-no-zone;
                      description
                        "The source of the LSP from which a diverse path is required";
                    }
                    leaf destination {
                      type inet:ipv4-address-no-zone;
                      description
                        "The destination of the LSP from which a diverse path is required";
                    }
                    leaf tunnel-id {
                      type uint32 {
                        range "0..65535" {
                          description
                            "The LSP's tunnel-id";
                        }
                      }
                      description
                        "The tunnel-id of the LSP from which a diverse path is required";
                    }
                    leaf extended-tunnel-id {
                      type inet:ipv4-address-no-zone;
                      description
                        "The extended tunnel-id of the LSP from which a diverse path is required";
                    }
                    leaf lsp-id {
                      type uint32 {
                        range "0..65535" {
                          description
                            "The LSP's lsp-id";
                        }
                      }
                      description
                        "The lsp-id of the LSP from which a diverse path is required";
                    }
                  }
                }
                container srlgs {
                  description
                    "Specify path-diversity based on SRLGs";
                  list srlg {
                    key "value";
                    description
                      "Specify SRLG value";
                    leaf value {
                      type uint32 {
                        range "0..4294967295" {
                          description
                            "The SRLG from which diversity is required";
                        }
                      }
                      description
                        "Specify SRLG value";
                    }
                  }
                }
              }
            }
            container path-selection {
              presence "Indicates a path-selection node is configured.";
              description
                "Specify path selection";
            }
          }
        }
        container p2mp-tes {
          description
            "Attribute-set of p2mp-te type";
          list p2mp-te {
            key "attribute-set-name";
            description
              "Attribute-set of p2mp-te type";
            leaf attribute-set-name {
              type xr:Cisco-ios-xr-string {
                length "1..64" {
                  description
                    "Specify attribute-set name (maximum 64 characters)";
                }
              }
              description
                "Attribute-set of p2mp-te type";
            }
            container priority {
              presence "Indicates a priority node is configured.";
              description
                "Tunnel priority";
              leaf setup-priority {
                type uint32 {
                  range "0..7" {
                    description
                      "Setup Priority";
                  }
                }
                mandatory true;
                description
                  "Tunnel priority";
              }
              leaf hold-priority {
                type uint32 {
                  range "0..7" {
                    description
                      "Hold Priority";
                  }
                }
                mandatory true;
                description
                  "Hold Priority";
              }
            }
            container signalled-bandwidth {
              presence "Indicates a signalled-bandwidth node is configured.";
              description
                "Tunnel bandwidth requirement to be signalled";
              leaf bandwidth {
                type uint32 {
                  range "0..4294967295" {
                    description
                      "Bandwidth requirement in kbps";
                  }
                }
                mandatory true;
                description
                  "Tunnel bandwidth requirement to be signalled";
              }
              leaf class-type {
                type uint32 {
                  range "0..1" {
                    description
                      "Class type number";
                  }
                }
                description
                  "Specify the bandwidth class type";
              }
            }
            container affinity {
              description
                "Link attributes for links traversed by tunnel";
              leaf affinity-attribute {
                type uint32 {
                  range "0..4294967295" {
                    description
                      "Affinity value";
                  }
                }
                description
                  "Link attributes for links traversed by tunnel";
              }
              leaf mask {
                type uint32 {
                  range "0..4294967295" {
                    description
                      "Affinity mask value";
                  }
                }
                description
                  "Affinity mask value";
              }
              container includes {
                description
                  "Links with all these attributes are included in path calculation";
                list include1 {
                  key "name1";
                  description
                    "Links with all these attributes are included in path calculation";
                  leaf name1 {
                    type xr:Cisco-ios-xr-string {
                      length "1..32" {
                        description
                          "Attribute or affinity name";
                      }
                    }
                    description
                      "Attribute or affinity name";
                  }
                }
                list include2 {
                  key "name1 name2";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                }
                list include3 {
                  key "name1 name2 name3";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                }
                list include4 {
                  key "name1 name2 name3 name4";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                }
                list include5 {
                  key "name1 name2 name3 name4 name5";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                }
                list include6 {
                  key "name1 name2 name3 name4 name5 name6";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                  leaf name6 {
                    type xr:Cisco-ios-xr-string {
                      length "1..32" {
                        description
                          "Attribute or affinity name";
                      }
                    }
                    description
                      "Attribute or affinity name";
                  }
                }
                list include7 {
                  key "name1 name2 name3 name4 name5 name6 name7";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                  leaf name6 {
                    type xr:Cisco-ios-xr-string {
                      length "1..32" {
                        description
                          "Attribute or affinity name";
                      }
                    }
                    description
                      "Attribute or affinity name";
                  }
                  leaf name7 {
                    type xr:Cisco-ios-xr-string {
                      length "1..32" {
                        description
                          "Attribute or affinity name";
                      }
                    }
                    description
                      "Attribute or affinity name";
                  }
                }
                list include8 {
                  key "name1 name2 name3 name4 name5 name6 name7 name8";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                  leaf name6 {
                    type xr:Cisco-ios-xr-string {
                      length "1..32" {
                        description
                          "Attribute or affinity name";
                      }
                    }
                    description
                      "Attribute or affinity name";
                  }
                  leaf name7 {
                    type xr:Cisco-ios-xr-string {
                      length "1..32" {
                        description
                          "Attribute or affinity name";
                      }
                    }
                    description
                      "Attribute or affinity name";
                  }
                  leaf name8 {
                    type xr:Cisco-ios-xr-string {
                      length "1..32" {
                        description
                          "Attribute or affinity name";
                      }
                    }
                    description
                      "Attribute or affinity name";
                  }
                }
                list include9 {
                  key "name1 name2 name3 name4 name5 name6 name7 name8 name9";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                  leaf name6 {
                    type xr:Cisco-ios-xr-string {
                      length "1..32" {
                        description
                          "Attribute or affinity name";
                      }
                    }
                    description
                      "Attribute or affinity name";
                  }
                  leaf name7 {
                    type xr:Cisco-ios-xr-string {
                      length "1..32" {
                        description
                          "Attribute or affinity name";
                      }
                    }
                    description
                      "Attribute or affinity name";
                  }
                  leaf name8 {
                    type xr:Cisco-ios-xr-string {
                      length "1..32" {
                        description
                          "Attribute or affinity name";
                      }
                    }
                    description
                      "Attribute or affinity name";
                  }
                  leaf name9 {
                    type xr:Cisco-ios-xr-string {
                      length "1..32" {
                        description
                          "Attribute or affinity name";
                      }
                    }
                    description
                      "Attribute or affinity name";
                  }
                }
                list include10 {
                  key "name1 name2 name3 name4 name5 name6 name7 name8 name9 name10";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                  leaf name6 {
                    type xr:Cisco-ios-xr-string {
                      length "1..32" {
                        description
                          "Attribute or affinity name";
                      }
                    }
                    description
                      "Attribute or affinity name";
                  }
                  leaf name7 {
                    type xr:Cisco-ios-xr-string {
                      length "1..32" {
                        description
                          "Attribute or affinity name";
                      }
                    }
                    description
                      "Attribute or affinity name";
                  }
                  leaf name8 {
                    type xr:Cisco-ios-xr-string {
                      length "1..32" {
                        description
                          "Attribute or affinity name";
                      }
                    }
                    description
                      "Attribute or affinity name";
                  }
                  leaf name9 {
                    type xr:Cisco-ios-xr-string {
                      length "1..32" {
                        description
                          "Attribute or affinity name";
                      }
                    }
                    description
                      "Attribute or affinity name";
                  }
                  leaf name10 {
                    type xr:Cisco-ios-xr-string {
                      length "1..32" {
                        description
                          "Attribute or affinity name";
                      }
                    }
                    description
                      "Attribute or affinity name";
                  }
                }
              }
              container include-stricts {
                description
                  "Links with exactly all these attributes are included in path calculation";
                list include1 {
                  key "name1";
                  description
                    "Links with all these attributes are included in path calculation";
                  leaf name1 {
                    type xr:Cisco-ios-xr-string {
                      length "1..32" {
                        description
                          "Attribute or affinity name";
                      }
                    }
                    description
                      "Attribute or affinity name";
                  }
                }
                list include2 {
                  key "name1 name2";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                }
                list include3 {
                  key "name1 name2 name3";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                }
                list include4 {
                  key "name1 name2 name3 name4";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                }
                list include5 {
                  key "name1 name2 name3 name4 name5";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                }
                list include6 {
                  key "name1 name2 name3 name4 name5 name6";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                  leaf name6 {
                    type xr:Cisco-ios-xr-string {
                      length "1..32" {
                        description
                          "Attribute or affinity name";
                      }
                    }
                    description
                      "Attribute or affinity name";
                  }
                }
                list include7 {
                  key "name1 name2 name3 name4 name5 name6 name7";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                  leaf name6 {
                    type xr:Cisco-ios-xr-string {
                      length "1..32" {
                        description
                          "Attribute or affinity name";
                      }
                    }
                    description
                      "Attribute or affinity name";
                  }
                  leaf name7 {
                    type xr:Cisco-ios-xr-string {
                      length "1..32" {
                        description
                          "Attribute or affinity name";
                      }
                    }
                    description
                      "Attribute or affinity name";
                  }
                }
                list include8 {
                  key "name1 name2 name3 name4 name5 name6 name7 name8";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                  leaf name6 {
                    type xr:Cisco-ios-xr-string {
                      length "1..32" {
                        description
                          "Attribute or affinity name";
                      }
                    }
                    description
                      "Attribute or affinity name";
                  }
                  leaf name7 {
                    type xr:Cisco-ios-xr-string {
                      length "1..32" {
                        description
                          "Attribute or affinity name";
                      }
                    }
                    description
                      "Attribute or affinity name";
                  }
                  leaf name8 {
                    type xr:Cisco-ios-xr-string {
                      length "1..32" {
                        description
                          "Attribute or affinity name";
                      }
                    }
                    description
                      "Attribute or affinity name";
                  }
                }
                list include9 {
                  key "name1 name2 name3 name4 name5 name6 name7 name8 name9";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                  leaf name6 {
                    type xr:Cisco-ios-xr-string {
                      length "1..32" {
                        description
                          "Attribute or affinity name";
                      }
                    }
                    description
                      "Attribute or affinity name";
                  }
                  leaf name7 {
                    type xr:Cisco-ios-xr-string {
                      length "1..32" {
                        description
                          "Attribute or affinity name";
                      }
                    }
                    description
                      "Attribute or affinity name";
                  }
                  leaf name8 {
                    type xr:Cisco-ios-xr-string {
                      length "1..32" {
                        description
                          "Attribute or affinity name";
                      }
                    }
                    description
                      "Attribute or affinity name";
                  }
                  leaf name9 {
                    type xr:Cisco-ios-xr-string {
                      length "1..32" {
                        description
                          "Attribute or affinity name";
                      }
                    }
                    description
                      "Attribute or affinity name";
                  }
                }
                list include10 {
                  key "name1 name2 name3 name4 name5 name6 name7 name8 name9 name10";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                  leaf name6 {
                    type xr:Cisco-ios-xr-string {
                      length "1..32" {
                        description
                          "Attribute or affinity name";
                      }
                    }
                    description
                      "Attribute or affinity name";
                  }
                  leaf name7 {
                    type xr:Cisco-ios-xr-string {
                      length "1..32" {
                        description
                          "Attribute or affinity name";
                      }
                    }
                    description
                      "Attribute or affinity name";
                  }
                  leaf name8 {
                    type xr:Cisco-ios-xr-string {
                      length "1..32" {
                        description
                          "Attribute or affinity name";
                      }
                    }
                    description
                      "Attribute or affinity name";
                  }
                  leaf name9 {
                    type xr:Cisco-ios-xr-string {
                      length "1..32" {
                        description
                          "Attribute or affinity name";
                      }
                    }
                    description
                      "Attribute or affinity name";
                  }
                  leaf name10 {
                    type xr:Cisco-ios-xr-string {
                      length "1..32" {
                        description
                          "Attribute or affinity name";
                      }
                    }
                    description
                      "Attribute or affinity name";
                  }
                }
              }
              container excludes {
                description
                  "Links with all these attributes are excluded from path calculation";
                list exclude1 {
                  key "name1";
                  description
                    "Links with all these attributes are included in path calculation";
                  leaf name1 {
                    type xr:Cisco-ios-xr-string {
                      length "1..32" {
                        description
                          "Attribute or affinity name";
                      }
                    }
                    description
                      "Attribute or affinity name";
                  }
                }
                list exclude2 {
                  key "name1 name2";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                }
                list exclude3 {
                  key "name1 name2 name3";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                }
                list exclude4 {
                  key "name1 name2 name3 name4";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                }
                list exclude5 {
                  key "name1 name2 name3 name4 name5";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                }
                list exclude6 {
                  key "name1 name2 name3 name4 name5 name6";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                  leaf name6 {
                    type xr:Cisco-ios-xr-string {
                      length "1..32" {
                        description
                          "Attribute or affinity name";
                      }
                    }
                    description
                      "Attribute or affinity name";
                  }
                }
                list exclude7 {
                  key "name1 name2 name3 name4 name5 name6 name7";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                  leaf name6 {
                    type xr:Cisco-ios-xr-string {
                      length "1..32" {
                        description
                          "Attribute or affinity name";
                      }
                    }
                    description
                      "Attribute or affinity name";
                  }
                  leaf name7 {
                    type xr:Cisco-ios-xr-string {
                      length "1..32" {
                        description
                          "Attribute or affinity name";
                      }
                    }
                    description
                      "Attribute or affinity name";
                  }
                }
                list exclude8 {
                  key "name1 name2 name3 name4 name5 name6 name7 name8";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                  leaf name6 {
                    type xr:Cisco-ios-xr-string {
                      length "1..32" {
                        description
                          "Attribute or affinity name";
                      }
                    }
                    description
                      "Attribute or affinity name";
                  }
                  leaf name7 {
                    type xr:Cisco-ios-xr-string {
                      length "1..32" {
                        description
                          "Attribute or affinity name";
                      }
                    }
                    description
                      "Attribute or affinity name";
                  }
                  leaf name8 {
                    type xr:Cisco-ios-xr-string {
                      length "1..32" {
                        description
                          "Attribute or affinity name";
                      }
                    }
                    description
                      "Attribute or affinity name";
                  }
                }
                list exclude9 {
                  key "name1 name2 name3 name4 name5 name6 name7 name8 name9";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                  leaf name6 {
                    type xr:Cisco-ios-xr-string {
                      length "1..32" {
                        description
                          "Attribute or affinity name";
                      }
                    }
                    description
                      "Attribute or affinity name";
                  }
                  leaf name7 {
                    type xr:Cisco-ios-xr-string {
                      length "1..32" {
                        description
                          "Attribute or affinity name";
                      }
                    }
                    description
                      "Attribute or affinity name";
                  }
                  leaf name8 {
                    type xr:Cisco-ios-xr-string {
                      length "1..32" {
                        description
                          "Attribute or affinity name";
                      }
                    }
                    description
                      "Attribute or affinity name";
                  }
                  leaf name9 {
                    type xr:Cisco-ios-xr-string {
                      length "1..32" {
                        description
                          "Attribute or affinity name";
                      }
                    }
                    description
                      "Attribute or affinity name";
                  }
                }
                list exclude10 {
                  key "name1 name2 name3 name4 name5 name6 name7 name8 name9 name10";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                  leaf name6 {
                    type xr:Cisco-ios-xr-string {
                      length "1..32" {
                        description
                          "Attribute or affinity name";
                      }
                    }
                    description
                      "Attribute or affinity name";
                  }
                  leaf name7 {
                    type xr:Cisco-ios-xr-string {
                      length "1..32" {
                        description
                          "Attribute or affinity name";
                      }
                    }
                    description
                      "Attribute or affinity name";
                  }
                  leaf name8 {
                    type xr:Cisco-ios-xr-string {
                      length "1..32" {
                        description
                          "Attribute or affinity name";
                      }
                    }
                    description
                      "Attribute or affinity name";
                  }
                  leaf name9 {
                    type xr:Cisco-ios-xr-string {
                      length "1..32" {
                        description
                          "Attribute or affinity name";
                      }
                    }
                    description
                      "Attribute or affinity name";
                  }
                  leaf name10 {
                    type xr:Cisco-ios-xr-string {
                      length "1..32" {
                        description
                          "Attribute or affinity name";
                      }
                    }
                    description
                      "Attribute or affinity name";
                  }
                }
              }
              container ignore {
                presence "Indicates a ignore node is configured.";
                description
                  "All links are included in path calculation regardless of attributes";
              }
              container exclude-all {
                presence "Indicates a exclude-all node is configured.";
                description
                  "Links with any attribute are excluded from path calculation";
              }
            }
            container fast-reroute {
              presence "Indicates a fast-reroute node is configured.";
              description
                "Specify MPLS tunnel can be fast-rerouted";
              container protect {
                description
                  "Enable protection request";
                container node {
                  presence "Indicates a node node is configured.";
                  description
                    "Enable node protection request";
                }
                container bandwidth {
                  presence "Indicates a bandwidth node is configured.";
                  description
                    "Enable bandwidth protection request";
                }
              }
            }
            container record-route {
              presence "Indicates a record-route node is configured.";
              description
                "Record the route used by the tunnel";
            }
            container logging {
              description
                "Per-interface logging configuration";
              container events {
                description
                  "Per-interface logging events";
                container lsp-status {
                  description
                    "Enable interface LSP state change alarms";
                  container state {
                    presence "Indicates a state node is configured.";
                    description
                      "Enable interface LSP UP/DOWN change alarms";
                  }
                  container reoptimize {
                    presence "Indicates a reoptimize node is configured.";
                    description
                      "Enable interface LSP REOPT change alarms";
                  }
                  container reoptimize-attempts {
                    presence "Indicates a reoptimize-attempts node is configured.";
                    description
                      "Enable interface LSP REOPT attempts change alarms";
                  }
                  container bw-change {
                    presence "Indicates a bw-change node is configured.";
                    description
                      "Enable interface LSP BANDWIDTH change alarms";
                  }
                  container reroute {
                    presence "Indicates a reroute node is configured.";
                    description
                      "Enable interface LSP REROUTE change alarms";
                  }
                  container insufficient-bandwidth {
                    presence "Indicates a insufficient-bandwidth node is configured.";
                    description
                      "Enable Syslog for setup/reopt failure due to bandwidth";
                  }
                }
                container pcalc-failure {
                  presence "Indicates a pcalc-failure node is configured.";
                  description
                    "Enable logging for path calculation failures";
                }
                container sub-lsp-status {
                  description
                    "Enable all sub-LSP state change alarms";
                  container state {
                    presence "Indicates a state node is configured.";
                    description
                      "Enable interface LSP UP/DOWN change alarms";
                  }
                }
              }
            }
            leaf bandwidth {
              type uint32 {
                range "0..4294967295" {
                  description
                    "bandwidth in kbps";
                }
              }
              description
                "Set the bandwidth of an interface";
            }
            container path-selection {
              presence "Indicates a path-selection node is configured.";
              description
                "Specify path selection";
            }
          }
        }
        container path-protection-apses {
          description
            "Attribute-set of path protection";
          list path-protection-aps {
            key "attribute-set-name";
            description
              "Attribute-set of path protection";
            leaf attribute-set-name {
              type xr:Cisco-ios-xr-string {
                length "1..64" {
                  description
                    "Specify attribute-set name (maximum 32 characters)";
                }
              }
              description
                "Attribute-set of path protection";
            }
            container sub-network {
              description
                "Specify sub-network connection mode";
              container connection-mode {
                description
                  "Specify sub-network connection mode";
                container snc-n {
                  presence "Indicates a snc-n node is configured.";
                  description
                    "Sub-network connection mode N";
                }
                container snc-i {
                  presence "Indicates a snc-i node is configured.";
                  description
                    "Sub-network connection mode I";
                }
                container snc-s {
                  presence "Indicates a snc-s node is configured.";
                  description
                    "Sub-network connection mode S";
                  leaf tcm-id {
                    type uint32 {
                      range "1..6" {
                        description
                          "Enter the Tandem Connection Monitoring ID";
                      }
                    }
                    description
                      "Optional, for SNC-S mode only: Tandem Connection                           Monitoring ID";
                  }
                }
              }
            }
            container protection-type {
              description
                "Specify APS protection type";
              container bidir-aps {
                presence "Indicates a bidir-aps node is configured.";
                description
                  "Protection type bi-directional APS";
              }
              container unidir-aps {
                presence "Indicates a unidir-aps node is configured.";
                description
                  "Protection type uni-directional APS";
              }
              container unidir-no-aps {
                presence "Indicates a unidir-no-aps node is configured.";
                description
                  "Protection type uni-directional no APS";
              }
            }
            container protection-mode {
              description
                "Specify APS protection mode";
              container revertive {
                presence "Indicates a revertive node is configured.";
                description
                  "APS protection mode revertive";
              }
            }
            container timers {
              description
                "Specify APS protection timers";
              leaf wait-to-restore {
                type uint32 {
                  range "0..720" {
                    description
                      "G.709 path protection wait to restore timer in seconds";
                  }
                }
                description
                  "APS wait to restore timer";
              }
              leaf hold-off {
                type uint32 {
                  range "100..10000" {
                    description
                      "G.709 PP hold-off timer in milliseconds";
                  }
                }
                description
                  "APS hold-off timer";
              }
            }
            container revert-schedules {
              description
                "Specify APS revert schedule";
              list revert-schedule {
                key "schedule-name";
                description
                  "Specify APS revert schedule";
                leaf schedule-name {
                  type xr:Cisco-ios-xr-string {
                    length "1..254" {
                      description
                        "Name this revert schedule configuration (MAX 64 CHARACTERS)";
                    }
                  }
                  description
                    "Name Identifier for revert schedule";
                }
                container date {
                  presence "Indicates a date node is configured.";
                  description
                    "Set the time and date in format hh:mm MMM DD YYYY";
                  leaf hour {
                    type uint32 {
                      range "0..23" {
                        description
                          "Enter (hh) of schedule time (hh:mm) in 24hr format. Eg. 2:15PM as 14:15";
                      }
                    }
                    mandatory true;
                    description
                      "Set the time and date in format hh:mm MMM DD YYYY";
                  }
                  leaf minute {
                    type uint32 {
                      range "0..59" {
                        description
                          "Enter (mm) of schedule time (hh:mm) in 24hr format. Eg. 2:15PM as 14:15";
                      }
                    }
                    mandatory true;
                    description
                      "Enter (mm) of schedule time (hh:mm) in 24hr format. Eg. 2:15PM as 14:15";
                  }
                  leaf month {
                    type enumeration {
                      enum "JAN" {
                        value 0;
                        description
                          "January";
                      }
                      enum "FEB" {
                        value 1;
                        description
                          "February";
                      }
                      enum "MAR" {
                        value 2;
                        description
                          "March";
                      }
                      enum "APR" {
                        value 3;
                        description
                          "April";
                      }
                      enum "MAY" {
                        value 4;
                        description
                          "May";
                      }
                      enum "JUN" {
                        value 5;
                        description
                          "Jun";
                      }
                      enum "JUL" {
                        value 6;
                        description
                          "July";
                      }
                      enum "AUG" {
                        value 7;
                        description
                          "August";
                      }
                      enum "SEP" {
                        value 8;
                        description
                          "September";
                      }
                      enum "OCT" {
                        value 9;
                        description
                          "October";
                      }
                      enum "NOV" {
                        value 10;
                        description
                          "November";
                      }
                      enum "DEC" {
                        value 11;
                        description
                          "December";
                      }
                    }
                    mandatory true;
                    description
                      "configure month";
                  }
                  leaf day {
                    type uint32 {
                      range "1..31" {
                        description
                          "Enter day of month (DD) of schedule date MMM DD YYYY";
                      }
                    }
                    mandatory true;
                    description
                      "Enter day of month (DD) of schedule date MMM DD YYYY";
                  }
                  leaf year {
                    type uint32 {
                      range "2015..2035" {
                        description
                          "Enter year (YYYY) of schedule date MMM DD YYYY";
                      }
                    }
                    mandatory true;
                    description
                      "Enter year (YYYY) of schedule date MMM DD YYYY";
                  }
                }
                container duration {
                  presence "Indicates a duration node is configured.";
                  description
                    "Enter duration for reversion schedule in hh:mm format";
                  leaf hour {
                    type uint32 {
                      range "0..167" {
                        description
                          "Enter (hh) of duration (hh:mm). Eg. Duration of 15hour and 20min is 15:20 ";
                      }
                    }
                    mandatory true;
                    description
                      "Enter duration for reversion schedule in hh:mm format";
                  }
                  leaf minute {
                    type uint32 {
                      range "0..59" {
                        description
                          "Enter (mm) of duration (hh:mm). Eg. Duration of 15hour and 20min is 15:20 ";
                      }
                    }
                    mandatory true;
                    description
                      "Enter (mm) of duration (hh:mm). Eg. Duration of 15hour and 20min is 15:20 ";
                  }
                }
                leaf frequency {
                  type enumeration {
                    enum "once" {
                      value 1;
                      description
                        "Execute only ONCE on scheduled date and time";
                    }
                    enum "daily" {
                      value 2;
                      description
                        "Execute DAILY at scheduled time starting from scheduled date";
                    }
                    enum "weekly" {
                      value 3;
                      description
                        "Execute WEEKLY at scheduled time starting from scheduled date";
                    }
                  }
                  description
                    "Frequency to execute the scheduled reversion";
                }
                leaf max-tries {
                  type uint32 {
                    range "1..2016" {
                      description
                        "Number of retries. Eg : If three tries to be done for reversion, enter 3";
                    }
                  }
                  description
                    "Maximum number of retries for scheduled reversion";
                }
              }
            }
            container path-selection {
              presence "Indicates a path-selection node is configured.";
              description
                "Specify path selection";
            }
          }
        }
        container p2p-tes {
          description
            "Attribute-set of p2p-te type";
          list p2p-te {
            key "attribute-set-name";
            description
              "Attribute-set of p2p-te type";
            leaf attribute-set-name {
              type xr:Cisco-ios-xr-string {
                length "1..64" {
                  description
                    "Specify attribute-set name (maximum 64 characters)";
                }
              }
              description
                "Attribute-set of p2p-te type";
            }
            container affinity {
              description
                "Link attributes for links traversed by tunnel";
              leaf affinity-attribute {
                type uint32 {
                  range "0..4294967295" {
                    description
                      "Affinity value";
                  }
                }
                description
                  "Link attributes for links traversed by tunnel";
              }
              leaf mask {
                type uint32 {
                  range "0..4294967295" {
                    description
                      "Affinity mask value";
                  }
                }
                description
                  "Affinity mask value";
              }
              container includes {
                description
                  "Links with all these attributes are included in path calculation";
                list include1 {
                  key "name1";
                  description
                    "Links with all these attributes are included in path calculation";
                  leaf name1 {
                    type xr:Cisco-ios-xr-string {
                      length "1..32" {
                        description
                          "Attribute or affinity name";
                      }
                    }
                    description
                      "Attribute or affinity name";
                  }
                }
                list include2 {
                  key "name1 name2";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                }
                list include3 {
                  key "name1 name2 name3";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                }
                list include4 {
                  key "name1 name2 name3 name4";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                }
                list include5 {
                  key "name1 name2 name3 name4 name5";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                }
                list include6 {
                  key "name1 name2 name3 name4 name5 name6";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                  leaf name6 {
                    type xr:Cisco-ios-xr-string {
                      length "1..32" {
                        description
                          "Attribute or affinity name";
                      }
                    }
                    description
                      "Attribute or affinity name";
                  }
                }
                list include7 {
                  key "name1 name2 name3 name4 name5 name6 name7";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                  leaf name6 {
                    type xr:Cisco-ios-xr-string {
                      length "1..32" {
                        description
                          "Attribute or affinity name";
                      }
                    }
                    description
                      "Attribute or affinity name";
                  }
                  leaf name7 {
                    type xr:Cisco-ios-xr-string {
                      length "1..32" {
                        description
                          "Attribute or affinity name";
                      }
                    }
                    description
                      "Attribute or affinity name";
                  }
                }
                list include8 {
                  key "name1 name2 name3 name4 name5 name6 name7 name8";
                  description
                    "Links with all these attributes are included in path calculation";
                  leaf name1 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                  leaf name6 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name7 {
                    type xr:Cisco-ios-xr-string {
                      length "1..32" {
                        description
                          "Attribute or affinity name";
                      }
                    }
                    description
                      "Attribute or affinity name";
                  }
                  leaf name8 {
                    type xr:Cisco-ios-xr-string {
                      length "1..32" {
                        description
                          "Attribute or affinity name";
                      }
                    }
                    description
                      "Attribute or affinity name";
                  }
                }
                list include9 {
                  key "name1 name2 name3 name4 name5 name6 name7 name8 name9";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name7 {
                    type xr:Cisco-ios-xr-string {
                      length "1..32" {
                        description
                          "Attribute or affinity name";
                      }
                    }
                    description
                      "Attribute or affinity name";
                  }
                  leaf name8 {
                    type xr:Cisco-ios-xr-string {
                      length "1..32" {
                        description
                          "Attribute or affinity name";
                      }
                    }
                    description
                      "Attribute or affinity name";
                  }
                  leaf name6 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                  leaf name9 {
                    type xr:Cisco-ios-xr-string {
                      length "1..32" {
                        description
                          "Attribute or affinity name";
                      }
                    }
                    description
                      "Attribute or affinity name";
                  }
                }
                list include10 {
                  key "name1 name2 name3 name4 name5 name6 name7 name8 name9 name10";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                  leaf name6 {
                    type xr:Cisco-ios-xr-string {
                      length "1..32" {
                        description
                          "Attribute or affinity name";
                      }
                    }
                    description
                      "Attribute or affinity name";
                  }
                  leaf name7 {
                    type xr:Cisco-ios-xr-string {
                      length "1..32" {
                        description
                          "Attribute or affinity name";
                      }
                    }
                    description
                      "Attribute or affinity name";
                  }
                  leaf name8 {
                    type xr:Cisco-ios-xr-string {
                      length "1..32" {
                        description
                          "Attribute or affinity name";
                      }
                    }
                    description
                      "Attribute or affinity name";
                  }
                  leaf name9 {
                    type xr:Cisco-ios-xr-string {
                      length "1..32" {
                        description
                          "Attribute or affinity name";
                      }
                    }
                    description
                      "Attribute or affinity name";
                  }
                  leaf name10 {
                    type xr:Cisco-ios-xr-string {
                      length "1..32" {
                        description
                          "Attribute or affinity name";
                      }
                    }
                    description
                      "Attribute or affinity name";
                  }
                }
              }
              container include-stricts {
                description
                  "Links with exactly all these attributes are included in path calculation";
                list include1 {
                  key "name1";
                  description
                    "Links with all these attributes are included in path calculation";
                  leaf name1 {
                    type xr:Cisco-ios-xr-string {
                      length "1..32" {
                        description
                          "Attribute or affinity name";
                      }
                    }
                    description
                      "Attribute or affinity name";
                  }
                }
                list include2 {
                  key "name1 name2";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                }
                list include3 {
                  key "name1 name2 name3";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                }
                list include4 {
                  key "name1 name2 name3 name4";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                }
                list include5 {
                  key "name1 name2 name3 name4 name5";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                }
                list include6 {
                  key "name1 name2 name3 name4 name5 name6";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                  leaf name6 {
                    type xr:Cisco-ios-xr-string {
                      length "1..32" {
                        description
                          "Attribute or affinity name";
                      }
                    }
                    description
                      "Attribute or affinity name";
                  }
                }
                list include7 {
                  key "name1 name2 name3 name4 name5 name6 name7";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                  leaf name6 {
                    type xr:Cisco-ios-xr-string {
                      length "1..32" {
                        description
                          "Attribute or affinity name";
                      }
                    }
                    description
                      "Attribute or affinity name";
                  }
                  leaf name7 {
                    type xr:Cisco-ios-xr-string {
                      length "1..32" {
                        description
                          "Attribute or affinity name";
                      }
                    }
                    description
                      "Attribute or affinity name";
                  }
                }
                list include8 {
                  key "name1 name2 name3 name4 name5 name6 name7 name8";
                  description
                    "Links with all these attributes are included in path calculation";
                  leaf name1 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                  leaf name6 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name7 {
                    type xr:Cisco-ios-xr-string {
                      length "1..32" {
                        description
                          "Attribute or affinity name";
                      }
                    }
                    description
                      "Attribute or affinity name";
                  }
                  leaf name8 {
                    type xr:Cisco-ios-xr-string {
                      length "1..32" {
                        description
                          "Attribute or affinity name";
                      }
                    }
                    description
                      "Attribute or affinity name";
                  }
                }
                list include9 {
                  key "name1 name2 name3 name4 name5 name6 name7 name8 name9";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name7 {
                    type xr:Cisco-ios-xr-string {
                      length "1..32" {
                        description
                          "Attribute or affinity name";
                      }
                    }
                    description
                      "Attribute or affinity name";
                  }
                  leaf name8 {
                    type xr:Cisco-ios-xr-string {
                      length "1..32" {
                        description
                          "Attribute or affinity name";
                      }
                    }
                    description
                      "Attribute or affinity name";
                  }
                  leaf name6 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                  leaf name9 {
                    type xr:Cisco-ios-xr-string {
                      length "1..32" {
                        description
                          "Attribute or affinity name";
                      }
                    }
                    description
                      "Attribute or affinity name";
                  }
                }
                list include10 {
                  key "name1 name2 name3 name4 name5 name6 name7 name8 name9 name10";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                  leaf name6 {
                    type xr:Cisco-ios-xr-string {
                      length "1..32" {
                        description
                          "Attribute or affinity name";
                      }
                    }
                    description
                      "Attribute or affinity name";
                  }
                  leaf name7 {
                    type xr:Cisco-ios-xr-string {
                      length "1..32" {
                        description
                          "Attribute or affinity name";
                      }
                    }
                    description
                      "Attribute or affinity name";
                  }
                  leaf name8 {
                    type xr:Cisco-ios-xr-string {
                      length "1..32" {
                        description
                          "Attribute or affinity name";
                      }
                    }
                    description
                      "Attribute or affinity name";
                  }
                  leaf name9 {
                    type xr:Cisco-ios-xr-string {
                      length "1..32" {
                        description
                          "Attribute or affinity name";
                      }
                    }
                    description
                      "Attribute or affinity name";
                  }
                  leaf name10 {
                    type xr:Cisco-ios-xr-string {
                      length "1..32" {
                        description
                          "Attribute or affinity name";
                      }
                    }
                    description
                      "Attribute or affinity name";
                  }
                }
              }
              container excludes {
                description
                  "Links with all these attributes are excluded from path calculation";
                list exclude1 {
                  key "name1";
                  description
                    "Links with all these attributes are included in path calculation";
                  leaf name1 {
                    type xr:Cisco-ios-xr-string {
                      length "1..32" {
                        description
                          "Attribute or affinity name";
                      }
                    }
                    description
                      "Attribute or affinity name";
                  }
                }
                list exclude2 {
                  key "name1 name2";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                }
                list exclude3 {
                  key "name1 name2 name3";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                }
                list exclude4 {
                  key "name1 name2 name3 name4";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                }
                list exclude5 {
                  key "name1 name2 name3 name4 name5";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                }
                list exclude6 {
                  key "name1 name2 name3 name4 name5 name6";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                  leaf name6 {
                    type xr:Cisco-ios-xr-string {
                      length "1..32" {
                        description
                          "Attribute or affinity name";
                      }
                    }
                    description
                      "Attribute or affinity name";
                  }
                }
                list exclude7 {
                  key "name1 name2 name3 name4 name5 name6 name7";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                  leaf name6 {
                    type xr:Cisco-ios-xr-string {
                      length "1..32" {
                        description
                          "Attribute or affinity name";
                      }
                    }
                    description
                      "Attribute or affinity name";
                  }
                  leaf name7 {
                    type xr:Cisco-ios-xr-string {
                      length "1..32" {
                        description
                          "Attribute or affinity name";
                      }
                    }
                    description
                      "Attribute or affinity name";
                  }
                }
                list exclude8 {
                  key "name1 name2 name3 name4 name5 name6 name7 name8";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                  leaf name6 {
                    type xr:Cisco-ios-xr-string {
                      length "1..32" {
                        description
                          "Attribute or affinity name";
                      }
                    }
                    description
                      "Attribute or affinity name";
                  }
                  leaf name7 {
                    type xr:Cisco-ios-xr-string {
                      length "1..32" {
                        description
                          "Attribute or affinity name";
                      }
                    }
                    description
                      "Attribute or affinity name";
                  }
                  leaf name8 {
                    type xr:Cisco-ios-xr-string {
                      length "1..32" {
                        description
                          "Attribute or affinity name";
                      }
                    }
                    description
                      "Attribute or affinity name";
                  }
                }
                list exclude9 {
                  key "name1 name2 name3 name4 name5 name6 name7 name8 name9";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                  leaf name6 {
                    type xr:Cisco-ios-xr-string {
                      length "1..32" {
                        description
                          "Attribute or affinity name";
                      }
                    }
                    description
                      "Attribute or affinity name";
                  }
                  leaf name7 {
                    type xr:Cisco-ios-xr-string {
                      length "1..32" {
                        description
                          "Attribute or affinity name";
                      }
                    }
                    description
                      "Attribute or affinity name";
                  }
                  leaf name8 {
                    type xr:Cisco-ios-xr-string {
                      length "1..32" {
                        description
                          "Attribute or affinity name";
                      }
                    }
                    description
                      "Attribute or affinity name";
                  }
                  leaf name9 {
                    type xr:Cisco-ios-xr-string {
                      length "1..32" {
                        description
                          "Attribute or affinity name";
                      }
                    }
                    description
                      "Attribute or affinity name";
                  }
                }
                list exclude10 {
                  key "name1 name2 name3 name4 name5 name6 name7 name8 name9 name10";
                  description
                    "Links with all these attributes are included in path calculation";
                  leaf name1 {
                    type xr:Cisco-ios-xr-string {
                      length "1..32" {
                        description
                          "Attribute or affinity name";
                      }
                    }
                    description
                      "Attribute or affinity name";
                  }
                  leaf name2 {
                    type xr:Cisco-ios-xr-string {
                      length "1..32" {
                        description
                          "Attribute or affinity name";
                      }
                    }
                    description
                      "Attribute or affinity name";
                  }
                  leaf name3 {
                    type xr:Cisco-ios-xr-string {
                      length "1..32" {
                        description
                          "Attribute or affinity name";
                      }
                    }
                    description
                      "Attribute or affinity name";
                  }
                  leaf name4 {
                    type xr:Cisco-ios-xr-string {
                      length "1..32" {
                        description
                          "Attribute or affinity name";
                      }
                    }
                    description
                      "Attribute or affinity name";
                  }
                  leaf name5 {
                    type xr:Cisco-ios-xr-string {
                      length "1..32" {
                        description
                          "Attribute or affinity name";
                      }
                    }
                    description
                      "Attribute or affinity name";
                  }
                  leaf name6 {
                    type xr:Cisco-ios-xr-string {
                      length "1..32" {
                        description
                          "Attribute or affinity name";
                      }
                    }
                    description
                      "Attribute or affinity name";
                  }
                  leaf name7 {
                    type xr:Cisco-ios-xr-string {
                      length "1..32" {
                        description
                          "Attribute or affinity name";
                      }
                    }
                    description
                      "Attribute or affinity name";
                  }
                  leaf name8 {
                    type xr:Cisco-ios-xr-string {
                      length "1..32" {
                        description
                          "Attribute or affinity name";
                      }
                    }
                    description
                      "Attribute or affinity name";
                  }
                  leaf name9 {
                    type xr:Cisco-ios-xr-string {
                      length "1..32" {
                        description
                          "Attribute or affinity name";
                      }
                    }
                    description
                      "Attribute or affinity name";
                  }
                  leaf name10 {
                    type xr:Cisco-ios-xr-string {
                      length "1..32" {
                        description
                          "Attribute or affinity name";
                      }
                    }
                    description
                      "Attribute or affinity name";
                  }
                }
              }
              container ignore {
                presence "Indicates a ignore node is configured.";
                description
                  "All links are included in path calculation regardless of attributes";
              }
              container exclude-all {
                presence "Indicates a exclude-all node is configured.";
                description
                  "Links with any attribute are excluded from path calculation";
              }
            }
            container logging {
              description
                "Per-interface logging configuration";
              container events {
                description
                  "Per-interface logging events";
                container lsp-status {
                  description
                    "Enable interface LSP state change alarms";
                  container state {
                    presence "Indicates a state node is configured.";
                    description
                      "Enable interface LSP UP/DOWN change alarms";
                  }
                  container reoptimize {
                    presence "Indicates a reoptimize node is configured.";
                    description
                      "Enable interface LSP REOPT change alarms";
                  }
                  container reoptimize-attempts {
                    presence "Indicates a reoptimize-attempts node is configured.";
                    description
                      "Enable interface LSP REOPT attempts change alarms";
                  }
                  container bw-change {
                    presence "Indicates a bw-change node is configured.";
                    description
                      "Enable interface LSP BANDWIDTH change alarms";
                  }
                  container reroute {
                    presence "Indicates a reroute node is configured.";
                    description
                      "Enable interface LSP REROUTE change alarms";
                  }
                  container insufficient-bandwidth {
                    presence "Indicates a insufficient-bandwidth node is configured.";
                    description
                      "Enable Syslog for setup/reopt failure due to bandwidth";
                  }
                }
                container pcalc-failure {
                  presence "Indicates a pcalc-failure node is configured.";
                  description
                    "Enable logging for path calculation failures";
                }
                container all {
                  presence "Indicates a all node is configured.";
                  description
                    "Enable logging for all events";
                }
              }
            }
            container path-selection {
              presence "Indicates a path-selection node is configured.";
              description
                "Specify path selection";
              container metric {
                description
                  "Metric type for path calculation";
                container igp {
                  presence "Indicates a igp node is configured.";
                  description
                    "Use IGP metric";
                }
                container te {
                  presence "Indicates a te node is configured.";
                  description
                    "Use TE metric";
                }
              }
            }
            container pce {
              presence "Indicates a pce node is configured.";
              description
                "Specify PCE Configuration";
              container disjoint-path {
                description
                  "Disjoint Path Configuration";
                leaf source {
                  type inet:ipv4-address-no-zone;
                  description
                    "Source address";
                }
                container type {
                  must "link or node or srlg";
                  presence "Indicates a type node is configured.";
                  description
                    "Disjointness type";
                  container link {
                    presence "Indicates a link node is configured.";
                    description
                      "Link Disjointness";
                  }
                  container node {
                    presence "Indicates a node node is configured.";
                    description
                      "Node Disjointness";
                  }
                  container srlg {
                    presence "Indicates a srlg node is configured.";
                    description
                      "SRLG Disjointness";
                  }
                }
                leaf group-id {
                  type uint32 {
                    range "1..4294967295" {
                      description
                        "Enter group-id";
                    }
                  }
                  description
                    "Enter group-id";
                }
              }
            }
          }
        }
        container uni-protections {
          description
            "Attribute-set to specify uni-protection type";
          list uni-protection {
            key "attribute-set-name";
            description
              "Attribute-set to specify uni-protection type";
            leaf attribute-set-name {
              type xr:Cisco-ios-xr-string {
                length "1..64" {
                  description
                    "Specify attribute-set name (maximum 32 characters)";
                }
              }
              description
                "Attribute-set to specify uni-protection type";
            }
            container lsp-flags {
              must "unprotected or reroute or reroute-no-et or oneton-et or onepluse1-uni or onepluse1-bi";
              presence "Indicates a lsp-flags node is configured.";
              description
                "End-to-end LSP recovery type";
              container unprotected {
                presence "Indicates a unprotected node is configured.";
                description
                  "end-to-end unprotected";
              }
              container reroute {
                presence "Indicates a reroute node is configured.";
                description
                  "end-to-end rerouting";
              }
              container reroute-no-et {
                presence "Indicates a reroute-no-et node is configured.";
                description
                  "end-to-end rerouting without extra traffic";
              }
              container oneton-et {
                presence "Indicates a oneton-et node is configured.";
                description
                  "1:N Protection with extra traffic";
              }
              container onepluse1-uni {
                presence "Indicates a onepluse1-uni node is configured.";
                description
                  "1+1 unidirectional protection";
              }
              container onepluse1-bi {
                presence "Indicates a onepluse1-bi node is configured.";
                description
                  "1+1 bidirectional protection";
              }
            }
            container seg-flags {
              must "unprotected or reroute or reroute-no-et or oneton-et or onepluse1-uni or onepluse1-bi";
              presence "Indicates a seg-flags node is configured.";
              description
                "Specify APS protection type";
              container unprotected {
                presence "Indicates a unprotected node is configured.";
                description
                  "end-to-end unprotected";
              }
              container reroute {
                presence "Indicates a reroute node is configured.";
                description
                  "end-to-end rerouting";
              }
              container reroute-no-et {
                presence "Indicates a reroute-no-et node is configured.";
                description
                  "end-to-end rerouting without extra traffic";
              }
              container oneton-et {
                presence "Indicates a oneton-et node is configured.";
                description
                  "1:N Protection with extra traffic";
              }
              container onepluse1-uni {
                presence "Indicates a onepluse1-uni node is configured.";
                description
                  "1+1 unidirectional protection";
              }
              container onepluse1-bi {
                presence "Indicates a onepluse1-bi node is configured.";
                description
                  "1+1 bidirectional protection";
              }
            }
            container set-in-place-bit {
              presence "Indicates a set-in-place-bit node is configured.";
              description
                "Set the inplace bit";
            }
            container set-required-bit {
              presence "Indicates a set-required-bit node is configured.";
              description
                "Set Required bit";
            }
          }
        }
      }
      container ltrace-buffer {
        description
          "MPLS Traffic Engineering LTrace buffer files";
        container multiplier {
          presence "Indicates a multiplier node is configured.";
          description
            "Ltrace buffer file size multiplier";
          leaf multiplier-factor {
            type uint32 {
              range "2..6" {
                description
                  "Multiplier factor";
              }
            }
            mandatory true;
            description
              "Ltrace buffer file size multiplier";
          }
          container event {
            presence "Indicates a event node is configured.";
            description
              "Event (Init, FO, Conn/Disc, Timer, etc.) trace buffer";
          }
          container sig {
            presence "Indicates a sig node is configured.";
            description
              "Signaling trace buffer";
          }
          container head-end {
            presence "Indicates a head-end node is configured.";
            description
              "Head-end (Path, PCALC, Tunnel config etc.) trace buffer";
          }
          container generic {
            presence "Indicates a generic node is configured.";
            description
              "Generic (Admit, FRR, Rewrite, Label, DB etc.) trace buffer";
          }
          container fsm {
            presence "Indicates a fsm node is configured.";
            description
              "Finite State Machine trace buffer";
          }
          container destroy {
            presence "Indicates a destroy node is configured.";
            description
              "Delete trace buffer";
          }
          container chkpt {
            presence "Indicates a chkpt node is configured.";
            description
              "Check Point (HA, Chkpt etc.) trace buffer";
          }
          container topology {
            presence "Indicates a topology node is configured.";
            description
              "Topology (Flooding, Adjacency etc.) trace buffer";
          }
          container link {
            presence "Indicates a link node is configured.";
            description
              "Link (Interface, IM, DS-TE, BW config etc.) trace buffer";
          }
          container error {
            presence "Indicates a error node is configured.";
            description
              "Error trace buffer";
          }
          container auto-bw {
            presence "Indicates a auto-bw node is configured.";
            description
              "Auto Bandwidth trace buffer";
          }
          container default {
            presence "Indicates a default node is configured.";
            description
              "Default trace buffer";
          }
          container bselect {
            presence "Indicates a bselect node is configured.";
            description
              "Backup Selection Buffer trace";
          }
          container instrument {
            presence "Indicates a instrument node is configured.";
            description
              "Trace buffer used for code instrumentation";
          }
          container automesh {
            presence "Indicates a automesh node is configured.";
            description
              "Trace buffer used for auto-tunnel mesh";
          }
          container async-server {
            presence "Indicates a async-server node is configured.";
            description
              "Trace buffer used for TE async server";
          }
          container auto-onehop {
            presence "Indicates a auto-onehop node is configured.";
            description
              "Trace buffer used for auto-tunnel mesh onehop";
          }
          container bandwidth-accounting {
            presence "Indicates a bandwidth-accounting node is configured.";
            description
              "Trace buffer used for bandwidth-accounting";
          }
          container config {
            presence "Indicates a bandwidth-accounting node is configured.";
            description
              "Trace buffer used for config events";
          }
          container bfd {
            presence "Indicates a bfd node is configured.";
            description
              "Trace buffer used for BFD events";
          }
          container all {
            presence "Indicates a all node is configured.";
            description
              "All trace buffers";
          }
        }
      }
      container path-selection {
        description
          "MPLS Traffic Engineering Path-Selection submode";
        container loose-expansion {
          description
            "Loose ERO Hop Expansion Configuration";
          container affinity {
            description
              "Desired link attributes for links comprising tunnel";
            list class-type {
              key "type";
              description
                "Specify the class type";
              leaf type {
                type uint32 {
                  range "0..1" {
                    description
                      "Class type number";
                  }
                }
                description
                  "Specify the class type";
              }
              leaf affinity-attribute {
                type uint32 {
                  range "0..4294967295" {
                    description
                      "Affinity value";
                  }
                }
                description
                  "Desired link attributes for links comprising tunnel";
              }
              leaf mask {
                type uint32 {
                  range "0..4294967295" {
                    description
                      "Affinity mask value";
                  }
                }
                description
                  "Affinity mask value";
              }
            }
          }
          container metric {
            description
              "Metric Type for path calculation";
            list class-type {
              key "type";
              description
                "Specify the class type";
              leaf type {
                type uint32 {
                  range "0..1" {
                    description
                      "Class type number";
                  }
                }
                description
                  "Specify the class type";
              }
              container igp {
                presence "Indicates a igp node is configured.";
                description
                  "Use IGP metric";
              }
              container te {
                presence "Indicates a te node is configured.";
                description
                  "Use TE metric";
              }
              container delay {
                presence "Indicates a delay node is configured.";
                description
                  "Use delay metric";
              }
            }
          }
          container domain-match {
            presence "Indicates a domain-match node is configured.";
            description
              "Use only the IGP instance of the incoming interface";
          }
        }
        container metric {
          description
            "Metric Type Configuration";
          container igp {
            presence "Indicates a igp node is configured.";
            description
              "Use IGP metric";
          }
          container te {
            presence "Indicates a te node is configured.";
            description
              "Use TE metric";
          }
          container delay {
            presence "Indicates a delay node is configured.";
            description
              "Use delay metric";
          }
        }
        leaf cost-limit {
          type uint32 {
            range "1..4294967295" {
              description
                "Cost limit";
            }
          }
          description
            "Cost limit configuration";
        }
        leaf delay-limit {
          type uint32 {
            range "1..4294967295" {
              description
                "Delay limit in usec";
            }
          }
          description
            "Delay limit configuration";
        }
        container ignore {
          description
            "Ignore specified condition during CSPF";
          container overload {
            presence "Indicates a overload node is configured.";
            description
              "Ignore overload node during CSPF";
            container head {
              presence "Indicates a head node is configured.";
              description
                "Ignore overload node during CSPF for role head";
            }
            container mid {
              presence "Indicates a mid node is configured.";
              description
                "Ignore overload node during CSPF for role mid";
            }
            container tail {
              presence "Indicates a tail node is configured.";
              description
                "Ignore overload node during CSPF for role tail";
            }
          }
        }
        container tiebreaker {
          description
            "Equal cost multipath tiebreaker for path calculation (default: min-fill).";
          container min-fill {
            presence "Indicates a min-fill node is configured.";
            description
              "Prefer the path with the least-utilized links";
          }
          container max-fill {
            presence "Indicates a max-fill node is configured.";
            description
              "Prefer the path with the most-utilized links";
          }
          container random {
            presence "Indicates a random node is configured.";
            description
              "Prefer a path with links utilized randomly";
          }
        }
      }
      container bandwidth-accounting {
        presence "Indicates a bandwidth-accounting node is configured.";
        description
          "MPLS Traffic Engineering Bandwidth Accounting submode";
        leaf sampling-interval {
          type uint32 {
            range "10..600" {
              description
                "Set the frequency of collecting bandwidth rate samples in seconds (default 60 sec)";
            }
          }
          description
            "Configure bandwidth accounting sampling interval";
        }
        leaf adjustment-factor {
          type uint32 {
            range "0..200" {
              description
                "Set the percentage adjustment of bandwidth (default 100%)";
            }
          }
          description
            "Configure bandwidth accounting adjustment factor";
        }
        container flooding {
          description
            "Configure bandwidth accounting flooding";
          container threshold {
            description
              "Configure bandwidth accounting flooding thresholds";
            leaf up {
              type uint32 {
                range "0..100" {
                  description
                    "Upward flooding threshold as percentage of maximum reservable bandwidth change (default 10%)";
                }
              }
              description
                "Upward flooding threshold for maximum reservable bandwidth";
            }
            leaf down {
              type uint32 {
                range "0..100" {
                  description
                    "Downward flooding threshold as percentage of maximum reservable bandwidth change (default 10%)";
                }
              }
              description
                "Downward flooding threshold for maximum reservable bandwidth";
            }
          }
        }
        container collection {
          description
            "Configure bandwidth accounting traffic sample collection type";
          container rsvp-te {
            presence "Indicates a rsvp-te node is configured.";
            description
              "Collect RSVP-TE traffic samples (default Segment-Routing)";
          }
        }
        container application {
          description
            "Configure bandwidth accounting application";
          container enforced {
            presence "Indicates a enforced node is configured.";
            description
              "Enforce application of bandwidth accounting";
          }
          leaf interval {
            type uint32 {
              range "30..1800" {
                description
                  "Set the frequency of application in seconds (default 180 sec)";
              }
            }
            description
              "Configure application interval";
          }
        }
      }
    }
  }
}
