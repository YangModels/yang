module Cisco-IOS-XR-aaa-tacacs-oper {
  namespace "http://cisco.com/ns/yang/Cisco-IOS-XR-aaa-tacacs-oper";
  prefix aaa-tacacs-oper;

  import cisco-semver {
    prefix semver;
  }
  import Cisco-IOS-XR-aaa-locald-oper {
    prefix a1;
  }
  include Cisco-IOS-XR-aaa-tacacs-oper-sub1 {
    revision-date 2021-10-01;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR aaa-tacacs package operational data.
     
     This YANG module augments the
       Cisco-IOS-XR-aaa-locald-oper
     module with state data.
     
     Copyright (c) 2013-2021 by Cisco Systems, Inc.
     All rights reserved.";

  revision 2021-10-01 {
    description
      "Support to print IPv6 address in operational data.";
    semver:module-version "1.2.0";
  }
  revision 2021-01-06 {
    description
      "Added last-contact-attempt entry in show tacacs.";
    semver:module-version "1.2.0";
  }
  revision 2019-04-05 {
    description
      "Establish semantic version baseline.";
    semver:module-version "1.1.0";
  }
  revision 2015-11-09 {
    description
      "IOS XR 6.0 revision.";
  }

  augment "/a1:aaa" {
    description
      "This augment extends the operational data of
       'Cisco-IOS-XR-aaa-locald-oper'";
    container tacacs {
      description
        "TACACS operational data";
      container requests {
        description
          "TACACS Active Request List";
        uses TACACS-REQUESTS;
      }
      container servers {
        description
          "TACACS server Information";
        uses TACACS-SERVERS;
      }
      container server-groups {
        description
          "TACACS sg Information";
        uses TACACS-SERVER-GROUPS;
      }
    }
  }
}
