module Cisco-IOS-XR-um-mibs-fabric-cfg {
  namespace "http://cisco.com/ns/yang/Cisco-IOS-XR-um-mibs-fabric-cfg";
  prefix um-mibs-fabric-cfg;

  import Cisco-IOS-XR-um-snmp-server-cfg {
    prefix a1;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR mibs-fabric package configuration.
     
     This YANG module augments the
     modules with configuration data.
     
     Copyright (c) 2020-2022 by Cisco Systems, Inc.
     All rights reserved.";

  revision 2022-07-11 {
    description
      "Added missing description statement to nodes";
    semver:module-version "1.0.0";
  }
  revision 2020-06-26 {
    description
      "Initial release";
    semver:module-version "1.0.0";
  }

  augment "/a1:snmp-server/a1:traps" {
    description
      "This augment extends snmp-server traps nodes
       configuration";
    container fabric {
      description
        "Enable SNMP fabric traps";
      container plane {
        presence "Indicates a plane node is configured.";
        description
          "Enable SNMP fabric plane state change traps";
      }
      container bundle {
        description
          "Enable SNMP fabric bundle traps";
        container state {
          presence "Indicates a state node is configured.";
          description
            "Enable SNMP fabric bundle state change traps";
        }
        container link {
          presence "Indicates a link node is configured.";
          description
            "Enable SNMP fabric bundle downed link traps";
        }
      }
    }
  }
}
