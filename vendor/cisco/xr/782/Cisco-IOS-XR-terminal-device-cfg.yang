module Cisco-IOS-XR-terminal-device-cfg {
  namespace "http://cisco.com/ns/yang/Cisco-IOS-XR-terminal-device-cfg";
  prefix terminal-device-cfg;

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR terminal-device package configuration.
     
     This module contains definitions
     for the following management objects:
       transceivers: Transceivers in mxp
       logical-channels: Logical channel in mxp
       optical-channels: Optical Channel
     
     Copyright (c) 2013-2022 by Cisco Systems, Inc.
     All rights reserved.";

  revision 2022-05-06 {
    description
      "Interface name support removed, not required.
       2021-10-22
         Interface name support added";
    semver:module-version "2.1.0";
  }
  revision 2021-05-20 {
    description
      "Oduflex support for CBR and GFP added";
    semver:module-version "2.0.0";
  }
  revision 2020-05-20 {
    description
      "Logical channel index changed from 65536 to 100000
       2020-03-05
           Ethernet client-als,als-delay and fec-mode support added";
    semver:module-version "1.2.0";
  }
  revision 2019-04-05 {
    description
      "Establish semantic version baseline.";
    semver:module-version "1.1.0";
  }
  revision 2015-11-09 {
    description
      "IOS XR 6.0 revision.";
  }

  typedef Logical-channel-otn-tti-auto {
    type enumeration {
      enum "false" {
        value 0;
        description
          "Otn tti auto mode false";
      }
      enum "true" {
        value 1;
        description
          "Otn tti auto mode true";
      }
    }
    description
      "Logical channel otn tti auto";
  }

  typedef Logical-admin-state {
    type enumeration {
      enum "enable" {
        value 1;
        description
          "Enable";
      }
      enum "disable" {
        value 2;
        description
          "Disable";
      }
      enum "maintenance" {
        value 3;
        description
          "Maintenance";
      }
    }
    description
      "Logical admin state";
  }

  typedef Logical-loopback-mode {
    type enumeration {
      enum "none" {
        value 0;
        description
          "None";
      }
      enum "facility" {
        value 1;
        description
          "Facility";
      }
      enum "terminal" {
        value 2;
        description
          "Terminal";
      }
    }
    description
      "Logical loopback mode";
  }

  typedef Logical-trib-rate {
    type enumeration {
      enum "trib-rate1g" {
        value 1;
        description
          "TribRate1G";
      }
      enum "trib-rate2-5g" {
        value 2;
        description
          "TribRate25G";
      }
      enum "trib-rate10g" {
        value 3;
        description
          "TribRate10G";
      }
      enum "trib-rate40g" {
        value 4;
        description
          "TribRate40G";
      }
      enum "trib-rate100g" {
        value 5;
        description
          "TribRate100G";
      }
      enum "trib-rate150g" {
        value 6;
        description
          "TribRate150G";
      }
      enum "trib-rate200g" {
        value 7;
        description
          "TribRate200G";
      }
      enum "trib-rate250g" {
        value 8;
        description
          "TribRate250G";
      }
      enum "trib-rate300g" {
        value 9;
        description
          "TribRate300G";
      }
      enum "trib-rate400g" {
        value 10;
        description
          "TribRate400G";
      }
      enum "trib-rate500g" {
        value 11;
        description
          "TribRate500G";
      }
      enum "trib-rate600g" {
        value 12;
        description
          "TribRate600G";
      }
      enum "trib-rate700g" {
        value 13;
        description
          "TribRate700G";
      }
      enum "trib-rate800g" {
        value 14;
        description
          "TribRate800G";
      }
      enum "trib-rate900g" {
        value 15;
        description
          "TribRate900G";
      }
      enum "trib-rate1000g" {
        value 16;
        description
          "TribRate1000G";
      }
      enum "trib-rate1100g" {
        value 17;
        description
          "TribRate1100G";
      }
    }
    description
      "Logical trib rate";
  }

  typedef Logical-trib-protocol {
    type enumeration {
      enum "trib-proto-type1ge" {
        value 1;
        description
          "1G Ethernet protocol";
      }
      enum "trib-proto-type-oc48" {
        value 2;
        description
          "OC48 protocol";
      }
      enum "trib-proto-type-stm16" {
        value 3;
        description
          "STM 16 protocol";
      }
      enum "trib-proto-type10gelan" {
        value 4;
        description
          "10G Ethernet LAN protocol";
      }
      enum "trib-proto-type10gewan" {
        value 5;
        description
          "10G Ethernet WAN protocol";
      }
      enum "trib-proto-type-oc192" {
        value 6;
        description
          "OC 192 (9.6GB) port protocol";
      }
      enum "trib-proto-type-stm64" {
        value 7;
        description
          "STM 64 protocol";
      }
      enum "trib-proto-type-otu2" {
        value 8;
        description
          "OTU 2 protocol";
      }
      enum "trib-proto-type-otu2e" {
        value 9;
        description
          "OTU 2e protocol";
      }
      enum "trib-proto-type-otu1e" {
        value 10;
        description
          "OTU 1e protocol";
      }
      enum "trib-proto-type-odu2" {
        value 11;
        description
          "ODU 2 protocol";
      }
      enum "trib-proto-type-odu2e" {
        value 12;
        description
          "ODU 2e protocol";
      }
      enum "trib-proto-type40ge" {
        value 13;
        description
          "40G Ethernet port protocol";
      }
      enum "trib-proto-type-oc768" {
        value 14;
        description
          "OC 768 protocol";
      }
      enum "trib-proto-type-stm256" {
        value 15;
        description
          "STM 256 protocol";
      }
      enum "trib-proto-type-otu3" {
        value 16;
        description
          "OTU 3 protocol";
      }
      enum "trib-proto-type-odu3" {
        value 17;
        description
          "ODU 3 protocol";
      }
      enum "trib-proto-type100ge" {
        value 18;
        description
          "100G Ethernet protocol";
      }
      enum "trib-proto-type100g-mlg" {
        value 19;
        description
          "100G MLG protocol";
      }
      enum "trib-proto-type-otu4" {
        value 20;
        description
          "OTU4 signal protocol (112G) for transporting
           100GE signal";
      }
      enum "trib-proto-type-otu-cn" {
        value 21;
        description
          "OTU Cn protocol";
      }
      enum "trib-proto-type-odu4" {
        value 22;
        description
          "ODU 4 protocol";
      }
      enum "trib-proto-type-odu-cn" {
        value 23;
        description
          "ODU Cn protocol";
      }
      enum "trib-proto-type-oduflex-cbr" {
        value 24;
        description
          "ODU FLEX CBR protocol";
      }
      enum "trib-proto-type-oduflex-gfp" {
        value 25;
        description
          "ODU FLEX GFP protocol";
      }
      enum "trib-proto-type400ge" {
        value 26;
        description
          "400G Ethernet protocol";
      }
    }
    description
      "Logical trib protocol";
  }

  typedef Logical-channel-assignment {
    type enumeration {
      enum "type-logical-channel" {
        value 1;
        description
          "Type Logical channel";
      }
      enum "type-optical-channel" {
        value 2;
        description
          "Type Optical channel";
      }
    }
    description
      "Logical channel assignment";
  }

  typedef Logical-client-als {
    type enumeration {
      enum "none" {
        value 0;
        description
          "NONE";
      }
      enum "ethernet" {
        value 1;
        description
          "ETHERNET";
      }
      enum "laser-shutdown" {
        value 2;
        description
          "LASER SHUTDOWN";
      }
    }
    description
      "Logical client als";
  }

  typedef Logical-fec-mode {
    type enumeration {
      enum "fec-disabled" {
        value 0;
        description
          "FEC DISABLED";
      }
      enum "fec-enabled" {
        value 1;
        description
          "FEC ENABLED";
      }
      enum "fec-auto" {
        value 2;
        description
          "FEC AUTO";
      }
    }
    description
      "Logical fec mode";
  }

  typedef Logical-protocol {
    type enumeration {
      enum "type-ethernet" {
        value 1;
        description
          "Type Ethernet";
      }
      enum "type-otn" {
        value 2;
        description
          "Type OTN";
      }
    }
    description
      "Logical protocol";
  }

  container transceivers {
    description
      "Transceivers in mxp";
    list transceiver {
      key "ifname";
      description
        "Transceiver name";
      leaf fec-mode {
        type Logical-fec-mode;
        description
          "Configure the fec-mode ";
      }
      leaf ifname {
        type xr:Cisco-ios-xr-string;
        description
          "Transceiver Name";
      }
    }
  }
  container logical-channels {
    description
      "Logical channel in mxp";
    list channel {
      key "channel-index";
      description
        "Logical channel index";
      container ethernet {
        description
          "Ethernet Related configs for Logical channel";
        leaf client-als {
          type Logical-client-als;
          description
            "Configure the client-als";
        }
        leaf als-delay {
          type uint32;
          description
            "Configure the als-delay ";
        }
      }
      container logical-channel-assignments {
        description
          "Logical channel assignment for logical channel";
        list logical-channel-assignment {
          key "assignment-index";
          description
            "Logical Channel Assignment id";
          leaf logical-channel-id {
            type uint32 {
              range "1..100000";
            }
            description
              "Configure logical channel for this assignment";
          }
          leaf allocation {
            type uint32;
            description
              "Configure Allocation for this assignment(10,
               40 or 100G)";
          }
          leaf description {
            type string {
              length "1..255";
            }
            description
              "Configure description for this assignment";
          }
          leaf optical-channel-id {
            type string;
            description
              "Configure optical channel for this assignment";
          }
          leaf assignment-type {
            type Logical-channel-assignment;
            description
              "Type of assignment for logical channel";
          }
          leaf assignment-index {
            type uint32 {
              range "1..100000";
            }
            description
              "Logical channel assignment index";
          }
        }
      }
      container otn {
        description
          "Otn Related configs for Logical channel";
        leaf tti-msg-expected {
          type string {
            length "1..255";
          }
          description
            "Trail trace identifier (TTI) message
             expectedTrail trace identifier (TTI) message
             expected";
        }
        leaf tti-msg-auto {
          type Logical-channel-otn-tti-auto;
          description
            "Trail trace identifier (TTI) transmit message
             automatically created. If True, then setting a
             custom transmit message would be invalid.
             Trail trace identifier (TTI) transmit message
             automatically created.";
        }
        leaf tti-msg-transmit {
          type string {
            length "1..255";
          }
          description
            "Trail trace identifier (TTI) message
             transmittedTrail trace identifier (TTI)
             message transmitted";
        }
      }
      leaf trib-protocol {
        type Logical-trib-protocol;
        description
          "Protocol framing of the tributary signal";
      }
      leaf if-name {
        type xr:Cisco-ios-xr-string {
          length "1..255";
        }
        description
          "Description (Max 255 characters)";
      }
      leaf ingress-client-port {
        type xr:Interface-name;
        description
          "Configure ingress client port for this logical
           channel";
      }
      leaf loopback-mode {
        type Logical-loopback-mode;
        description
          "Configure the loopback mode ";
      }
      leaf description {
        type string {
          length "1..255";
        }
        description
          "Description (Max 255 characters)";
      }
      leaf ingress-physical-channel {
        type uint32 {
          range "1..4";
        }
        description
          "Configure ingress physical channel for this
           logical channel";
      }
      leaf rate-class {
        type Logical-trib-rate;
        description
          "Rounded bit rate of the tributary signal";
      }
      leaf admin-state {
        type Logical-admin-state;
        description
          "Configure the admin-state ";
      }
      leaf logical-channel-type {
        type Logical-protocol;
        description
          "Configure the logical-channel-type ";
      }
      leaf channel-index {
        type uint32 {
          range "1..100000";
        }
        description
          "Logical Channel Index";
      }
    }
  }
  container optical-channels {
    description
      "Optical Channel";
    list optical-channel {
      key "ifname";
      description
        "Optical Channel index";
      leaf enh-colorless-mode {
        type uint32 {
          range "1..3";
        }
        description
          "Select enhanced colorless mode";
      }
      leaf cd-min {
        type int32 {
          range "-350000..350000";
        }
        description
          "Select min chromatic dispersion (in units of
           ps/nm)";
      }
      leaf power {
        type int32 {
          range "-1900..500";
        }
        description
          "Select power level (in units of 0.01dBm)";
      }
      leaf cross-pol-gain-mode {
        type uint32 {
          range "1..15";
        }
        description
          "Select carrier phase recovery cross
           polarization gain    mode";
      }
      leaf operational-mode {
        type uint32 {
          range "1..65536";
        }
        description
          "Configure operational mode";
      }
      leaf cpr-ext-win-mode {
        type uint32 {
          range "1..9";
        }
        description
          "Select carrier phase recovery extended window
           mode";
      }
      leaf enh-sop-tol-mode {
        type uint32 {
          range "1..3";
        }
        description
          "Select enhanced SOP tolerance mode";
      }
      leaf line-port {
        type xr:Interface-name;
        description
          "Specify R/S/I/P";
      }
      leaf rx-voa-fixed-ratio {
        type int32 {
          range "-100..1700";
        }
        description
          "Receive Ratio of Optical Attenuation in 0.01
           db";
      }
      leaf frequency {
        type uint32 {
          range "186100000..196137500";
        }
        description
          "Configure optical channel frequency in Mhz";
      }
      leaf cd-low-threshold {
        type int32 {
          range "-350000..350000";
        }
        description
          "Select chromatic    dispersion low threshold(in
           units of ps/nm)";
      }
      leaf filter-roll-off-factor {
        type string {
          length "5";
        }
        description
          "RRC Filter Roll-Off factor in increments of 0.
           001";
      }
      leaf cpr-win-mode {
        type uint32 {
          range "1..4";
        }
        description
          "Select carrier phase recovery window mode";
      }
      leaf rx-voa-target-power {
        type int32 {
          range "-190..30";
        }
        description
          "Rx-voa Target Power configuration";
      }
      leaf nleq-comp-mode {
        type uint32 {
          range "1..5";
        }
        description
          "Select non linear effect compenstation mode";
      }
      leaf cross-pol-weight-mode {
        type uint32 {
          range "1..7";
        }
        description
          "Select carrier phase recovery cross
           polarization weight     mode";
      }
      leaf cd-high-threshold {
        type int32 {
          range "-350000..350000";
        }
        description
          "Select chromatic   dispersion high threshold(in
           units of ps/nm)";
      }
      leaf cd-max {
        type int32 {
          range "-350000..350000";
        }
        description
          "Select max chromatic dispersion (in units of
           ps/nm)";
      }
      leaf ifname {
        type xr:Cisco-ios-xr-string;
        description
          "Optical Channel Name";
      }
    }
  }
}
