module Cisco-IOS-XR-openconfig-isis-ext {
  yang-version 1;
  namespace "http://cisco.com/ns/yang/Cisco-IOS-XR-openconfig-isis-ext";
  prefix oc-isis-cisco-xr-ext;

  import openconfig-extensions {
    prefix oc-ext;
  }
  import openconfig-network-instance {
    prefix oc-ni;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module adds extensions to the OpenConfig ISIS model to
     provide extensions which allow index option for SR prefix sid
     configuration. It augments the existing OpenConfig ISIS
     model where required.";

  revision 2021-02-13 {
    description
      "Initial version";
    reference "0.1.0";
  }

  grouping prefix-sid-ext-info {
    description
      "perfix sid type and index value for prefix sid";
    leaf sid-type {
      type enumeration {
        enum "INDEX" {
          value 1;
          description
            "sid as an index";
        }
        enum "ABSOLUTE" {
          value 2;
          description
            "sid as an absolute label or address";
        }
      }
      description
        "sid type";
    }
    leaf sid-index {
      type uint32 {
        range "0..1048575";
      }
      description
        "Sid index value";
    }
  }

  augment "/oc-ni:network-instances/oc-ni:network-instance/oc-ni:protocols/oc-ni:protocol/oc-ni:isis/oc-ni:interfaces/oc-ni:interface/oc-ni:levels/oc-ni:level/oc-ni:afi-safi/oc-ni:af/oc-ni:segment-routing/oc-ni:prefix-sids/oc-ni:prefix-sid/oc-ni:config" {
    description
      "Add sid option and sid-index parameters to prefix-sid
       configuration hierarchy.";
    uses prefix-sid-ext-info;
  }
  augment "/oc-ni:network-instances/oc-ni:network-instance/oc-ni:protocols/oc-ni:protocol/oc-ni:isis/oc-ni:interfaces/oc-ni:interface/oc-ni:levels/oc-ni:level/oc-ni:afi-safi/oc-ni:af/oc-ni:segment-routing/oc-ni:prefix-sids/oc-ni:prefix-sid/oc-ni:state" {
    description
      "Add sid option and sid-index parameters to prefix-sid
       configuration hierarchy.";
    uses prefix-sid-ext-info;
  }
  oc-ext:openconfig-version "0.1.0";
}
