module opertest1 {
  namespace "http://www.cisco.com/panini/calvados/opertest1";
  prefix opertest1;

  import tailf-common {
    prefix tailf;
  }

  import tailf-xsd-types {
    prefix xs;
  }

  import Cisco-IOS-XR-sysadmin-types {
    prefix calvados;
  }

  organization
    "Cisco Systems Inc.";

  contact
    "conger@cisco.com";

  description
    "This module holds a sample operational data store.

     Copyright (c) 2012-2020 by Cisco Systems, Inc.
     All rights reserved.";

  revision "2016-10-12" {
    description "Unhide commands and configs. Moved to advanced-grp";
  }

  revision "2011-08-28" {
    description "Initial revision";
  }

  grouping uname-group {
    leaf system {
      type string;
      description
        "The operating system name";
    }
    leaf nodename {
      type string;
      description
        "The hostname or nodename";
    }
    leaf release {
      type string;
      description
        "The release level of the operating system implementation";
    }
    leaf version {
      type string;
      description
        "The operating system implmentation version level";
    }
    leaf machine {
      type string;
      description
        "The name of the hardware type the system is running on";
    }
    leaf all {
      type string;
      description
        "All the fields";
    }
  }

  grouping uptime-group {
    leaf curtime {
      type xs:time;
      description
        "Current time";
    }
    leaf uptime {
      type string;
      description
        "Time since boot";
    }
    leaf loadavg1min {
      type xs:float;
      description
        "Weighted Exponential One-Minute Load Average";
    }
    leaf loadavg5min {
      type xs:float;
      description
        "Weighted Exponential Five-Minute Load Average";
    }
    leaf loadavg15min {
      type xs:float;
      description
        "Weighted Exponential Fifteen-Minute Load Average";
    }
  }

  grouping w-group {
    container header-info {
      uses uptime-group;
    }
    container users {
      list user {
        key "tty";
        leaf user {
          type string;
        }
        leaf tty {
          type string;
        }
        leaf from {
          type string;
        }
        leaf login-at {
          type xs:time;
        }
        leaf idle {
          type string;
        }
        leaf jcpu {
          type string;
        }
        leaf pcpu {
          type string;
        }
        leaf what {
          type string;
        }
      }
    }
  }
  container oper {
    config false;
    leaf fred {
      type int32 {
        range "0..9";
      }
    }
    leaf barney {
      type int32 {
        range "0..9999";
      }
    }
    leaf wilma {
      type int32 {
        range "0..9999";
      }
    }
    leaf betty {
      type int32 {
        range "0..9999";
      }
    }
    list slates {
      key "slatenum";
      leaf slatenum {
        type int32 {
          range "0..999";
        }
      }
      leaf mrslate {
        type int32 {
          range "0..99999999";
        }
      }
    }
    container uname {
      uses uname-group;
    }
    container uptime {
      uses uptime-group;
    }
    container w {
      uses w-group;
    }
  }
  container actions {
    tailf:action "BamBam" {
      input {
        leaf location {
          type calvados:location-id;
          mandatory true;
        }
        leaf when {
          type string;
          mandatory true;
        }
        leaf graceful {
          type empty;
        }
      }
      output {
        leaf result {
          type string;
          mandatory true;
        }
        leaf chatty {
          type string;
        }
      }
    }
  }
}
