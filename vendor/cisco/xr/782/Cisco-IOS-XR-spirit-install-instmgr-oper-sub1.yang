submodule Cisco-IOS-XR-spirit-install-instmgr-oper-sub1 {
  belongs-to Cisco-IOS-XR-spirit-install-instmgr-oper {
    prefix Cisco-IOS-XR-spirit-install-instmgr-oper;
  }

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR spirit-install-instmgr package operational data.
     
     Copyright (c) 2013-2021 by Cisco Systems, Inc.
     All rights reserved.";

  revision 2021-12-08 {
    description
      "Add optional fields for show request cli";
    semver:module-version "3.2.0";
  }
  revision 2021-01-08 {
    description
      "Deprecating ISSU show commands in Install code as the information is already provided by the ISSU infra.";
    semver:module-version "3.1.0";
  }
  revision 2020-10-06 {
    description
      "Fixing backward compatible addition of new leafs.";
    semver:module-version "3.0.0";
  }
  revision 2020-03-03 {
    description
      "Fixing schema-describe support.
       2019-06-28
         Common yang action model between lindt and eXR install.";
    semver:module-version "2.1.0";
  }
  revision 2019-04-05 {
    description
      "Establish semantic version baseline.";
    semver:module-version "2.0.0";
  }
  revision 2018-11-29 {
    description
      "Structured the yang response for show CLIs.";
  }
  revision 2018-08-24 {
    description
      "Changed model structure for software version and deprecated img-info node.";
  }
  revision 2017-09-07 {
    description
      "Fixed type translation error.";
  }
  revision 2017-07-24 {
    description
      "Fixing backward compatibility error in module.";
  }
  revision 2015-11-09 {
    description
      "IOS XR 6.0 revision.";
  }

  typedef Inst-req-state {
    type enumeration {
      enum "in-progress" {
        value 0;
        description
          "In progress";
      }
      enum "success" {
        value 1;
        description
          "Success";
      }
      enum "failure" {
        value 2;
        description
          "Failure";
      }
    }
    description
      "Install request state type";
  }

  typedef Inst-fp-request-status {
    type enumeration {
      enum "generation-up-to-date" {
        value 0;
        description
          "Runtime fingerprint generation up to date.";
      }
      enum "generation-in-progress" {
        value 1;
        description
          "Runtime fingerprint generation in progress";
      }
      enum "to-be-regenerated-at-apply" {
        value 2;
        description
          "Runtime fingerprints will be regenerated on
           apply";
      }
    }
    description
      "package Fingerprint request status";
  }

  typedef Install-opt-string {
    type string;
    description
      "Install opt string";
  }

  typedef Install-bag-optional-string {
    type string;
    description
      "Install bag optional string";
  }

  typedef Inst-state {
    type enumeration {
      enum "success" {
        value 1;
        description
          "Success";
      }
      enum "failure" {
        value 2;
        description
          "Failure";
      }
    }
    description
      "Install request state type";
  }

  grouping INST-STRING-PTR {
    description
      "inst string ptr";
    leaf package {
      type string;
      description
        "package";
    }
  }

  grouping INSTMGR-SHOW-INSTALL-PREPARE {
    description
      "show install prepare";
    leaf no-prepare-done {
      type string;
      description
        "NoPrepareDone";
    }
    leaf prepared-boot-image {
      type string;
      description
        "PreparedBootImage";
    }
    leaf prepared-boot-partition {
      type string;
      description
        "PreparedBootPartition";
    }
    leaf restart-type {
      type string;
      description
        "RestartType";
    }
    leaf activate-message {
      type string;
      description
        "ActivateMessage";
    }
    leaf prepare-clean-message {
      type string;
      description
        "PrepareCleanMessage";
    }
    leaf error-message {
      type string;
      description
        "ErrorMessage";
    }
    list rpm {
      description
        "rpm";
      uses INST-STRING-PTR;
    }
    list package {
      description
        "package";
      uses INST-STRING-PTR;
    }
  }

  grouping INST-ALL-PKG-TYPE {
    description
      "Information for all nodes";
    leaf node {
      type string;
      description
        "Node";
    }
    list package {
      description
        "Details of package";
      uses INST-PKG-TYPE;
    }
  }

  grouping INST-ALL-PACKAGES-BAG {
    description
      "Package result bag";
    list node {
      description
        "node name";
      uses INST-ALL-PKG-TYPE;
    }
  }

  grouping INSTMGR-SHOW-INST-LOG {
    description
      "show install log info";
    container input-packages {
      description
        "packages given when triggering the operation";
      uses PACKAGE-LIST;
    }
    container skipped-packages {
      description
        "packages skipped";
      uses PACKAGE-LIST;
    }
    leaf raw-data {
      type string;
      description
        "RawData";
    }
    leaf op-id {
      type uint32;
      description
        "OpId";
    }
    leaf action {
      type string;
      description
        "Operation triggered";
    }
    leaf status {
      type Inst-req-state;
      description
        "Status of operation";
    }
    leaf error {
      type string;
      description
        "Error";
    }
  }

  grouping INSTMGR-SHOW-INST-SUP-SUMMARY {
    description
      "show install superseded summary info";
    container packages {
      description
        "List of packages";
      uses PACKAGE-LIST-SUP;
    }
    leaf number-of-packages {
      type uint32;
      description
        "NumberOfPackages";
    }
    leaf error {
      type string;
      description
        "Error";
    }
  }

  grouping INST-REQUEST-BAG {
    description
      "Request result bag";
    leaf request {
      type string;
      description
        "The last user request";
    }
    leaf state {
      type Inst-req-state;
      description
        "The state of the last user request. Added
         telemetry event for operation state";
      xr:event-telemetry "Subscribe Telemetry Event";
    }
    leaf timestamp {
      type string;
      description
        "The time the current state was entered";
    }
    leaf error {
      type string;
      description
        "String describing the error, if any";
    }
    leaf operation-id {
      type Install-opt-string;
      description
        "Operation ID of the ongoing or  previous
         completed install operation.            Added
         telemetry event for install operation id";
      xr:event-telemetry "Subscribe Telemetry Event";
    }
    leaf warning {
      type Install-opt-string;
      description
        "String describing a warning, if any";
    }
  }

  grouping INSTMGR-REPO {
    description
      "contains packages in repository";
    container packages {
      description
        "Package in repository";
      uses PACKAGE-LIST;
    }
    leaf number-of-packages {
      type uint32;
      description
        "NumberOfPackages";
    }
  }

  grouping INSTMGR-SHOW-INST-REPO {
    description
      "show install repository info";
    container host {
      description
        "Host packages";
      uses INSTMGR-REPO;
    }
    container admin {
      description
        "Admin packages";
      uses INSTMGR-REPO;
    }
    container xr {
      description
        "XR packages";
      uses INSTMGR-REPO;
    }
    leaf error {
      type string;
      description
        "Error";
    }
  }

  grouping INST-VER-PKG-TYPE {
    description
      "Install package type";
    leaf name {
      type string;
      description
        "Name";
    }
    leaf version {
      type string;
      description
        "Version";
    }
    leaf built-by {
      type string;
      description
        "User built by";
    }
    leaf built-on {
      type string;
      description
        "Time built";
    }
    leaf workspace {
      type string;
      description
        "Workspace built in";
    }
    leaf build-host {
      type string;
      description
        "Build host";
    }
  }

  grouping INST-VERSION-BAG {
    description
      "Install version bag";
    leaf label {
      type string;
      description
        "Added telemetry event on Label field";
      xr:event-telemetry "Subscribe Telemetry Event";
    }
    leaf copyright-info {
      type string;
      description
        "Copyright information";
    }
    leaf hardware-info {
      type string;
      description
        "Hardware information";
    }
    leaf uptime {
      type string;
      description
        "System uptime";
    }
    leaf location {
      type Install-opt-string;
      description
        "Prefix for the path where packages will be
         installed";
    }
    leaf processor {
      type Install-opt-string;
      description
        "Processor";
    }
    leaf chassis-pid {
      type Install-opt-string;
      description
        "Chassis PID";
    }
    leaf chassis-description {
      type Install-opt-string;
      description
        "Chassis Unique Device Identifier description";
    }
    leaf xr-host-name {
      type Install-opt-string;
      description
        "Configured XR hostname";
    }
    leaf total-ram {
      type uint64;
      description
        "Total physical memory in GB";
    }
    list package {
      description
        "Packages";
      uses INST-VER-PKG-TYPE;
    }
  }

  grouping INST-TOP-LEVEL-PKG-TYPE {
    description
      "Install user-installable package type";
    container rpm-fingerprint {
      description
        "RPM Fingerprint at install and run time";
      uses INST-RPM-FINGER-PRINT;
    }
    leaf name {
      type string;
      description
        "Package name";
    }
    leaf architecture {
      type string;
      description
        "Architecture";
    }
    leaf version {
      type string;
      description
        "Version";
    }
    leaf release {
      type string;
      description
        "Release";
    }
    leaf epoch {
      type Install-opt-string;
      description
        "Epoch";
    }
    leaf xr-mandatory {
      type boolean;
      description
        "XR Mandatory";
    }
    leaf xr-optional {
      type boolean;
      description
        "XR Optional";
    }
    leaf gpg-key-id {
      type Install-opt-string;
      description
        "The GPG key ID at install time. A key ID of '0'
         indicates a package with no GPG signature.";
    }
  }

  grouping INST-SUMMARY-PACKAGES-BAG {
    description
      "Summary packages result bag";
    leaf xr-packages-hash {
      type string;
      description
        "Hash of XR packages";
    }
    leaf label {
      type Install-opt-string;
      description
        "Label of image";
    }
    leaf rpm-fingerprint-status {
      type Inst-fp-request-status;
      description
        "Package Fingerprint request status";
    }
    leaf rpm-fingerprint-timestamp {
      type Install-opt-string;
      description
        "Package run time fingerprint collection time";
    }
    list package {
      description
        "Added telemetry event at packages level";
      uses INST-TOP-LEVEL-PKG-TYPE;
    }
  }

  grouping INST-PACKAGES-BAG {
    description
      "Package result bag";
    leaf rpm-fingerprint-status {
      type Inst-fp-request-status;
      description
        "Package Fingerprint request status";
    }
    leaf rpm-fingerprint-timestamp {
      type Install-opt-string;
      description
        "Package run time fingerprint collection time";
    }
    leaf label {
      type Install-opt-string;
      description
        "Label of image";
    }
    leaf xr-packages-hash {
      type Install-opt-string;
      description
        "Hash of XR packages in this bag";
    }
    list package {
      description
        "Packages";
      uses INST-PKG-TYPE;
    }
  }

  grouping INSTMGR-CALV-SHOW-INST-ACT-ROW {
    description
      "calvados show install active";
    leaf error-message {
      type string;
      description
        "ErrorMessage";
    }
    leaf location {
      type string;
      description
        "Location";
    }
    leaf node-type {
      type string;
      description
        "NodeType";
    }
    leaf boot-partition-name {
      type string;
      description
        "BootPartitionName";
    }
    leaf number-of-active-packages {
      type uint32;
      description
        "NumberOfActivePackages";
    }
    leaf active-packages {
      type string;
      description
        "ActivePackages";
    }
  }

  grouping INSTMGR-CALV-SHOW-INST-ACT {
    description
      "Calvados show install active info";
    leaf label {
      type string;
      description
        "Label";
    }
    list active-package-info {
      description
        "active package info";
      uses INSTMGR-CALV-SHOW-INST-ACT-ROW;
    }
  }

  grouping INSTMGR-YANG-SHOW-INSTALL-PREPARE {
    description
      "show install prepare";
    container packages {
      description
        "prepared packages";
      uses PACKAGE-LIST;
    }
    leaf no-prepare-done {
      type string;
      description
        "NoPrepareDone";
    }
    leaf prepared-boot-image {
      type string;
      description
        "boot image name";
    }
    leaf prepared-boot-partition {
      type string;
      description
        "boot partition name";
    }
    leaf restart-type {
      type string;
      description
        "RestartType";
    }
  }

  grouping INSTMGR-CALV-SHOW-INST-COMMIT-ROW {
    description
      "calvados show install committed";
    leaf error-message {
      type string;
      description
        "ErrorMessage";
    }
    leaf location {
      type string;
      description
        "Location";
    }
    leaf node-type {
      type string;
      description
        "NodeType";
    }
    leaf boot-partition-name {
      type string;
      description
        "BootPartitionName";
    }
    leaf number-of-committed-packages {
      type uint32;
      description
        "NumberOfCommittedPackages";
    }
    leaf committed-packages {
      type string;
      description
        "CommittedPackages";
    }
  }

  grouping INSTMGR-CALV-SHOW-INST-COMMIT {
    description
      "Calvados show install commit info";
    leaf label {
      type string;
      description
        "Label";
    }
    list committed-package-info {
      description
        "committed package info";
      uses INSTMGR-CALV-SHOW-INST-COMMIT-ROW;
    }
  }

  grouping PACKAGE-LIST {
    description
      "List of packages";
    list package {
      description
        "Details of package";
      uses INST-PKG-TYPE;
    }
  }

  grouping INSTMGR-SHOW-INST-INACTIVE {
    description
      "show install inactive/inactive summary info";
    container packages {
      description
        "inactive packages";
      uses PACKAGE-LIST;
    }
    leaf number-of-packages {
      type uint32;
      description
        "NumberOfPackages";
    }
    leaf node {
      type string;
      description
        "Node";
    }
    leaf error {
      type string;
      description
        "Error";
    }
  }

  grouping INSTMGR-SHOW-INST-SUP-ROW {
    description
      "show install superseded";
    leaf error-message {
      type string;
      description
        "ErrorMessage";
    }
    leaf location {
      type string;
      description
        "Location";
    }
    leaf node-type {
      type string;
      description
        "NodeType";
    }
    leaf boot-partition-name {
      type string;
      description
        "BootPartitionName";
    }
    leaf superseded-packages {
      type string;
      description
        "SupersededPackages";
    }
    leaf number-of-packages {
      type uint32;
      description
        "NumberOfPackages";
    }
  }

  grouping INSTMGR-SHOW-INST-SUP {
    description
      " show install superseded info";
    list superseded-package-info {
      description
        "superseded package info";
      uses INSTMGR-SHOW-INST-SUP-ROW;
    }
  }

  grouping INSTMGR-SHOW-VALID-LOGID {
    description
      "show valid lod ids";
    leaf from {
      type uint32;
      description
        "From";
    }
    leaf to {
      type uint32;
      description
        "To";
    }
    leaf error {
      type string;
      description
        "Error";
    }
  }

  grouping SUPERSEDED-INFO {
    description
      "contains superseded-by details of a package";
    list package {
      description
        "Details of package";
      uses INST-PKG-TYPE;
    }
  }

  grouping INST-RPM-FINGER-PRINT {
    description
      "Install package fingerprint type";
    leaf rpm-fingerprint-install-time {
      type Install-opt-string;
      description
        "Package fingerprint at install time.";
    }
    leaf rpm-fingerprint-run-time {
      type Install-opt-string;
      description
        "Package fingerprint at run time. A runtime
         fingerprint of '0' indicates that the runtime
         fingerprint for this package has not yet been
         calculated.";
    }
  }

  grouping INST-PKG-TYPE {
    description
      "Install package type";
    container rpm-fingerprint {
      description
        "RPM Fingerprint at install and run time";
      uses INST-RPM-FINGER-PRINT;
    }
    leaf name {
      type string;
      description
        "Package name";
    }
    leaf architecture {
      type string;
      description
        "Architecture";
    }
    leaf version {
      type string;
      description
        "Version";
    }
    leaf release {
      type string;
      description
        "Release";
    }
    leaf epoch {
      type Install-opt-string;
      description
        "Epoch";
    }
    leaf gpg-key-id {
      type Install-opt-string;
      description
        "The GPG key ID at install time. A key ID of '0'
         indicates a package with no GPG signature.";
    }
  }

  grouping PACKAGE-INFO-SUP {
    description
      "List of packages";
    list package {
      description
        "superseded package";
      uses INST-PKG-TYPE;
    }
    list superseded-by {
      description
        "superseding packages";
      uses SUPERSEDED-INFO;
    }
  }

  grouping PACKAGE-LIST-SUP {
    description
      "List of packages";
    list superseded-package {
      description
        "info of packages superseded";
      uses PACKAGE-INFO-SUP;
    }
  }

  grouping INSTMGR-SHOW-INST-SUPERSEDED-ROW {
    description
      "show install superseded";
    container packages {
      description
        "Superseded packages";
      uses PACKAGE-LIST-SUP;
    }
    leaf location {
      type string;
      description
        "node location";
    }
    leaf node-type {
      type string;
      description
        "type of node";
    }
    leaf boot-partition-name {
      type string;
      description
        "name of boot partition";
    }
    leaf number-of-packages {
      type uint32;
      description
        "package count";
    }
    leaf error {
      type string;
      description
        "Error";
    }
  }

  grouping INSTMGR-SHOW-INST-SUPERSEDED {
    description
      "show install superseded info";
    list package-info {
      description
        "Superseded package info";
      uses INSTMGR-SHOW-INST-SUPERSEDED-ROW;
    }
  }

  grouping CURRENT-INSTALL-OPERATION {
    description
      "Show install request info";
    leaf curr-inst-oper {
      type string;
      description
        "CurrInstOper";
    }
    leaf status {
      type Inst-state;
      description
        "Status";
    }
    leaf request {
      type Install-bag-optional-string;
      description
        "Request";
    }
    leaf operation-id {
      type uint32;
      description
        "OperationId";
    }
    leaf error {
      type Install-bag-optional-string;
      description
        "Error";
    }
  }

  grouping INSTALL-LOG {
    description
      "Install Log";
    leaf log {
      type string;
      description
        "operation log";
    }
  }
}
