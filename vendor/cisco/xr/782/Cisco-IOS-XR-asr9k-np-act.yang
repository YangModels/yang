module Cisco-IOS-XR-asr9k-np-act {
  namespace "http://cisco.com/ns/yang/Cisco-IOS-XR-np-act.yang";
  prefix asr9k-np-act;

  import cisco-semver {
    prefix semver;
  }
  import Cisco-IOS-XR-types {
    prefix csc;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR action package configuration.
     
     Copyright (c) 2016-2021 by Cisco Systems, Inc.
     All rights reserved.";

  revision 2020-12-08 {
    description
      "IOS XR 7.3.1 revision.";
    semver:module-version "1.0.0";
  }

  rpc prm-np-clear-counters {
    description
      "Action to clear prm np debug counters";
    input {
      leaf location {
        type string;
        mandatory true;
        description
          "Location string for LC to perform clear on.";
      }
      leaf np {
        type string;
        mandatory true;
        description
          "NP to perform clear operation on. All is accepted.";
      }
    }
    csc:xr-task "system";
    csc:cli-command "clear controller np counters <np> location <location>";
  }
}
