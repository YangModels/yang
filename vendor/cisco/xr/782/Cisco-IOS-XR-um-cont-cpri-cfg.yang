module Cisco-IOS-XR-um-cont-cpri-cfg {
  namespace "http://cisco.com/ns/yang/Cisco-IOS-XR-um-cont-cpri-cfg";
  prefix um-cont-cpri-cfg;

  import Cisco-IOS-XR-um-interface-cfg {
    prefix a1;
  }
  import tailf-common {
    prefix tailf;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR cont-cpri package configuration.
     
     This YANG module augments the
     modules with configuration data.
     
     Copyright (c) 2021-2022 by Cisco Systems, Inc.
     All rights reserved.";

  revision 2022-07-11 {
    description
      "Added missing description statement to nodes
       2022-06-01
         Adjusted controller augmentation hierarchy";
    semver:module-version "1.1.0";
  }
  revision 2021-05-07 {
    description
      "Initial release";
    semver:module-version "1.0.0";
  }

  feature cpri {
    description
      "cpri";
  }

  grouping CONT-BODY {
    description
      "Grouping for controller";
    container loopback {
      when "../a1:controller-name[starts-with(text(),'CPRI')]" {
        tailf:dependency "../a1:controller-name";
      }
      if-feature "cpri";
      description
        "Configure various loopback mode";
      container line {
        must "not(../internal)";
        presence "Indicates a line node is configured.";
        description
          "CPRI Line side(external) loopback";
      }
      container internal {
        must "not(../line)";
        presence "Indicates a internal node is configured.";
        description
          "CPRI Internal loopback";
      }
    }
    container extended-loopback {
      when "../a1:controller-name[starts-with(text(),'CPRI')]" {
        tailf:dependency "../a1:controller-name";
      }
      if-feature "cpri";
      description
        "Extended loopback level and mode for diagnostics";
      leaf level {
        type uint32 {
          range "1..3" {
            description
              "";
          }
        }
        must "../enable-loopback";
        description
          "Extended loopback level and mode for diagnostics";
      }
      leaf enable-loopback {
        type enumeration {
          enum "line" {
            value 1;
            description
              "Enable line loopback";
          }
          enum "internal" {
            value 4;
            description
              "Enable internal loopback";
          }
        }
        must "../level";
        description
          "configure this node";
      }
    }
    leaf l1-startup-timer {
      when "../a1:controller-name[starts-with(text(),'CPRI')]" {
        tailf:dependency "../a1:controller-name";
      }
      if-feature "cpri";
      type uint32 {
        range "0..65536" {
          description
            "Configure L1 startup timer value";
        }
      }
      description
        "Configure L1 startup timer";
    }
    leaf attach-roe-profile {
      when "../a1:controller-name[starts-with(text(),'CPRI')]" {
        tailf:dependency "../a1:controller-name";
      }
      if-feature "cpri";
      type uint32 {
        range "1..255" {
          description
            "Configure RoE profile ID";
        }
      }
      description
        "Attach RoE profile to this controller";
    }
  }

  augment "/a1:controllers/a1:controller" {
    description
      "This augment extends active nodes configuration";
    uses CONT-BODY;
  }
  augment "/a1:controllers/a1:controller-preconfigure" {
    description
      "This augment extends preconfigured nodes
       configuration";
    uses CONT-BODY;
  }
}
