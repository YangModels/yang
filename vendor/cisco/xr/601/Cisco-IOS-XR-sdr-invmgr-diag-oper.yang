module Cisco-IOS-XR-sdr-invmgr-diag-oper {

  /*** NAMESPACE / PREFIX DEFINITION ***/

  namespace "http://cisco.com/ns/yang"+
    "/Cisco-IOS-XR-sdr-invmgr-diag-oper";


  prefix "sdr-invmgr-diag-oper";

  /*** LINKAGE (IMPORTS / INCLUDES) ***/

  import Cisco-IOS-XR-types { prefix "xr"; }

  include Cisco-IOS-XR-sdr-invmgr-diag-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR sdr-invmgr-diag package operational data.

     This module contains definitions
     for the following management objects:
       diag: Diag information

     Copyright (c) 2013-2015 by Cisco Systems, Inc.
     All rights reserved.";

  revision "2015-11-09" {
    description
      "IOS XR 6.0 revision.";
  }


  grouping INFORMATION {
    description "Common node of power-supply, fans";

    container information {
      xr:xr-xml-map "inv_diag_oper:Information";
      description "Basic information";
      uses DIAG-EEPROM;
    }
  }

  container diag {
    xr:xr-xml-map "inv_diag_oper:Diag";
    config false;
    description "Diag information";

    container racks {
      xr:xr-xml-map "inv_diag_oper:RackTable";
      description "Table of racks";

      list rack {
        xr:xr-xml-map "inv_diag_oper:Rack";
        key "rack-name";
        description "Rack name";

        container power-shelfs {
          xr:xr-xml-map "inv_diag_oper:PowerShelfTable";
          description "Table for rack power shelf ";

          list power-shelf {
            xr:xr-xml-map "inv_diag_oper:PowerShelf";
            key "power-shelf-name";
            description "Power shelf name";

            container power-supplies {
              xr:xr-xml-map "inv_diag_oper:PowerSupplyTable";
              description "Table for rack power supply ";

              list power-supply {
                xr:xr-xml-map "inv_diag_oper:PowerSupply";
                key "power-supply-name";
                description "Power Supply name";
                leaf power-supply-name {
                  xr:xr-xml-map "inv_diag_oper:PowerSupplyName";
                  type xr:Cisco-ios-xr-string;
                  description "Power Supply name";
                }
                uses INFORMATION;
              }
            }
            leaf power-shelf-name {
              xr:xr-xml-map "inv_diag_oper:PowerShelfName";
              type xr:Cisco-ios-xr-string;
              description "Power Shelf name";
            }
          }
        }

        container fan-traies {
          xr:xr-xml-map "inv_diag_oper:FanTrayTable";
          description "Table for rack fan trays";

          list fan-tray {
            xr:xr-xml-map "inv_diag_oper:FanTray";
            key "fan-tray-name";
            description "Fan tray name";

            container fanses {
              xr:xr-xml-map "inv_diag_oper:FanTable";
              description "Table for rack fans ";

              list fans {
                xr:xr-xml-map "inv_diag_oper:Fans";
                key "fans-name";
                description "Fan name";
                leaf fans-name {
                  xr:xr-xml-map "inv_diag_oper:FansName";
                  type xr:Cisco-ios-xr-string;
                  description "Fans name";
                }
                uses INFORMATION;
              }
            }
            leaf fan-tray-name {
              xr:xr-xml-map "inv_diag_oper:FanTrayName";
              type xr:Cisco-ios-xr-string;
              description "Fan tray name";
            }
          }
        }

        container slots {
          xr:xr-xml-map "inv_diag_oper:SlotTable";
          description "Table of slots";

          list slot {
            xr:xr-xml-map "inv_diag_oper:Slot";
            key "slot-name";
            description "Slot name";

            container instances {
              xr:xr-xml-map "inv_diag_oper:InstanceTable";
              description "Table of instances";

              list instance {
                xr:xr-xml-map "inv_diag_oper:Instance";
                key "name";
                description "instance number";

                container detail {
                  xr:xr-xml-map "inv_diag_oper:Detail";
                  description "Detail information";
                  uses DIAG-CARD;
                }
                leaf name {
                  xr:xr-xml-map "inv_diag_oper:Name";
                  type xr:Cisco-ios-xr-string;
                  description "Instance name";
                }
              }
            }
            leaf slot-name {
              xr:xr-xml-map "inv_diag_oper:SlotName";
              type xr:Cisco-ios-xr-string;
              description "Slot name";
            }
          }
        }

        container chassis {
          xr:xr-xml-map "inv_diag_oper:Chassis";
          description "Chassis information";
          uses DIAG-EEPROM;
        }
        leaf rack-name {
          xr:xr-xml-map "inv_diag_oper:RackName";
          type xr:Cisco-ios-xr-string;
          description "Rack name";
        }
      }
    }
  }
}
