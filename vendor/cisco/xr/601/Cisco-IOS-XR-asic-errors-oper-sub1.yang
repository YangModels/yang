submodule Cisco-IOS-XR-asic-errors-oper-sub1 {

  belongs-to Cisco-IOS-XR-asic-errors-oper {
    prefix Cisco-IOS-XR-asic-errors-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR asic-errors package operational data.

     Copyright (c) 2013-2015 by Cisco Systems, Inc.
     All rights reserved.";

  revision "2015-11-09" {
    description
      "IOS XR 6.0 revision.";
  }


  grouping CIHERR-ERROR-DATA-BG {
    description "CIHERR ERROR DATA BG";
    leaf at-time {
      xr:xr-xml-map "asic_errors_ciherr:at_time";
      type uint64;
      description "at time";
    }
    leaf at-time-nsec {
      xr:xr-xml-map "asic_errors_ciherr:at_time_nsec";
      type uint64;
      description "at time nsec";
    }
    leaf counter-val {
      xr:xr-xml-map "asic_errors_ciherr:counter_val";
      type uint32;
      description "counter val";
    }
    leaf error-desc {
      xr:xr-xml-map "asic_errors_ciherr:error_desc";
      type string;
      description "error desc";
    }
    leaf-list error-regval {
      xr:xr-xml-map "asic_errors_ciherr:error_regval";
      type uint8;
      description "error regval";
    }
  }

  grouping CSRS-INFO-BG {
    description "CSRS INFO BG";
    leaf name {
      xr:xr-xml-map "asic_errors_ciherr:name";
      type string;
      description "name";
    }
    leaf address {
      xr:xr-xml-map "asic_errors_ciherr:address";
      type uint64;
      description "address";
    }
    leaf width {
      xr:xr-xml-map "asic_errors_ciherr:width";
      type uint32;
      description "width";
    }
  }

  grouping CIHERR-NODE-BG {
    description "CIHERR NODE BG";
    leaf name {
      xr:xr-xml-map "asic_errors_ciherr:name";
      type string;
      description "Name assigned to mem";
    }
    leaf asic-info {
      xr:xr-xml-map "asic_errors_ciherr:asic_info";
      type string;
      description "Name of rack/board/asic";
    }
    leaf node-key {
      xr:xr-xml-map "asic_errors_ciherr:node_key";
      type uint32;
      description "32 bit key";
    }
    leaf alarm-on {
      xr:xr-xml-map "asic_errors_ciherr:alarm_on";
      type boolean;
      description "High threshold crossed";
    }
    leaf thresh-hi {
      xr:xr-xml-map "asic_errors_ciherr:thresh_hi";
      type uint32;
      description "High threshold value";
    }
    leaf period-hi {
      xr:xr-xml-map "asic_errors_ciherr:period_hi";
      type uint32;
      description "High period value";
    }
    leaf thresh-lo {
      xr:xr-xml-map "asic_errors_ciherr:thresh_lo";
      type uint32;
      description "High threshold value";
    }
    leaf period-lo {
      xr:xr-xml-map "asic_errors_ciherr:period_lo";
      type uint32;
      description "High period value";
    }
    leaf count {
      xr:xr-xml-map "asic_errors_ciherr:count";
      type uint32;
      description "Accumulated count";
    }
    leaf intr-type {
      xr:xr-xml-map "asic_errors_ciherr:intr_type";
      type uint32;
      description "Type of error";
    }
    leaf leaf-id {
      xr:xr-xml-map "asic_errors_ciherr:leaf_id";
      type uint32;
      description "Leaf ID defined in user data";
    }
    leaf last-cleared {
      xr:xr-xml-map "asic_errors_ciherr:last_cleared";
      type uint64;
      description "Time  cleared";
    }

    list csrs-info {
      description "List of csrs_info";
      uses CSRS-INFO-BG;
    }

    list last-err {
      description "Last Printable error information";
      uses CIHERR-ERROR-DATA-BG;
    }
  }

  grouping CIHERR-NODES-BG {
    description "CIHERR NODES BG";

    list error {
      description "Collection of errors";
      uses CIHERR-NODE-BG;
    }
  }
}
