module Cisco-IOS-XR-ipv4-vrrp-cfg {

  /*** NAMESPACE / PREFIX DEFINITION ***/

  namespace "http://cisco.com/ns/yang/Cisco-IOS-XR-ipv4-vrrp-cfg";


  prefix "ipv4-vrrp-cfg";

  /*** LINKAGE (IMPORTS / INCLUDES) ***/

  import ietf-inet-types { prefix "inet"; }

  import Cisco-IOS-XR-types { prefix "xr"; }

  import Cisco-IOS-XR-snmp-agent-cfg { prefix "a1"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ipv4-vrrp package configuration.

     This module contains definitions
     for the following management objects:
       vrrp: VRRP configuration

     This YANG module augments the
       Cisco-IOS-XR-snmp-agent-cfg
     module with configuration data.

     Copyright (c) 2013-2015 by Cisco Systems, Inc.
     All rights reserved.";

  revision "2015-11-09" {
    description
      "IOS XR 6.0 revision.";
  }


  container vrrp {
    xr:xr-xml-map "vrrp_cfg:VRRP";
    description "VRRP configuration";

    container logging {
      xr:xr-xml-map "vrrp_cfg:Logging";
      description "VRRP logging options";
      leaf state-change-disable {
        xr:xr-xml-map "vrrp_cfg:StateChangeDisable";
        xr:xr-cli-map "vrrp message state disable ";
        type empty;
        description "VRRP state change IOS messages disable";
      }
    }

    container interfaces {
      xr:xr-xml-map "vrrp_cfg:InterfaceTable";
      description "Interface configuration table";

      list interface {
        xr:xr-xml-map "vrrp_cfg:Interface";
        key "interface-name";
        description "The interface being configured";

        container ipv6 {
          xr:xr-xml-map "vrrp_ipv6_cfg:IPv6";
          description "IPv6 VRRP configuration";

          container version3 {
            xr:xr-xml-map "vrrp_ipv6_cfg:Version3";
            description "Version 3 VRRP configuration";

            container virtual-routers {
              xr:xr-xml-map "vrrp_ipv6_cfg:VirtualRouterTable";
              description
                "The VRRP virtual router configuration table";

              list virtual-router {
                xr:xr-xml-map "vrrp_ipv6_cfg:VirtualRouter";
                key "vr-id";
                description
                  "The VRRP virtual router being configured";

                container global-ipv6-addresses {
                  xr:xr-xml-map "vrrp_ipv6_cfg:GlobalIPv6AddressTab"+
                    "le";
                  description
                    "The table of VRRP virtual global IPv6
                    addresses";

                  list global-ipv6-address {
                    xr:xr-xml-map "vrrp_ipv6_cfg:GlobalIPv6Address";
                    key "ip-address";
                    description
                      "A VRRP virtual global IPv6 IP address";
                    leaf ip-address {
                      xr:xr-xml-map "vrrp_ipv6_cfg:IPAddress";
                      type inet:ip-address-no-zone;
                      description
                        "VRRP virtual global IPv6 address";
                    }
                  }
                }

                container tracks {
                  xr:xr-xml-map "vrrp_ipv6_cfg:TrackTable";
                  description
                    "Track an item, reducing priority if it
                    goes down";

                  list track {
                    xr:xr-xml-map "vrrp_ipv6_cfg:Track";
                    key "interface-name";
                    description "Object to be tracked";
                    leaf interface-name {
                      xr:xr-xml-map "vrrp_ipv6_cfg:InterfaceName";
                      type xr:Interface-name;
                      description
                        "Object to be tracked, interface name for
                        interfaces";
                    }
                    leaf priority {
                      xr:xr-xml-map "vrrp_ipv6_cfg:Priority";
                      type uint32 {
                        range "1..254";
                      }
                      mandatory true;
                      description "Priority decrement";
                    }
                  }
                }

                container timer {
                  xr:xr-xml-map "vrrp_ipv6_cfg:Timer";
                  description "Set advertisement timer";
                  leaf in-msec {
                    xr:xr-xml-map "vrrp_ipv6_cfg:InMsec";
                    type boolean;
                    default "false";
                    description
                      "TRUE - Advertise time configured in
                      milliseconds, FALSE - Advertise time
                      configured in seconds";
                  }
                  leaf advertisement-time-in-msec {
                    xr:xr-xml-map "vrrp_ipv6_cfg:AdvertisementTimeI"+
                      "nMsec";
                    when "../in-msec = 'true'" {
                      description "../InMsec = TRUE";
                    }
                    type uint32 {
                      range "100..3000";
                    }
                    units "millisecond";
                    description
                      "Advertisement time in milliseconds";
                  }
                  leaf advertisement-time-in-sec {
                    xr:xr-xml-map "vrrp_ipv6_cfg:AdvertisementTimeI"+
                      "nSec";
                    when "../in-msec != 'true'" {
                      description "../InMsec != TRUE";
                    }
                    type uint32 {
                      range "1..40";
                    }
                    units "second";
                    description "Advertisement time in seconds";
                  }
                  leaf forced {
                    xr:xr-xml-map "vrrp_ipv6_cfg:Forced";
                    when "../in-msec = 'true' or ../in-msec ="+
                      " 'false'" {
                        description
                          "../InMsec = TRUE or ../InMsec = FALSE";
                    }
                    type boolean;
                    default "false";
                    description
                      "TRUE - Force configured timer values to
                      be used, required when configured in
                      milliseconds";
                  }
                }

                container tracked-objects {
                  xr:xr-xml-map "vrrp_ipv6_cfg:TrackedObjectTable";
                  description
                    "Track an object, reducing priority if it
                    goes down";

                  list tracked-object {
                    xr:xr-xml-map "vrrp_ipv6_cfg:TrackedObject";
                    key "object-name";
                    description "Object to be tracked";
                    leaf object-name {
                      xr:xr-xml-map "vrrp_ipv6_cfg:ObjectName";
                      type xr:Cisco-ios-xr-string;
                      description
                        "Object to be tracked, interface name for
                        interfaces";
                    }
                    leaf priority-decrement {
                      xr:xr-xml-map "vrrp_ipv6_cfg:PriorityDecremen"+
                        "t";
                      type uint32 {
                        range "1..254";
                      }
                      mandatory true;
                      description "Priority decrement";
                    }
                  }
                }

                container link-local-ipv6-address {
                  xr:xr-xml-map "vrrp_ipv6_cfg:LinkLocalIPv6Address";
                  description
                    "The VRRP IPv6 virtual linklocal address";
                  leaf ip-address {
                    xr:xr-xml-map "vrrp_ipv6_cfg:IPAddress";
                    when "../auto-configure = 0" {
                      description "../AutoConfigure = <expr>";
                    }
                    type inet:ip-address-no-zone;
                    description
                      "VRRP IPv6 virtual linklocal address";
                  }
                  leaf auto-configure {
                    xr:xr-xml-map "vrrp_ipv6_cfg:AutoConfigure";
                    type boolean;
                    default "false";
                    description
                      "TRUE if the virtual linklocal address is
                      to be autoconfigured FALSE if an IPv6
                      virtual linklocal address is configured";
                  }
                }
                leaf bfd {
                  xr:xr-xml-map "vrrp_ipv6_cfg:BFD";
                  type inet:ip-address-no-zone;
                  description
                    "Enable use of Bidirectional Forwarding
                    Detection for this IP";
                }
                leaf priority {
                  xr:xr-xml-map "vrrp_ipv6_cfg:Priority";
                  type uint32 {
                    range "1..254";
                  }
                  default "100";
                  description "Priority value";
                }
                leaf accept-mode-disable {
                  xr:xr-xml-map "vrrp_ipv6_cfg:AcceptModeDisable";
                  type empty;
                  description
                    "Disable Accept Mode for this virtual
                    IPAddress";
                }
                leaf preempt {
                  xr:xr-xml-map "vrrp_ipv6_cfg:Preempt";
                  type uint32 {
                    range "0..3600";
                  }
                  default "0";
                  description
                    "Preempt Master router if higher priority";
                }
                leaf session-name {
                  xr:xr-xml-map "vrrp_ipv6_cfg:SessionName";
                  type xr:Cisco-ios-xr-string {
                    length "0..16";
                  }
                  description "VRRP Session Name";
                }
                leaf vr-id {
                  xr:xr-xml-map "vrrp_ipv6_cfg:VR_ID";
                  type uint32 {
                    range "1..255";
                  }
                  description "VRID Virtual Router Identifier";
                }
              }
            }
          }

          container slave-virtual-routers {
            xr:xr-xml-map "vrrp_slave_ipv6_cfg:SlaveVirtualRouterTa"+
              "ble";
            description "The VRRP slave group configuration table";

            list slave-virtual-router {
              xr:xr-xml-map "vrrp_slave_ipv6_cfg:SlaveVirtualRouter";
              key "slave-virtual-router-id";
              description "The VRRP slave being configured";

              container link-local-ipv6-address {
                xr:xr-xml-map "vrrp_slave_ipv6_cfg:LinkLocalIPv6Add"+
                  "ress";
                description
                  "The VRRP IPv6 virtual linklocal address";
                leaf ip-address {
                  xr:xr-xml-map "vrrp_slave_ipv6_cfg:IPAddress";
                  when "../auto-configure = 0" {
                    description "../AutoConfigure = <expr>";
                  }
                  type inet:ip-address-no-zone;
                  description "VRRP IPv6 virtual linklocal address";
                }
                leaf auto-configure {
                  xr:xr-xml-map "vrrp_slave_ipv6_cfg:AutoConfigure";
                  type boolean;
                  default "false";
                  description
                    "TRUE if the virtual linklocal address is
                    to be autoconfigured FALSE if an IPv6
                    virtual linklocal address is configured";
                }
              }

              container global-ipv6-addresses {
                xr:xr-xml-map "vrrp_slave_ipv6_cfg:GlobalIPv6Addres"+
                  "sTable";
                description
                  "The table of VRRP virtual global IPv6
                  addresses";

                list global-ipv6-address {
                  xr:xr-xml-map "vrrp_slave_ipv6_cfg:GlobalIPv6Addr"+
                    "ess";
                  key "ip-address";
                  description
                    "A VRRP virtual global IPv6 IP address";
                  leaf ip-address {
                    xr:xr-xml-map "vrrp_slave_ipv6_cfg:IPAddress";
                    type inet:ip-address-no-zone;
                    description "VRRP virtual global IPv6 address";
                  }
                }
              }
              leaf follow {
                xr:xr-xml-map "vrrp_slave_ipv6_cfg:Follow";
                type string;
                description
                  "VRRP Session name for this slave to follow";
              }
              leaf accept-mode-disable {
                xr:xr-xml-map "vrrp_slave_ipv6_cfg:AcceptModeDisabl"+
                  "e";
                type empty;
                description
                  "Disable Accept Mode for this virtual
                  IPAddress";
              }
              leaf slave-virtual-router-id {
                xr:xr-xml-map "vrrp_slave_ipv6_cfg:SlaveVirtualRout"+
                  "erID";
                type uint32 {
                  range "1..255";
                }
                description "Virtual Router ID";
              }
            }
          }
        }

        container delay {
          xr:xr-xml-map "vrrp_cfg:Delay";
          description "Minimum and Reload Delay";
          leaf min-delay {
            xr:xr-xml-map "vrrp_cfg:MinDelay";
            type uint32 {
              range "0..10000";
            }
            units "second";
            description "Minimum delay in seconds";
          }
          leaf reload-delay {
            xr:xr-xml-map "vrrp_cfg:ReloadDelay";
            type uint32 {
              range "0..10000";
            }
            units "second";
            description "Reload delay in seconds";
          }
        }

        container ipv4 {
          xr:xr-xml-map "vrrp_cfg:IPv4";
          description "IPv4 VRRP configuration";

          container version3 {
            xr:xr-xml-map "vrrp_ipv4_v3_cfg:Version3";
            description "Version 3 VRRP configuration";

            container virtual-routers {
              xr:xr-xml-map "vrrp_ipv4_v3_cfg:VirtualRouterTable";
              description
                "The VRRP virtual router configuration table";

              list virtual-router {
                xr:xr-xml-map "vrrp_ipv4_v3_cfg:VirtualRouter";
                key "vr-id";
                description
                  "The VRRP virtual router being configured";

                container timer {
                  xr:xr-xml-map "vrrp_ipv4_v3_cfg:Timer";
                  description "Set advertisement timer";
                  leaf in-msec {
                    xr:xr-xml-map "vrrp_ipv4_v3_cfg:InMsec";
                    type boolean;
                    default "false";
                    description
                      "TRUE - Advertise time configured in
                      milliseconds, FALSE - Advertise time
                      configured in seconds";
                  }
                  leaf advertisement-time-in-msec {
                    xr:xr-xml-map "vrrp_ipv4_v3_cfg:AdvertisementTi"+
                      "meInMsec";
                    when "../in-msec = 'true'" {
                      description "../InMsec = TRUE";
                    }
                    type uint32 {
                      range "100..3000";
                    }
                    units "millisecond";
                    description
                      "Advertisement time in milliseconds";
                  }
                  leaf advertisement-time-in-sec {
                    xr:xr-xml-map "vrrp_ipv4_v3_cfg:AdvertisementTi"+
                      "meInSec";
                    when "../in-msec != 'true'" {
                      description "../InMsec != TRUE";
                    }
                    type uint32 {
                      range "1..40";
                    }
                    units "second";
                    description "Advertisement time in seconds";
                  }
                  leaf forced {
                    xr:xr-xml-map "vrrp_ipv4_v3_cfg:Forced";
                    when "../in-msec = 'true' or ../in-msec ="+
                      " 'false'" {
                        description
                          "../InMsec = TRUE or ../InMsec = FALSE";
                    }
                    type boolean;
                    default "false";
                    description
                      "TRUE - Force configured timer values to
                      be used, required when configured in
                      milliseconds";
                  }
                }

                container secondary-ipv4-addresses {
                  xr:xr-xml-map "vrrp_ipv4_v3_cfg:SecondaryIPv4Addr"+
                    "essTable";
                  description
                    "The table of VRRP secondary IPv4 addresses";

                  list secondary-ipv4-address {
                    xr:xr-xml-map "vrrp_ipv4_v3_cfg:SecondaryIPv4Ad"+
                      "dress";
                    key "ip-address";
                    description "A VRRP secondary IPv4 address";
                    leaf ip-address {
                      xr:xr-xml-map "vrrp_ipv4_v3_cfg:IPAddress";
                      type inet:ipv4-address-no-zone;
                      description "VRRP Secondary IPv4 address";
                    }
                  }
                }

                container tracked-objects {
                  xr:xr-xml-map "vrrp_ipv4_v3_cfg:TrackedObjectTabl"+
                    "e";
                  description
                    "Track an object, reducing priority if it
                    goes down";

                  list tracked-object {
                    xr:xr-xml-map "vrrp_ipv4_v3_cfg:TrackedObject";
                    key "object-name";
                    description "Object to be tracked";
                    leaf object-name {
                      xr:xr-xml-map "vrrp_ipv4_v3_cfg:ObjectName";
                      type xr:Cisco-ios-xr-string;
                      description
                        "Object to be tracked, interface name for
                        interfaces";
                    }
                    leaf priority-decrement {
                      xr:xr-xml-map "vrrp_ipv4_v3_cfg:PriorityDecre"+
                        "ment";
                      type uint32 {
                        range "1..254";
                      }
                      mandatory true;
                      description "Priority decrement";
                    }
                  }
                }

                container tracks {
                  xr:xr-xml-map "vrrp_ipv4_v3_cfg:TrackTable";
                  description
                    "Track an item, reducing priority if it
                    goes down";

                  list track {
                    xr:xr-xml-map "vrrp_ipv4_v3_cfg:Track";
                    key "interface-name";
                    description "Object to be tracked";
                    leaf interface-name {
                      xr:xr-xml-map "vrrp_ipv4_v3_cfg:InterfaceName";
                      type xr:Interface-name;
                      description
                        "Object to be tracked, interface name for
                        interfaces";
                    }
                    leaf priority {
                      xr:xr-xml-map "vrrp_ipv4_v3_cfg:Priority";
                      type uint32 {
                        range "1..254";
                      }
                      mandatory true;
                      description "Priority decrement";
                    }
                  }
                }
                leaf session-name {
                  xr:xr-xml-map "vrrp_ipv4_v3_cfg:SessionName";
                  type xr:Cisco-ios-xr-string {
                    length "0..16";
                  }
                  description "VRRP Session Name";
                }
                leaf bfd {
                  xr:xr-xml-map "vrrp_ipv4_v3_cfg:BFD";
                  type inet:ipv4-address-no-zone;
                  description
                    "Enable use of Bidirectional Forwarding
                    Detection for this IP";
                }
                leaf primary-ipv4-address {
                  xr:xr-xml-map "vrrp_ipv4_v3_cfg:PrimaryIPv4Addres"+
                    "s";
                  type inet:ipv4-address-no-zone;
                  description "The Primary VRRP IPv4 address";
                }
                leaf preempt {
                  xr:xr-xml-map "vrrp_ipv4_v3_cfg:Preempt";
                  type uint32 {
                    range "0..3600";
                  }
                  default "0";
                  description
                    "Preempt Master router if higher priority";
                }
                leaf accept-mode-disable {
                  xr:xr-xml-map "vrrp_ipv4_v3_cfg:AcceptModeDisable";
                  type empty;
                  description
                    "Disable Accept Mode for this virtual
                    IPAddress";
                }
                leaf priority {
                  xr:xr-xml-map "vrrp_ipv4_v3_cfg:Priority";
                  type uint32 {
                    range "1..254";
                  }
                  default "100";
                  description "Priority value";
                }
                leaf vr-id {
                  xr:xr-xml-map "vrrp_ipv4_v3_cfg:VR_ID";
                  type uint32 {
                    range "1..255";
                  }
                  description "VRID Virtual Router Identifier";
                }
              }
            }
          }

          container slave-virtual-routers {
            xr:xr-xml-map "vrrp_slave_ipv4_cfg:SlaveVirtualRouterTa"+
              "ble";
            description "The VRRP slave group configuration table";

            list slave-virtual-router {
              xr:xr-xml-map "vrrp_slave_ipv4_cfg:SlaveVirtualRouter";
              key "slave-virtual-router-id";
              description "The VRRP slave being configured";

              container secondary-ipv4-addresses {
                xr:xr-xml-map "vrrp_slave_ipv4_cfg:SecondaryIPv4Add"+
                  "ressTable";
                description
                  "The table of VRRP secondary IPv4 addresses";

                list secondary-ipv4-address {
                  xr:xr-xml-map "vrrp_slave_ipv4_cfg:SecondaryIPv4A"+
                    "ddress";
                  key "ip-address";
                  description "A VRRP secondary IPv4 address";
                  leaf ip-address {
                    xr:xr-xml-map "vrrp_slave_ipv4_cfg:IPAddress";
                    type inet:ipv4-address-no-zone;
                    description "VRRP Secondary IPv4 address";
                  }
                }
              }
              leaf follow {
                xr:xr-xml-map "vrrp_slave_ipv4_cfg:Follow";
                type string;
                description
                  "VRRP Session name for this slave to follow";
              }
              leaf accept-mode-disable {
                xr:xr-xml-map "vrrp_slave_ipv4_cfg:AcceptModeDisabl"+
                  "e";
                type empty;
                description
                  "Disable Accept Mode for this virtual
                  IPAddress";
              }
              leaf primary-ipv4-address {
                xr:xr-xml-map "vrrp_slave_ipv4_cfg:PrimaryIPv4Addre"+
                  "ss";
                type inet:ipv4-address-no-zone;
                description "The Primary VRRP IPv4 address";
              }
              leaf slave-virtual-router-id {
                xr:xr-xml-map "vrrp_slave_ipv4_cfg:SlaveVirtualRout"+
                  "erID";
                type uint32 {
                  range "1..255";
                }
                description "Virtual Router ID";
              }
            }
          }

          container version2 {
            xr:xr-xml-map "vrrp_cfg:Version2";
            description "Version 2 VRRP configuration";

            container virtual-routers {
              xr:xr-xml-map "vrrp_cfg:VirtualRouterTable";
              description
                "The VRRP virtual router configuration table";

              list virtual-router {
                xr:xr-xml-map "vrrp_cfg:VirtualRouter";
                key "vr-id";
                description
                  "The VRRP virtual router being configured";

                container timer {
                  xr:xr-xml-map "vrrp_cfg:Timer";
                  description "Set advertisement timer";
                  leaf in-msec {
                    xr:xr-xml-map "vrrp_cfg:InMsec";
                    type boolean;
                    default "false";
                    description
                      "TRUE - Advertise time configured in
                      milliseconds, FALSE - Advertise time
                      configured in seconds";
                  }
                  leaf advertisement-time-in-msec {
                    xr:xr-xml-map "vrrp_cfg:AdvertisementTimeInMsec";
                    when "../in-msec = 'true'" {
                      description "../InMsec = TRUE";
                    }
                    type uint32 {
                      range "100..3000";
                    }
                    units "millisecond";
                    description
                      "Advertisement time in milliseconds";
                  }
                  leaf advertisement-time-in-sec {
                    xr:xr-xml-map "vrrp_cfg:AdvertisementTimeInSec";
                    when "../in-msec != 'true'" {
                      description "../InMsec != TRUE";
                    }
                    type uint32 {
                      range "1..255";
                    }
                    units "second";
                    description "Advertisement time in seconds";
                  }
                  leaf forced {
                    xr:xr-xml-map "vrrp_cfg:Forced";
                    when "../in-msec = 'true' or ../in-msec ="+
                      " 'false'" {
                        description
                          "../InMsec = TRUE or ../InMsec = FALSE";
                    }
                    type boolean;
                    default "false";
                    description
                      "TRUE - Force configured timer values to
                      be used, required when configured in
                      milliseconds";
                  }
                }

                container secondary-ipv4-addresses {
                  xr:xr-xml-map "vrrp_cfg:SecondaryIPv4AddressTable";
                  description
                    "The table of VRRP secondary IPv4 addresses";

                  list secondary-ipv4-address {
                    xr:xr-xml-map "vrrp_cfg:SecondaryIPv4Address";
                    xr:xr-cli-map "vrrp interface <interface> vrrp "+
                      "<number> ipv4 <IPv4 address> secondary ";
                    key "ip-address";
                    description "A VRRP secondary IPv4 address";
                    leaf ip-address {
                      xr:xr-xml-map "vrrp_cfg:IPAddress";
                      type inet:ipv4-address-no-zone;
                      description "VRRP Secondary IPv4 address";
                    }
                  }
                }

                container tracks {
                  xr:xr-xml-map "vrrp_cfg:TrackTable";
                  description
                    "Track an item, reducing priority if it
                    goes down";

                  list track {
                    xr:xr-xml-map "vrrp_cfg:Track";
                    xr:xr-cli-map "vrrp interface <interface> vrrp "+
                      "<number> track interface <interface> [<numbe"+
                      "r>] ";
                    key "interface-name";
                    description "Object to be tracked";
                    leaf interface-name {
                      xr:xr-xml-map "vrrp_cfg:InterfaceName";
                      type xr:Interface-name;
                      description
                        "Object to be tracked, interface name for
                        interfaces";
                    }
                    leaf priority {
                      xr:xr-xml-map "vrrp_cfg:Priority";
                      type uint32 {
                        range "1..254";
                      }
                      mandatory true;
                      description "Priority decrement";
                    }
                  }
                }

                container tracked-objects {
                  xr:xr-xml-map "vrrp_cfg:TrackedObjectTable";
                  description
                    "Track an object, reducing priority if it
                    goes down";

                  list tracked-object {
                    xr:xr-xml-map "vrrp_cfg:TrackedObject";
                    key "object-name";
                    description "Object to be tracked";
                    leaf object-name {
                      xr:xr-xml-map "vrrp_cfg:ObjectName";
                      type xr:Cisco-ios-xr-string;
                      description
                        "Object to be tracked, interface name for
                        interfaces";
                    }
                    leaf priority-decrement {
                      xr:xr-xml-map "vrrp_cfg:PriorityDecrement";
                      type uint32 {
                        range "1..254";
                      }
                      mandatory true;
                      description "Priority decrement";
                    }
                  }
                }
                leaf priority {
                  xr:xr-xml-map "vrrp_cfg:Priority";
                  xr:xr-cli-map "vrrp interface <interface> vrrp <n"+
                    "umber> priority <number> ";
                  type uint32 {
                    range "1..254";
                  }
                  default "100";
                  description "Priority value";
                }
                leaf primary-ipv4-address {
                  xr:xr-xml-map "vrrp_cfg:PrimaryIPv4Address";
                  xr:xr-cli-map "vrrp interface <interface> vrrp <n"+
                    "umber> ipv4 <IPv4 address> ";
                  type inet:ipv4-address-no-zone;
                  description "The Primary VRRP IPv4 address";
                }
                leaf preempt {
                  xr:xr-xml-map "vrrp_cfg:Preempt";
                  xr:xr-cli-map "vrrp interface <interface> vrrp <n"+
                    "umber> preempt delay <number> disable ";
                  type uint32 {
                    range "0..3600";
                  }
                  default "0";
                  description
                    "Preempt Master router if higher priority";
                }
                leaf text-password {
                  xr:xr-xml-map "vrrp_cfg:TextPassword";
                  xr:xr-cli-map "vrrp interface <interface> vrrp <n"+
                    "umber> text-authentication <string> ";
                  type string;
                  description
                    "Authentication password, 8 chars max";
                }
                leaf bfd {
                  xr:xr-xml-map "vrrp_cfg:BFD";
                  xr:xr-cli-map "vrrp interface <interface> vrrp <n"+
                    "umber> bfd fast-detect peer ipv4 <IPv4 address"+
                    "> ";
                  type inet:ipv4-address-no-zone;
                  description
                    "Enable use of Bidirectional Forwarding
                    Detection for this IP";
                }
                leaf session-name {
                  xr:xr-xml-map "vrrp_cfg:SessionName";
                  type xr:Cisco-ios-xr-string {
                    length "0..16";
                  }
                  description "VRRP Session Name";
                }
                leaf accept-mode-disable {
                  xr:xr-xml-map "vrrp_cfg:AcceptModeDisable";
                  xr:xr-cli-map "vrrp interface <interface> vrrp <n"+
                    "umber> assume-ownership disable ";
                  type empty;
                  description
                    "Disable Accept Mode for this virtual
                    IPAddress";
                }
                leaf vr-id {
                  xr:xr-xml-map "vrrp_cfg:VR_ID";
                  type uint32 {
                    range "1..255";
                  }
                  description "VRID Virtual Router Identifier";
                }
              }
            }
          }
        }

        container bfd {
          xr:xr-xml-map "vrrp_cfg:BFD";
          description "BFD configuration";
          leaf interval {
            xr:xr-xml-map "vrrp_cfg:Interval";
            xr:xr-cli-map "vrrp interface <interface> bfd minimum-i"+
              "nterval <number> ";
            type uint32 {
              range "3..30000";
            }
            units "millisecond";
            description
              "Hello interval for BFD sessions created by
              vrrp";
          }
          leaf detection-multiplier {
            xr:xr-xml-map "vrrp_cfg:DetectionMultiplier";
            xr:xr-cli-map "vrrp interface <interface> bfd multiplie"+
              "r <number> ";
            type uint32 {
              range "2..50";
            }
            description
              "Detection multiplier for BFD sessions created
              by vrrp";
          }
        }
        leaf mac-refresh {
          xr:xr-xml-map "vrrp_cfg:MACRefresh";
          xr:xr-cli-map "vrrp interface <interface> mac-refresh <nu"+
            "mber> ";
          type uint32 {
            range "0..10000";
          }
          units "second";
          default "60";
          description "VRRP Slave MAC-refresh rate in seconds";
        }
        leaf interface-name {
          xr:xr-xml-map "vrrp_cfg:InterfaceName";
          type xr:Interface-name;
          description "Interface name to configure";
        }
      }
    }
  }

  augment "/a1:snmp/a1:notification" {

    container vrrp {
      xr:xr-xml-map "vrrpmib_cfg:VRRP";
      description "VRRP-MIB notification configuration";
      leaf enable {
        xr:xr-xml-map "vrrpmib_cfg:Enable";
        type empty;
        description "Enable VRRP-MIB notifications";
      }
    }
    description
      "This augment extends the configuration data of
      'Cisco-IOS-XR-snmp-agent-cfg'";
  }
}
