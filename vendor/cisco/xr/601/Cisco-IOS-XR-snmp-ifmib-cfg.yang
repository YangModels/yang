module Cisco-IOS-XR-snmp-ifmib-cfg {

  /*** NAMESPACE / PREFIX DEFINITION ***/

  namespace "http://cisco.com/ns/yang/Cisco-IOS-XR-snmp-ifmib-cfg";


  prefix "snmp-ifmib-cfg";

  /*** LINKAGE (IMPORTS / INCLUDES) ***/

  import Cisco-IOS-XR-types { prefix "xr"; }

  import Cisco-IOS-XR-snmp-agent-cfg { prefix "a1"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR snmp-ifmib package configuration.

     This YANG module augments the
       Cisco-IOS-XR-snmp-agent-cfg,
     module with configuration data.

     Copyright (c) 2013-2015 by Cisco Systems, Inc.
     All rights reserved.";

  revision "2015-05-14" {
    description
      "IOS XR 5.3.2 revision.";
  }

  revision "2015-01-07" {
    description
      "IOS XR 5.3.1 revision.";
  }


  augment "/a1:mib" {

    container interface-mib {
      xr:xr-xml-map "ifmib_cfg:InterfaceMIB";
      description "Interface MIB configuration";

      container notification {
        xr:xr-xml-map "ifmib_cfg:Notification";
        description "MIB notification configuration";
        leaf link-ietf {
          xr:xr-xml-map "ifmib_cfg:LinkIETF";
          type empty;
          description
            "Set the varbind of linkupdown trap to the RFC
            specified varbinds (default cisco)";
        }
      }

      container subsets {
        xr:xr-xml-map "ifmib_cfg:SubsetTable";
        description "Add configuration for an interface subset";

        list subset {
          xr:xr-xml-map "ifmib_cfg:Subset";
          key "subset-id";
          description
            "Subset priorityID to group ifNames based on
            Regular Expression";

          container link-up-down {
            xr:xr-xml-map "ifmib_cfg:LinkUpDown";
            description "SNMP linkUp and linkDown notifications";
            leaf enable {
              xr:xr-xml-map "ifmib_cfg:Enable";
              type boolean;
              description
                "Enable or disable linkupdown notification";
            }
            leaf regular-expression {
              xr:xr-xml-map "ifmib_cfg:RegularExpression";
              type string;
              description "Regular expression to match ifName";
            }
          }
          leaf subset-id {
            xr:xr-xml-map "ifmib_cfg:SubsetID";
            type uint32 {
              range "1..255";
            }
            description "The interface subset PriorityID";
          }
        }
      }
      leaf internal-cache {
        xr:xr-xml-map "ifmib_cfg:InternalCache";
        type uint32 {
          range "0..60";
        }
        default "15";
        description "Get cached interface statistics";
      }
      leaf interface-alias-long {
        xr:xr-xml-map "ifmib_cfg:InterfaceAliasLong";
        type empty;
        description
          "Enable support for ifAlias values longer than
          64 characters";
      }
      leaf ip-subscriber {
        xr:xr-xml-map "ifmib_cfg:IPSubscriber";
        type empty;
        description "Enable IP subscriber interfaces in IFMIB";
      }
      leaf interface-index-persistence {
        xr:xr-xml-map "ifmib_cfg:InterfaceIndexPersistence";
        type empty;
        description "Enable ifindex persistence";
      }
      leaf statistics-cache {
        xr:xr-xml-map "ifmib_cfg:StatisticsCache";
        type empty;
        description "Enable cached interface statistics";
      }
    }
    description
      "This augment extends the configuration data of
      'Cisco-IOS-XR-snmp-agent-cfg'";
  }

  augment "/a1:snmp/a1:notification/a1:snmp" {
    leaf link-down {
      xr:xr-xml-map "snmp_ifmib_cfg:LinkDown";
      type empty;
      description "Enable link down notification";
    }
    description
      "This augment extends the configuration data of
      'Cisco-IOS-XR-snmp-agent-cfg'";
  }

  augment "/a1:snmp/a1:notification/a1:snmp" {
    leaf link-up {
      xr:xr-xml-map "snmp_ifmib_cfg:LinkUp";
      type empty;
      description "Enable link up notification";
    }
    description
      "This augment extends the configuration data of
      'Cisco-IOS-XR-snmp-agent-cfg'";
  }
}
