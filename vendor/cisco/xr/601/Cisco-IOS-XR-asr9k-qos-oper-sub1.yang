submodule Cisco-IOS-XR-asr9k-qos-oper-sub1 {

  belongs-to Cisco-IOS-XR-asr9k-qos-oper {
    prefix Cisco-IOS-XR-asr9k-qos-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR asr9k-qos package operational data.

     Copyright (c) 2013-2015 by Cisco Systems, Inc.
     All rights reserved.";

  revision "2015-11-09" {
    description
      "IOS XR 6.0 revision.";
  }

  typedef Shape-profiletype-v2 {
    type enumeration {
      enum invalid {
        description "Shape Profile Type Invalid";
      }
      enum always {
        description "Shape Profile Type Always";
      }
      enum never {
        description "Shape Profile Type Never";
      }
      enum explicit {
        description "Shape Profile Type Explicit";
      }
      enum scale {
        description "Shape Profile Type Scale";
      }
      enum grid {
        description "Shape Profile Type Grid";
      }
    }
    description "SHAPE profile type";
  }
  typedef Action {
    type enumeration {
      enum police-transmit {
        description "Police action transmit";
      }
      enum police-set-transmit {
        description "Police action set transmit";
      }
      enum police-drop {
        description "Police action drop";
      }
      enum police-unknown {
        description "Police action unknown";
      }
    }
    description "Action type";
  }
  typedef Action-opcode {
    type enumeration {
      enum precedence {
        value 0;
        description "Precedence";
      }
      enum dscp {
        value 1;
        description "DSCP";
      }
      enum discard-class {
        value 2;
        description "Discard class";
      }
      enum qos-group {
        value 3;
        description "QoS group";
      }
      enum cos-inner {
        value 4;
        description "COS inner";
      }
      enum cos {
        value 5;
        description "COS";
      }
      enum exp-top {
        value 6;
        description "EXP top";
      }
      enum exp-imp {
        value 7;
        description "EXP IMP";
      }
      enum tunnel-precedence {
        value 8;
        description "Tunnel precedence";
      }
      enum tunnel-dscp {
        value 9;
        description "Tunnel DSCP";
      }
      enum itag-dei {
        value 10;
        description "ITAG DEI";
      }
      enum itag-cos {
        value 11;
        description "ITAG COS";
      }
      enum cos-imposition {
        value 12;
        description "COS imposition";
      }
      enum dei-imposition {
        value 13;
        description "DEI imposition";
      }
      enum dei {
        value 14;
        description "DEI";
      }
      enum no-marking {
        value 15;
        description "No marking";
      }
    }
    description "Action opcode";
  }
  typedef Wred1 {
    type enumeration {
      enum wred-cos {
        description "WRED based on COS";
      }
      enum wred-dscp {
        description "WRED based on DSCP";
      }
      enum wred-precedence {
        description "WRED based on Precedence";
      }
      enum wred-discard-class {
        description "WRED based on discard class";
      }
      enum wred-mpls-exp {
        description "WRED based on MPLS EXP";
      }
      enum red-with-user-min-max {
        description "RED with user defined min and max";
      }
      enum red-with-default-min-max {
        description "RED with default min and max";
      }
      enum wred-dei {
        description "WRED DEI";
      }
    }
    description "WRED type";
  }
  typedef Tb-algorithm {
    type enumeration {
      enum inactive {
        value 0;
        description "Inactive, configured but disabled";
      }
      enum single {
        value 1;
        description "Single token bucket";
      }
      enum single-rate-tcm {
        value 2;
        description "Single rate three color marker";
      }
      enum two-rate-tcm {
        value 3;
        description "Two rate three color marker";
      }
      enum mef-tcm {
        value 4;
        description "Allows coupling between CIR and PIR tb's";
      }
      enum dummy {
        value 5;
        description
          "Internal dummy token bucket for coupled-policer
          child";
      }
    }
    description "Tokenbucket type";
  }
  typedef Queue {
    type enumeration {
      enum port-default {
        description "Port default queue";
      }
      enum class-default {
        description "The default queue in this policy";
      }
      enum priority1-queue {
        description
          "Create the priority 1 queue in the level which
          will be shared by other p1 classes";
      }
      enum priority2-queue {
        description
          "Create the priority 2 queue in the level, which
          will be shared by other p2 classes";
      }
      enum priority3-queue {
        description
          "Create the priority 3 queue in the level, which
          will be shared by other p3 classes";
      }
      enum priority4-queue {
        description
          "Create the priority 4 queue in the level, which
          will be shared by other p4 classes";
      }
      enum priority5-queue {
        description
          "Create the priority 5 queue in the level, which
          will be shared by other p5 classes";
      }
      enum priority6-queue {
        description
          "Create the priority 6 queue in the level, which
          will be shared by other p6 classes";
      }
      enum priority7-queue {
        description
          "Create the priority 7 queue in the level, which
          will be shared by other p7 classes";
      }
      enum first-p1-class-name {
        description "Current level's priority 1 queue";
      }
      enum first-p2-class-name {
        description "Current level's priority 2 queue";
      }
      enum first-p3-class-name {
        description "Current level's priority 3 queue";
      }
      enum first-p4-class-name {
        description "Current level's priority 4 queue";
      }
      enum first-p5-class-name {
        description "Current level's priority 5 queue";
      }
      enum first-p6-class-name {
        description "Current level's priority 6 queue";
      }
      enum first-p7-class-name {
        description "Current level's priority 7 queue";
      }
      enum port-priority1 {
        description "Port priority 1 queue";
      }
      enum port-priority2 {
        description "Port priority 2 queue";
      }
      enum port-priority3 {
        description "Port priority 3 queue";
      }
      enum port-priority4 {
        description "Port priority 4 queue";
      }
      enum port-priority5 {
        description "Port priority 5 queue";
      }
      enum port-priority6 {
        description "Port priority 6 queue";
      }
      enum port-priority7 {
        description "Port priority 7 queue";
      }
      enum new {
        description "Create a new queue for this class";
      }
      enum parent-class {
        description "Under parent queue";
      }
      enum priority1 {
        description "Priority 1";
      }
      enum priority2 {
        description "Priority 2";
      }
      enum priority3 {
        description "Priority 3";
      }
      enum priority4 {
        description "Priority 4";
      }
      enum priority5 {
        description "Priority 5";
      }
      enum priority6 {
        description "Priority 6";
      }
      enum priority7 {
        description "Priority 7";
      }
      enum priority-ignored-normal {
        description "Priority ignored level";
      }
      enum normal-priority {
        description "Normal priority";
      }
      enum class-unknown {
        description "Class unknown";
      }
      enum unknown-priority {
        description "Unknown priority";
      }
    }
    description "Queue type";
  }
  typedef Qos-unit {
    type enumeration {
      enum invalid {
        value 0;
        description "Invalid type";
      }
      enum bytes {
        value 1;
        description "Bytes";
      }
      enum kilobytes {
        value 2;
        description "Kilobytes";
      }
      enum megabytes {
        value 3;
        description "Megabytes";
      }
      enum gigabytes {
        value 4;
        description "Gigabytes";
      }
      enum bps {
        value 5;
        description "Bits per second";
      }
      enum kbps {
        value 6;
        description "Kilo bits per second";
      }
      enum mbps {
        value 7;
        description "Mega bits per second";
      }
      enum gbps {
        value 8;
        description "Giga bits per second";
      }
      enum cells-per-second {
        value 9;
        description "Cells per second";
      }
      enum packets-per-second {
        value 10;
        description "Packets per second";
      }
      enum microsecond {
        value 11;
        description "Microsecond";
      }
      enum millisecond {
        value 12;
        description "Millisecond";
      }
      enum packets {
        value 13;
        description "Number of packets";
      }
      enum cells {
        value 14;
        description "Number of cells";
      }
      enum percentage {
        value 15;
        description "Percentage";
      }
      enum ratio {
        value 16;
        description "Ratio";
      }
    }
    description "QoS parameter unit";
  }

  grouping WRED-CURVE-PARAMS-V2 {
    description "Typhoon WRED curve parameters";

    container min-threshold {
      description "Minimum threshold";
      uses QOS-PARAM;
    }

    container min-threshold-user-config {
      description "Minimum threshold WRED context";
      uses QOS-PARAM;
    }

    container max-threshold {
      description "Maximum threshold";
      uses QOS-PARAM;
    }

    container max-threshold-user-config {
      description "Maximum threshold WRED context";
      uses QOS-PARAM;
    }
    leaf absolute-index {
      xr:xr-xml-map "qos_ea_show:AbsoluteIndex";
      type uint16;
      description "Absolute Index";
    }
    leaf template-id {
      xr:xr-xml-map "qos_ea_show:TemplateID";
      type uint16;
      description "Template ID";
    }
    leaf curve-id {
      xr:xr-xml-map "qos_ea_show:CurveID";
      type uint16;
      description "Curve ID";
    }
    leaf match {
      xr:xr-xml-map "qos_ea_show:Match";
      type string;
      description
        "WRED match if precedence start value equals to
        end value Format: <start-value> , else range
        Format: <start-value> <end-value>";
    }
    leaf exp-match {
      xr:xr-xml-map "qos_ea_show:ExpMatch";
      type string;
      description
        "WRED exp match if EXP start value equals to end
        value Format: <start-value> , else range Format:
        <start-value> <end-value>";
    }
  }

  grouping WRED-PARAMS-V2 {
    description "Typhoon WRED parameters";
    leaf type {
      xr:xr-xml-map "qos_ea_show:Type";
      type Wred1;
      description "WRED type";
    }
    leaf curve-xr {
      xr:xr-xml-map "qos_ea_show:Curves";
      type uint16;
      description "Number of curves";
    }

    list curve {
      max-elements "64";
      description "Curve details";
      uses WRED-CURVE-PARAMS-V2;
    }
  }

  grouping PIR-SHAPE-PARAMS-V2 {
    description "PIR Shape Params";

    container pir {
      description "PIR in kbps";
      uses QOS-PARAM;
    }

    container pbs {
      description "PBS in bytes";
      uses QOS-PARAM;
    }
    leaf chunk-id {
      xr:xr-xml-map "qos_ea_show:ChunkID";
      type uint32;
      description "Shape Chunk ID";
    }
    leaf profile-id {
      xr:xr-xml-map "qos_ea_show:ProfileID";
      type uint16;
      description "Shape profile ID";
    }
    leaf scale-factor {
      xr:xr-xml-map "qos_ea_show:ScaleFactor";
      type uint16;
      description "Scale Factor";
    }
  }

  grouping CIR-SHAPE-PARAMS-V2 {
    description "CIR Shape Params";

    container cir {
      description "CIR in kbps";
      uses QOS-PARAM;
    }

    container config-bandwidth {
      description "Config bandwidth";
      uses SHAPE-USER-CFG-BW;
    }

    container cbs {
      description "CBS in bytes";
      uses QOS-PARAM;
    }
    leaf chunk-id {
      xr:xr-xml-map "qos_ea_show:ChunkID";
      type uint32;
      description "Shape Chunk ID";
    }
    leaf profile-id {
      xr:xr-xml-map "qos_ea_show:ProfileID";
      type uint16;
      description "Shape profile ID";
    }
    leaf scale-factor {
      xr:xr-xml-map "qos_ea_show:ScaleFactor";
      type uint16;
      description "Scale Factor";
    }
  }

  grouping SHAPER-PARAMS-V2 {
    description "Shaper parameters";

    container cir-shape {
      description "CIR shaper params";
      uses CIR-SHAPE-PARAMS-V2;
    }

    container pir-shape {
      description "PIR shaper params";
      uses PIR-SHAPE-PARAMS-V2;
    }
    leaf cir-shape-type {
      xr:xr-xml-map "qos_ea_show:CIRShapeType";
      type Shape-profiletype-v2;
      description "CIR Shaper type";
    }
    leaf pir-shape-type {
      xr:xr-xml-map "qos_ea_show:PIRShapeType";
      type Shape-profiletype-v2;
      description "PIR Shaper type";
    }
  }

  grouping QUEUE-LIMIT-PARAMS-V2 {
    description "Queue limit parameters";

    container queue-limit {
      description "Queue limit in kbytes";
      uses QOS-PARAM;
    }

    container config-queue-limit {
      description "Config queue limit";
      uses QOS-PARAM;
    }
    leaf absolute-index {
      xr:xr-xml-map "qos_ea_show:AbsoluteIndex";
      type uint16;
      description "Absolute Index";
    }
    leaf template-id {
      xr:xr-xml-map "qos_ea_show:TemplateID";
      type uint16;
      description "Template ID";
    }
    leaf curve-id {
      xr:xr-xml-map "qos_ea_show:CurveID";
      type uint16;
      description "Curve ID";
    }
  }

  grouping QOS-SHOW-EA-ST-V2 {
    description "QoS policy";

    list qos-show-ea-st-v2 {
      description "qos show ea st v2";

      container queue {
        description "Queue parameters";
        uses QUEUE-PARAMS;
      }

      container queue-limit-parameters {
        description "Queue limit parameters";
        uses QUEUE-LIMIT-PARAMS-V2;
      }

      container shape {
        description "Shape parameters";
        uses SHAPER-PARAMS-V2;
      }

      container police {
        description "Police parameters";
        uses POLICE-PARAMS;
      }

      container wfq {
        description "WFQ parameters";
        uses WFQ-PARAMS;
      }

      container wred {
        description "WRED parameters";
        uses WRED-PARAMS-V2;
      }

      container mark {
        description "Mark parameters";
        uses CLASS-MARK-ACTIONS;
      }
      leaf class-level {
        type uint8;
        description "Class level";
      }
      leaf class-name {
        type string {
          length "0..65";
        }
        description "Class name";
      }
      leaf policy-name {
        type string {
          length "0..65";
        }
        description "Policy name";
      }
      leaf parent-policy-name {
        type string {
          length "0..65";
        }
        description "Parent policy name";
      }
      leaf parent-class-name {
        type string {
          length "0..65";
        }
        description "Parent class name";
      }
    }
  }

  grouping MARK-ACTION {
    description "Marking parameters";
    leaf mark-value {
      xr:xr-xml-map "qos_ea_show:MarkValue";
      type uint8;
      description "Mark value";
    }
    leaf action-opcode {
      xr:xr-xml-map "qos_ea_show:ActionOpcode";
      type Action-opcode;
      description "Action opcode";
    }
  }

  grouping MARK-ACTION-PER-CATEGORY {
    description "Marking action";
    leaf action-type {
      xr:xr-xml-map "qos_ea_show:ActionType";
      type Action;
      description "Action type";
    }

    list mark-detail {
      max-elements "2";
      description "Mark value";
      uses MARK-ACTION;
    }
  }

  grouping CLASS-MARK-ACTIONS {
    description "Mark parameters";

    container child-mark {
      description "Child mark only";
      uses MARK-ACTION-PER-CATEGORY;
    }

    container police-conform {
      description "Child police conform mark";
      uses MARK-ACTION-PER-CATEGORY;
    }

    container police-exceed {
      description "Child police exceed mark";
      uses MARK-ACTION-PER-CATEGORY;
    }

    container police-violate {
      description "Child police violate mark";
      uses MARK-ACTION-PER-CATEGORY;
    }

    container parent-mark {
      description "Parent mark only";
      uses MARK-ACTION-PER-CATEGORY;
    }

    container parent-police-conform {
      description "Parent police conform mark";
      uses MARK-ACTION-PER-CATEGORY;
    }

    container parent-police-exceed {
      description "Parent police exceed mark";
      uses MARK-ACTION-PER-CATEGORY;
    }

    container parent-police-violate {
      description "Parent police violate mark";
      uses MARK-ACTION-PER-CATEGORY;
    }
  }

  grouping WRED-CURVE-PARAMS-V1 {
    description "Trident WRED curve parameters";

    container min-threshold {
      description "Minimum threshold";
      uses QOS-PARAM;
    }

    container min-threshold-user-config {
      description "Minimum threshold WRED context";
      uses QOS-PARAM;
    }

    container max-threshold {
      description "Maximum threshold";
      uses QOS-PARAM;
    }

    container max-threshold-user-config {
      description "Maximum threshold WRED context";
      uses QOS-PARAM;
    }
    leaf match {
      xr:xr-xml-map "qos_ea_show:Match";
      type string;
      description
        "WRED precedence match if precedence start value
        equals to end value Format: <start-value> , else
        range Format: <start-value> <end-value>";
    }
  }

  grouping WRED-PARAMS-V1 {
    description "Trident WRED parameters";
    leaf type {
      xr:xr-xml-map "qos_ea_show:Type";
      type Wred1;
      description "WRED type";
    }
    leaf curve-xr {
      xr:xr-xml-map "qos_ea_show:Curves";
      type uint16;
      description "Number of curves";
    }
    leaf table-id {
      xr:xr-xml-map "qos_ea_show:TableID";
      type uint8;
      description "Table ID";
    }
    leaf profile-id {
      xr:xr-xml-map "qos_ea_show:ProfileID";
      type uint32;
      description "Profile ID";
    }
    leaf scaling-profile-id {
      xr:xr-xml-map "qos_ea_show:ScalingProfileID";
      type uint32;
      description "Scaling profile ID";
    }

    list curve {
      max-elements "64";
      description "Curve details";
      uses WRED-CURVE-PARAMS-V1;
    }
  }

  grouping WFQ-PARAMS {
    description "WFQ parameters";

    container parent-bandwidth {
      description "Parent bandwidth";
      uses QOS-PARAM;
    }

    container bandwidth {
      description "CFG Bandwidth";
      uses QOS-PARAM;
    }
    leaf profile-id {
      xr:xr-xml-map "qos_ea_show:ProfileID";
      type uint32;
      description "WFQ profile";
    }
    leaf committed-weight {
      xr:xr-xml-map "qos_ea_show:CommittedWeight";
      type uint32;
      description "Committed weight";
    }
    leaf excess-weight {
      xr:xr-xml-map "qos_ea_show:ExcessWeight";
      type uint16;
      description "Excess weight";
    }
    leaf excess-ratio {
      xr:xr-xml-map "qos_ea_show:ExcessRatio";
      type uint16;
      description "Parent Excess ratio";
    }
    leaf chunk-id {
      xr:xr-xml-map "qos_ea_show:ChunkID";
      type uint32;
      description "Chunk ID";
    }
    leaf level {
      xr:xr-xml-map "qos_ea_show:Level";
      type uint8;
      description "Level";
    }
  }

  grouping CFG-POLICE {
    description "Config police parameters";

    container average-rate {
      description "Average rate";
      uses QOS-PARAM;
    }

    container peak-rate {
      description "Peak rate";
      uses QOS-PARAM;
    }

    container conform-burst {
      description "Conform burst";
      uses QOS-PARAM;
    }

    container exceed-burst {
      description "Exceed burst";
      uses QOS-PARAM;
    }
  }

  grouping POLICE-PARAMS {
    description "Police parameters";

    container cir {
      description "CIR";
      uses QOS-PARAM;
    }

    container cbs {
      description "CBS";
      uses QOS-PARAM;
    }

    container pir {
      description "PIR";
      uses QOS-PARAM;
    }

    container pbs {
      description "PBS";
      uses QOS-PARAM;
    }

    container police-config-parameters {
      description "Police config parameters";
      uses CFG-POLICE;
    }
    leaf policer-type {
      xr:xr-xml-map "qos_ea_show:PolicerType";
      type Tb-algorithm;
      description "Policer type";
    }
    leaf profile-id {
      xr:xr-xml-map "qos_ea_show:ProfileID";
      type uint32;
      description "Police profile ID";
    }
  }

  grouping SHAPE-USER-CFG-BW {
    description "Config bandwidth parameters";

    container minimum-rate {
      description "Minimum bandwidth rate";
      uses QOS-PARAM;
    }
  }

  grouping SHAPER-PARAMS-V1 {
    description "Shaper parameters";

    container cir {
      description "CIR in kbps";
      uses QOS-PARAM;
    }

    container config-bandwidth {
      description "Config bandwidth";
      uses SHAPE-USER-CFG-BW;
    }

    container cbs {
      description "CBS in bytes";
      uses QOS-PARAM;
    }

    container pir {
      description "PIR in kbps";
      uses QOS-PARAM;
    }

    container pbs {
      description "PBS in bytes";
      uses QOS-PARAM;
    }
    leaf profile-id {
      xr:xr-xml-map "qos_ea_show:ProfileID";
      type uint16;
      description "Shape profile ID";
    }
  }

  grouping QUEUE-LIMIT-PARAMS-V1 {
    description "Queue limit parameters";

    container queue-limit {
      description "Queue limit in kbytes";
      uses QOS-PARAM;
    }

    container config-queue-limit {
      description "Config queue limit";
      uses QOS-PARAM;
    }
    leaf profile-id {
      xr:xr-xml-map "qos_ea_show:ProfileID";
      type uint32;
      description "Profile ID";
    }
    leaf scaling-profile-id {
      xr:xr-xml-map "qos_ea_show:ScalingProfileID";
      type uint32;
      description "Scaling profile ID";
    }
  }

  grouping QUEUE-PARAMS {
    description "Queue parameters";
    leaf queue-id {
      xr:xr-xml-map "qos_ea_show:QueueID";
      type uint32;
      description "Queue ID";
    }
    leaf queue-type {
      xr:xr-xml-map "qos_ea_show:QueueType";
      type Queue;
      description "Queue type";
    }
    leaf class-name {
      xr:xr-xml-map "qos_ea_show:ClassName";
      type string {
        length "0..65";
      }
      description "Class name";
    }
  }

  grouping QOS-SHOW-EA-ST-V1 {
    description "QoS policy";

    list qos-show-ea-st-v1 {
      description "qos show ea st v1";

      container queue {
        description "Queue parameters";
        uses QUEUE-PARAMS;
      }

      container queue-limit-parameters {
        description "Queue limit parameters";
        uses QUEUE-LIMIT-PARAMS-V1;
      }

      container shape {
        description "Shape parameters";
        uses SHAPER-PARAMS-V1;
      }

      container police {
        description "Police parameters";
        uses POLICE-PARAMS;
      }

      container wfq {
        description "WFQ parameters";
        uses WFQ-PARAMS;
      }

      container wred {
        description "WRED parameters";
        uses WRED-PARAMS-V1;
      }

      container mark {
        description "Mark parameters";
        uses CLASS-MARK-ACTIONS;
      }
      leaf class-level {
        type uint8;
        description "Class level";
      }
      leaf class-name {
        type string {
          length "0..65";
        }
        description "Class name";
      }
      leaf policy-name {
        type string {
          length "0..65";
        }
        description "Policy name";
      }
      leaf parent-policy-name {
        type string {
          length "0..65";
        }
        description "Parent policy name";
      }
      leaf parent-class-name {
        type string {
          length "0..65";
        }
        description "Parent class name";
      }
    }
  }

  grouping QOS-PARAM {
    description "Config details";
    leaf value {
      xr:xr-xml-map "qos_ea_show:Value";
      type uint32;
      description "Config value";
    }
    leaf unit {
      xr:xr-xml-map "qos_ea_show:Unit";
      type Qos-unit;
      description "Config unit";
    }
  }

  grouping INTF-CONFIG-PROGRAMED {
    description "Interface configured and programmed parameters";

    container port-config-bandwidth {
      description "Bandwidth due to port speed change";
      uses QOS-PARAM;
    }

    container ancp-config-bandwidth {
      description "Bandwidth obtain from IM";
      uses QOS-PARAM;
    }

    container ancp-programmed-bandwidth {
      description "ANCP bandwidth that was programmed";
      uses QOS-PARAM;
    }

    container port-shaper-rate {
      description "Bandwidth that was programmed";
      uses QOS-PARAM;
    }
  }

  grouping QOS-SHOW-EA-HEADER-ST {
    description "QoS policy header";

    container interface-parameters {
      description "Interface config and programmed parameters";
      uses INTF-CONFIG-PROGRAMED;
    }

    container programmed-bandwidth {
      description "Bandwidth that was programmed";
      uses QOS-PARAM;
    }
    leaf classes {
      xr:xr-xml-map "qos_ea_show:Classes";
      type uint16;
      description "Number of classes";
    }
    leaf policy-name {
      xr:xr-xml-map "qos_ea_show:PolicyName";
      type string {
        length "0..65";
      }
      description "Policy name";
    }
  }

  grouping QOS-SHOW-EA-POLICY {
    description "QoS policy";

    container header {
      description "QoS policy header";
      uses QOS-SHOW-EA-HEADER-ST;
    }

    container policy {
      description "Trident QoS policy details";
      uses QOS-SHOW-EA-ST-V1;
    }

    container policy-typhoon {
      description "Typhoon QoS policy details";
      uses QOS-SHOW-EA-ST-V2;
    }
  }

  grouping QOS-EA-CAPABILITY {
    description "QoS capability";
    leaf max-policy-maps {
      xr:xr-xml-map "qos_ea_show:MaxPolicyMaps";
      type uint32;
      description "Maximum policy maps per system";
    }
    leaf max-policy-hierarchy {
      xr:xr-xml-map "qos_ea_show:MaxPolicyHierarchy";
      type uint32;
      description "Maximum policy hierarchy";
    }
    leaf max-policy-name-length {
      xr:xr-xml-map "qos_ea_show:MaxPolicyNameLength";
      type uint32;
      description "Maximum policy name length";
    }
    leaf max-classes-per-child-policy {
      xr:xr-xml-map "qos_ea_show:MaxClassesPerChildPolicy";
      type uint32;
      description "Maximum classes per child policy";
    }
    leaf max-classes-per-policy {
      xr:xr-xml-map "qos_ea_show:MaxClassesPerPolicy";
      type uint32;
      description "Maximum classes per policy";
    }
    leaf max-classes-per-grand-parent-policy {
      xr:xr-xml-map "qos_ea_show:MaxClassesPerGrandParentPolicy";
      type uint32;
      description "Maximum classes per parent policy";
    }
    leaf max-police-actions-per-class {
      xr:xr-xml-map "qos_ea_show:MaxPoliceActionsPerClass";
      type uint32;
      description "Maximum police actions per class";
    }
    leaf max-marking-actions-per-class {
      xr:xr-xml-map "qos_ea_show:MaxMarkingActionsPerClass";
      type uint32;
      description "Maximum marking action  per class";
    }
    leaf max-matches-per-class {
      xr:xr-xml-map "qos_ea_show:MaxMatchesPerClass";
      type uint32;
      description "Maximum matches per class";
    }
    leaf max-classmap-name-length {
      xr:xr-xml-map "qos_ea_show:MaxClassmapNameLength";
      type uint32;
      description "Maximum classmap name length";
    }
    leaf max-bundle-members {
      xr:xr-xml-map "qos_ea_show:MaxBundleMembers";
      type uint32;
      description "Maximum bundle members";
    }
    leaf max-instance-name-length {
      xr:xr-xml-map "qos_ea_show:MaxInstanceNameLength";
      type uint32;
      description "Maximum instance name length";
    }
  }
}
