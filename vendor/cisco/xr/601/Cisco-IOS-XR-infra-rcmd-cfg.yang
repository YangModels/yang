module Cisco-IOS-XR-infra-rcmd-cfg {

  /*** NAMESPACE / PREFIX DEFINITION ***/

  namespace "http://cisco.com/ns/yang/Cisco-IOS-XR-infra-rcmd-cfg";


  prefix "infra-rcmd-cfg";

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR infra-rcmd package configuration.

     This module contains definitions
     for the following management objects:
       router-convergence: Configure Router Convergence Monitoring

     Copyright (c) 2013-2015 by Cisco Systems, Inc.
     All rights reserved.";

  revision "2015-11-09" {
    description
      "IOS XR 6.0 revision.";
  }

  typedef Rcmd-priority {
    type enumeration {
      enum critical {
        value 0;
        description "Critical routes";
      }
      enum high {
        value 1;
        description "High priority routes";
      }
      enum medium {
        value 2;
        description "Medium priority routes";
      }
      enum low {
        value 3;
        description "Low priority routes";
      }
    }
    description "Rcmd priority";
  }
  typedef Protocol-name {
    type enumeration {
      enum ospf {
        value 0;
        description "Configure parameters related to OSPF";
      }
      enum isis {
        value 1;
        description "Configure parameters related to ISIS";
      }
    }
    description "Protocol name";
  }

  container router-convergence {
    xr:xr-xml-map "rcmd_cfg:RouterConvergence";
    description "Configure Router Convergence Monitoring";

    container protocols {
      xr:xr-xml-map "rcmd_cfg:ProtocolTable";
      description "Table of Protocol";

      list protocol {
        xr:xr-xml-map "rcmd_cfg:Protocol";
        key "protocol-name";
        description
          "Protocol for which to configure RCMD parameters";

        container priorities {
          xr:xr-xml-map "rcmd_cfg:PriorityTable";
          description "Table of Priority";

          list priority {
            xr:xr-xml-map "rcmd_cfg:Priority";
            key "rcmd-priority";
            description "Priority";
            leaf threshold {
              xr:xr-xml-map "rcmd_cfg:Threshold";
              xr:xr-cli-map "priority <enum> threshold <number> ";
              type int32;
              description
                "Threshold value for convergence (in msec)";
            }
            leaf leaf-networks {
              xr:xr-xml-map "rcmd_cfg:LeafNetworks";
              xr:xr-cli-map "priority <enum> leaf-network <number> ";
              type uint32 {
                range "10..100";
              }
              description
                "Specify the maximum number of leaf networks
                monitored";
            }
            leaf disable {
              xr:xr-xml-map "rcmd_cfg:Disable";
              xr:xr-cli-map "priority <enum> disable ";
              type empty;
              description
                "Disables the monitoring of route convergence
                for specified priority";
            }
            leaf enable {
              xr:xr-xml-map "rcmd_cfg:Enable";
              type empty;
              description
                "Enable Priority. Deletion of this object
                also causes deletion of all associated
                objects under Priority.";
            }
            leaf frr-threshold {
              xr:xr-xml-map "rcmd_cfg:FrrThreshold";
              xr:xr-cli-map "priority <enum> frr-threshold <number>"+
                " ";
              type uint32 {
                range "1..100";
              }
              units "percentage";
              description
                "Threshold value for Fast ReRoute Coverage
                (in percentage)";
            }
            leaf rcmd-priority {
              xr:xr-xml-map "rcmd_cfg:RCMDPriority";
              type Rcmd-priority;
              description "Specify the priority";
            }
          }
        }
        leaf enable {
          xr:xr-xml-map "rcmd_cfg:Enable";
          type empty;
          description
            "Enable Protocol for which to configure RCMD
            parameters. Deletion of this object also
            causes deletion of all associated objects
            under Protocol.";
        }
        leaf protocol-name {
          xr:xr-xml-map "rcmd_cfg:ProtocolName";
          type Protocol-name;
          description "Specify the protocol";
        }
      }
    }

    container storage-location {
      xr:xr-xml-map "rcmd_cfg:StorageLocation";
      presence "Indicates a storage-location node is configured.";
      description
        "Absolute directory path for saving the archive
        files. Example /disk0:/rcmd/ or
        <tftp-location>/rcmd/";
      leaf diagnostics {
        xr:xr-xml-map "rcmd_cfg:Diagnostics";
        xr:xr-cli-map "diagnostics <string> ";
        type string;
        description
          "Absolute directory path for storing diagnostic
          reports. Example /disk0:/rcmd/ or
          <tftp-location>/rcmd/";
      }
      leaf diagnostics-size {
        xr:xr-xml-map "rcmd_cfg:DiagnosticsSize";
        xr:xr-cli-map "diagnostics-size <number> ";
        type uint32 {
          range "5..80";
        }
        description
          "Maximum size of diagnostics dir (5% - 80%) for
          local storage.";
      }
      leaf enable {
        xr:xr-xml-map "rcmd_cfg:Enable";
        type empty;
        description
          "Enable Absolute directory path for saving the
          archive files. Example /disk0:/rcmd/ or
          <tftp-location>/rcmd/. Deletion of this object
          also causes deletion of all associated objects
          under StorageLocation.";
      }
      leaf reports-size {
        xr:xr-xml-map "rcmd_cfg:ReportsSize";
        xr:xr-cli-map "reports-size <number> ";
        type uint32 {
          range "5..80";
        }
        description
          "Maximum size of reports dir (5% - 80%) for
          local storage.";
      }
      leaf reports {
        xr:xr-xml-map "rcmd_cfg:Reports";
        xr:xr-cli-map "reports <string> ";
        type string;
        description
          "Absolute directory path for storing reports.
          Example /disk0:/rcmd/ or <tftp-location>/rcmd/";
      }
    }

    container mpls-ldp {
      xr:xr-xml-map "rcmd_cfg:MPLS-LDP";
      presence "Indicates a mpls-ldp node is configured.";
      description "RCMD related configuration for MPLS-LDP";

      container remote-lfa {
        xr:xr-xml-map "rcmd_cfg:RemoteLFA";
        presence "Indicates a remote-lfa node is configured.";
        description "Monitoring configuration for Remote LFA";
        leaf threshold {
          xr:xr-xml-map "rcmd_cfg:Threshold";
          xr:xr-cli-map "remote-lfa label-coverage-threshold <numbe"+
            "r> ";
          type uint32 {
            range "1..100";
          }
          units "percentage";
          description
            "Threshold value for label coverage (in
            percentage)";
        }
        leaf enable {
          xr:xr-xml-map "rcmd_cfg:Enable";
          type empty;
          description
            "Enable Monitoring configuration for Remote LFA
            . Deletion of this object also causes deletion
            of all associated objects under RemoteLFA.";
        }
      }
      leaf enable {
        xr:xr-xml-map "rcmd_cfg:Enable";
        type empty;
        description
          "Enable RCMD related configuration for MPLS-LDP.
          Deletion of this object also causes deletion of
          all associated objects under MPLS-LDP.";
      }
    }

    container collect-diagnostics {
      xr:xr-xml-map "rcmd_cfg:CollectDiagnosticsTable";
      description "Table of CollectDiagnostics";

      list collect-diagnostic {
        xr:xr-xml-map "rcmd_cfg:CollectDiagnostics";
        key "node-name";
        description "Collect diagnostics on specified node";
        leaf enable {
          xr:xr-xml-map "rcmd_cfg:Enable";
          xr:xr-cli-map "router-convergence collect-diagnostics <lo"+
            "cation> ";
          type empty;
          description
            "Enables collection of diagnostics on the
            specified location";
        }
        leaf node-name {
          xr:xr-xml-map "rcmd_cfg:NodeName";
          type xr:Node-id;
          description "Specified location";
        }
      }
    }

    container nodes {
      xr:xr-xml-map "rcmd_cfg:NodeTable";
      description "Table of Node";

      list node {
        xr:xr-xml-map "rcmd_cfg:Node";
        key "node-name";
        description
          "Configure parameters for the specified node
          (Partially qualified location allowed)";
        leaf disable {
          xr:xr-xml-map "rcmd_cfg:Disable";
          xr:xr-cli-map "disable ";
          type empty;
          description
            "Disables the monitoring of route convergence
            on specified location";
        }
        leaf enable {
          xr:xr-xml-map "rcmd_cfg:Enable";
          type empty;
          description
            "Enable Configure parameters for the specified
            node (Partially qualified location allowed).
            Deletion of this object also causes deletion
            of all associated objects under Node.";
        }
        leaf node-name {
          xr:xr-xml-map "rcmd_cfg:NodeName";
          type xr:Pq-node-id;
          description
            "Wildcard expression(eg. */*/*, R/*/*, R/S/*,
            R/S/I)";
        }
      }
    }
    leaf event-buffer-size {
      xr:xr-xml-map "rcmd_cfg:EventBufferSize";
      xr:xr-cli-map "router-convergence event-buffer-size <number> ";
      type uint32 {
        range "100..500";
      }
      description
        "Event buffer size for storing event traces (as
        number of events)";
    }
    leaf prefix-monitor-limit {
      xr:xr-xml-map "rcmd_cfg:PrefixMonitorLimit";
      xr:xr-cli-map "router-convergence prefix-monitoring-limit <nu"+
        "mber> ";
      type uint32 {
        range "0..100";
      }
      description "Limits Individual Prefix Monitoring";
    }
    leaf disable {
      xr:xr-xml-map "rcmd_cfg:Disable";
      xr:xr-cli-map "router-convergence disable ";
      type empty;
      description
        "Disable the monitoring of route convergence on
        the entire router";
    }
    leaf enable {
      xr:xr-xml-map "rcmd_cfg:Enable";
      type empty;
      description
        "Enable Configure Router Convergence Monitoring.
        Deletion of this object also causes deletion of
        all associated objects under RouterConvergence.";
    }
    leaf max-events-stored {
      xr:xr-xml-map "rcmd_cfg:MaxEventsStored";
      xr:xr-cli-map "router-convergence max-events-stored <number> ";
      type uint32 {
        range "10..500";
      }
      description "Maximum number of events stored in the server";
    }
    leaf monitoring-interval {
      xr:xr-xml-map "rcmd_cfg:MonitoringInterval";
      xr:xr-cli-map "router-convergence monitoring-interval <number"+
        "> ";
      type uint32 {
        range "5..120";
      }
      units "minute";
      description "Interval in which to collect logs (in mins)";
    }
  }
}
