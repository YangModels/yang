module Cisco-IOS-XR-ethernet-lldp-cfg {

  /*** NAMESPACE / PREFIX DEFINITION ***/

  namespace "http://cisco.com/ns"+
    "/yang/Cisco-IOS-XR-ethernet-lldp-cfg";


  prefix "ethernet-lldp-cfg";

  /*** LINKAGE (IMPORTS / INCLUDES) ***/

  import Cisco-IOS-XR-types { prefix "xr"; }

  import Cisco-IOS-XR-ifmgr-cfg { prefix "a1"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ethernet-lldp package configuration.

     This module contains definitions
     for the following management objects:
       lldp: Enable LLDP, or configure global LLDP subcommands

     This YANG module augments the
       Cisco-IOS-XR-ifmgr-cfg
     module with configuration data.

     Copyright (c) 2013-2015 by Cisco Systems, Inc.
     All rights reserved.";

  revision "2015-11-09" {
    description
      "IOS XR 6.0 revision.";
  }


  container lldp {
    xr:xr-xml-map "lldp_cfg:LLDP";
    description "Enable LLDP, or configure global LLDP subcommands";

    container tlv-select {
      xr:xr-xml-map "lldp_cfg:tlv-select";
      presence "Indicates a tlv-select node is configured.";
      description "Selection of LLDP TLVs to disable";

      container system-name {
        xr:xr-xml-map "lldp_cfg:system-name";
        description "System Name TLV";
        leaf disable {
          xr:xr-xml-map "lldp_cfg:Disable";
          xr:xr-cli-map "lldp tlv-select system-name disable ";
          type boolean;
          default "false";
          description "disable System Name TLV";
        }
      }

      container port-description {
        xr:xr-xml-map "lldp_cfg:port-description";
        description "Port Description TLV";
        leaf disable {
          xr:xr-xml-map "lldp_cfg:Disable";
          xr:xr-cli-map "lldp tlv-select port-description disable ";
          type boolean;
          default "false";
          description "disable Port Description TLV";
        }
      }

      container system-description {
        xr:xr-xml-map "lldp_cfg:system-description";
        description "System Description TLV";
        leaf disable {
          xr:xr-xml-map "lldp_cfg:Disable";
          xr:xr-cli-map "lldp tlv-select system-description disable"+
            " ";
          type boolean;
          default "false";
          description "disable System Description TLV";
        }
      }

      container system-capabilities {
        xr:xr-xml-map "lldp_cfg:system-capabilities";
        description "System Capabilities TLV";
        leaf disable {
          xr:xr-xml-map "lldp_cfg:Disable";
          xr:xr-cli-map "lldp tlv-select system-capabilities disabl"+
            "e ";
          type boolean;
          default "false";
          description "disable System Capabilities TLV";
        }
      }

      container management-address {
        xr:xr-xml-map "lldp_cfg:management-address";
        description "Management Address TLV";
        leaf disable {
          xr:xr-xml-map "lldp_cfg:Disable";
          xr:xr-cli-map "lldp tlv-select management-address disable"+
            " ";
          type boolean;
          default "false";
          description "disable Management Address TLV";
        }
      }
      leaf tlv-select-enter {
        xr:xr-xml-map "lldp_cfg:tlv-select-enter";
        type boolean;
        mandatory true;
        description "enter lldp tlv-select submode";
      }
    }
    leaf holdtime {
      xr:xr-xml-map "lldp_cfg:Holdtime";
      xr:xr-cli-map "lldp holdtime <number> ";
      type uint32 {
        range "0..65535";
      }
      description
        "Length  of time  (in sec) that receiver must
        keep this packet";
    }
    leaf enable-subintf {
      xr:xr-xml-map "lldp_cfg:EnableSubintf";
      xr:xr-cli-map "lldp subinterfaces enable ";
      type boolean;
      default "false";
      description
        "Enable or disable LLDP on Sub-interfaces as well
        globally";
    }
    leaf timer {
      xr:xr-xml-map "lldp_cfg:Timer";
      xr:xr-cli-map "lldp timer <number> ";
      type uint32 {
        range "5..65534";
      }
      default "30";
      description
        "Specify the rate at which LLDP packets are sent
        (in sec)";
    }
    leaf reinit {
      xr:xr-xml-map "lldp_cfg:Reinit";
      xr:xr-cli-map "lldp reinit <number> ";
      type uint32 {
        range "2..5";
      }
      default "2";
      description
        "Delay (in sec) for LLDP initialization on any
        interface";
    }
    leaf enable {
      xr:xr-xml-map "lldp_cfg:Enable";
      type boolean;
      default "false";
      description "Enable or disable LLDP globally";
    }
  }

  augment "/a1:interface-configurations/a1:interface-configuration" {

    container lldp {
      xr:xr-xml-map "lldp_interface_cfg:LLDP";
      presence "Indicates a lldp node is configured.";
      description "Disable LLDP TX or RX";

      container transmit {
        xr:xr-xml-map "lldp_interface_cfg:Transmit";
        description "Disable LLDP TX";
        leaf disable {
          xr:xr-xml-map "lldp_interface_cfg:Disable";
          type boolean;
          default "false";
          description "disable LLDP TX";
        }
      }

      container receive {
        xr:xr-xml-map "lldp_interface_cfg:Receive";
        description "Disable LLDP RX";
        leaf disable {
          xr:xr-xml-map "lldp_interface_cfg:Disable";
          type boolean;
          default "false";
          description "disable LLDP RX";
        }
      }
      leaf lldp-intf-enter {
        xr:xr-xml-map "lldp_interface_cfg:lldp-intf-enter";
        type boolean;
        mandatory true;
        description "enter LLDP interface submode";
      }
    }
    description
      "This augment extends the configuration data of
      'Cisco-IOS-XR-ifmgr-cfg'";
  }
}
