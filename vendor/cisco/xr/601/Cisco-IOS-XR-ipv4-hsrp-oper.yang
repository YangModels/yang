module Cisco-IOS-XR-ipv4-hsrp-oper {

  /*** NAMESPACE / PREFIX DEFINITION ***/

  namespace "http://cisco.com/ns/yang/Cisco-IOS-XR-ipv4-hsrp-oper";


  prefix "ipv4-hsrp-oper";

  /*** LINKAGE (IMPORTS / INCLUDES) ***/

  import ietf-inet-types { prefix "inet"; }

  import Cisco-IOS-XR-types { prefix "xr"; }

  include Cisco-IOS-XR-ipv4-hsrp-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ipv4-hsrp package operational data.

     This module contains definitions
     for the following management objects:
       hsrp: HSRP operational data

     Copyright (c) 2013-2015 by Cisco Systems, Inc.
     All rights reserved.";

  revision "2015-11-09" {
    description
      "IOS XR 6.0 revision.";
  }


  container hsrp {
    xr:xr-xml-map "hsrp_oper:HSRP";
    config false;
    description "HSRP operational data";

    container ipv4 {
      xr:xr-xml-map "hsrp_oper:IPv4";
      description "IPv4 HSRP information";

      container groups {
        xr:xr-xml-map "hsrp_oper:GroupTable";
        description "The HSRP standby group table";

        list group {
          xr:xr-xml-map "hsrp_oper:Group";
          key "interface-name group-number";
          description "An HSRP standby group";
          leaf interface-name {
            xr:xr-xml-map "hsrp_oper:InterfaceName";
            type xr:Interface-name;
            description "The interface name";
          }
          leaf group-number {
            xr:xr-xml-map "hsrp_oper:GroupNumber";
            type int32;
            description "The HSRP group number";
          }
          uses STANDBY-GRP-INFO;
        }
      }

      container tracked-interfaces {
        xr:xr-xml-map "hsrp_oper:TrackedInterfaceTable";
        description "The HSRP tracked interfaces table";

        list tracked-interface {
          xr:xr-xml-map "hsrp_oper:TrackedInterface";
          key "interface-name group-number tracked-interface-name";
          description "An HSRP tracked interface entry";
          leaf interface-name {
            xr:xr-xml-map "hsrp_oper:InterfaceName";
            type xr:Interface-name;
            description "The interface name of the interface";
          }
          leaf group-number {
            xr:xr-xml-map "hsrp_oper:GroupNumber";
            type int32;
            description "The HSRP group number";
          }
          leaf tracked-interface-name {
            xr:xr-xml-map "hsrp_oper:TrackedInterfaceName";
            type xr:Interface-name;
            description
              "The interface name of the interface being
              tracked";
          }
          uses STANDBY-TRACKEDIF-INFO;
        }
      }

      container interfaces {
        xr:xr-xml-map "hsrp_oper:InterfaceTable";
        description "The HSRP interface information table";

        list interface {
          xr:xr-xml-map "hsrp_oper:Interface";
          key "interface-name";
          description "A HSRP interface entry";
          leaf interface-name {
            xr:xr-xml-map "hsrp_oper:InterfaceName";
            type xr:Interface-name;
            description "The interface name";
          }
          uses STANDBY-IF-INFO;
        }
      }
    }

    container mgo-sessions {
      xr:xr-xml-map "hsrp_oper:MGOSessionTable";
      description "HSRP MGO session table";

      list mgo-session {
        xr:xr-xml-map "hsrp_oper:MGOSession";
        key "session-name";
        description "HSRP MGO session";
        leaf session-name {
          xr:xr-xml-map "hsrp_oper:SessionName";
          type xr:Cisco-ios-xr-string;
          description "HSRP MGO session name";
        }
        uses HSRP-MGO-INFO;
      }
    }

    container ipv6 {
      xr:xr-xml-map "hsrp_ipv6_oper:IPv6";
      description "IPv6 HSRP information";

      container tracked-interfaces {
        xr:xr-xml-map "hsrp_ipv6_oper:TrackedInterfaceTable";
        description "The HSRP tracked interfaces table";

        list tracked-interface {
          xr:xr-xml-map "hsrp_ipv6_oper:TrackedInterface";
          key "interface-name group-number tracked-interface-name";
          description "An HSRP tracked interface entry";
          leaf interface-name {
            xr:xr-xml-map "hsrp_ipv6_oper:InterfaceName";
            type xr:Interface-name;
            description "The interface name of the interface";
          }
          leaf group-number {
            xr:xr-xml-map "hsrp_ipv6_oper:GroupNumber";
            type int32;
            description "The HSRP group number";
          }
          leaf tracked-interface-name {
            xr:xr-xml-map "hsrp_ipv6_oper:TrackedInterfaceName";
            type xr:Interface-name;
            description
              "The interface name of the interface being
              tracked";
          }
          uses STANDBY-TRACKEDIF-INFO;
        }
      }

      container groups {
        xr:xr-xml-map "hsrp_ipv6_oper:GroupTable";
        description "The HSRP standby group table";

        list group {
          xr:xr-xml-map "hsrp_ipv6_oper:Group";
          key "interface-name group-number";
          description "An HSRP standby group";
          leaf interface-name {
            xr:xr-xml-map "hsrp_ipv6_oper:InterfaceName";
            type xr:Interface-name;
            description "The interface name";
          }
          leaf group-number {
            xr:xr-xml-map "hsrp_ipv6_oper:GroupNumber";
            type int32;
            description "The HSRP group number";
          }
          uses STANDBY-GRP-INFO;
        }
      }

      container interfaces {
        xr:xr-xml-map "hsrp_ipv6_oper:InterfaceTable";
        description "The HSRP interface information table";

        list interface {
          xr:xr-xml-map "hsrp_ipv6_oper:Interface";
          key "interface-name";
          description "A HSRP interface entry";
          leaf interface-name {
            xr:xr-xml-map "hsrp_ipv6_oper:InterfaceName";
            type xr:Interface-name;
            description "The interface name";
          }
          uses STANDBY-IF-INFO;
        }
      }
    }

    container bfd-sessions {
      xr:xr-xml-map "hsrp_oper:BFDSessionTable";
      description "The table of HSRP BFD Sessions";

      list bfd-session {
        xr:xr-xml-map "hsrp_oper:BFDSession";
        key "interface-name ip-address";
        description "An HSRP BFD Session";
        leaf interface-name {
          xr:xr-xml-map "hsrp_oper:InterfaceName";
          type xr:Interface-name;
          description "The interface name";
        }
        leaf ip-address {
          xr:xr-xml-map "hsrp_oper:IPAddress";
          type inet:ip-address-no-zone;
          description "Destination IP Address of BFD Session";
        }
        uses STANDBY-BFD-INFO;
      }
    }

    container summary {
      xr:xr-xml-map "hsrp_oper:Summary";
      description "HSRP summary statistics";
      uses HSRP-SUMMARY-INFO;
    }
  }
}
