module Cisco-IOS-XR-atm-vcm-oper {

  /*** NAMESPACE / PREFIX DEFINITION ***/

  namespace "http://cisco.com/ns/yang/Cisco-IOS-XR-atm-vcm-oper";


  prefix "atm-vcm-oper";

  /*** LINKAGE (IMPORTS / INCLUDES) ***/

  import Cisco-IOS-XR-types { prefix "xr"; }

  import Cisco-IOS-XR-atm-common-datatypes { prefix "dt1"; }

  include Cisco-IOS-XR-atm-vcm-oper-sub4 {
    revision-date 2015-11-09;
  }

  include Cisco-IOS-XR-atm-vcm-oper-sub3 {
    revision-date 2015-11-09;
  }

  include Cisco-IOS-XR-atm-vcm-oper-sub2 {
    revision-date 2015-11-09;
  }

  include Cisco-IOS-XR-atm-vcm-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR atm-vcm package operational data.

     This module contains definitions
     for the following management objects:
       atm-vcm: ATM VCM operational data

     Copyright (c) 2013-2015 by Cisco Systems, Inc.
     All rights reserved.";

  revision "2015-11-09" {
    description
      "IOS XR 6.0 revision.";
  }

  typedef Atm-pvc-vpi-range {
    type uint32 {
      range "0..4095";
    }
    description "Atm pvc vpi range";
  }
  typedef Atm-pvc-vci-range {
    type uint32 {
      range "1..65535";
    }
    description "Atm pvc vci range";
  }

  container atm-vcm {
    xr:xr-xml-map "atm_vcm_oper:ATM_VCM";
    config false;
    description "ATM VCM operational data";

    container nodes {
      xr:xr-xml-map "atm_vcm_oper:NodeTable";
      description "Contains all the nodes";

      list node {
        xr:xr-xml-map "atm_vcm_oper:Node";
        key "node-name";
        description
          "The node on which ATM Interfaces/VCs/VPs are
          located";

        container vcs {
          xr:xr-xml-map "atm_vcm_oper:VCTable";
          description "Contains all VC information for node";

          list vc {
            xr:xr-xml-map "atm_vcm_oper:VC";
            key "interface-name";
            description "All VC information on a node";
            leaf interface-name {
              xr:xr-xml-map "atm_vcm_oper:InterfaceName";
              type xr:Interface-name;
              description "Interface name";
            }
            leaf vpi {
              xr:xr-xml-map "atm_vcm_oper:VPI";
              type Atm-pvc-vpi-range;
              description "VPI";
            }
            leaf vci {
              xr:xr-xml-map "atm_vcm_oper:VCI";
              type Atm-pvc-vci-range;
              description "VCI";
            }
            uses ATM-VCM-VC;
          }
        }

        container cell-packs {
          xr:xr-xml-map "atm_vcm_oper:CellPackTable";
          description
            "Contains all cell packing information for node";

          list cell-pack {
            xr:xr-xml-map "atm_vcm_oper:CellPack";
            description "All cell packing information on a node";
            leaf interface-name {
              xr:xr-xml-map "atm_vcm_oper:InterfaceName";
              type xr:Interface-name;
              description "Interface name";
            }
            leaf pci {
              xr:xr-xml-map "atm_vcm_oper:PCI";
              type int32;
              description "PCI";
            }
            uses ATM-CELL-PACKING-DATA;
          }
        }

        container pvps {
          xr:xr-xml-map "atm_vcm_oper:PVPTable";
          description "Contains all L2 PVP information for node";

          list pvp {
            xr:xr-xml-map "atm_vcm_oper:PVP";
            key "interface-name";
            description "All L2 PVP information on a node";
            leaf interface-name {
              xr:xr-xml-map "atm_vcm_oper:InterfaceName";
              type xr:Interface-name;
              description "Interface name";
            }
            leaf vpi {
              xr:xr-xml-map "atm_vcm_oper:VPI";
              type int32;
              description "VPI";
            }
            uses ATM-VCM-VC;
          }
        }

        container class-links {
          xr:xr-xml-map "atm_vcm_oper:ClassLinkTable";
          description
            "Contains all class link information for node";

          list class-link {
            xr:xr-xml-map "atm_vcm_oper:ClassLink";
            key "vpi";
            description "All ATM VC information on a node";
            leaf vpi {
              xr:xr-xml-map "atm_vcm_oper:VPI";
              type int32;
              description "VPI";
            }
            leaf vci {
              xr:xr-xml-map "atm_vcm_oper:VCI";
              type int32;
              description "VCI";
            }
            uses ATM-CLASS-LINK-VPI-VCI;
          }
        }

        container interfaces {
          xr:xr-xml-map "atm_vcm_oper:InterfaceTable";
          description "Contains all Interface information for node";

          list interface {
            xr:xr-xml-map "atm_vcm_oper:Interface";
            key "interface-name";
            description "ATM Interface data";
            leaf interface-name {
              xr:xr-xml-map "atm_vcm_oper:InterfaceName";
              type xr:Interface-name;
              description "Interface name";
            }
            uses ATM-VCM-IF;
          }
        }

        container vp-tunnels {
          xr:xr-xml-map "atm_vcm_oper:VPTunnelTable";
          description "Contains all VP-tunnel information for node";

          list vp-tunnel {
            xr:xr-xml-map "atm_vcm_oper:VPTunnel";
            key "interface-name";
            description "All VP-tunnel information on a node";
            leaf interface-name {
              xr:xr-xml-map "atm_vcm_oper:InterfaceName";
              type xr:Interface-name;
              description "Interface name";
            }
            leaf vpi {
              xr:xr-xml-map "atm_vcm_oper:VPI";
              type int32;
              description "VPI";
            }
            uses ATM-VCM-VP;
          }
        }
        leaf node-name {
          xr:xr-xml-map "atm_vcm_oper:NodeName";
          type xr:Node-id;
          description "The node name";
        }
      }
    }
  }
}
