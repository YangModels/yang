submodule Cisco-IOS-XR-procfind-oper-sub1 {
  belongs-to Cisco-IOS-XR-procfind-oper {
    prefix Cisco-IOS-XR-procfind-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR procfind package operational data.
     
     Copyright (c) 2013-2020 by Cisco Systems, Inc.
     All rights reserved.";

  revision 2020-02-28 {
    description
      "Added new field PID in schema.";
    semver:module-version "2.0.0";
  }
  revision 2019-04-05 {
    description
      "Establish semantic version baseline.";
    semver:module-version "1.0.1";
  }
  revision 2019-02-18 {
    description
      "Added good description for bag fields.";
  }
  revision 2015-11-09 {
    description
      "IOS XR 6.0 revision.";
  }

  grouping PROCFIND-PROC {
    description
      "Procfind information on a single running process";
    leaf nodeid {
      type uint32;
      description
        "Node ID";
    }
    leaf nodetype {
      type uint32;
      description
        "Type of the node RP/LC/DRP";
    }
    leaf pid {
      type int32;
      description
        "Process ID";
    }
    leaf jid {
      type int32;
      description
        "Job ID";
    }
    leaf num-threads {
      type int32;
      description
        "Number of threads";
    }
    leaf name {
      type string;
      description
        "Process name";
    }
  }
}
