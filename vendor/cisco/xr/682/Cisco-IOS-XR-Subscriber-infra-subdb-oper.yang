module Cisco-IOS-XR-Subscriber-infra-subdb-oper {
  namespace "http://cisco.com/ns/yang/Cisco-IOS-XR-Subscriber-infra-subdb-oper";
  prefix subscriber-infra-subdb-oper;

  import Cisco-IOS-XR-types {
    prefix xr;
  }
  import cisco-semver {
    prefix semver;
  }
  include Cisco-IOS-XR-Subscriber-infra-subdb-oper-sub2 {
    revision-date 2021-09-17;
  }
  include Cisco-IOS-XR-Subscriber-infra-subdb-oper-sub1 {
    revision-date 2021-09-17;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR Subscriber-infra-subdb package operational data.
     
     This module contains definitions
     for the following management objects:
       subscriber-database: Subscriber database operational data
     
     Copyright (c) 2013-2021 by Cisco Systems, Inc.
     All rights reserved.";

  revision 2021-09-17 {
    description
      "Adding new bag for retrieving subdb sirflap history .";
    semver:module-version "2.1.0";
  }
  revision 2021-02-22 {
    description
      "Adding yang support to retrive server connection time-stats.
       2020-11-19
       Added new bag for Subscriber database connection client statistics.";
    semver:module-version "2.1.0";
  }
  revision 2020-04-02 {
    description
      "Added new bag for Subscriber database transition states and cfg object types.";
    semver:module-version "2.0.0";
  }
  revision 2019-04-05 {
    description
      "Establish semantic version baseline.";
    semver:module-version "1.0.1";
  }
  revision 2018-09-28 {
    description
      "Fixed Subscriber database Association.";
  }
  revision 2015-11-09 {
    description
      "IOS XR 6.0 revision.";
  }

  typedef Sub-db-time-stat {
    type enumeration {
      enum "activate-time-stats" {
        value 0;
        description
          "SUBDB time stats activate-time-stats";
      }
      enum "config-gen-time-stats" {
        value 1;
        description
          "SUBDB time stats config-gen-time-stats";
      }
      enum "config-done-time-stats" {
        value 2;
        description
          "SUBDB time stats config-done-time-stats";
      }
      enum "apply-time-stats" {
        value 3;
        description
          "SUBDB time stats apply-time-stats";
      }
    }
    description
      "Sub db time stat";
  }

  container subscriber-database {
    config false;
    description
      "Subscriber database operational data";
    container nodes {
      description
        "List of nodes for which subscriber data is
         collected";
      list node {
        key "node-name";
        description
          "Subscriber data for a particular node";
        container subdb-assoc {
          description
            "Subscriber data for associated templates";
          container labels {
            description
              "List of associated subscriber labels";
            list label {
              key "subscriber-label";
              description
                "Association for a given subscriber label";
              leaf subscriber-label {
                type uint32;
                description
                  "Subscriber label";
              }
              uses SUBDB-ASSOC-SESSION;
            }
          }
        }
        container association {
          description
            "Subscriber data for associated templates";
          container labels {
            description
              "List of associated subscriber labels";
            list label {
              key "subscriber-label";
              description
                "Association for a given subscriber label";
              leaf subscriber-label {
                type xr:Hex-integer;
                description
                  "Subscriber label";
              }
              uses SUBDB-ASSOC-SESSION;
            }
          }
        }
        container summary {
          description
            "Subscriber data for associated templates";
          uses SUBDB-SUMMARY-COUNTS-BAG;
        }
        container connection {
          description
            "Subscriber data for a client connected";
          container server-time-stats {
            description
              "Subscriber data for a client connected";
            list server-time-stat {
              description
                "Subscriber timestats for client connected.";
              leaf client-name {
                type xr:Cisco-ios-xr-string;
                description
                  "Client Name";
              }
              leaf type-id {
                type Sub-db-time-stat;
                description
                  "Stats Type ID";
              }
              uses SUBDB-SERVER-TIMESTAT-INFO;
            }
          }
        }
        container session {
          description
            "Subscriber management session information";
          container labels {
            description
              "Subscriber management list of subscriber
               labels";
            list label {
              key "subscriber-label";
              description
                "Session information for a subscriber label";
              leaf subscriber-label {
                type xr:Hex-integer;
                description
                  "Subscriber label";
              }
              uses SUBDB-SUBSCRIBER-OBJ;
            }
          }
        }
        leaf node-name {
          type xr:Node-id;
          description
            "Node name";
        }
      }
    }
  }
}
