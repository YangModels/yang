module Cisco-IOS-XR-ipv4-smiap-oper {
  namespace "http://cisco.com/ns/yang/Cisco-IOS-XR-ipv4-smiap-oper";
  prefix ipv4-smiap-oper;

  import Cisco-IOS-XR-types {
    prefix xr;
  }
  import cisco-semver {
    prefix semver;
  }
  include Cisco-IOS-XR-ipv4-smiap-oper-sub1 {
    revision-date 2019-04-05;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ipv4-smiap package operational data.
     
     This module contains definitions
     for the following management objects:
       ipv4-virtual: IPv4 virtual address for management interfaces
     
     Copyright (c) 2013-2019 by Cisco Systems, Inc.
     All rights reserved.";

  revision 2019-04-05 {
    description
      "Establish semantic version baseline.";
    semver:module-version "2.0.0";
  }
  revision 2015-11-09 {
    description
      "IOS XR 6.0 revision.";
  }

  container ipv4-virtual {
    config false;
    description
      "IPv4 virtual address for management interfaces";
    container address {
      description
        "Address family";
      container vrfs {
        description
          "VRF entry table";
        list vrf {
          key "vrf-name";
          description
            "smiap vrf entry";
          leaf vrf-name {
            type xr:Cisco-ios-xr-string;
            description
              "VRF name";
          }
          uses SMIAP-VRF-ENTRY;
        }
      }
    }
  }
}
