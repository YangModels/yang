module Cisco-IOS-XR-olc-cfg {
  namespace "http://cisco.com/ns/yang/Cisco-IOS-XR-olc-cfg";
  prefix olc-cfg;

  import ietf-inet-types {
    prefix inet;
  }
  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR olc package configuration.
     
     This module contains definitions
     for the following management objects:
       olc: Optical Application Configurations
     
     Copyright (c) 2013-2024 by Cisco Systems, Inc.
     All rights reserved.";

  revision 2024-12-20 {
    description
      "Added new rules for message generation for syslogs";
    semver:module-version "1.0.0";
  }
  revision 2024-12-04 {
    description
      "Add new configs for NCS1014 APC control loop applications";
  }
  revision 2024-10-01 {
    description
      "Added new enum entry for CALIBRATION mode in bag";
  }
  revision 2024-08-21 {
    description
      "Fix controller name in ALC Local Status bag";
  }
  revision 2024-05-28 {
    description
      "1010-1014 CLI re-group for conditional install";
  }
  revision 2024-04-09 {
    description
      "Fix units in bag description";
  }
  revision 2023-12-18 {
    description
      "Added new configs for ALC span loss deviation alarm threshold";
  }
  revision 2023-10-18 {
    description
      "Added new configs for span loss deviation alarm threshold";
  }
  revision 2023-10-12 {
    description
      "Added gain-range-margin config";
  }
  revision 2023-09-29 {
    description
      "Added enum type for config manual mode configs for olc applications that support it";
  }
  revision 2023-08-21 {
    description
      "APC manual config addition";
  }
  revision 2023-08-16 {
    description
      "Updated sysdb path for span-loss-corr-threshold";
  }
  revision 2023-07-12 {
    description
      "Otdr Raman Turn Up Relaxation Factor configuration CLI";
  }
  revision 2023-06-27 {
    description
      "Span-Mode APC configs for enable, pause, thresholds added";
  }
  revision 2023-05-29 {
    description
      "Added Raman Tuning Mode configuration CLI";
  }
  revision 2023-05-02 {
    description
      "Raman Tuning Manual Mode config CLI addition";
  }
  revision 2023-04-20 {
    description
      "Otdr Autoscan and Raman Turn Up CLI addition";
  }
  revision 2023-03-25 {
    description
      "Added Max patchcord loss threshold configuration CLI";
  }
  revision 2023-01-20 {
    description
      "Bfr pause config added";
  }
  revision 2022-06-21 {
    description
      "APC Dual Band PSD configuration CLI";
  }
  revision 2022-06-01 {
    description
      "C+L band partner band IPV4 configurations CLI";
  }
  revision 2022-05-31 {
    description
      "Automatic link config CLI addition.";
  }
  revision 2022-02-28 {
    description
      "Enhancement to fiber_type configuration by adding new fiber type.";
  }
  revision 2022-01-19 {
    description
      "Enhancement to Span length config tx direction CLI addition.";
  }
  revision 2022-01-17 {
    description
      "Enhancement to Link tuner config CLI addition.";
  }
  revision 2021-12-07 {
    description
      "Link tuner config CLI addition.";
  }
  revision 2021-01-19 {
    description
      "APC config CLI addition.";
  }
  revision 2020-11-04 {
    description
      "Initial Revision.";
  }
  revision 2019-04-05 {
    description
      "Establish semantic version baseline.";
  }
  revision 2015-11-09 {
    description
      "IOS XR 6.0 revision.";
  }

  typedef Cfg-state {
    type enumeration {
      enum "none" {
        value 0;
        description
          "NONE";
      }
      enum "disable" {
        value 1;
        description
          "DISABLE";
      }
      enum "enable" {
        value 2;
        description
          "ENABLE";
      }
    }
    description
      "Cfg state";
  }

  typedef Cfg-state-ext {
    type enumeration {
      enum "none" {
        value 0;
        description
          "NONE";
      }
      enum "disable" {
        value 1;
        description
          "DISABLE";
      }
      enum "enable" {
        value 2;
        description
          "ENABLE";
      }
      enum "manual" {
        value 3;
        description
          "MANUAL";
      }
    }
    description
      "Cfg state ext";
  }

  typedef Ampli-apc-cfg-mode {
    type enumeration {
      enum "none" {
        value 0;
        description
          "NONE";
      }
      enum "span-mode" {
        value 1;
        description
          "SPAN MODE";
      }
    }
    description
      "Ampli apc cfg mode";
  }

  typedef Channel-apc-cfg-mode {
    type enumeration {
      enum "none" {
        value 0;
        description
          "NONE";
      }
      enum "flat-psd-eq-mode" {
        value 1;
        description
          "FLAT PSD EQ MODE";
      }
    }
    description
      "Channel apc cfg mode";
  }

  typedef Raman-tuning-mode {
    type enumeration {
      enum "none" {
        value 0;
        description
          "NONE";
      }
      enum "c-l-band" {
        value 1;
        description
          "C L band";
      }
      enum "c-band-only" {
        value 2;
        description
          "C band only";
      }
    }
    description
      "Raman tuning mode";
  }

  typedef Fiber {
    type enumeration {
      enum "smf" {
        value 1;
        description
          "SMF";
      }
      enum "smf-28e" {
        value 2;
        description
          "SMF 28E";
      }
      enum "tw-rs" {
        value 3;
        description
          "TW RS";
      }
      enum "tw-reach" {
        value 4;
        description
          "TW Reach";
      }
      enum "e-leaf" {
        value 5;
        description
          "E LEAF";
      }
      enum "free-light" {
        value 6;
        description
          "FREE LIGHT";
      }
      enum "metro-core" {
        value 7;
        description
          "METRO CORE";
      }
      enum "tera-light" {
        value 8;
        description
          "TERA LIGHT";
      }
      enum "tw-minus" {
        value 9;
        description
          "TW minus";
      }
      enum "tw-plus" {
        value 10;
        description
          "TW plus";
      }
      enum "ull-smf28" {
        value 11;
        description
          "ULL SMF28";
      }
    }
    description
      "Fiber";
  }

  grouping APC-SPAN-MODE-ENABLE {
    description
      "Common node of apc-span-mode-dir-tx,
       apc-span-mode-dir-rx";
    leaf apc-span-mode-enable {
      type empty;
      description
        "Configuration to enable APC span-mode
         configuration.";
    }
  }

  grouping APC-LOCAL-DIR-DISABLE {
    description
      "Common node of apc-local-dir-tx, apc-local-dir-rx";
    leaf apc-local-dir-disable {
      type empty;
      description
        "Configuration to disable local APC regulation.
         APC is enabled on by default.";
    }
  }

  grouping APC-SPAN-MODE-PAUSE-ENABLE {
    description
      "Common node of apc-span-mode-pause-dir-tx,
       apc-span-mode-pause-dir-rx";
    leaf apc-span-mode-pause-enable {
      type empty;
      description
        "Configuration to pause APC span-mode
         configuration.";
    }
  }

  grouping APC-SPAN-LOSS-CORR-THRESHOLD-VALUE {
    description
      "Common node of
       apc-span-loss-corr-threshold-dir-tx,
       apc-span-loss-corr-threshold-dir-rx";
    leaf apc-span-loss-corr-threshold-value {
      type uint32 {
        range "2..200";
      }
      description
        "APC spanloss correction threshold configuration
         in TX direction";
    }
  }

  container olc {
    description
      "Optical Application Configurations";
    container controller-rsips {
      description
        "Global scope configurations";
      list controller-rsip {
        key "controller";
        description
          "Controller specific configurations";
        container apc {
          description
            "APC configuration";
          container dual-band-psds {
            description
              "Dual Band Power spectral density
               configuration";
            list dual-band-psd {
              key "psd-index";
              description
                "Dual Band PSD Configuration";
              leaf psd-index {
                type uint32 {
                  range "1..33";
                }
                description
                  "PSD Index";
              }
              leaf psd-value {
                type int32 {
                  range "-300..230";
                }
                mandatory true;
                description
                  "Value in increments of 0.1 dBm per 12.5 GHz
                   , between -30.0 to 23.0.";
              }
            }
          }
          container psds {
            description
              "Power spectral density configuration";
            list psd {
              key "psd-index";
              description
                "PSD Configuration";
              leaf psd-index {
                type uint32 {
                  range "1..33";
                }
                description
                  "PSD Index";
              }
              leaf psd-value {
                type int32 {
                  range "-300..230";
                }
                mandatory true;
                description
                  "Value in increments of 0.1 dBm per 12.5 GHz
                   , between -30.0 to 23.0.";
              }
            }
          }
          leaf drop-psd {
            type int32 {
              range "-300..230";
            }
            description
              "Configuration for drop psd in increments of 0
               .1 dBm per 12.5 GHz, between -30.0 to 23.0.";
          }
          leaf apc-pause {
            type empty;
            description
              "Pause APC on the domain";
          }
          leaf apc-cfg-state {
            type Cfg-state-ext;
            default "none";
            description
              "Config Enable, Disable or Manual";
          }
          leaf psd-min {
            type int32 {
              range "-400..230";
            }
            description
              "Configuration for minimum psd in increments
               of 0.1 dBm per 12.5 GHz, between -40.0 to 23
               .0.";
          }
        }
        container apc-local {
          description
            "APC agent per direction disable configuration";
          container apc-local-dir-tx {
            description
              "Disable APC agent in TX direction";
            uses APC-LOCAL-DIR-DISABLE;
          }
          container apc-local-dir-rx {
            description
              "Disable APC agent in RX direction";
            uses APC-LOCAL-DIR-DISABLE;
          }
        }
        container partner-band-config {
          description
            "Partner band port configuration";
          container partner-band-ipv4 {
            description
              "Partner band port IPv4 address configuration";
            container partner-port-ipv4-info {
              presence "enable partner-port-ipv4-info";
              description
                "IPv4 address of partner node and OTS
                 controller port information";
              leaf neighbor-address {
                type inet:ipv4-address-no-zone;
                description
                  "IPv4 address of the partner band";
              }
              leaf controller {
                type xr:Interface-name;
                description
                  "Controller RSIP";
              }
            }
          }
          container partner-band-local {
            description
              "Partner band port IPv4 address configuration";
            leaf partner-port-local-info {
              type xr:Interface-name;
              description
                "IPv4 address of partner node and OTS
                 controller port information";
            }
          }
        }
        container apc-span-mode {
          description
            "APC span-mode configuration";
          container apc-span-mode-dir-tx {
            description
              "APC span-mode configuration in TX direction";
            uses APC-SPAN-MODE-ENABLE;
          }
          container apc-span-mode-dir-rx {
            description
              "APC span-mode configuration in RX direction";
            uses APC-SPAN-MODE-ENABLE;
          }
        }
        container raman {
          description
            "Raman configuration";
          leaf raman-tune-mode-cfg-state {
            type Raman-tuning-mode;
            default "c-l-band";
            description
              "Config C and L band or C-band Only";
          }
          leaf raman-tune-target-gain {
            type uint32 {
              range "0..300";
            }
            description
              "Gain Value in increments of 0.1 dB, between 0
               .0 and 30.0 dB";
          }
          leaf raman-tune-cfg-state {
            type Cfg-state-ext;
            default "none";
            description
              "Change config state of Automatic Raman Tuning";
          }
        }
        container apc-span-loss-corr-threshold {
          description
            "APC spanloss correction threshold
             configuration";
          container apc-span-loss-corr-threshold-dir-rx {
            description
              "APC spanloss correction threshold
               configuration in RX direction";
            uses APC-SPAN-LOSS-CORR-THRESHOLD-VALUE;
          }
          container apc-span-loss-corr-threshold-dir-tx {
            description
              "APC spanloss correction threshold
               configuration in TX direction";
            uses APC-SPAN-LOSS-CORR-THRESHOLD-VALUE;
          }
        }
        container apc-span-mode-pause {
          description
            "APC span-mode pause configuration";
          container apc-span-mode-pause-dir-tx {
            description
              "APC span-mode pause configuration in TX
               direction";
            uses APC-SPAN-MODE-PAUSE-ENABLE;
          }
          container apc-span-mode-pause-dir-rx {
            description
              "APC span-mode pause configuration in RX
               direction";
            uses APC-SPAN-MODE-PAUSE-ENABLE;
          }
        }
        container link-tuner {
          description
            "Link tuner configuration";
          leaf spectrum-density {
            type uint32 {
              range "1..100";
            }
            default "81";
            description
              "Spectrum density configuration for the given
               controller";
          }
          leaf link-tuner-cfg-state {
            type Cfg-state-ext;
            default "none";
            description
              "Change config state of Link Tuner";
          }
        }
        container ampli-apc {
          description
            "Amplifier APC configuration";
          leaf ampli-apc-pause {
            type empty;
            description
              "Pause Amplifier APC on the domain";
          }
          leaf ampli-apc-cfg-state {
            type Ampli-apc-cfg-mode;
            default "none";
            description
              "Change config state of Amplifier APC.";
          }
        }
        container span-loss {
          description
            "Span loss configuration";
          leaf max-baseline-deviation {
            type uint32 {
              range "0..420";
            }
            description
              "Maximum allowed difference between measured
               Rx and baselined Rx span loss";
          }
          leaf signal-osc-max-deviation {
            type uint32 {
              range "0..420";
            }
            description
              "Minimum allowed difference between measured
               OSC and signal span loss";
          }
          leaf signal-osc-min-deviation {
            type uint32 {
              range "0..420";
            }
            description
              "Minimum allowed difference between measured
               OSC and signal span loss";
          }
          leaf min-baseline-deviation {
            type uint32 {
              range "0..420";
            }
            description
              "Minimum allowed difference between measured
               Rx and baselined Rx span loss";
          }
          leaf max-threshold {
            type uint32 {
              range "0..420";
            }
            description
              "Maximum threshold configuration for the given
               controller";
          }
          leaf min-threshold {
            type uint32 {
              range "0..420";
            }
            description
              "Minimum threshold configuration for the given
               controller";
          }
        }
        container bfr {
          description
            "BFR configuration";
          leaf bfr-pause {
            type empty;
            description
              "Pause BFR on the domain";
          }
        }
        container channel-apc {
          description
            "Wavelength Blocker APC configuration";
          leaf psd-target {
            type int32 {
              range "-400..230";
            }
            description
              "Value in increments of 0.1 dB, between -40.0
               and 23.0.";
          }
          leaf channel-apc-cfg-state {
            type Channel-apc-cfg-mode;
            default "none";
            description
              "Change config state of Amplifier APC.";
          }
          leaf channel-apc-pause {
            type empty;
            description
              "Pause Wavelength Blocker APC on the domain";
          }
        }
        container gain-estimator {
          description
            "Gain estimator configuration";
          leaf gain-estimator-cfg-state {
            type Cfg-state-ext;
            default "none";
            description
              "Change config state of Gain Estimator";
          }
        }
        container otdr {
          description
            "OTDR configuration";
          leaf otdr-autoscan-cfg-state {
            type Cfg-state;
            default "none";
            description
              "Change config state of Otdr Autoscan.";
          }
          leaf otdr-rtu-relaxation-factor {
            type uint32 {
              range "0..100";
            }
            units "percentage";
            default "0";
            description
              "Relaxation Factor configuration for the given
               controller";
          }
          leaf otdr-rtu-cfg-state {
            type Cfg-state;
            default "none";
            description
              "Change config state of Otdr Raman Turn Up.";
          }
        }
        leaf apc-alarm-discrepancy-threshold {
          type uint32 {
            range "5..200";
          }
          description
            "APC discrepancy threshold in increments of 0.1
             dB";
        }
        leaf rx-connector-loss {
          type string {
            length "1..6";
          }
          description
            "Rx connector loss in dB";
        }
        leaf tx-connector-loss {
          type string {
            length "1..6";
          }
          description
            "Tx connector loss in dB";
        }
        leaf fiber-type {
          type Fiber;
          default "smf";
          description
            "Fiber Type for given controller";
        }
        leaf max-patchcord-loss {
          type uint32 {
            range "0..200";
          }
          default "20";
          description
            "Max patchcord loss threshold configuration for
             the given controller";
        }
        leaf gain-range-margin {
          type uint32 {
            range "0..30";
          }
          description
            "RX Gain Range Margin between 0 and 3 dB";
        }
        leaf span-length {
          type uint32 {
            range "1..2000";
          }
          description
            "Span length in 0.1 km";
        }
        leaf apc-alarm-hold-off-timer {
          type uint32 {
            range "1..1800";
          }
          units "second";
          description
            "APC hold-off timer duration in seconds";
        }
        leaf controller {
          type xr:Interface-name;
          description
            "Controller RSIP";
        }
      }
    }
    container global-config {
      description
        "Global scope configurations";
      leaf auto-link-bringup {
        type empty;
        description
          "Enable Automatic link bringup.";
      }
    }
  }
}
