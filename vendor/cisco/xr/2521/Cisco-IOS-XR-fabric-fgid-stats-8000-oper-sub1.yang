submodule Cisco-IOS-XR-fabric-fgid-stats-8000-oper-sub1 {
  belongs-to Cisco-IOS-XR-fabric-fgid-stats-8000-oper {
    prefix Cisco-IOS-XR-fabric-fgid-stats-8000-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR fabric-fgid-stats-8000 package operational data.
     
     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  grouping FE-HW-FGID-BITMAP {
    description
      "Fgid bitmap on FE Asic HW";
    leaf asic-name {
      type string {
        length "0..16";
      }
      description
        "FE Asic";
    }
    leaf asic-type {
      type string {
        length "0..8";
      }
      description
        "FE Asic type";
    }
    leaf status {
      type string {
        length "0..4";
      }
      description
        "SW/HW fgid bitmap match";
    }
    list bitmap {
      max-elements "2";
      description
        "FGID Bitmap";
      leaf entry {
        type uint64;
        description
          "FGID Bitmap";
      }
    }
  }

  grouping FGID-DIAG-INFO {
    description
      "Fgid bitmap on rack FE asics";
    leaf rack-num {
      type uint32;
      description
        "Rack num";
    }
    list fe-asic {
      description
        "FGID bitmaps info on FE HW";
      uses FE-HW-FGID-BITMAP;
    }
  }

  grouping RACK-FGID-BITMAP {
    description
      "Rack Fgid Bitmaps";
    leaf rack {
      type uint32;
      description
        "Rack";
    }
    list bitmap {
      max-elements "2";
      description
        "Fgid bitmap";
      leaf entry {
        type uint64;
        description
          "Fgid bitmap";
      }
    }
  }

  grouping FAPID-INFO {
    description
      "Fabid information";
    leaf fapid {
      type uint32;
      description
        "Fapid";
    }
    leaf rack {
      type uint32;
      description
        "Rack";
    }
    leaf slot {
      type uint32;
      description
        "Slot";
    }
    leaf asic {
      type uint32;
      description
        "Asic";
    }
  }

  grouping FGID-INFO {
    description
      "Per FGID ID information";
    leaf fgid-id-xr {
      type uint32;
      description
        "FGID ID";
    }
    leaf num-fapids {
      type uint32;
      description
        "Number of assoicated fapids";
    }
    leaf client-id {
      type uint32;
      description
        "Client ID";
    }
    leaf client-name {
      type string;
      description
        "Client name";
    }
    leaf sdr-name {
      type string;
      description
        "SDR Name";
    }
    leaf num-up-racks {
      type uint32;
      description
        "Number of UP Racks";
    }
    leaf max-lcc-racks {
      type uint32;
      description
        "Maximum LCC Racks";
    }
    list fapid {
      description
        "Associated fapids";
      uses FAPID-INFO;
    }
    list fgid-bitmap {
      description
        "Racks FGID Bitmaps";
      uses RACK-FGID-BITMAP;
    }
    list rack-fgid-diag-info {
      description
        "FGID Diag per rack";
      uses FGID-DIAG-INFO;
    }
  }

  grouping FGID-APPL-STATS-INFO {
    description
      "Per application basis fabric multicast resource
       statistics information - no LR info";
    leaf appl-name {
      type string;
      description
        "multicast resource application name";
    }
    leaf inuse-fgids {
      type uint32;
      description
        "the number of inuse FGIDs by the appl";
    }
    leaf hwm-inuse-fgids {
      type uint32;
      description
        "the high water mark of inused FGIDs";
    }
    leaf inuse-fgids-act {
      type uint32;
      description
        "inuse FGIDs by the appl at appl registration
         time";
    }
    leaf alloc-fgids-act {
      type uint32;
      description
        "number allocated FGIDs by the appl after appl
         registration";
    }
    leaf free-fgids-act {
      type uint32;
      description
        "number free FGIDs by the appl after appl
         registration";
    }
  }

  grouping FGID-SYS-STATS-INFO {
    description
      "Per HFR basis fabric multicast resource
       statistics information";
    leaf total-fgids {
      type uint32;
      description
        "the total number of FGIDs";
    }
    leaf inuse-fgids {
      type uint32;
      description
        "the number of inuse FGIDs";
    }
    leaf hwm-inuse-fgids {
      type uint32;
      description
        "the high water mark of inuse FGIDs";
    }
  }

  grouping FGID-ALL-STATS-INFO {
    description
      "Fgid statistics information";
    container sys-stats {
      description
        "FGID system statistics";
      uses FGID-SYS-STATS-INFO;
    }
    list appl-stat {
      description
        "Application statistics";
      uses FGID-APPL-STATS-INFO;
    }
  }
}
