module Cisco-IOS-XR-openconfig-wavelength-router-ext {
  namespace "http://cisco.com/ns/yang/Cisco-IOS-XR-openconfig-wavelength-router-ext";
  prefix oc-wave-ext;

  import openconfig-wavelength-router {
    prefix oc-wave-router;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module is an extension of optical wavelength router model
     and contains the definition of extended parameters for media
     channels in order to optimize the AC1200 settings to get the highest
     performance and spectral efficiency.
     
     This module contains definitions for the following management objects:
     General Parameters
     Submarine Parameters
     
     Copyright (c) 2024 by Cisco Systems, Inc.
     All rights reserved.";

  revision 2024-11-30 {
    description
      "IOS XR 6.0 revision";
    reference "7.3.1";
  }

  grouping oc-wave-extended-regulation {
    description
      "Extended wavelength router parameters";
    container cisco {
      description
        "Extended wavelength router parameters";
      container config {
        description
          "Extended wavelength router config parameters";
        leaf regulation-enable {
          type boolean;
          description
            "Regulation config value";
        }
      }
      container state {
        config false;
        description
          "Regulation state container";
        leaf regulation-enable {
          type boolean;
          description
            "Regulation state value";
        }
      }
    }
  }

  augment "/oc-wave-router:wavelength-router/oc-wave-router:port-spectrum-power-profiles/oc-wave-router:port" {
    description
      "This augment extends the configuration data of
       'oc-wave-router'";
    uses oc-wave-extended-regulation;
  }
}
