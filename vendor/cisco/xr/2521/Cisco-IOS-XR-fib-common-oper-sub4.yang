submodule Cisco-IOS-XR-fib-common-oper-sub4 {
  belongs-to Cisco-IOS-XR-fib-common-oper {
    prefix Cisco-IOS-XR-fib-common-oper;
  }

  import ietf-inet-types {
    prefix inet;
  }
  import ietf-yang-types {
    prefix yang;
  }
  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR fib-common package operational data.
     
     Copyright (c) 2013-2025 by Cisco Systems, Inc.
     All rights reserved.";

  revision 2025-01-30 {
    description
      "Added UDP port global bag
       2025-01-24
         Added counter for ignoring FRR event
       2025-01-17
         Added number of allocated bytes to per protocol debug stats
       2025-01-09
         Added GUE V1 tunnel type
       2024-12-02
         Added Event History for NextHop Group Make-before-break
       2024-10-29
         Added tunnel encapsulation flag in route table information and added a new list of tunnel encapsulation data in route path information
       2024-10-10
         Added EncapID event history
       2024-09-24
         Added nexthop group named table
       2024-09-20
         Added backup-active leaf to next-hop-group/state container
       2024-09-17
         Added SRv6 prefix support for BSID accounting
       2024-09-11
         Moved misc container to global container instead of protocol container
       2024-09-10
         Added EncapID programming related fields
       2024-08-21
         Added time-of-last-rsrc-msg-update-in-msec and time-of-last-rsrc-nfn-update-in-msec to object counters
       2024-08-19
         Added viability info to FIB external-client instances
       2024-08-16
         Added FIB oor prevention support to FIB cef summary
       2024-08-12
         Added support for information display of PWHE Interfaces, added new entry (gil-interface-name) to key of RTEP table and modified existing entry type (tunnel-interface-name) of RTEP table
       2024-08-09
         Added aysnc error notify capability
       2024-07-26
         Added per-NHOP nh-idb-usable and per-interface usable elements
       2024-06-28
         Added key to route summary counters
       2024-06-26
         Removed oor-resource-counter
       2024-06-24
         Added misc/per-protocol-debug-statistics/bcdlv2-stats
       2024-06-20
         Added route summary counters per protocol
       2024-05-28
         Added l3-unequal-cost-ip-route-paths-count to platform capabilities
       2024-05-23
         Standardize naming of ipvpn-tunnel-type and add new ipvpn-tunnel-type-nh type
       2024-05-23
         Add is-loadinfo-collapsed flag to basic FIB table information
       2024-05-02
         Added rtep-source, tunnel-id, tunnel-ifh and overlay-proto keys to tunnel tables
       2024-01-25
         Increased ECMP/UCMP capability
       2024-01-12
         Add back error/oor state for telemetry in oc-aft-l3 model
       2023-12-01
         Add platform-pbtsv6-support to platform capabilities
       2023-11-29
         Added Nexthop group ID information
       2023-11-27
         Optimized schema for linklocal. Added is-non-recursive field to IP prefixes.
       2023-10-25
         Added GIL ID in PWHE information and Interface List attribute
       2023-10-24
         Consolidated nh-info tables by type
       2023-10-19
         Added NextHop group ID to ext client output
       2023-10-11
         Added schema for external client, fixed schema for hardware egress/ingress
       2023-10-10
         Added and modified NPU mask and PWHE information
       2023-10-04
         Added encap-id and stat-id to recursive-nexthop dependents.
       2023-10-02
         Added VXLAN TEP tables.
       2023-09-21
         Eliminate name conflicts between keys and values
       2023-09-18
         Separated schema of linklocal prefix table from generic prefix table.
       2023-09-14
         Added via-nexthop-group to show cef output
       2023-08-15
         Added new errors sub-tree.
       2023-07-31
         Made hierarchical-loadbalancing parameters mandatory
       2023-07-28
         Internal cleanup, some type name changes.
       2023-07-26
         Fixed schema for exact-route and linklocal
       2023-07-17
         Changed pbts related variable type from static to dynamic array
       2023-07-13
         Added is-unresolved and is-frr to prefix tables
       2023-07-07
         Standardized leaf names and types throughout.
       2023-06-26
         Fix schema for hardware egress/ingress option
       2023-06-15
         Changed vni-info-key-type to an enum and added tblid-vni-key to vni-info-key-type
       2023-06-02
         Two Stage platform ObjectId capability added for cef-misc
       2023-06-01
         Added new field to ltep-nve-tunnels in order keep track of destination address protocol
       2023-05-31
         SRv6 accounting support added for FIB cef
       2023-05-25
         SRv6 accounting support added for FIB cef-accounting
       2023-05-24
         Added new detail field for hardware egress/ingress option
       2023-05-11
         Added class-id to support full exact-route functionality
       2023-05-08
         Remove oc-aft model from fib oper model
       2023-05-04
         Added new field to rtep-tunnels in order keep track of destination address protocol
       2023-04-24
         Combined separate evni tables for BGP and RTEP-ID to single evni table
       2023-04-15
         Added changes for show cef Interface
       2023-04-14
         Added hardware ingress and egress path for evni
       2023-04-05
         Added srv6_hardware ingress/egress
       2023-03-31
         Added resource-summary-infos and modified ip-prefix-detail
       2023-03-29
         Changed recursive nexthop display to be generic for address types
       2023-03-28
         Modified Interface List ID size from 16-bit to 32-bit
       2023-03-28
         Modifed fib_sh_policy_rl_entry rate field to uint64_t
       2023-03-20
         Added some preprograming related fields.
       2023-03-18
         Removed node tag from cef-accounting container.
       2023-03-06
         Added global policy table
       2023-02-07
         Added Exact route schema changes
       2023-02-06
         Added proto-retry-db-summary.
       2023-02-06
         Added disable-rfc5549-ipv4-over-ipv6-nexthop platform capability.
       2023-01-27
         Updated schema for ResourceHardwareIngress and Egress support
       2023-01-27
         Added exceptions-v4, exceptions-v6 and exceptions-mpls.
       2023-01-25
         Added global-retry-db-summary.
       2023-01-24
         Added cef-table-summary, drops-v6 and drops-mpls.
       2023-01-23
         srv6 accounting support
       2023-01-20
         Summary statistics: Added udp-src-port-msb information
       2023-01-04
         Updated evni-tunnel-bgp keys for VxLAN support
       2022-12-20
         Added changes for NHInfoHardwareIngress and NHInfoHardwareEgress in schema file.
       2022-12-06
         Added destionation address to Tunnel Decap, added destination address and underlay table id to Tunnel Decap-NVE
       2022-11-07
         protocol origin changes
       2022-11-01
         Updated FIB ext-client info bag to support ECD LTEP registrations
       2022-10-17
         CNHG changes
       2022-10-05
         Added PWHE and NPU mask for interface details
       2022-10-04
         Tunnel Encap/Decap: Added Prefix Length to the source and destination addresses
       2022-09-22
         Rate limiter statistics: Added drop stats
       2022-09-15
         Added Internal ID in PW-HE extension
       2022-08-29
         Summary statistics: Added udp-port information
       2022-07-19
         Added async-ack-support to FIB-SH-PLAT-CAPABILITIES, and ack-status, ack-latency, to FIB-GRIBI-ENTRY-INFO and FIB-GLOBAL-GRIBI-ENTRY.
       2022-07-07
         Added VRF base filtering for MPLS label stats
       2022-06-14
         Added program id, dst_ip and src_ip in next-hop and nhg fib.bag
       2022-06-13
         Added destination address to nve-ltep bag
       2022-05-13
         Added aft vrf-id to gribi bags
       2022-04-27
         Added vxlan-vni-id to ltep-tunnel
       2022-04-25
         Added RNH state
       2022-04-08
         Added table statistics
       2022-03-31
         Added sr-frr-nhid to frr-nhinfo-pending
       2022-03-24
         Added retry counts to object summary attributes
       2022-03-15
         Added vxlan-tunnels
       2022-03-01
         Added policy and hardware ingress and egress paths
       2022-02-16
         Added some SRv6 SIDs data
       2021-12-14
         Added gribi-table and hardware ingress and egress paths
       2021-11-26
         Added ltep-tunnels and hardware ingress and egress paths
       2021-11-05
         Added rtep-tunnels and hardware ingress and egress paths
       2021-11-03
         Added ltep-nve-tunnels hardware ingress and egress paths
       2021-10-23
         Added ltep-nve-tunnels and added object-id to object-base";
    semver:module-version "5.0.0";
  }
  revision 2021-10-17 {
    description
      "Modify the type of list fsum-attr-cnt
       2021-09-17
          Rename lists unicast-prefix, broadcast-prefix and leafs num-retry-objects, old-unresolved-entries, new-unresolved-entries, unresolved-entries
       2021-07-30
          Added evpn bridge ID and SHG ID to srv6-information-for-path bag
       2021-07-06
          Added global-main subtree and support show CLIs for FIB IPC infra
       2021-05-25
          Migrate NHINFO to TI infra";
    semver:module-version "4.0.0";
  }
  revision 2020-12-02 {
    description
      "Adding per-object accounting.
       2020-10-20
           NBC documentation of CSCvu06764, CSCvv14573,CSCvv76648
       2020-05-26
           Update SRv6 Block Space naming convention
       2020-05-05
           changes related to treat SRv6 and SID as well-known when parsing XML for yang";
    semver:module-version "3.0.0";
  }
  revision 2020-01-16 {
    description
      "NBC documentation of CSCvs27272,CSCvs22018,CSCvs45512
       2019-10-29
         Updated srv6 global bag";
    semver:module-version "2.0.0";
  }
  revision 2019-09-27 {
    description
      "IOS XR 7.0.x revision.";
    semver:module-version "1.1.0";
  }
  revision 2019-04-05 {
    description
      "Establish semantic version baseline.";
    semver:module-version "1.0.0";
  }
  revision 2019-04-02 {
    description
      "Fixed schema descriptions.";
  }
  revision 2017-09-07 {
    description
      "Fixed type translation error.";
  }
  revision 2017-05-01 {
    description
      "Fixing backward compatibility error in module.";
  }
  revision 2017-01-20 {
    description
      "IOS XR 6.2.1 revision";
  }
  revision 2015-11-09 {
    description
      "IOS XR 6.0 revision.";
  }

  typedef Fib-mpls-llc-entry-bag {
    type enumeration {
      enum "fib-mpls-llc-bag-type-xc" {
        value 1;
        description
          "fib mpls llc bag type xc";
      }
      enum "fib-mpls-llc-bag-type-pfx" {
        value 2;
        description
          "fib mpls llc bag type pfx";
      }
      enum "fib-mpls-llc-bag-type-lsm" {
        value 3;
        description
          "fib mpls llc bag type lsm";
      }
      enum "fib-mpls-llc-bag-type-max" {
        value 4;
        description
          "fib mpls llc bag type max";
      }
    }
    description
      "Fib mpls llc entry bag";
  }

  typedef Fib-object-queue-item-bag {
    type enumeration {
      enum "marker" {
        description
          "Queue Item Marker";
      }
      enum "node" {
        description
          "Queue Item Node";
      }
    }
    description
      "FIB Object Queue item type";
  }

  typedef Mgmt-srv6-sid-fmt {
    type enumeration {
      enum "none" {
        value 0;
        description
          "No format";
      }
      enum "base" {
        value 1;
        description
          "Base Format";
      }
      enum "f3216" {
        value 2;
        description
          "Micro-segment F3216 Format";
      }
    }
    description
      "SRv6 SID Format Type";
  }

  typedef Srv6-op-mode {
    type enumeration {
      enum "none" {
        description
          "No mode";
      }
      enum "srv6-base" {
        description
          "SRv6 base";
      }
      enum "srv6-micro-segment" {
        description
          "SRv6 micro-segment";
      }
    }
    description
      "SRv6 operational mode";
  }

  typedef Fib-sh-rec-nh-state {
    type enumeration {
      enum "resolved" {
        value 0;
        description
          "REC NH is resolved";
      }
      enum "unresolved" {
        value 1;
        description
          "REC NH is unresolved";
      }
      enum "drop" {
        value 2;
        description
          "REC NH is pointing drop";
      }
    }
    description
      "Fib sh rec nh state";
  }

  typedef Fib-nhinfo-ext-bag {
    type enumeration {
      enum "replicated-nh-info" {
        description
          "Replicated NHINFO";
      }
      enum "shared-nh-info" {
        description
          "Shared NHINFO";
      }
      enum "tunnel-endpoint" {
        description
          "Tunnel Endpoint";
      }
    }
    description
      "FIB NHINFO extension type";
  }

  typedef Fib-bag-adj-pref {
    type enumeration {
      enum "unspecified" {
        description
          "Preference is unspecified";
      }
      enum "low" {
        description
          "Preference is low";
      }
      enum "high" {
        description
          "Preference is high";
      }
    }
    description
      "FIB adjacency preference";
  }

  typedef Fib-rpf-mode {
    type enumeration {
      enum "fib-rpf-mode-strict" {
        description
          "RPF mode strict";
      }
      enum "fib-rpf-mode-loose" {
        description
          "RPF mode loose";
      }
      enum "fib-rpf-mode-unknown" {
        description
          "RPF mode unknown";
      }
    }
    description
      "RPF mode types";
  }

  typedef Fibidb-oper {
    type enumeration {
      enum "fibidb-none" {
        value 0;
        description
          "fibidb none";
      }
      enum "fibidb-create" {
        value 1;
        description
          "fibidb create";
      }
      enum "fibidb-delete" {
        value 2;
        description
          "fibidb delete";
      }
      enum "fibidb-modify" {
        value 3;
        description
          "fibidb modify";
      }
      enum "fibidb-max" {
        value 4;
        description
          "fibidb max";
      }
    }
    description
      "Fibidb oper";
  }

  typedef Fib-sh-marker-feature {
    type enumeration {
      enum "lb-oor-dampen" {
        description
          "FIB LB OOR Dampening";
      }
      enum "lb-oor-dlb" {
        description
          "FIB LB OOR DLB";
      }
      enum "lb-oor-hlb-site-dampen" {
        description
          "FIB LB OOR Dampening for HLB Site Routes";
      }
    }
    description
      "Fib sh marker feature";
  }

  typedef Fib-sh-og {
    type enumeration {
      enum "local" {
        value 0;
        description
          "origin proto LOCAL";
      }
      enum "bgp" {
        value 1;
        description
          "origin proto BGP";
      }
      enum "isis" {
        value 2;
        description
          "origin proto ISIS";
      }
      enum "ospf" {
        value 3;
        description
          "origin proto OSPF";
      }
      enum "ospfv3" {
        value 4;
        description
          "origin proto OSPF3";
      }
      enum "static" {
        value 5;
        description
          "origin proto STATIC";
      }
      enum "directly-connected" {
        value 6;
        description
          "origin proto DIRECTLY_CONNECTED";
      }
      enum "gribi" {
        value 7;
        description
          "origin proto GRIBI";
      }
      enum "invalid" {
        value 8;
        description
          "origin proto invalid/max";
      }
    }
    description
      "Fib sh og";
  }

  typedef Ss-lba-state {
    type enumeration {
      enum "l3" {
        description
          "L3 Load Balance config";
      }
      enum "l4" {
        description
          "L4 Load Balance config";
      }
    }
    description
      "Load Balance config";
  }

  typedef Fib-rsrc-mode-bag {
    type enumeration {
      enum "green" {
        description
          "Resource is in Green mode";
      }
      enum "yellow" {
        description
          "Resource is in Yellow mode";
      }
      enum "red" {
        description
          "Resource is in Red mode";
      }
    }
    description
      "FIB Resource Mode";
  }

  typedef Fib-bag-shmwin {
    type enumeration {
      enum "ipv4" {
        description
          "IPv4 Shared Memory Window";
      }
      enum "ipv6" {
        description
          "IPv6 Shared Memory Window";
      }
      enum "mpls" {
        description
          "MPLS Shared Memory Window";
      }
      enum "common" {
        description
          "Common Shared Memory Window";
      }
    }
    description
      "Shared Memory Window Type";
  }

  typedef Fib-retry-entry-bag-sched-class {
    type enumeration {
      enum "slow" {
        description
          "Slow Scheduling Class";
      }
      enum "regular" {
        description
          "Regular Scheduling Class";
      }
      enum "fast" {
        description
          "Fast Scheduling Class";
      }
    }
    description
      "Fib retry entry bag sched class";
  }

  typedef Fib-aib-adjacency {
    type enumeration {
      enum "tx-adjacency" {
        description
          "TX Adjacency";
      }
      enum "tx-vxlan-adjacency" {
        description
          "TX Vxlan Adjacency";
      }
      enum "tx-mpls-mcast-adjacency" {
        description
          "TX MPLS Mcast Adjacency";
      }
      enum "tx-subscriber-adjacency" {
        description
          "TX Subscriber Adjacency";
      }
      enum "rx-adjacency" {
        description
          "RX Adjacency";
      }
    }
    description
      "FIB AIB Adjacency type";
  }

  typedef Ipv6-address {
    type inet:ipv6-address;
    description
      "IPV6 Address ";
  }

  typedef Fib-misc-protocol {
    type enumeration {
      enum "ipv4" {
        description
          "IPv4 Protocol";
      }
      enum "ipv6" {
        description
          "IPv6 Protocol";
      }
      enum "mpls" {
        description
          "MPLS Protocol";
      }
      enum "max" {
        description
          "Max Protocol";
      }
    }
    description
      "Protocol definitions for FIB Misc Bags";
  }

  typedef Fib-sh-policy-bag {
    type enumeration {
      enum "none" {
        description
          "None type";
      }
      enum "saf" {
        description
          "Source Address Filtering type";
      }
      enum "vxlan-vrf-rate-limit" {
        description
          "VXLAN VRF Rate Limit type";
      }
    }
    description
      "FIB Policy Bag Type";
  }

  typedef Fib-vni-info-type-in-bag {
    type enumeration {
      enum "unspecified" {
        value 0;
        description
          "unspecified";
      }
      enum "evni" {
        value 1;
        description
          "evni";
      }
    }
    description
      "Fib vni info type in bag";
  }

  typedef Fib-vni-info-key-type-in-bag {
    type enumeration {
      enum "rtep-id" {
        value 0;
        description
          "rtep id";
      }
      enum "bgp" {
        value 1;
        description
          "bgp";
      }
      enum "tblid-vni" {
        value 2;
        description
          "tblid vni";
      }
    }
    description
      "Fib vni info key type in bag";
  }

  typedef Fib-sh-tbl-fib-ext-bag {
    type enumeration {
      enum "leaf-extension" {
        value 1;
        description
          "Leaf Extension";
      }
    }
    description
      "Fib sh tbl fib ext bag";
  }

  typedef Mgmt-srv6-endpoint {
    type enumeration {
      enum "unknown" {
        value 0;
        description
          "Unknown Endpoint type";
      }
      enum "end" {
        value 1;
        description
          "End (no PSP/USP)";
      }
      enum "end-with-psp" {
        value 2;
        description
          "End with PSP";
      }
      enum "end-with-usp" {
        value 3;
        description
          "End with USP";
      }
      enum "end-with-psp-usp" {
        value 4;
        description
          "End with PSP/USP";
      }
      enum "end-x" {
        value 5;
        description
          "End.X (no PSP/USP)";
      }
      enum "end-x-with-psp" {
        value 6;
        description
          "End.X with PSP";
      }
      enum "end-x-with-usp" {
        value 7;
        description
          "End.X with USP";
      }
      enum "end-x-with-psp-usp" {
        value 8;
        description
          "End.X with PSP/USP";
      }
      enum "end-tbl" {
        value 9;
        description
          "End.T (no PSP/USP)";
      }
      enum "end-tbl-with-psp" {
        value 10;
        description
          "End.T with PSP";
      }
      enum "end-tbl-with-usp" {
        value 11;
        description
          "End.T with USP";
      }
      enum "end-tbl-with-psp-usp" {
        value 12;
        description
          "End.T with PSP/USP";
      }
      enum "end-b6-insert" {
        value 13;
        description
          "End.B6.Insert";
      }
      enum "end-b6-encaps" {
        value 14;
        description
          "End.B6.Encaps";
      }
      enum "end-bm" {
        value 15;
        description
          "End.BM";
      }
      enum "end-dx6" {
        value 16;
        description
          "End.DX6";
      }
      enum "end-dx4" {
        value 17;
        description
          "End.DX4";
      }
      enum "end-dt6" {
        value 18;
        description
          "End.DT6";
      }
      enum "end-dt4" {
        value 19;
        description
          "End.DT4";
      }
      enum "end-dt46" {
        value 20;
        description
          "End.DT46";
      }
      enum "end-dx2" {
        value 21;
        description
          "End.DX2";
      }
      enum "end-dx2v" {
        value 22;
        description
          "End.DX2V";
      }
      enum "end-dt2u" {
        value 23;
        description
          "End.DT2U";
      }
      enum "end-dt2m" {
        value 24;
        description
          "End.DT2M";
      }
      enum "end-s" {
        value 25;
        description
          "End.S";
      }
      enum "end-b6-insert-red" {
        value 26;
        description
          "End.B6.Insert.Reduced";
      }
      enum "end-b6-encaps-red" {
        value 27;
        description
          "End.B6.Encaps.Reduced";
      }
      enum "end-with-usd" {
        value 28;
        description
          "End with USD";
      }
      enum "end-with-psp-usd" {
        value 29;
        description
          "End with PSP/USD";
      }
      enum "end-with-usp-usd" {
        value 30;
        description
          "End with USP/USD";
      }
      enum "end-with-psp-usp-usd" {
        value 31;
        description
          "End with PSP/USP/USD";
      }
      enum "end-x-with-usd" {
        value 32;
        description
          "End.X with USD";
      }
      enum "end-x-with-psp-usd" {
        value 33;
        description
          "End.X with PSP/USD";
      }
      enum "end-x-with-usp-usd" {
        value 34;
        description
          "End.X with USP/USD";
      }
      enum "end-x-with-psp-usp-usd" {
        value 35;
        description
          "End.X with PSP/USP/USD";
      }
      enum "end-tbl-with-usd" {
        value 36;
        description
          "End.T with USD";
      }
      enum "end-tbl-with-psp-usd" {
        value 37;
        description
          "End.T with PSP/USD";
      }
      enum "end-tbl-with-usp-usd" {
        value 38;
        description
          "End.T with USP/USD";
      }
      enum "end-tbl-with-psp-usp-usd" {
        value 39;
        description
          "End.T with PSP/USP/USD";
      }
      enum "end-op" {
        value 40;
        description
          "End.OP";
      }
      enum "end-otp" {
        value 41;
        description
          "End.OTP";
      }
      enum "un-shift-only" {
        value 42;
        description
          "uN Shift-only";
      }
      enum "un" {
        value 43;
        description
          "uN";
      }
      enum "un-psp" {
        value 44;
        description
          "uN with PSP";
      }
      enum "un-usp" {
        value 45;
        description
          "uN with USP";
      }
      enum "un-psp-usp" {
        value 46;
        description
          "uN with PSP-USP";
      }
      enum "un-usd" {
        value 47;
        description
          "uN with USD";
      }
      enum "un-psp-usd" {
        value 48;
        description
          "uN with PSP-USD";
      }
      enum "un-usp-usd" {
        value 49;
        description
          "uN with USP-USD";
      }
      enum "un-psp-usp-usd" {
        value 50;
        description
          "uN with PSP_USP-USD";
      }
      enum "ua-shift-only" {
        value 51;
        description
          "uA Shift-only";
      }
      enum "ua" {
        value 52;
        description
          "uA";
      }
      enum "ua-psp" {
        value 53;
        description
          "uA with PSP";
      }
      enum "ua-usp" {
        value 54;
        description
          "uA with USP";
      }
      enum "ua-psp-usp" {
        value 55;
        description
          "uA with PSP-USP";
      }
      enum "ua-usd" {
        value 56;
        description
          "uA with USD";
      }
      enum "ua-psp-usd" {
        value 57;
        description
          "uA with PSP-USD";
      }
      enum "ua-usp-usd" {
        value 58;
        description
          "uA with USP-USD";
      }
      enum "ua-psp-usp-usd" {
        value 59;
        description
          "uA with PSP_USP-USD";
      }
      enum "udx6" {
        value 60;
        description
          "uDX6";
      }
      enum "udx4" {
        value 61;
        description
          "uDX4";
      }
      enum "udt6" {
        value 62;
        description
          "uDT6";
      }
      enum "udt4" {
        value 63;
        description
          "uDT4";
      }
      enum "udt46" {
        value 64;
        description
          "uDT46";
      }
      enum "udx2" {
        value 65;
        description
          "uDX2";
      }
      enum "udx2v" {
        value 66;
        description
          "uDX2V";
      }
      enum "udt2u" {
        value 67;
        description
          "uDT2U";
      }
      enum "udt2m" {
        value 68;
        description
          "uDT2M";
      }
      enum "ub6-insert" {
        value 69;
        description
          "uB6 Insert";
      }
      enum "ub6-encaps" {
        value 70;
        description
          "uB6 Encaps";
      }
      enum "ub6-insert-red" {
        value 71;
        description
          "uB6 Insert.Red";
      }
      enum "ub6-encaps-red" {
        value 72;
        description
          "uB6 Encaps.Red";
      }
      enum "ubm" {
        value 73;
        description
          "uBM";
      }
      enum "ub6-psp-usd-insert-red" {
        value 79;
        description
          "uB6 with PSP-USD Insert.Red";
      }
      enum "ub6-psp-usd-encaps-red" {
        value 80;
        description
          "uB6 with PSP-USD Encaps.Red";
      }
      enum "utef" {
        value 81;
        description
          "PT uTEF";
      }
    }
    description
      "SRv6 Endpoint Behavior Type";
  }

  typedef Fib-update-path-lfa-protection {
    type enumeration {
      enum "not-lfa-protected" {
        description
          "Not LFA-protected";
      }
      enum "protected" {
        description
          "Protected";
      }
      enum "local-lfa-backup" {
        description
          "Local-LFA backup";
      }
      enum "remote-lfa-backup" {
        description
          "Remote-LFA backup";
      }
      enum "ti-lfa-backup" {
        description
          "TI-LFA backup";
      }
    }
    description
      "LFA protection type";
  }

  typedef Fib-sh-ipencap-hdr {
    type enumeration {
      enum "fib-sh-ip-encap-none" {
        description
          "No Header";
      }
      enum "fib-sh-ip-encap-ip4" {
        description
          "IPv4 Header";
      }
      enum "fib-sh-ip-encap-ip6" {
        description
          "IPv6 Header";
      }
      enum "fib-sh-ip-encap-udp" {
        description
          "UDP Header";
      }
      enum "fib-sh-ip-encap-lisp" {
        description
          "Lisp Header";
      }
    }
    description
      "IP Encap Header Type";
  }

  typedef Fib-neh-special {
    type enumeration {
      enum "nh-not-found" {
        description
          "nh not found";
      }
      enum "nh-null0" {
        description
          "nh null0";
      }
      enum "nh-punt" {
        description
          "nh punt";
      }
      enum "nh-drop" {
        description
          "nh drop";
      }
      enum "nh-glean" {
        description
          "nh glean";
      }
      enum "nh-receive" {
        description
          "nh receive";
      }
      enum "nh-broadcast" {
        description
          "nh broadcast";
      }
      enum "nh-external" {
        description
          "nh external";
      }
      enum "nh-lisp" {
        description
          "nh lisp";
      }
      enum "nh-lookup" {
        description
          "nh lookup";
      }
      enum "nh-max-type" {
        description
          "nh max type";
      }
    }
    description
      "Fib neh special";
  }

  typedef Fib-neh {
    type enumeration {
      enum "nh-local" {
        description
          "nh local";
      }
      enum "nh-remote" {
        description
          "nh remote";
      }
      enum "nh-special" {
        description
          "nh special";
      }
    }
    description
      "Fib neh";
  }

  typedef Fib-adjacency-show {
    type enumeration {
      enum "fib-adjacency-normal" {
        description
          "Normal adjacency";
      }
      enum "fib-adjacency-null" {
        description
          "Null adjacency";
      }
      enum "fib-adjacency-punt" {
        description
          "Punt adjacency";
      }
      enum "fib-adjacency-drop" {
        description
          "Drop adjacency";
      }
      enum "fib-adjacency-glean" {
        description
          "Glean adjacency";
      }
      enum "fib-adjacency-discard" {
        description
          "Discard adjacency";
      }
      enum "fib-adjacency-broadcast" {
        description
          "Broadcast adjacency";
      }
      enum "fib-adjacency-external" {
        description
          "external adjacency";
      }
      enum "fib-adjacency-lisp" {
        description
          "LISP adjacency";
      }
      enum "fib-adjacency-unknown" {
        description
          "Unknown adjacency";
      }
    }
    description
      "Adjacency types";
  }

  typedef Fib-loadshare-show {
    type enumeration {
      enum "fib-load-share-none" {
        description
          "No loadsharing";
      }
      enum "fib-load-share-per-packet" {
        description
          "Per packet loadsharing";
      }
      enum "fib-load-share-dest-sharing" {
        description
          "Destination loadsharing";
      }
    }
    description
      "Loadsharing type";
  }

  typedef Fib-ack-status {
    type enumeration {
      enum "unspecified" {
        description
          "Status unspecified";
      }
      enum "ack" {
        description
          "Positively acknowledged";
      }
      enum "nack" {
        description
          "Negatively acknowledged";
      }
    }
    description
      "Hardware acknowledgement status";
  }

  typedef Fib-common-in6-addr {
    type inet:ipv6-address;
    description
      "Fib common in6 addr";
  }

  typedef Fib-common-in-addr {
    type inet:ipv4-address;
    description
      "Fib common in addr";
  }

  typedef Fib-common-af-id {
    type enumeration {
      enum "none" {
        value 0;
        description
          "No address family";
      }
      enum "ipv4" {
        value 2;
        description
          "IPv4 AFI";
      }
      enum "ipv6" {
        value 10;
        description
          "IPv6 AFI";
      }
    }
    description
      "Fib common af id";
  }

  typedef Fib-bag-object {
    type enumeration {
      enum "none" {
        value 0;
        description
          "None";
      }
      enum "pathlist" {
        value 7;
        description
          "Pathlist";
      }
      enum "adjacency" {
        value 8;
        description
          "NHINFO";
      }
      enum "all" {
        value 23;
        description
          "ALL";
      }
      enum "tep" {
        value 65;
        description
          "TEP";
      }
      enum "ltep" {
        value 66;
        description
          "LTEP";
      }
    }
    description
      "Object type definitions for FIB Bags";
  }

  typedef Fib-common-aft-nh {
    type enumeration {
      enum "invalid" {
        value 0;
        description
          "Invalid AFT type";
      }
      enum "aft-nh" {
        value 1;
        description
          "AFT nexthops type";
      }
      enum "aft-nhg" {
        value 2;
        description
          "AFT nexthop group type";
      }
      enum "aft-max" {
        value 3;
        description
          "AFT max type";
      }
      enum "vxlan-l3-if-less" {
        value 4;
        description
          "VxLAN L3 Interfaceless encap type";
      }
    }
    description
      "Fib common aft nh";
  }

  typedef Fib-common-ipvpn-tunnel {
    type enumeration {
      enum "invalid" {
        value 0;
        description
          "Invalid encap type";
      }
      enum "l2tp" {
        value 1;
        description
          "L2TP encap type";
      }
      enum "mgre" {
        value 2;
        description
          "mGRE encap type";
      }
      enum "vxlan-l2" {
        value 3;
        description
          "VxLAN L2 encap type";
      }
      enum "gre" {
        value 4;
        description
          "GRE encap type";
      }
      enum "ip" {
        value 5;
        description
          "IP-in-IP encap type";
      }
      enum "te" {
        value 6;
        description
          "TE encap type";
      }
      enum "vxlan-l3" {
        value 7;
        description
          "VxLAN L3 encap type";
      }
      enum "vxlan-l3-sfi" {
        value 8;
        description
          "VxLAN L3 over SFI encap type";
      }
      enum "mpls-udp" {
        value 9;
        description
          "MPLS over UDP encap type";
      }
      enum "ipvpn-ip-nh" {
        value 10;
        description
          "IP NH Tunnel Type";
      }
      enum "ipvpn-ip-nh-tbl" {
        value 11;
        description
          "IP NH TBL Tunnel Type";
      }
      enum "vxlan" {
        value 12;
        description
          "VxLAN encap type";
      }
      enum "ipvpn-per-interface" {
        value 13;
        description
          "Per-Interface Tunnel Type";
      }
      enum "ipvpn-nh" {
        value 14;
        description
          "NH Tunnel Type";
      }
      enum "ipvpn-gue-v1" {
        value 15;
        description
          "GUE V1 Tunnel Type";
      }
    }
    description
      "Fib common ipvpn tunnel";
  }

  typedef Fib-bag-protocol {
    type enumeration {
      enum "ipv4" {
        description
          "IPv4 Protocol";
      }
      enum "ipv6" {
        description
          "IPv6 Protocol";
      }
      enum "mpls" {
        description
          "MPLS Protocol";
      }
    }
    description
      "Protocol definitions for FIB Bags";
  }

  grouping FIB-SH-PWHE-PRUNED-INT {
    description
      "FIB PWHE pruned chain information";
    container pruned-leaf {
      description
        "Pruned Leaf";
      uses FIB-SH-TBL-FIB;
    }
    leaf pruned-tep-id {
      type uint64;
      description
        "Pruned identifier";
    }
  }

  grouping FIB-SH-PWHE-DET {
    description
      "FIB PWHE entry";
    container il-iid-leaf {
      description
        "IL/IID Leaf";
      uses FIB-SH-TBL-FIB;
    }
    container pwhe-attribute {
      description
        "Information about PWHE attribute";
      uses FIB-SH-INT-PWHE-IDB-ATTR;
    }
    leaf pwhe-interface-name {
      type xr:Interface-name;
      description
        "PWHE interface name";
    }
    leaf is-resolved {
      type boolean;
      description
        "Is Resolved";
    }
    leaf is-pwhe-attribute-present {
      type boolean;
      description
        "PWHE attribute present";
    }
    leaf string-representation {
      type string;
      description
        "String Representation of IL leaf Chain";
    }
    list pruned-info {
      description
        "Pruned chain information";
      uses FIB-SH-PWHE-PRUNED-INT;
    }
  }

  grouping FIB-MPLS-LLC-LSM {
    description
      "FIB MPLS LLC LSM";
    leaf nh {
      type string {
        length "0..52";
      }
      description
        "nh";
    }
    leaf mcast-id {
      type uint32;
      description
        "mcast id";
    }
  }

  grouping FIB-MPLS-LLC-PFX {
    description
      "FIB MPLS LLC PFX";
    leaf prefix {
      type string {
        length "0..52";
      }
      description
        "Prefix";
    }
    leaf table-id {
      type uint32;
      description
        "TableID";
    }
  }

  grouping FIB-MPLS-LLC-TYPE-EXT {
    description
      "FIB MPLS LLC TYPE EXT";
    container pfx {
      when "../type = 'fib-mpls-llc-bag-type-pfx'" {
        description
          "../type = 'FIB_MPLS_LLC_BAG_TYPE_PFX'";
      }
      description
        "pfx";
      uses FIB-MPLS-LLC-PFX;
    }
    container lsm {
      when "../type = 'fib-mpls-llc-bag-type-lsm'" {
        description
          "../type = 'FIB_MPLS_LLC_BAG_TYPE_LSM'";
      }
      description
        "lsm";
      uses FIB-MPLS-LLC-LSM;
    }
    leaf type {
      type Fib-mpls-llc-entry-bag;
      description
        "type";
    }
  }

  grouping FIB-MPLS-LLC {
    description
      "FIB MPLS LLC";
    container extension {
      description
        "extension";
      uses FIB-MPLS-LLC-TYPE-EXT;
    }
    leaf local-label {
      type uint32;
      description
        "LocalLabel";
    }
    leaf source {
      type uint32;
      description
        "Source";
    }
    leaf update-timestamp {
      type uint64;
      description
        "UpdateTimestamp";
    }
    leaf retry-timestamp {
      type uint64;
      description
        "RetryTimestamp";
    }
    leaf number-of-retries {
      type uint32;
      description
        "NumberOfRetries";
    }
  }

  grouping FIB-OBJECT-QUEUE-NODE-INFO {
    description
      "FIB Object Queue Information";
    leaf key-string {
      type string;
      description
        "Object String Key";
    }
  }

  grouping FIB-OBJECT-QUEUE-ITEM-CMN {
    description
      "FIB OBJECT QUEUE ITEM CMN";
    container object-marker {
      when "../type = 'marker'" {
        description
          "../type = 'Marker'";
      }
      description
        "Queue Item Marker";
      uses FIB-OBJECT-MARKER-INFO;
    }
    container object-node {
      when "../type = 'node'" {
        description
          "../type = 'Node'";
      }
      description
        "Queue Item Node";
      uses FIB-OBJECT-QUEUE-NODE-INFO;
    }
    leaf type {
      type Fib-object-queue-item-bag;
      description
        "type";
    }
  }

  grouping FIB-OBJECT-QUEUE-ITEM-INFO {
    description
      "FIB Object Queue Information";
    container object-base {
      description
        "Object Base";
      uses FIB-SH-FIB-OBJ-BASE;
    }
    container object-item {
      description
        "Object Item";
      uses FIB-OBJECT-QUEUE-ITEM-CMN;
    }
  }

  grouping FIB-SH-TBL-EXT-CLIENT-SUM {
    description
      "FIB external client summary information";
    container ecd-pathlist-summary {
      description
        "ECD pathlist summary";
      uses FIB-SH-TBL-EXT-PL-SUM;
    }
    leaf external-client-name {
      type string;
      description
        "External client name";
    }
    leaf registration-protocol-type {
      type uint32;
      description
        "Registration proto";
    }
    leaf number-of-registration {
      type uint32;
      description
        "Number of registrations";
    }
    leaf number-of-pending-notifications {
      type uint32;
      description
        "Number of pending notifs";
    }
    leaf client-pulsed-timestamp {
      type uint64;
      description
        "Client pulsed timestamp";
    }
    leaf client-component-id {
      type uint32;
      description
        "component-id of the client";
    }
    leaf ecd-version {
      type uint32;
      description
        "ECD version";
    }
  }

  grouping FIB-SH-FRR-NHINFO {
    description
      "FIB per nhinfo information";
    leaf frr-nhinfo-type {
      type uint32;
      description
        "FRR-NHinfo Type";
    }
    leaf next-hop-reference-count {
      type uint32;
      description
        "Next Hop Reference Count";
    }
    leaf frr-nhinfo-flags {
      type uint32;
      description
        "FRR nhinfo flags";
    }
    leaf vrf-table-id {
      type uint32;
      description
        "VRF table ID";
    }
    leaf frr-nh-interface-name {
      type xr:Interface-name;
      description
        "interface assoc w FRR nh";
    }
    leaf main-interface-name {
      type xr:Interface-name;
      description
        "main interface assoc w prot-frr nh";
    }
    leaf link-type {
      type uint32;
      description
        "Linktype using this FRR object";
    }
    leaf nh-prefix-protocol {
      type uint32;
      description
        "Protocol for next-hop prefix";
    }
    leaf nh-prefix {
      type yang:hex-string;
      description
        "nh prefix";
    }
    leaf prefix-length {
      type uint32;
      description
        "prefix len";
    }
    leaf tunnel-id {
      type uint32;
      description
        "tunnel id for c12k";
    }
    leaf frr-nhinfo-pointer {
      type uint64;
      description
        "frr-nhinfo pointer";
    }
    leaf protected-frr-pointer {
      type uint64;
      description
        "prot-frr-nhinfo pointer for a bkup-frr";
    }
    leaf parent-nhinfo-pointer {
      type uint64;
      description
        "parent nhinfo pointer";
    }
    leaf partner-nhinfo-pointer {
      type uint64;
      description
        "partner nhinfo pointer";
    }
    leaf replicated-parent-nhinfo-type {
      type uint8;
      description
        "replicated parent nhinfo type";
    }
    leaf update-timestamp {
      type uint64;
      description
        "update timestamp";
    }
    leaf frr-nhid {
      type uint32;
      description
        "frr nhid";
    }
  }

  grouping FIB-SH-NHID-ENTRY {
    description
      "FIB per NHID entry information";
    leaf nh-interface-name {
      type xr:Interface-name;
      description
        "Next-hop interface";
    }
    leaf nh-address {
      type string;
      description
        "Next-hop address";
    }
    leaf nh-protocol {
      type uint8;
      description
        "Next-hop address protocol, IPv4/IPv6";
    }
    leaf nh-link-type {
      type uint8;
      description
        "Payload linktype";
    }
    leaf nh-table-id {
      type uint32;
      description
        "Table-ID entry notified for";
    }
    leaf nhid {
      type uint32;
      description
        "NHID value";
    }
    leaf nhid-application {
      type uint8;
      description
        "NHID application type";
    }
    leaf version {
      type uint64;
      description
        "RIB version";
    }
    leaf time-of-last-update-in-msec {
      type uint64;
      description
        "The time of last update in msec";
    }
    leaf encap-id {
      type uint64;
      description
        "ENCAP ID value";
    }
  }

  grouping MGMT-SRV6-SID-FMT {
    description
      "SRv6 SID Format Info";
    leaf type {
      type Mgmt-srv6-sid-fmt;
      description
        "Format type";
    }
    leaf description {
      type string;
      description
        "Format description";
    }
  }

  grouping MGMT-SRV6-OP-MODE {
    description
      "SRv6 operational mode Info";
    leaf type {
      type Srv6-op-mode;
      description
        "Mode type";
    }
    leaf description {
      type string;
      description
        "Mode description";
    }
  }

  grouping FIB-SRV6-GBL-MODE-INFO {
    description
      "FIB SRv6 global mode info";
    container mode {
      description
        "Mode (type and desc)";
      uses MGMT-SRV6-OP-MODE;
    }
    container sid-format {
      description
        "SID Format";
      uses MGMT-SRV6-SID-FMT;
    }
    leaf block-srv6-space {
      type string;
      description
        "Block SRv6 space";
    }
  }

  grouping FIB-SRV6-GBL-UPD-SET-OR-PROP {
    description
      "FIB SRv6 global param set or propagate value";
    leaf use-default {
      type boolean;
      description
        "Use default value";
    }
    leaf do-propagate {
      type boolean;
      description
        "Propagate from incoming packet/frame";
    }
    leaf value {
      type uint8;
      description
        "Specific value";
    }
  }

  grouping FIB-SRV6-GBL-UPD {
    description
      "FIB SRv6 global update";
    container encap-hop-limit {
      description
        "Encap Hop-limit info";
      uses FIB-SRV6-GBL-UPD-SET-OR-PROP;
    }
    container encap-traffic-class {
      description
        "Encap Traffic-class info";
      uses FIB-SRV6-GBL-UPD-SET-OR-PROP;
    }
    leaf srv6-enabled {
      type boolean;
      description
        "Is SRv6 enabled?";
    }
    leaf encap-source-address {
      type inet:ipv6-address;
      description
        "Encap Source Address";
    }
    list mode-info {
      description
        "Info per SRv6 Mode";
      uses FIB-SRV6-GBL-MODE-INFO;
    }
  }

  grouping FIB-SRV6-PATH-SH {
    description
      "FIB SRv6 Path";
    leaf outgoing-interface {
      type xr:Interface-name;
      description
        "Outgoing Interface name";
    }
    leaf nexthop-addr {
      type string {
        length "0..52";
      }
      description
        "Nexthop address";
    }
  }

  grouping FIB-SRV6-SH {
    description
      "FIB SRv6";
    leaf vrf-name {
      type string;
      description
        "VRF Name";
    }
    leaf srv6-prefix {
      type string {
        length "0..52";
      }
      description
        "SRV6 address";
    }
    leaf prefix-length {
      type uint32;
      description
        "Prefix length for this entry";
    }
    leaf fsei-path-cnt {
      type uint32;
      description
        "Number of per-path stats";
    }
    list next-hop {
      description
        "Prefix Nexthops";
      uses FIB-SRV6-PATH-SH;
    }
  }

  grouping FIB-ATTRIBUTE-SUMMARY {
    description
      "Summary of downloaded fib route attributes";
  }

  grouping FIB-SH-REC-NH-INT {
    description
      "FIB RNH's Internal information";
    container recursive-nh-event-history {
      description
        "Event History for Recursive nexthop";
      uses EVT-HIST-INFO;
    }
    leaf string-rep {
      type string;
      description
        "String Representation of a RNH";
    }
  }

  grouping FIB-SH-REC-NH-DEP-INT {
    description
      "RNH Dependent's Internal Info";
    container fib-rtep-history {
      description
        "FIB Rtep History";
      uses EVT-HIST-INFO;
    }
    container fib-ecd-history {
      description
        "FIB Ecd History";
      uses EVT-HIST-INFO;
    }
  }

  grouping FIB-SH-NHINFO-EXT-TEP-DET {
    description
      "NHINFO entry extension object information";
    leaf nh-info-tep-type {
      type uint8;
      description
        "TEP type";
    }
    leaf is-tep-single-pass {
      type boolean;
      description
        "Is TEP is Single Pass";
    }
  }

  grouping FIB-SH-NHINFO-EXT-REP-DET {
    description
      "NHINFO entry extension object information";
    leaf nh-info-replicated-type {
      type uint8;
      description
        "Replicated NHINFO type";
    }
    leaf nh-info-replicated-nhid {
      type uint32;
      description
        "NHID of the replicated NHINFO";
    }
    leaf nh-info-replicated-encap-id {
      type uint64;
      description
        "ENCAP ID of the replicated NHINFO";
    }
    leaf nh-info-replicated-interface {
      type xr:Interface-name;
      description
        "Interface of the replicated NHINFO";
    }
  }

  grouping FIB-SH-NHINFO-EXT-CMN-DET {
    description
      "FIB SH NHINFO EXT CMN DET";
    container snecd-nhr {
      when "../type = 'replicated-nh-info'" {
        description
          "../type = 'ReplicatedNHINFO'";
      }
      description
        "snecd nhr";
      uses FIB-SH-NHINFO-EXT-REP-DET;
    }
    container snecd-tep {
      when "../type = 'tunnel-endpoint'" {
        description
          "../type = 'TunnelEndpoint'";
      }
      description
        "snecd tep";
      uses FIB-SH-NHINFO-EXT-TEP-DET;
    }
    leaf type {
      type Fib-nhinfo-ext-bag;
      description
        "type";
    }
  }

  grouping FIB-SH-EXT-BASE {
    description
      "FIB object extension base information";
    container object-base {
      description
        "FIB Object Base information";
      uses FIB-SH-FIB-OBJ-BASE;
    }
    leaf parent-object-pointer {
      type uint64;
      description
        "FIB Extension Object's parent pointer";
    }
    leaf back-object-pointer {
      type uint64;
      description
        "FIB Extension Object's back pointer";
    }
  }

  grouping FIB-SH-NHINFO-EXT-DET {
    description
      "NHINFO entry extension internal information";
    container base {
      description
        "NHINFO Extension object base information";
      uses FIB-SH-EXT-BASE;
    }
    container detail {
      description
        "NHINFO Extension Detail Information";
      uses FIB-SH-NHINFO-EXT-CMN-DET;
    }
  }

  grouping FIB-SH-NHINFO-EXT {
    description
      "FIB per nhinfo info";
    list detail {
      description
        "NHINFO Extension Detail";
      uses FIB-SH-NHINFO-EXT-DET;
    }
  }

  grouping FIB-SH-NHINFO-PWHE-EXT {
    description
      "FIB PW-HE specific info";
    leaf adjacency-client-data {
      type uint32;
      description
        "PW-HE specific client data in adjacency";
    }
    leaf vctype {
      type uint32;
      description
        "VC type";
    }
    leaf vc-internal-label {
      type uint32;
      description
        "VC Internal Label";
    }
    leaf cw-enabled {
      type boolean;
      description
        "Is CW enabled?";
    }
    leaf l2-overhead-bytes {
      type uint16;
      units "byte";
      description
        "L2 overhead bytes for interface stats accounting";
    }
    leaf dot1q-vlan-tag {
      type uint32;
      description
        "VLAN tag";
    }
    leaf internal-id {
      type inet:ipv6-address;
      description
        "Internal ID";
    }
  }

  grouping FIB-SH-NHINFO {
    description
      "FIB per nhinfo information";
    container pwhe-interface-extension {
      description
        "PW-HE interface extension";
      uses FIB-SH-NHINFO-PWHE-EXT;
    }
    container nh-info-extension {
      description
        "NHinfo Extensions";
      uses FIB-SH-NHINFO-EXT;
    }
    container nh-info-event-history {
      description
        "NHinfo Event History";
      uses EVT-HIST-INFO;
    }
    leaf prototype {
      type uint32;
      description
        "FIB Protocol Type for NHINFO linktype";
    }
    leaf nh-info-type {
      type uint32;
      description
        "NHinfo Type";
    }
    leaf interface-name {
      type xr:Interface-name;
      description
        "Interface assoc w nhinfo";
    }
    leaf pfi-interface-type {
      type uint32;
      description
        "Pamna Interface Type";
    }
    leaf adjacency-pointer {
      type uint32;
      description
        "Adj Ptr";
    }
    leaf adjacency-is-present {
      type boolean;
      description
        "nhinfo point to adj";
    }
    leaf special-nh-info-type {
      type uint32;
      description
        "nature of special nhinfo";
    }
    leaf nh-reference-count {
      type uint32;
      description
        "Next Hop Reference Count";
    }
    leaf flags {
      type uint32;
      description
        "nhinfo flags";
    }
    leaf base-extended-flags {
      type uint16;
      description
        "NHInfo Base Extended Flags";
    }
    leaf adjacency-interface-name {
      type xr:Interface-name;
      description
        "ADJ Interface name";
    }
    leaf extension-prefix {
      type yang:hex-string;
      description
        "Extension Prefix";
    }
    leaf extension-prefix-len {
      type uint32;
      description
        "Extension Prefix Len";
    }
    leaf extension-prefix-protocol {
      type uint32;
      description
        "Extension Prefix Protocol";
    }
    leaf aib-l3-address {
      type yang:hex-string;
      description
        "AIB L3 Address";
    }
    leaf adjacency-address-length {
      type uint32;
      description
        "ADJ L3 address length";
    }
    leaf adjacency-address-protocol {
      type uint32;
      description
        "ADJ L3 address Protocol";
    }
    leaf macstring-length {
      type uint32;
      description
        "Length of Macstring";
    }
    leaf adjacency-macstring {
      type yang:hex-string;
      description
        "Macstring for Adjacency";
    }
    leaf adjacency-route-preference {
      type Fib-bag-adj-pref;
      description
        "Adjacency route preference";
    }
    leaf dependent-nh-info-type {
      type uint32;
      description
        "Depenedent nhinfo type";
    }
    leaf dependent-nh-info-pointer {
      type uint32;
      description
        "Dependent nhinfo";
    }
    leaf dependent-nh-info-interface-name {
      type xr:Interface-name;
      description
        "Dependent nhinfo interface";
    }
    leaf backup-frr {
      type uint32;
      description
        "pointer to Backup FRR obj";
    }
    leaf protect-frr {
      type uint32;
      description
        "pointer to protect FRR object";
    }
    leaf backup-nh-info {
      type uint32;
      description
        "Backup NHINFO obj";
    }
    leaf backup-interface-name {
      type xr:Interface-name;
      description
        "Backup interface";
    }
    leaf backup-l3-address {
      type yang:hex-string;
      description
        "Bkup L3 Address";
    }
    leaf backup-l3-address-length {
      type uint32;
      description
        "BKup L3 address length";
    }
    leaf backup-l3-address-protocol {
      type uint32;
      description
        "BKup L3 address Protocol";
    }
    leaf frr-is-active {
      type boolean;
      description
        "is FRR currently active";
    }
    leaf nh-is-externally-managed {
      type boolean;
      description
        "NH is externally managed";
    }
    leaf nh-is-incomplete {
      type boolean;
      description
        "NH is incomplete";
    }
    leaf nh-is-associated-with-te-tunnel {
      type boolean;
      description
        "NH is assoc w a TE tunnel";
    }
    leaf nh-is-associated-with-srte-tunnel {
      type boolean;
      description
        "NH is assoc w a SRTE tunnel";
    }
    leaf nh-is-associated-with-gre-tunnel {
      type boolean;
      description
        "NH is assoc w a GRE tunnel";
    }
    leaf gre-tunnel-info-pointer {
      type uint64;
      description
        "GRE tunnel info";
    }
    leaf gre-tunnel-info-flags {
      type uint32;
      description
        "Flags on GRE tunnel info";
    }
    leaf gre-tunnel-info-reference-count {
      type uint32;
      description
        "Refcount on GRE tunnel info";
    }
    leaf gre-tos-propagate {
      type boolean;
      description
        "Is GRE TOS propagate set";
    }
    leaf hardware {
      type yang:hex-string;
      description
        "Platform Hardware info";
    }
    leaf nh-info-pointer {
      type uint32;
      description
        "nhinfo pointer";
    }
    leaf idb-pointer {
      type uint32;
      description
        "pointer to idb";
    }
    leaf ancestor-interface-name {
      type xr:Interface-name;
      description
        "Ancestor interface";
    }
    leaf gre-resolving-i-pleaf {
      type uint64;
      description
        "GRE resolving ip-leaf";
    }
    leaf gre-destination-address {
      type yang:hex-string;
      description
        "GRE dest address";
    }
    leaf nhid-in-tx-nh {
      type uint32;
      description
        "NHID value in the TX NH";
    }
    leaf nh-update-timestamp {
      type uint64;
      description
        "NH update timestamp";
    }
    leaf nh-is-in-oor-state {
      type boolean;
      description
        "is NH in OOR";
    }
    leaf nh-idb-usable {
      type boolean;
      description
        "NH's IDB is usable for fowarding";
    }
  }

  grouping FIB-SH-REC-NH-DEP {
    description
      "FIB recursive nexthop dependant information";
    list fib-sh-rec-nh-dep {
      description
        "Next dependant";
      container vxlan-shadow-nh {
        description
          "VXLAN shadow NH";
        uses FIB-SH-NHINFO;
      }
      container internal-info {
        description
          "RNH dependent's Internal Info";
        uses FIB-SH-REC-NH-DEP-INT;
      }
      leaf dependant-type {
        type uint32;
        description
          "Dependant type";
      }
      leaf tunnel-endpoint-id {
        type uint32;
        description
          "Tunnel endpoint id";
      }
      leaf interface-name {
        type xr:Interface-name;
        description
          "Interface name";
      }
      leaf reference-count {
        type uint32;
        description
          "Ref count";
      }
      leaf is-dependent-resolved {
        type boolean;
        description
          "Dependant resolved";
      }
      leaf dependent-flags {
        type uint32;
        description
          "Dependant flags";
      }
      leaf local-tunnel-status {
        type uint32;
        description
          "Local tunnel status";
      }
      leaf tep-encapsulation-data {
        type yang:hex-string;
        description
          "TEP encapsulation details";
      }
      leaf sourec-address-pool-size {
        type uint32;
        description
          "Source addr pool size";
      }
      leaf stale-flag {
        type boolean;
        description
          "Stale flag";
      }
      leaf retry-flag {
        type boolean;
        description
          "Retry flag";
      }
      leaf gre-tunnel-info-pointer {
        type uint64;
        description
          "GRE tunnel info ptr";
      }
      leaf encap-id {
        type uint64;
        description
          "Encap ID";
      }
      leaf stat-id {
        type uint64;
        description
          "Stat Id";
      }
      leaf gre-vxlan-nh-info-pointer {
        type uint64;
        description
          "GRE/VXLAN NH-info ptr";
      }
      leaf vxlan-parent-nh-info-pointer {
        type uint64;
        description
          "VXLAN parent NH-info ptr";
      }
      leaf nh-protocol-type {
        type Fib-bag-protocol;
        description
          "NH proto";
      }
      leaf vxlan-rtep-info-pointer {
        type uint32;
        description
          "VXLAN rTEP info ptr";
      }
      leaf vxlan-egress-vni {
        type uint32;
        description
          "VXLAN egress VNI";
      }
      leaf vxlan-overlay-table-id {
        type uint32;
        description
          "VXLAN overlay tbl id";
      }
      leaf hardware-info {
        type yang:hex-string;
        description
          "Opaque hardware info";
      }
    }
  }

  grouping FIB-SH-REC-NH {
    description
      "FIB recursive nexthop information";
    container first-dependent {
      description
        "First dependant";
      uses FIB-SH-REC-NH-DEP;
    }
    container rnh-internal-representation {
      description
        "Internal representation of an RNH";
      uses FIB-SH-REC-NH-INT;
    }
    leaf recursive-nh-prefix {
      type yang:hex-string;
      description
        "Recursive nexthop prefix";
    }
    leaf prefix-length {
      type uint32;
      description
        "Prefix length";
    }
    leaf recursive-nh-resolved {
      type boolean;
      description
        "Recursive nexthop resolved";
    }
    leaf resolving-prefix {
      type yang:hex-string;
      description
        "Resolving prefix";
    }
    leaf resolving-prefix-length {
      type uint32;
      description
        "Resolving prefix length";
    }
    leaf address-is-v4-mapped-v6 {
      type boolean;
      description
        "Address is v4-mapped-v6";
    }
    leaf hardware-information-included {
      type boolean;
      description
        "Hardware info included";
    }
    leaf rnh-current-state {
      type Fib-sh-rec-nh-state;
      description
        "Current state of RNH";
    }
  }

  grouping FIB-SH-INT-GIL-IDB-ATTR {
    description
      "FIB IDB attribute GIL information";
    leaf interface-name {
      type string;
      description
        "Interface name";
    }
  }

  grouping FIB-SH-INT-PWHE-IDB-ATTR {
    description
      "FIB IDB attribute PWHE information";
    leaf pwhe-internal-label {
      type uint32;
      description
        "PWHE internal label";
    }
    leaf pwhe-iid {
      type inet:ipv6-address;
      description
        "IID for PWHE";
    }
    leaf pwhe-gil-interface-name {
      type string;
      description
        "GIL Interface attached to the PWHE";
    }
  }

  grouping FIB-SH-INT-IDB-ATTR {
    description
      "FIB per interface IDB attribute information";
    container pwhe-attribute {
      description
        "Information about PWHE attribute";
      uses FIB-SH-INT-PWHE-IDB-ATTR;
    }
    leaf npu-mask {
      type uint32;
      description
        "Value for NPU mask attribute";
    }
    leaf npu-mask-status {
      type string;
      description
        "Status of NPU mask";
    }
    list generic-interface {
      description
        "List of interfaces in GIL attribute";
      uses FIB-SH-INT-GIL-IDB-ATTR;
    }
  }

  grouping FIB-SH-INT-INTERNAL {
    description
      "FIB per interface internal information";
    container idb-event-history {
      description
        "Event History for IDB";
      uses EVT-HIST-INFO;
    }
    container srte-head-event-history {
      description
        "Event History for Srtehead";
      uses EVT-HIST-INFO;
    }
  }

  grouping FIB-SH-INT-DET {
    description
      "FIB per interface detail information";
    leaf interface-mtu {
      type uint16;
      description
        "Interface Protocol MTU";
    }
    leaf forwarding-flag {
      type boolean;
      description
        "Forwarding enabled/disabled flag";
    }
    leaf rpf-configured-flag {
      type boolean;
      description
        "RPF configured flag";
    }
    leaf rpf-mode {
      type Fib-rpf-mode;
      description
        "RPF mode";
    }
    leaf default-route-with-rpf {
      type boolean;
      description
        "Allow default route with RPF";
    }
    leaf self-ping-with-rpf {
      type boolean;
      description
        "Allow selfping with RPF";
    }
    leaf bgp-pa-input-configured-flag {
      type boolean;
      description
        "BGP PA configured flag";
    }
    leaf source-bgp-pa-input-configured-flag {
      type boolean;
      description
        "src BGP PA configured flag";
    }
    leaf destination-bgp-pa-input-configured-flag {
      type boolean;
      description
        "dst BGP PA configured flag";
    }
    leaf bgp-pa-output-configured-flag {
      type boolean;
      description
        "BGP PA configured flag";
    }
    leaf source-bgp-pa-output-configured-flag {
      type boolean;
      description
        "src BGP PA configured flag";
    }
    leaf destination-bgp-pa-output-configured-flag {
      type boolean;
      description
        "dst BGP PA configured flag";
    }
    leaf icmp-flag {
      type uint32;
      description
        "ICMP  configured flag";
    }
    leaf multi-label-drop-flag {
      type boolean;
      description
        "Drop packets with multiple-label-stack if set";
    }
  }

  grouping FIB-SH-INT-PT {
    description
      "FIB per interface path tracing information";
    leaf interface-id {
      type uint32;
      description
        "PT Interface ID";
    }
    leaf interface-load-inbound {
      type uint32;
      description
        "PT Interface Load (inbound)";
    }
    leaf interface-load-out {
      type uint32;
      description
        "PT Interface Load (outbound)";
    }
    leaf tts {
      type uint32;
      description
        "PT Timestamp template";
    }
  }

  grouping FIB-SH-INT {
    description
      "FIB per interface information";
    container path-tracing {
      description
        "Interface path tracing information";
      uses FIB-SH-INT-PT;
    }
    container detail-fib-interface-information {
      description
        "Detailed FIB interface information";
      uses FIB-SH-INT-DET;
    }
    container internal-info {
      description
        "Internal Information";
      uses FIB-SH-INT-INTERNAL;
    }
    container idb-attribute-info {
      description
        "IDB attribute information";
      uses FIB-SH-INT-IDB-ATTR;
    }
    leaf per-interface {
      type xr:Interface-name;
      description
        "Interface handle";
    }
    leaf fib-interface-type {
      type uint32;
      description
        "FIB Interface type";
    }
    leaf fib-id-pointer {
      type uint32;
      description
        "Pointer to fibidb";
    }
    leaf fib-id-flags {
      type uint32;
      description
        "Flags on fibidb";
    }
    leaf fib-id-extension-pointer {
      type uint32;
      description
        "Pointer to fibidb extension";
    }
    leaf fib-id-extension-flags {
      type uint32;
      description
        "Flags on fibidb extension";
    }
    leaf number-of-dependent-next-hop-information {
      type uint32;
      description
        "Number of dependent nhinfo's";
    }
    leaf vrf-local-cef-information-pointer {
      type uint32;
      description
        "Vrf local cef info ptr";
    }
    leaf reference-count {
      type uint16;
      description
        "Reference count";
    }
    leaf last-modified-time {
      type uint32;
      description
        "Time last modified";
    }
    leaf last-operation {
      type Fibidb-oper;
      description
        "Last Oper";
    }
    leaf protocol-enabled {
      type boolean;
      description
        "Is the protocol configured?";
    }
    leaf reference-count-for-protocol {
      type uint32;
      description
        "Reference count for the protocol";
    }
    leaf number-of-input-packets {
      type uint64;
      description
        "Number of input packets";
    }
    leaf number-of-input-bytes {
      type uint64;
      units "byte";
      description
        "Number of input bytes";
    }
    leaf number-of-output-packets {
      type uint64;
      description
        "Number of output packets";
    }
    leaf number-of-output-bytes {
      type uint64;
      units "byte";
      description
        "Number of output bytes";
    }
    leaf interface-up-flag {
      type boolean;
      description
        "Interface up flag";
    }
    leaf per-packet-load-balancing-flag {
      type boolean;
      description
        "Per packet loadbalancing flag";
    }
    leaf p2p-interface-flag {
      type boolean;
      description
        "P2P interface flag";
    }
    leaf loopback-interface-flag {
      type boolean;
      description
        "Loopback interface flag";
    }
    leaf null-interface-flag {
      type boolean;
      description
        "Null interface flag";
    }
    leaf tunnel-interface-flag {
      type boolean;
      description
        "Tunnel interface flag";
    }
    leaf gre-tunnel-interface-flag {
      type boolean;
      description
        "GRE Tunnel interface flag";
    }
    leaf punt-packets-from-fib-switching-flag {
      type boolean;
      description
        "Punt packets from FIB switching flag";
    }
    leaf drop-packets-while-fib-switching-flag {
      type boolean;
      description
        "Drop packets while FIB switching flag";
    }
    leaf punt-packets-from-linecard-flag {
      type boolean;
      description
        "Punt packets from linecard flag";
    }
    leaf primary-ipv4-address {
      type string {
        length "0..52";
      }
      description
        "Pimary local v4 address for the interface";
    }
    leaf primary-ipv6-address {
      type string {
        length "0..52";
      }
      description
        "Pimary local v6 address for the interface";
    }
    leaf usable {
      type boolean;
      description
        "Interface is Usable for forwarding if set";
    }
  }

  grouping FIB-SH-TBL-FIB-DVAR-VRF-DET {
    description
      "FIB table destination VRF information";
    container vrf-leak-timestamp {
      description
        "Destination Vrf Leak Timestamp";
      uses FIB-SH-TIMESPEC;
    }
    leaf destinationvrf-name {
      type string;
      description
        "Destination Vrf Name";
    }
    leaf destinationvrf-table-id {
      type uint32;
      description
        "Destination Vrf Table ID";
    }
    leaf destinationvrf-table-pointer {
      type uint64;
      description
        "Destination Vrf Table Ptr";
    }
  }

  grouping FIB-SH-TBL-FIB-DVARS {
    description
      "FIB table destination information";
    leaf protocol {
      type Fib-bag-protocol;
      description
        "Src Vrf Protocol";
    }
    leaf prefix-length {
      type uint32;
      description
        "Src Prefix Length";
    }
    leaf source-vrf {
      type uint32;
      description
        "Src VRF";
    }
    leaf destination-count {
      type uint32;
      description
        "Count of Number of Destination Vrfs this prefix
         is leaked in";
    }
    leaf flags {
      type uint32;
      description
        "Flags";
    }
    list destinationvrf-detail {
      description
        "Destination Vrf Detail";
      uses FIB-SH-TBL-FIB-DVAR-VRF-DET;
    }
  }

  grouping FIB-ATTRIBUTE-DET {
    description
      "Detailed info for downloaded fib route attributes";
    leaf bgp-attribute-id {
      type uint32;
      description
        "BGP attribute id";
    }
    leaf bgp-local-attribute-id {
      type uint32;
      description
        "BGP local attribute id";
    }
    leaf bgp-local-preference {
      type uint32;
      description
        "BGP attribute local preference of the path";
    }
    leaf bgp-attribute-origin-as {
      type uint32;
      description
        "BGP attribute origin as";
    }
    leaf bgp-attribute-nh-as {
      type uint32;
      description
        "BGP attribute next hop as";
    }
    leaf as-path-string {
      type yang:hex-string;
      description
        "As path string";
    }
    leaf extended-community-string {
      type yang:hex-string;
      description
        "extcom st";
    }
    leaf community-string {
      type yang:hex-string;
      description
        "com st";
    }
    leaf extended-community {
      type uint32;
      description
        "extended community";
    }
  }

  grouping FIB-COMMON-RTEP-TBL-STATS {
    description
      "FIB RTEP table stats bag";
    container common-table-stats {
      description
        "Common FIB subtype table stats bag";
      uses FIB-COMMON-TBL-STATS-BAG;
    }
  }

  grouping FIB-COMMON-LTEP-TBL-STATS {
    description
      "FIB LTEP table stats bag";
    container common-table-stats {
      description
        "Common FIB subtype table stats bag";
      uses FIB-COMMON-TBL-STATS-BAG;
    }
  }

  grouping FIB-SH-TIMESPEC {
    description
      "FIB SH TIMESPEC";
    leaf seconds {
      type int32;
      description
        "Seconds";
    }
    leaf nano-seconds {
      type int32;
      description
        "NanoSeconds";
    }
  }

  grouping FIB-SH-FRR-LOG {
    description
      "FIB frr log information";
    container frr-timestamp {
      description
        "FIB fast reroute timestamp";
      uses FIB-SH-TIMESPEC;
    }
    leaf frr-protocol-type {
      type Fib-bag-protocol;
      description
        "FIB Protocol Type";
    }
    leaf frr-interface-name {
      type xr:Interface-name;
      description
        "Interface assoc w FRR nh";
    }
    leaf frr-nexthop-address {
      type string {
        length "0..52";
      }
      description
        "nh prefix";
    }
    leaf frr-switching-time {
      type uint32;
      description
        "FIB fast reroute switching time";
    }
    leaf bundle-member-interface-name {
      type xr:Interface-name;
      description
        "bundle member";
    }
  }

  grouping FIB-SH-TBL-EXT-PL-SUM {
    description
      "FIB external client pathlist summary";
    leaf ecd-pathlist-count {
      type uint32;
      description
        "Number of ECD pathlists";
    }
    leaf unresolved-ecd-pathlist-count {
      type uint32;
      description
        "Number of ECD pathlists unresolved";
    }
    list ecd-pathlist-count-per-interest {
      max-elements "19";
      description
        "Number of ECD pathlists per interest";
      leaf entry {
        type uint32;
        description
          "Number of ECD pathlists per interest";
      }
    }
  }

  grouping FIB-SH-TBL-EXT-SUM-ALL {
    description
      "FIB external brief summary information across all
       clients";
    container external-pathlist-summary {
      description
        "External pathlist summary";
      uses FIB-SH-TBL-EXT-PL-SUM;
    }
    leaf number-of-external-clients {
      type uint32;
      description
        "Client information";
    }
  }

  grouping FIB-SH-LB-OOR-HLB-SITE-DAMPEN-INFO {
    description
      "fib LB oor HLB site dampening debug info";
    leaf dampen-obj-merged {
      type uint32;
      description
        "Number of HLB Site objects merged by FIB LB OOR
         dampening";
    }
  }

  grouping FIB-SH-LB-OOR-DLB-INFO {
    description
      "fib LB oor dlb debug info";
    leaf dlb-route-handled {
      type uint64;
      description
        "Number of routes be handled by FIB LB OOR DLB";
    }
    leaf dlb-retry-active {
      type boolean;
      description
        "FIB LB OOR DLB retry is in active";
    }
  }

  grouping FIB-SH-LB-OOR-DAMPEN-INFO {
    description
      "fib LB oor dampening debug info";
    leaf dampen-route-handled {
      type uint64;
      description
        "Number of routes be handled by FIB LB OOR
         dampening";
    }
    leaf dampen-max-duration {
      type uint32;
      description
        "Maximum FIB LB OOR dampening duration";
    }
    leaf dampen-retry-sleep {
      type uint32;
      description
        "Number of retry sleep on FIB LB OOR dampening
         retries";
    }
    leaf dampen-force-so {
      type uint32;
      description
        "Number of forced FIB LB OOR dampening switchover";
    }
    leaf dampen-retry-active {
      type boolean;
      description
        "FIB LB OOR Dampening retry is in active";
    }
    leaf dampen-obj-merged {
      type uint32;
      description
        "Number of objects merged by FIB LB OOR dampening";
    }
  }

  grouping FIB-SH-FEATURE-INFO {
    description
      "FIB SH FEATURE INFO";
    container dampen {
      when "../feature = 'lb-oor-dampen'" {
        description
          "../feature = 'LbOorDampen'";
      }
      description
        "dampen";
      uses FIB-SH-LB-OOR-DAMPEN-INFO;
    }
    container dlb {
      when "../feature = 'lb-oor-dlb'" {
        description
          "../feature = 'LbOorDlb'";
      }
      description
        "dlb";
      uses FIB-SH-LB-OOR-DLB-INFO;
    }
    container hlb-site-dampen {
      when "../feature = 'lb-oor-hlb-site-dampen'" {
        description
          "../feature = 'LbOorHlbSiteDampen'";
      }
      description
        "hlb site dampen";
      uses FIB-SH-LB-OOR-HLB-SITE-DAMPEN-INFO;
    }
    leaf feature {
      type Fib-sh-marker-feature;
      description
        "feature";
    }
  }

  grouping FIB-OBJECT-MARKER-INFO {
    description
      "FIB Object Marker Information";
    container object-base {
      description
        "Object Base";
      uses FIB-SH-FIB-OBJ-BASE;
    }
    container evt-hist {
      description
        "event history of partition";
      uses EVT-HIST-INFO;
    }
    container feature-info {
      description
        "Feature specific info";
      uses FIB-SH-FEATURE-INFO;
    }
    leaf name {
      type string;
      description
        "Marker Name";
    }
    leaf active {
      type boolean;
      description
        "Enabled";
    }
    leaf need-timer {
      type boolean;
      description
        "Need Timer Support";
    }
    leaf need-wrap {
      type boolean;
      description
        "Need Wrap Support";
    }
    leaf marker-id {
      type uint8;
      description
        "Marker Id";
    }
    leaf partition {
      type boolean;
      description
        "Is partition marker";
    }
    leaf partition-num-objs {
      type uint32;
      description
        "Num of objs in partition";
    }
    leaf partition-num-walks {
      type uint32;
      description
        "Num of walks of partition";
    }
    leaf partition-num-walk-del-objs {
      type uint64;
      description
        "Num of objs be walked in partition";
    }
    leaf timestamp-last-obj-add {
      type string;
      description
        "Timestamp of last obj add to partition";
    }
    leaf feature-type {
      type Fib-sh-marker-feature;
      description
        "Feature type";
    }
  }

  grouping FIB-OBJECT-QUEUE-INFO {
    description
      "FIB Object Queue Information";
    container object-base {
      description
        "Object Base";
      uses FIB-SH-FIB-OBJ-BASE;
    }
    leaf name {
      type string;
      description
        "Object Queue Name";
    }
    leaf queue-id {
      type uint32;
      description
        "Queue ID";
    }
    leaf number-of-nodes {
      type uint32;
      description
        "Number of Nodes";
    }
    leaf number-of-special-nodes {
      type uint32;
      description
        "Number of Special Nodes";
    }
    list marker {
      description
        "Object Markers";
      uses FIB-OBJECT-MARKER-INFO;
    }
  }

  grouping FIB-RSRC-BAG {
    description
      "Hardware object resource availability";
    leaf resource-name {
      type string;
      description
        "Resource Name";
    }
    leaf resource-mode {
      type Fib-rsrc-mode-bag;
      description
        "OOR mode for resource";
    }
  }

  grouping FIB-SH-RSRC-AVAIL-STATE {
    description
      "FIB resource availability state";
    leaf resource-mode {
      type Fib-rsrc-mode-bag;
      description
        "Current overall OOR mode";
    }
    leaf hardware-resource-info {
      type yang:hex-string;
      description
        "Opaque hardware resource state info";
    }
    leaf shared-memory-oor-counter {
      type uint8;
      description
        "Shared memory OOR count";
    }
    leaf hardware-oor-counter {
      type uint8;
      description
        "Hardware OOR count";
    }
    leaf incoming-oor-timestamp {
      type uint64;
      description
        "Incoming OOR timestamp";
    }
    leaf outgoing-oor-timestamp {
      type uint64;
      description
        "Outgoing OOR timestamp";
    }
    list shared-memory-status {
      description
        "Current status of shared memory windows";
      uses FIB-SH-RSRC-SHM;
    }
    list hardware-resource-mode {
      description
        "Hardware object resource mode";
      uses FIB-RSRC-BAG;
    }
  }

  grouping FIB-TC-UPDATE-INFO {
    description
      "Traffic-collector update info";
    leaf total-number-of-updates-since-last-registration {
      type uint32;
      description
        "Total number of updates sent to
         traffic-collector since last re/registration";
    }
    leaf number-of-last-update-sent-to-traffic-collector {
      type uint32;
      description
        "Number of last updates sent to traffic-collector";
    }
    leaf eod-is-sent-to-traffic-colletor {
      type boolean;
      description
        "A flag to indicate if EOD is sent to
         traffic-colletor";
    }
    leaf fib-has-more-updates-for-tc {
      type boolean;
      description
        "A flag to indicate if FIB has more updates to
         send to TC";
    }
    leaf number-of-walked-objects-since-last-registration {
      type uint32;
      description
        "Total number of walked objects since last
         re/registration";
    }
    leaf number-of-walked-delete-objects-since-last-registration {
      type uint32;
      description
        "Total number of walked del-objects since last
         re/registration";
    }
    leaf pending-update-size-as-per-last-walk {
      type uint32;
      description
        "Size of pending updates as per last walk";
    }
    leaf se-tc-num-q-obj-interval-start {
      type uint32;
      description
        " ";
    }
    leaf se-tc-num-q-obj-interval-end {
      type uint32;
      description
        " ";
    }
    leaf se-tc-num-updates {
      type uint32;
      description
        " ";
    }
    leaf se-tc-num-add-sr-label {
      type uint32;
      description
        " ";
    }
    leaf se-tc-num-del-sr-label {
      type uint32;
      description
        " ";
    }
    leaf se-tc-num-add-ldp-label {
      type uint32;
      description
        " ";
    }
    leaf se-tc-num-del-ldp-label {
      type uint32;
      description
        " ";
    }
    leaf se-tc-num-leaf-obj {
      type uint32;
      description
        " ";
    }
    leaf se-tc-num-del-obj {
      type uint32;
      description
        " ";
    }
    leaf se-tc-is-q-tail {
      type boolean;
      description
        " ";
    }
    leaf se-tc-tail-timestamp {
      type uint64;
      description
        " ";
    }
    leaf se-tc-is-fec-buff-full {
      type boolean;
      description
        " ";
    }
    leaf se-tc-fec-buf-full-timestamp {
      type uint64;
      description
        " ";
    }
    leaf se-tc-current-q-obj-cnt {
      type uint32;
      description
        " ";
    }
    leaf se-tc-is-tc-marker-at-tail {
      type boolean;
      description
        " ";
    }
  }

  grouping FIB-SH-TBL-INT {
    description
      "Internal Info";
    leaf ecd {
      type string;
      description
        "String Representation of ECD";
    }
  }

  grouping FIB-MPLS-RPF-IF-MAP {
    description
      "Mapping between interface and neighbour";
    leaf path-index {
      type uint32;
      description
        "PathIndex";
    }
    leaf interface-name {
      type xr:Interface-name;
      description
        "InterfaceName";
    }
  }

  grouping FIB-MPLS-RPF-V6-NBR {
    description
      "RPF info for V4 neighbour";
    leaf table-id {
      type uint32;
      description
        "TableID";
    }
    leaf ipv6-address {
      type inet:ipv6-address;
      description
        "IPv6Address";
    }
  }

  grouping FIB-MPLS-RPF-V4-NBR {
    description
      "RPF info for V4 neighbour";
    leaf table-id {
      type uint32;
      description
        "TableID";
    }
    leaf ipv4-address {
      type inet:ipv4-address;
      description
        "IPv4Address";
    }
  }

  grouping FIB-MPLS-LEAF-RPF {
    description
      " Leaf RPF info";
    leaf rpf-flags {
      type uint32;
      description
        "RPF flags";
    }
    leaf rpf-pl-flags {
      type uint32;
      description
        "RPF pathlist flags";
    }
    leaf rpf-create-ts {
      type uint64;
      description
        "Time when the LRPF was created";
    }
    leaf rpf-mod-ts {
      type uint64;
      description
        "Last time the LRPF modified";
    }
    leaf rpf-pd-ts {
      type uint64;
      description
        "Last time the PD action was sent for the LRPF";
    }
    leaf rpf-hardware {
      type yang:hex-string;
      description
        "Platform Hardware info";
    }
    list rpf-if {
      description
        "Array of interfaces in interface list";
      leaf entry {
        type xr:Interface-name;
        description
          "Array of interfaces in interface list";
      }
    }
    list rpf-v4-nbr {
      description
        "Array of V4 neighbours";
      uses FIB-MPLS-RPF-V4-NBR;
    }
    list rpf-v6-nbr {
      description
        "Array of V6 neighbours";
      uses FIB-MPLS-RPF-V6-NBR;
    }
    list rpf-if-map {
      description
        "Array of nbr/interface mapping";
      uses FIB-MPLS-RPF-IF-MAP;
    }
  }

  grouping FIB-SH-TBL-EXT {
    description
      "FIB external client information";
    container loadinfo-internal-data {
      description
        "Loadinfo internal data";
      uses FIB-SH-TBL-LOADINFO-DET;
    }
    container label-rpf-info {
      description
        " Label RPF info";
      uses FIB-MPLS-LEAF-RPF;
    }
    container internal-information {
      description
        "Internal Information";
      uses FIB-SH-TBL-INT;
    }
    container traffic-collector-update-information {
      description
        "Info about TC updates";
      uses FIB-TC-UPDATE-INFO;
    }
    leaf fib-entry-prefix {
      type yang:hex-string;
      description
        "Prefix of FIB entry";
    }
    leaf fib-entry-prefix-length {
      type uint32;
      description
        "Prefix length for this entry";
    }
    leaf registration-protocol-type {
      type uint32;
      description
        "Registration proto";
    }
    leaf interface-name {
      type xr:Interface-name;
      description
        "Interface";
    }
    leaf via-label {
      type uint32;
      description
        "Via label";
    }
    leaf platform-hardware-info {
      type yang:hex-string;
      description
        "Platform Hardware info";
    }
    leaf external-client-interest-type {
      type uint32;
      description
        "External client interest type";
    }
    leaf external-client-name {
      type string;
      description
        "External client name";
    }
    leaf ip-address {
      type yang:hex-string;
      description
        "IP address to recurse to";
    }
    leaf state-information {
      type uint32;
      description
        "State information";
    }
    leaf number-of-notification {
      type uint32;
      description
        "Number of notifications sent";
    }
    leaf registration-pointer {
      type uint32;
      description
        "Registration ptr";
    }
    leaf registration-pathlist-pointer {
      type uint32;
      description
        "Registration pathlist ptr";
    }
    leaf registration-pathlist-flags {
      type uint32;
      description
        "Registration pathlist flags";
    }
    leaf registration-pathlist-reference-count {
      type uint32;
      description
        "Registration pathlist refcount";
    }
    leaf registration-loadinfo-pointer {
      type uint32;
      description
        "Registration loadinfo ptr";
    }
    leaf registration-loadinfo-flags {
      type uint32;
      description
        "Registration loadinfo flags";
    }
    leaf registration-loadinfo-reference-count {
      type uint32;
      description
        "Registration loadinfo refcount";
    }
    leaf external-client-pointer {
      type uint32;
      description
        "External client ptr";
    }
    leaf registration-table-id {
      type uint32;
      description
        "Registration table-id";
    }
    leaf registration-cookie {
      type yang:hex-string;
      description
        "Registration cookie";
    }
    leaf registration-tunnel-type {
      type uint32;
      description
        "Registration ltep tunnel type";
    }
    leaf registration-ltep-vni-id {
      type uint32;
      description
        "Registration ltep vni_id";
    }
    leaf component-id {
      type uint32;
      description
        "component-id of the client";
    }
    leaf is-local-label-valid {
      type boolean;
      description
        "Is Local label valid";
    }
    leaf local-label-associated-with-prefix {
      type uint32;
      description
        "Local-label associated with pfx";
    }
    leaf route-version {
      type uint64;
      description
        "Route version";
    }
    leaf number-of-labels-for-segment-routing-o-prefix {
      type uint32;
      description
        "Number of labels for segment-routing prefix";
    }
    leaf next-hop-group-id {
      type uint32;
      description
        "NextHop Group ID";
    }
    leaf next-hop-group-type {
      type uint32;
      description
        "NextHop Group Type";
    }
  }

  grouping FIB-GENERIC-INTF-LIST-DATA {
    description
      "Data related to generic interface list";
    leaf interface-list-name {
      type string;
      description
        "Interface_list name";
    }
    leaf interface-list-id {
      type uint32;
      description
        "Interface_list id";
    }
    leaf stuct-pointer {
      type uint32;
      description
        "Address of struct";
    }
    leaf flag {
      type uint32;
      description
        "Flags";
    }
    leaf reference-count {
      type uint32;
      description
        "Ref count";
    }
    leaf last-updated-timestamp {
      type uint64;
      description
        "Last updated time stamp";
    }
    leaf interface-count {
      type uint32;
      description
        "Total interfaces in the list";
    }
    list interface-name {
      description
        "Array of member interfaces";
      leaf entry {
        type xr:Interface-name;
        description
          "Array of member interfaces";
      }
    }
  }

  grouping FIB-SH-PFX-MASKLEN-CNT {
    description
      "FIB Prefix Masklength counts";
    leaf mask-length {
      type uint8;
      description
        "FIB Prefix Mask length";
    }
    leaf number-of-prefixes {
      type uint32;
      description
        "Number of prefixes with given mask length";
    }
  }

  grouping FIB-SH-PFX-MASKLEN-DISTRIB {
    description
      "FIB Prefix Masklengths distribution";
    list unicast-prefix {
      description
        "Masklength counts for unicast prefixes";
      uses FIB-SH-PFX-MASKLEN-CNT;
    }
    list broadcast-prefix {
      description
        "Masklength counts for broadcast prefixes";
      uses FIB-SH-PFX-MASKLEN-CNT;
    }
    list multicast-prefix {
      description
        "Masklength counts for multicast prefixes";
      uses FIB-SH-PFX-MASKLEN-CNT;
    }
  }

  grouping FIB-BAG-RT-SUMMARY-COUNTERS {
    description
      "FIB BAG RT SUMMARY COUNTERS";
    leaf fib-og-proto {
      type Fib-sh-og;
      description
        "fib og proto";
    }
    leaf rt-summary-counters {
      type uint64;
      description
        "rt summary counters";
    }
  }

  grouping FIB-PL-LDI-COUNT {
    description
      "FIB Pathlist and Loadinfo summary";
    leaf total-load-sharing-element-bytes {
      type uint32;
      units "byte";
      description
        "Total memory used by load sharing elements in
         bytes";
    }
    leaf total-load-sharing-element-references {
      type uint64;
      description
        "Total count of references to load sharing
         elements";
    }
    leaf total-path-list-elements {
      type uint32;
      description
        "Total count of Pathlist elements";
    }
    leaf recursive-path-list-elements {
      type uint32;
      description
        "Count of recursive Pathlist elements";
    }
    leaf platform-shared-path-list-elements {
      type uint32;
      description
        "Count of platform shared Pathlist elements";
    }
    leaf retry-path-list-elements {
      type uint32;
      description
        "Count of Pathlist elements in retry";
    }
    leaf total-loadinfo-elements {
      type uint32;
      description
        "Total count of Loadinfo elements";
    }
    leaf recursive-loadinfo-elements {
      type uint32;
      description
        "Count of recursive Loadinfo elements";
    }
    leaf platform-shared-loadinfo-elements {
      type uint32;
      description
        "Count of platform shared Loadinfo elements";
    }
    leaf xpl-loadinfo-elements {
      type uint32;
      description
        "Count of XPL Loadinfo elements";
    }
  }

  grouping FIB-SH-SUM {
    description
      "FIB summary statistics";
    container exclusive-load-sharing-element {
      description
        "Exclusive load sharing element";
      uses FIB-PL-LDI-COUNT;
    }
    container shared-load-sharing-element {
      description
        "Shared load sharing element";
      uses FIB-PL-LDI-COUNT;
    }
    container cross-shared-load-sharing-element {
      description
        "Cross-table shared load sharing element";
      uses FIB-PL-LDI-COUNT;
    }
    container encap-shared-load-sharing-element {
      description
        "Encap-shared load sharing element";
      uses FIB-PL-LDI-COUNT;
    }
    container prefix-masklen-distribution {
      description
        "Distribution of prefix mask lengths";
      uses FIB-SH-PFX-MASKLEN-DISTRIB;
    }
    leaf prefix {
      type yang:hex-string;
      description
        "The router-id";
    }
    leaf table-id {
      type uint32;
      description
        "Table Id";
    }
    leaf table-id-pointer {
      type uint32;
      description
        "Table Id Ptr";
    }
    leaf vrf-id {
      type uint32;
      description
        "Virtual routing forwarding instance Id";
    }
    leaf virtual-router-id {
      type uint32;
      description
        "Virtual router instance Id";
    }
    leaf load-balancing {
      type Ss-lba-state;
      description
        "LBA configuration state";
    }
    leaf forwarding-elements {
      type uint32;
      description
        "Number of forwarding elements linked to the
         table";
    }
    leaf routes {
      type uint32;
      description
        "Number of routes";
    }
    leaf prefix-in-place-modifications {
      type uint32;
      description
        "Number of inplace modifications";
    }
    leaf stale-prefix-deletes {
      type uint32;
      description
        "Number of deleted stale leafs";
    }
    leaf load-sharing-elements {
      type uint32;
      description
        "Count of load sharing elements";
    }
    leaf load-sharing-references {
      type uint64;
      description
        "Count of load sharing references";
    }
    leaf total-load-share-element-bytes {
      type uint32;
      description
        "Total memory used by load sharing elements";
    }
    leaf leaves-used-bytes {
      type uint32;
      description
        "Total memory used by leaves";
    }
    leaf reresolve-entries {
      type uint32;
      description
        "Number of reresolved entries";
    }
    leaf old-unresolved-entries {
      type uint32;
      description
        "Number of old unresolved entries";
    }
    leaf new-unresolved-entries {
      type uint32;
      description
        "Number of new unresolved entries";
    }
    leaf unresolved-entries {
      type uint32;
      description
        "Number of total unresolved entries";
    }
    leaf cef-route-drops {
      type uint32;
      description
        "Number of routes dropped by CEF";
    }
    leaf cef-version-mismatch-route-drops {
      type uint64;
      description
        "the number of routes dropped due to version
         mismatch";
    }
    leaf delete-cache-num-entries {
      type uint32;
      description
        "Number of entries in the route delete cache";
    }
    leaf existing-leaves-revisions {
      type uint32;
      description
        "Number of entries present on addition";
    }
    leaf fib-default-prefix {
      type uint32;
      description
        "Default prefix";
    }
    leaf fib-default-prefix-mask-length {
      type uint32;
      description
        "Default prefix mask length";
    }
    leaf next-hops {
      type uint32;
      description
        "Number of NHINFOS";
    }
    leaf incomplete-next-hops {
      type uint32;
      description
        "Number of incomplete NHINFOS";
    }
    leaf resolution-timer {
      type uint32;
      units "second";
      description
        "IP CEF resolution timer in seconds";
    }
    leaf slow-process-timer {
      type uint32;
      units "second";
      description
        "IP CEF slow processing time in seconds";
    }
    leaf max-resolution-timer {
      type uint32;
      units "second";
      description
        "IP CEF max resolution time in seconds";
    }
    leaf imposition-prefixes {
      type uint32;
      description
        "Number of prefixes with imposition LDI";
    }
    leaf extended-prefixes {
      type uint32;
      description
        "Number of prefixes with extended path-list";
    }
    leaf cef-label-recycled-routes {
      type uint32;
      description
        "Number of routes updates with recycled label
         handled";
    }
    leaf loadinfo-backwalks {
      type uint32;
      description
        "pd backwalks on LDI modify with backup path";
    }
    leaf protected-route-count {
      type uint32;
      description
        "Number of routes with FRR protection";
    }
    leaf lisp-eid-prefixes {
      type uint32;
      description
        "Number of lisp eid prefixes associated with
         table";
    }
    leaf lisp-eid-valid-prefixes {
      type uint32;
      description
        "Number of lisp eid prefixes eligible for
         forwarding";
    }
    leaf lisp-rloc-objects {
      type uint32;
      description
        "Number of lisp rloc objects associated with
         table";
    }
    leaf number-routes-srv6-headend {
      type uint32;
      description
        "Number of SRv6 headend routes";
    }
    leaf number-routes-srv6-endpoint {
      type uint32;
      description
        "Number of SRv6 endpoint routes";
    }
    leaf number-of-sr-labels {
      type uint32;
      description
        "Number of SR labels";
    }
    leaf dropped-pathlist-count {
      type uint32;
      description
        "Number of dropped pathlists";
    }
    list ss-rt-summary-counter {
      description
        "Route summary counters per protocol";
      uses FIB-BAG-RT-SUMMARY-COUNTERS;
    }
  }

  grouping FIB-RSRC-OOR-BAG {
    description
      "Hardware object resource out of resource";
    leaf oor-resource-name {
      type string;
      description
        "OOR resource name";
    }
    leaf oor-resource-mode {
      type Fib-rsrc-mode-bag;
      description
        "OOR mode for resource";
    }
  }

  grouping FIB-SH-RSRC-SHM {
    description
      "Shared memory availability";
    leaf shared-memory-window {
      type Fib-bag-shmwin;
      description
        "Shared Memory Window Type";
    }
    leaf resource-mode {
      type Fib-rsrc-mode-bag;
      description
        "OOR mode for this shared memory window";
    }
    leaf average-bytes-available {
      type uint64;
      units "byte";
      description
        "Average number of bytes available";
    }
    leaf maximum-bytes-available {
      type uint64;
      units "byte";
      description
        "Maximum bytes available";
    }
  }

  grouping FIB-SH-RSRC-AVAIL-OOR-STATE {
    description
      "FIB resource availability state";
    list shared-memory-status {
      description
        "Shared memory out of resource";
      uses FIB-SH-RSRC-SHM;
    }
    list hardware-resource-mode {
      description
        "Hardware objects resource out of resource";
      uses FIB-RSRC-OOR-BAG;
    }
  }

  grouping FIB-RETRY-DB-INFO {
    description
      "FIB Retry DB information";
    leaf retry-flags {
      type uint32;
      description
        "FIB Retry flags";
    }
    leaf retry-count {
      type uint32;
      description
        "FIB Retry count";
    }
    leaf error-code {
      type uint32;
      description
        "Error Code";
    }
    leaf retry-object-info {
      type string;
      description
        "FIB Object String";
    }
    leaf retry-fib-object-type {
      type string;
      description
        "FIB Object type";
    }
    leaf retry-timestamp {
      type string;
      description
        "FIB Retry timestamp";
    }
    leaf retry-scheduling-class {
      type Fib-retry-entry-bag-sched-class;
      description
        "FIB Retry scheduling class";
    }
  }

  grouping FIB-RETRY-DB-SUMMARY {
    description
      "FIB Retry DB Summary information";
    leaf retry-queue-size {
      type uint32;
      description
        "the number of elements in retryq";
    }
    leaf service-time {
      type uint32;
      units "millisecond";
      description
        "the service time in msecs";
    }
    leaf number-of-retry-timeouts {
      type uint64;
      description
        "the number of retry timeouts";
    }
    list number-of-retry {
      description
        "the number of retries of each type";
      leaf entry {
        type uint64;
        description
          "the number of retries of each type";
      }
    }
    list number-of-timeouts-per-class {
      description
        "the number of timeouts per SC";
      leaf entry {
        type uint64;
        description
          "the number of timeouts per SC";
      }
    }
    list number-of-elements-per-class {
      description
        "the number of objects per SC";
      leaf entry {
        type uint32;
        description
          "the number of objects per SC";
      }
    }
    list timeout-value-per-class {
      description
        "the timeout value (in msecs) per SC";
      leaf entry {
        type uint32;
        units "millisecond";
        description
          "the timeout value (in msecs) per SC";
      }
    }
  }

  grouping FIB-SH-PLAT-RES-MON-STATS {
    description
      "FIB platform res mon stats";
    leaf mi-mbb-percentage {
      type uint32;
      units "percentage";
      description
        "percentage threshold to enter dampening mode";
    }
    leaf mi-dlb-percentage {
      type uint32;
      units "percentage";
      description
        "percentage threshold to enter DLB mode";
    }
    leaf mi-lvl1-used-group {
      type uint32;
      description
        "number of LB group counted in resmon for lvl1
         load balancing, LB oor Dampening and DLB trigger";
    }
    leaf mi-lvl1-used-paths {
      type uint32;
      description
        "number of LB paths counted in resmon for lvl1
         load balancing, LB oor Dampening and DLB trigger";
    }
    leaf mi-lvl1-max-num-group {
      type uint32;
      description
        "max number of LB group accounted in resmon for
         lvl1 load balancing";
    }
    leaf mi-lvl1-max-num-paths {
      type uint32;
      description
        "max number of LB paths accounted in resmon for
         lvl1 load balancing";
    }
    leaf mi-lvl1-group-high-watermark {
      type uint32;
      description
        "high watermark of LB lvl1 group";
    }
    leaf mi-lvl1-group-high-wm-tstamp {
      type uint64;
      description
        "high watermark timestamp of LB lvl1 group";
    }
    leaf mi-lvl1-paths-high-watermark {
      type uint32;
      description
        "high watermark of LB lvl1 paths";
    }
    leaf mi-lvl1-paths-high-wm-tstamp {
      type uint64;
      description
        "high watermark timestamp of LB lvl1 paths";
    }
    leaf mi-lvl2-used-group {
      type uint32;
      description
        "number of LB group counted in resmon for lvl2
         load balancing";
    }
    leaf mi-lvl2-used-paths {
      type uint32;
      description
        "number of LB paths counted in resmon for lvl2
         load balancing";
    }
    leaf mi-lvl2-max-num-group {
      type uint32;
      description
        "max number of LB group accounted in resmon for
         lvl2 load balancing";
    }
    leaf mi-lvl2-max-num-paths {
      type uint32;
      description
        "max number of LB paths accounted in resmon for
         lvl2 load balancing";
    }
    leaf mi-lvl2-group-high-watermark {
      type uint32;
      description
        "high watermark of LB lvl2 group";
    }
    leaf mi-lvl2-group-high-wm-tstamp {
      type uint64;
      description
        "high watermark timestamp of LB lvl2 group";
    }
    leaf mi-lvl2-paths-high-watermark {
      type uint32;
      description
        "high watermark of LB lvl2 paths";
    }
    leaf mi-lvl2-paths-high-wm-tstamp {
      type uint64;
      description
        "high watermark timestamp of LB lvl2 paths";
    }
  }

  grouping FIB-SH-PLAT-CAPABILITIES {
    description
      "FIB platform capabilities";
    leaf l3-load-balancing-levels {
      type uint16;
      description
        "L3 LBL levels";
    }
    leaf l3-load-balancing-paths-count {
      type uint16;
      description
        "L3 Hash buckets";
    }
    leaf l3-load-balancing-recursive-paths-count {
      type uint16;
      description
        "L3 Recursive Hash buckets";
    }
    leaf l3-load-balancing-ip-route-paths-count {
      type uint16;
      description
        "L3 IP Route Hash buckets";
    }
    leaf l3-unequal-cost-paths-count {
      type uint16;
      description
        "L3 Unequal cost hash buckets";
    }
    leaf l3-unequal-cost-ip-route-paths-count {
      type uint16;
      description
        "L3 Unequal cost hash buckets for IP routes";
    }
    leaf forwarding-stage-count {
      type uint8;
      description
        "Forwarding stages";
    }
    leaf local-label-split {
      type uint32;
      description
        "Label split";
    }
    leaf statistics-support {
      type boolean;
      description
        "Statistics support";
    }
    leaf platform-ready-callback-register {
      type boolean;
      description
        "Plat ready cb register";
    }
    leaf number-of-path-per-tunnel-class {
      type uint16;
      description
        "Path per tunnel class";
    }
    leaf v4-update-disable {
      type boolean;
      description
        "V4 update disable";
    }
    leaf v6-update-disable {
      type boolean;
      description
        "V6 update disable";
    }
    leaf lba-tuples {
      type uint32;
      description
        "LBA tuples";
    }
    leaf mraps-support {
      type boolean;
      description
        "MRAPS support";
    }
    leaf pbts-default-class-support {
      type boolean;
      description
        "PBTS default class support";
    }
    leaf loadinfo-filter-support {
      type boolean;
      description
        "loadinfo filter support";
    }
    leaf nhid-support {
      type boolean;
      description
        "NHID support";
    }
    leaf backwalk-dependents-is-required {
      type boolean;
      description
        "Backwalk dependents is required";
    }
    leaf link-mpls-ipv6-nh-support {
      type boolean;
      description
        "Link MPLS IPv6 NH support";
    }
    leaf exclude-deag-backup-paths {
      type boolean;
      description
        "Exclude Deag backup Paths";
    }
    leaf per-destination-load-balancing-support {
      type boolean;
      description
        "Per-destination load-balancing support";
    }
    leaf prefix-filter-level-of-support {
      type uint8;
      description
        "Prefix filter level of support";
    }
    leaf slowpath-ingress-inject-required {
      type boolean;
      description
        "Slowpath ingress inject required";
    }
    leaf cofo-supported {
      type boolean;
      description
        "COFO supported";
    }
    leaf srv6-supported {
      type boolean;
      description
        "SRv6 supported";
    }
    leaf srv6-replicated-lw-loadinfo-required {
      type boolean;
      description
        "SRv6 replicated LW-LDI required";
    }
    leaf ipv4-ipv6-collapse-loadinfo-support {
      type boolean;
      description
        "IPv4 over IPV6 Collapse LDI support";
    }
    leaf one-pass-gre-support {
      type boolean;
      description
        "1-pass GRE support";
    }
    leaf srte-collapse-support {
      type boolean;
      description
        "SR-TE collapse support";
    }
    leaf eint-interface-support {
      type boolean;
      description
        "EINT interface support";
    }
    leaf no-collapse-ip-over-mpls {
      type boolean;
      description
        "Disable collapse for IP routes over MPLS";
    }
    leaf encap-id-conflict {
      type boolean;
      description
        "Encap ID conflict Check";
    }
    leaf via-label-ignore-next-hop {
      type boolean;
      description
        "Ignore nexthop address and interface in case of
         via-label routes";
    }
    leaf platform-nsr-ready-required {
      type boolean;
      description
        "Platform NSR readiness is required";
    }
    leaf adjacency-replication-support {
      type boolean;
      description
        "Support Adjacency Replication in PI and
         allocation Encap ID for ADJ";
    }
    leaf adjacency-change-backwalk-reduction {
      type boolean;
      description
        "Reduce platform backwalk when adjacency is
         changed";
    }
    leaf async-ack-support {
      type boolean;
      description
        "Support async acknowledgement of hardware
         programming";
    }
    leaf disable-rfc5549ipv4-over-ipv6-nexthop {
      type boolean;
      description
        "Disable RFC5549 IPv4 over IPv6 nexthop";
    }
    leaf two-stage-object-id-support {
      type boolean;
      description
        "Support Two Stage platform ObjectId";
    }
    leaf two-stage-async-error-notify-support {
      type boolean;
      description
        "Support Two Stage Async Error Notify";
    }
    leaf platform-pbtsv6-support {
      type boolean;
      description
        "PBTS over v6 support";
    }
    list lisp-decapsulated-over-v4 {
      min-elements 3;
      max-elements "3";
      description
        "LISP Decap over 4";
      leaf entry {
        type boolean;
        description
          "Array entry.";
      }
    }
    list lisp-decapsulated-over-v6 {
      min-elements 3;
      max-elements "3";
      description
        "LISP Decap over 6";
      leaf entry {
        type boolean;
        description
          "Array entry.";
      }
    }
    list lisp-ucmp-support {
      min-elements 3;
      max-elements "3";
      description
        "LISP UCMP support";
      leaf entry {
        type boolean;
        description
          "Array entry.";
      }
    }
    list fallback-vrf-support {
      min-elements 3;
      max-elements "3";
      description
        "Fallback VRF support";
      leaf entry {
        type boolean;
        description
          "Array entry.";
      }
    }
  }

  grouping FIB-AIB-EOD-RECVD-TS {
    description
      "FIB AIB EOD received timestamp";
    leaf aib-type {
      type Fib-aib-adjacency;
      description
        "AIB requested type";
    }
    leaf aib-adjacency-flags {
      type uint32;
      description
        "AIB adjacency request flags";
    }
    leaf aibeod-timestamp {
      type string;
      description
        "AIB EOD Timestamp";
    }
    leaf aib-register-timestamp {
      type string;
      description
        "AIB Register Timestamp";
    }
  }

  grouping FIB-AIB-EOD-RECVD-TS-AFI {
    description
      "FIB AIB EOD timestamp per AFI";
    leaf aib-eod-address-family {
      type Fib-bag-protocol;
      description
        "FIB AIB EOD Address Family";
    }
    list aib-eod-tx-timestamp {
      description
        "FIB AIB Tx EODs";
      uses FIB-AIB-EOD-RECVD-TS;
    }
    list aib-eod-rx-timestamp {
      description
        "FIB AIB Rx EODs";
      uses FIB-AIB-EOD-RECVD-TS;
    }
  }

  grouping FIB-ISSU-PROTO-STATE {
    description
      "FIB ISSU protocol state";
    leaf protocol-name {
      type string {
        length "0..6";
      }
      description
        "FIB ISSU Protocol name";
    }
    leaf rsi-eod-valid {
      type boolean;
      description
        "RSI EOD expected/valid";
    }
    leaf rsi-eod-timestamp {
      type string {
        length "0..33";
      }
      description
        "RSI EOD received timestamp";
    }
    leaf lsd-eod-valid {
      type boolean;
      description
        "LSD EOD expected/valid";
    }
    leaf lsd-eod-timestamp {
      type string {
        length "0..33";
      }
      description
        "LSD EOD received timestamp";
    }
    leaf lmrib-eod-valid {
      type boolean;
      description
        "LMRIB EOD expected/valid";
    }
    leaf lmrib-eod-timestamp {
      type string {
        length "0..33";
      }
      description
        "LMRIB EOD received timestamp";
    }
    leaf rib-info-valid {
      type boolean;
      description
        "RIB table info valid";
    }
    leaf bcdl-tables {
      type uint32;
      description
        "Number of BCDL tables";
    }
    leaf converged-tables {
      type uint32;
      description
        "Number of tables converged";
    }
    leaf rib-tables-converged-timestamp {
      type string {
        length "0..33";
      }
      description
        "The converged timestamp for all rib tables";
    }
    leaf protocol-eod-valid {
      type boolean;
      description
        "Protocol EOD expected/valid";
    }
    leaf protocol-eod-timestamp {
      type string {
        length "0..33";
      }
      description
        "Protocol EOD sent timestamp";
    }
    list aib-eod-afi-timestamp {
      description
        "FIB AIB EODs";
      uses FIB-AIB-EOD-RECVD-TS-AFI;
    }
  }

  grouping FIB-ISSU-STATE {
    description
      "FIB ISSU state";
    leaf imdr-support {
      type boolean;
      description
        "IMDR supported";
    }
    leaf slc-support {
      type boolean;
      description
        "SLC supported";
    }
    leaf issu-restart {
      type boolean;
      description
        "ISSU restart";
    }
    leaf imdr-eoc-implicit {
      type boolean;
      description
        "IMDR End-of-config implicit";
    }
    leaf slc-eoc-implicit {
      type boolean;
      description
        "SLC End-of-config implicit";
    }
    leaf eoc-received-imdr-timestamp {
      type string {
        length "0..33";
      }
      description
        "End-of-config received from IMDR timestamp";
    }
    leaf eoc-received-slc-timestamp {
      type string {
        length "0..33";
      }
      description
        "End-of-config received from SLC timestamp";
    }
    leaf eod-received-im-timestamp {
      type string {
        length "0..33";
      }
      description
        "End-of-download received from IM timestamp";
    }
    leaf eod-sent-imdr-timestamp {
      type string {
        length "0..33";
      }
      description
        "End-of-download send to IMDR timestamp";
    }
    leaf eod-sent-slc-timestamp {
      type string {
        length "0..33";
      }
      description
        "End-of-download send to SLC timestamp";
    }
    leaf issu-error-sent-to-issumgr-timestamp {
      type uint64;
      description
        "ISSU error sent to ISSUMGR timetstamp";
    }
    list protocol-state {
      max-elements "3";
      description
        "IMDR state for the protocols";
      uses FIB-ISSU-PROTO-STATE;
    }
  }

  grouping ADDR-TYPE {
    description
      "Union for IPv4/Ipv6 addr";
    leaf afi {
      type int32;
      description
        "AFI";
    }
    leaf ipv4-address {
      when "../afi = '2'" {
        description
          "../AFI = '2'";
      }
      type inet:ipv4-address;
      description
        "IPV4 Address";
    }
    leaf ipv6-address {
      when "../afi = '10'" {
        description
          "../AFI = '10'";
      }
      type Ipv6-address;
      description
        "IPV6 Address";
    }
  }

  grouping FIB-SH-ROUTE-DEL-TS {
    description
      "FIB SH ROUTE DEL TS";
    container prefix {
      description
        "prefix";
      uses ADDR-TYPE;
    }
    leaf table-id {
      type uint32;
      description
        "TableID";
    }
    leaf prefix-length {
      type uint16;
      description
        "PrefixLength";
    }
    leaf prefix-protocol {
      type uint16;
      description
        "PrefixProtocol";
    }
    leaf time-in-milliseconds {
      type uint64;
      description
        "TimeInMilliseconds";
    }
  }

  grouping FIB-SH-PROTO-FRR-STATS {
    description
      "FIB per protocol frr counters";
    leaf number-of-frr-events-sent-on-nh-interface-down {
      type uint32;
      description
        "number of FRR events sent on nh interface down";
    }
    leaf number-of-frr-events-sent-on-nh-parent-interface-down {
      type uint32;
      description
        "number of FRR events sent on nh parent interface
         down";
    }
    leaf number-of-interface-down-frr-events-from-pfi {
      type uint32;
      description
        "number of interface down FRR events from PFI";
    }
    leaf nnumber-of-nh-down-frr-events-from-bfd {
      type uint32;
      description
        "number of NH down FRR events frm BFD";
    }
    leaf total-number-of-prot-frr-objects {
      type uint32;
      description
        "total number of prot FRR objects";
    }
    leaf total-number-of-backup-frr-objects {
      type uint32;
      description
        "total number of backup FRR objects";
    }
    leaf total-number-of-successful-frr-tunnel-id-allocations {
      type uint32;
      description
        "total number of successful FRR tunnel ID
         allocations";
    }
    leaf total-number-of-frr-tunnel-id-allocation-failures {
      type uint32;
      description
        "total number of FRR tunnel ID allocation
         failures";
    }
    leaf total-number-of-successful-frr-tunnel-id-frees {
      type uint32;
      description
        "total number of successful FRR tunnel ID frees";
    }
    leaf total-number-of-frr-tunnel-id-free-failures {
      type uint32;
      description
        "total number of FRR tunnel ID free failures";
    }
    leaf number-of-frr-reset-queue-adds {
      type uint32;
      description
        "number of FRR reset queue adds";
    }
    leaf number-of-frr-reset-queue-deletes {
      type uint32;
      description
        "number of FRR reset queue deletes";
    }
    leaf number-of-frr-resets {
      type uint32;
      description
        "number of FRR resets";
    }
    leaf number-of-frr-events-received-in-proto-thread {
      type uint32;
      description
        "number of frr events received in proto thread";
    }
    leaf frr-log-size {
      type uint32;
      description
        "frr log size";
    }
    leaf number-of-session-down-frr-events-from-pm {
      type uint32;
      description
        "number of session down FRR events from PM";
    }
    leaf number-of-frr-ignore {
      type uint32;
      description
        "number of FRR ignore";
    }
  }

  grouping FIB-SH-PROTO-PURGE-STATS {
    description
      "FIB per protocol purge counters";
    list number-of-free {
      max-elements "3";
      description
        "the number of frees for this proto";
      leaf entry {
        type uint32;
        description
          "the number of frees for this proto";
      }
    }
  }

  grouping FIB-SH-GTRIE-FN-TIMING {
    description
      "FIB timing statistics for individual gtrie
       functions";
    leaf gtrie-operation {
      type string {
        length "0..64";
      }
      description
        "Gtrie operation";
    }
    leaf total-updates-number {
      type uint64;
      description
        "Total number of updates";
    }
    leaf total-zero-time-updates-number {
      type uint64;
      description
        "Total number of updates with zero timing (due to
         timestamp granularity)";
    }
    leaf total-updates-time {
      type uint64;
      description
        "Total time for updates";
    }
    leaf max-update-time {
      type uint64;
      description
        "Time for the update";
    }
    leaf max-update-timestamp {
      type uint64;
      description
        "Time stamp of max update";
    }
  }

  grouping FIB-SH-GTRIE-TIMING {
    description
      "FIB platform update statistics";
    leaf successful-update-number {
      type uint64;
      description
        "Number of successful updates";
    }
    leaf failed-update-number {
      type uint64;
      description
        "Number of unsuccessful updates";
    }
    leaf total-update-time {
      type uint64;
      description
        "Total time for all pd updates";
    }
    list gtrie-function-timing-array {
      description
        "Array of max time info indexed by gtrie function";
      uses FIB-SH-GTRIE-FN-TIMING;
    }
  }

  grouping FIB-SH-OBJ-ACTION-STATS {
    description
      "FIB Max time statistics for each action types of
       an object";
    leaf total-updates-number {
      type uint64;
      description
        "Total number of updates";
    }
    leaf total-updates-time {
      type uint64;
      description
        "Total time for updates";
    }
    leaf total-zero-time-updates-number {
      type uint64;
      description
        "Total number of updates that took zero time";
    }
    leaf total-successful-update-number {
      type uint64;
      description
        "Total number of successful updates";
    }
    leaf total-failed-updates-number {
      type uint64;
      description
        "Total number of failed updates";
    }
    leaf object-per-action-oor {
      type uint64;
      description
        "Total number of out of resource updates";
    }
    leaf max-update-time {
      type uint64;
      description
        "Time for the update";
    }
    leaf max-update-timestamp {
      type uint64;
      description
        "Time stamp of max update";
    }
  }

  grouping FIB-SH-OBJ-STATS {
    description
      "FIB Max time statistics for each FIB object";
    leaf total-updates-number {
      type uint64;
      description
        "Total number of updates";
    }
    leaf total-updates-time {
      type uint64;
      description
        "Total time for updates";
    }
    leaf number-async-update-oor {
      type uint64;
      description
        "Number of asynchronous platform update out of
         resource";
    }
    leaf number-async-update-error {
      type uint64;
      description
        "Number of asynchronous platform update errors";
    }
    leaf number-async-oor-notify {
      type uint64;
      description
        "Number of asynchronous out of resource notify";
    }
    list max-time-info-array {
      description
        "Array of max time info indexed by action type";
      uses FIB-SH-OBJ-ACTION-STATS;
    }
  }

  grouping FIB-SH-PLATF-UPD-STATS {
    description
      "FIB platform update statistics";
    leaf number-of-successful-updates {
      type uint64;
      description
        "Number of successful updates";
    }
    leaf numer-of-failed-updates {
      type uint64;
      description
        "Number of unsuccessful updates";
    }
    leaf number-sync-update-oor {
      type uint64;
      description
        "Number of synchronous out of resources updates";
    }
    leaf number-async-update-oor {
      type uint64;
      description
        "Number of asynchronous out of resources updates";
    }
    leaf number-async-update-error {
      type uint64;
      description
        "Number of asynchronous update errors";
    }
    leaf number-async-oor-notify {
      type uint64;
      description
        "Number of asynchronous out of resources notify";
    }
    leaf total-update-time {
      type uint64;
      description
        "Total time for all pd updates";
    }
    leaf number-async-eod-done {
      type uint64;
      description
        "Number of asynchronous end of download done";
    }
    leaf number-async-eod-done-forwarded {
      type uint64;
      description
        "Number of asynchronous end of download done
         forwarded";
    }
    leaf number-async-rsrc-notify {
      type uint64;
      description
        "Number of asynchronous resources notify";
    }
    list object-status-array {
      description
        "Array of max time info indexed by object type";
      uses FIB-SH-OBJ-STATS;
    }
  }

  grouping FIB-SH-PROTO-BCDL2-IO-DEBUG-STATS {
    description
      "FIB BCDLv2 updates statistics";
    leaf buffer-count {
      type uint64;
      description
        "the number of bcdlv2 buffers";
    }
    leaf route-only-buffer-count {
      type uint64;
      description
        "the number of bcdlv2 buffers with routes only";
    }
    leaf non-route-only-buffer-count {
      type uint64;
      description
        "the number of bcdlv2 buffers with non-routes
         only";
    }
    leaf route-and-non-route-buffer-count {
      type uint64;
      description
        "the number of bcdlv2 buffers with both routes
         and non-routes";
    }
    leaf non-route-buffer-count {
      type uint64;
      description
        "the number of bcdlv2 buffers with non-routes";
    }
    leaf bcdl-handler-self-pulse-count {
      type uint64;
      description
        "the number of bcdlv2 self-pulses";
    }
    leaf bcdl-handler-afi-yield-self-pulse-count {
      type uint64;
      description
        "the number of times bcdlv2 handler self-pulsed
         to pause current AFI for yielding the other AFI
         thread";
    }
    leaf bcdl-handler-no-data-pulse-count {
      type uint64;
      description
        "the number of bcdlv2 pulses rcvd with no data
         found";
    }
  }

  grouping FIB-SH-PROTO-DEBUG-STATS {
    description
      "FIB per protocol debug information";
    container bcdlv2-stats {
      description
        "the stats related to BCDLv2 events";
      uses FIB-SH-PROTO-BCDL2-IO-DEBUG-STATS;
    }
    container platform-update-statistics {
      description
        "platform update statistics";
      uses FIB-SH-PLATF-UPD-STATS;
    }
    container gtrie-timing-statistics {
      description
        "Gtrie timing statistics";
      uses FIB-SH-GTRIE-TIMING;
    }
    leaf fib-entry-count-in-global-table {
      type uint64;
      description
        "the number of fib entries in global tbl";
    }
    leaf fib-entry-count-in-global-retry-table {
      type uint64;
      description
        "the number of fib entries in global retry tbl";
    }
    leaf fib-entry-count-invrf-table {
      type uint64;
      description
        "the number of fib entries in vrf tbls";
    }
    leaf fib-entry-count-invrf-retry-table {
      type uint64;
      description
        "the number of fib entries in vrf retry tbls";
    }
    leaf table-count {
      type uint32;
      description
        "the number of tables in table set";
    }
    leaf bcdl-message-count {
      type uint64;
      description
        "the number of bcdl msgs";
    }
    leaf route-update-count {
      type uint64;
      description
        "the number of route updates";
    }
    leaf route-deletes-count {
      type uint64;
      description
        "the number of route deletes";
    }
    leaf route-received-count {
      type uint64;
      description
        "the number of routes received";
    }
    leaf route-dropped-count {
      type uint64;
      description
        "the number of routes dropped";
    }
    leaf route-with-recycled-label-count {
      type uint64;
      description
        "the number of routes handled with recycled label";
    }
    leaf number-of-route-dropped-by-version-mismatch {
      type uint64;
      description
        "the number of routes dropped because of version
         mismatch";
    }
    leaf adjacency-update-count {
      type uint64;
      description
        "the number of adjacency updates";
    }
    leaf adjacency-deletes-count {
      type uint64;
      description
        "the number of adjacency deletes";
    }
    leaf tx-adjacency-update-count-from-aib {
      type uint64;
      description
        "number of TX adjacency updates from AIB";
    }
    leaf tx-adjacency-updates-found-or-created-nh-count {
      type uint64;
      description
        "number of TX adjacency updates that found or
         created NH";
    }
    leaf number-of-tx-adjacency-updates-that-retried {
      type uint64;
      description
        "number of TX adjacency updates that went to
         retry";
    }
    leaf tx-adjacency-retries-found-or-created-nh-count {
      type uint64;
      description
        "number of TX adj retries that found or created
         NH";
    }
    leaf tx-nh-retry-objects-updated-count {
      type uint64;
      description
        "number of times TX NH retry objects updated";
    }
    leaf adjacency-updates-dropped-count {
      type uint64;
      description
        "number of adj updates dropped because of OOR";
    }
    leaf aib-message-count {
      type uint64;
      description
        "number of AIB messages";
    }
    leaf received-te-updates-count {
      type uint64;
      description
        "the number of TE upds received";
    }
    leaf number-of-te-updates-dropped-by-version-mismatch {
      type uint64;
      description
        "the number of TE upds dropped because of version
         mismatch";
    }
    leaf retry-timeout-count {
      type uint64;
      description
        "the number of retry timeouts";
    }
    leaf fixup-loadinfo-count {
      type uint64;
      description
        "the number of fixup LDIs";
    }
    leaf corrected-fixup-loadinfo-count {
      type uint64;
      description
        "the number of corrected fixup LDIs";
    }
    leaf number-of-pl-queued-for-fixup {
      type uint64;
      description
        "the number of PL queued for fixup";
    }
    leaf corrected-fixup-pl-count {
      type uint64;
      description
        "the number of corrected fixup PLs";
    }
    leaf number-of-pl-added-to-retry-while-already-in-retry {
      type uint64;
      description
        "the number PLs added to retry while already in
         retry";
    }
    leaf number-of-pl-linked-to-resolving-tables-for-inline-res {
      type uint64;
      description
        "the number of PLs linked to resolving tables for
         inline res";
    }
    leaf number-of-pl-create-with-backup-path {
      type uint64;
      description
        "number of pl creates with backup path";
    }
    leaf number-of-pl-delete-with-backup-path {
      type uint64;
      description
        "number of pl deletes with backup path";
    }
    leaf number-of-pl-marked-to-include-backup-path {
      type uint64;
      description
        "number of PLs marked to include backup path";
    }
    leaf number-of-pl-unmarked-to-include-backup-path {
      type uint64;
      description
        " number of PLs unmarked to include backup path";
    }
    leaf number-of-pl-visited-on-fast-notification {
      type uint64;
      description
        "number of PLs visited on fast notification";
    }
    leaf loadinfo-backup-path-activation-count {
      type uint64;
      description
        "number of ldi backup path activations";
    }
    leaf loadinfo-mod-time-for-last-backup-activation {
      type uint64;
      description
        "ldi mod time for last backup activation";
    }
    leaf max-loadinfo-mod-time-for-backup-activation {
      type uint64;
      description
        "max ldi mod time for backup activation";
    }
    leaf min-loadinfo-mod-time-for-backup-activation {
      type uint64;
      description
        "min ldi mod time for backup activation";
    }
    leaf total-loadinfo-mod-time-for-backup-activation {
      type uint64;
      description
        "total ldi mod time for backup activation";
    }
    leaf average-loadinfo-mod-time-for-backup-activation {
      type uint64;
      description
        "avg ldi mod time for backup activation";
    }
    leaf resolution-failures-caused-by-recursion-constraint-count {
      type uint64;
      description
        "number of resolution failures because of
         recursion constraint";
    }
    leaf number-of-delete-with-non-zero-reference-count {
      type uint64;
      description
        "the number of deleted with non-zero refcount";
    }
    leaf retry-queue-size {
      type uint32;
      description
        "the number of elements in retryq";
    }
    leaf number-of-allocs {
      type uint64;
      description
        "the number of allocs for this proto";
    }
    leaf number-of-frees {
      type uint64;
      description
        "the number of frees for this proto";
    }
    leaf number-of-bytes {
      type uint64;
      units "byte";
      description
        "the number of allocated bytes for this proto";
    }
    leaf retry-queue-timeout-value {
      type uint32;
      description
        "timeout value in msec";
    }
    leaf retry-queue-scheduler-time {
      type uint32;
      description
        "Scheduler time period in msec";
    }
    leaf fixup-correct-delays {
      type uint64;
      description
        "the number of PL fixup correction delays";
    }
    list global-route-count {
      max-elements "16";
      description
        "Number of global routes from each route source";
      leaf entry {
        type uint64;
        description
          "Number of global routes from each route source";
      }
    }
    list vrf-route-count {
      max-elements "16";
      description
        "Number of vrf routes from each route source";
      leaf entry {
        type uint64;
        description
          "Number of vrf routes from each route source";
      }
    }
    list number-of-retries-array {
      description
        "the number of retries of each type";
      leaf entry {
        type uint64;
        description
          "the number of retries of each type";
      }
    }
  }

  grouping FIB-SH-MISC-PROTO {
    description
      "FIB misc per proto information";
    container per-protocol-debug-statistics {
      description
        "Per protocol miscellaneous stats";
      uses FIB-SH-PROTO-DEBUG-STATS;
    }
    container number-of-idb-purge-counters {
      description
        "the number of counters used for purge counter
         stats";
      uses FIB-SH-PROTO-PURGE-STATS;
    }
    container frr-statistics {
      description
        "FRR statistics";
      uses FIB-SH-PROTO-FRR-STATS;
    }
    leaf protocol {
      type Fib-misc-protocol;
      description
        "Per protocol stats";
    }
    leaf idb-extension-cleanup-failed-count {
      type uint32;
      description
        "Number of recycled idb extensions that failed
         cleanup";
    }
    leaf per-protocol-number-of-label-rpf {
      type uint32;
      description
        "Per protocol number of label RPFs";
    }
    leaf number-of-interfaces-with-label-security-enabled {
      type uint32;
      description
        "Number of interfaces having label security
         enabled";
    }
    leaf number-of-lisp-eid-prefix {
      type uint32;
      description
        "number of LISP EID prefixes";
    }
    leaf number-of-forwarding-eligible-lisp-eid-prefix {
      type uint32;
      description
        "number of LISP EID prefixes eligible for
         forwarding";
    }
    leaf retry-backoff-timer {
      type uint32;
      description
        "The value of the retry backoff timer";
    }
    leaf retry-syslog-backoff-timer-is-running {
      type boolean;
      description
        "is retry syslog/backoff timer running";
    }
    list per-protocol-failure-stats-label-rpf {
      max-elements "9";
      description
        "Per protocol Failure stats for label RPF";
      leaf entry {
        type uint32;
        description
          "Per protocol Failure stats for label RPF";
      }
    }
    list per-protocol-action-stats-label-rpf {
      max-elements "24";
      description
        "Per protocol actions stats for label RPF";
      leaf entry {
        type uint32;
        description
          "Per protocol actions stats for label RPF";
      }
    }
  }

  grouping FIB-SH-MISC {
    description
      "FIB miscellaneous info";
    container fib-issu-state {
      description
        "FIB ISSU state";
      uses FIB-ISSU-STATE;
    }
    container fib-platform-capabilities {
      description
        "FIB platform capabilities";
      uses FIB-SH-PLAT-CAPABILITIES;
    }
    container fib-plat-res-stats {
      description
        "FIB platform resmon accounting stats";
      uses FIB-SH-PLAT-RES-MON-STATS;
    }
    leaf pfi-interface-handle-create-notification-count {
      type uint64;
      description
        "number of pfi ifh create notif";
    }
    leaf pfi-interface-handle-delete-notification-count {
      type uint64;
      description
        "number of pfi ifh delete notif";
    }
    leaf stale-interface-handle-removed-count {
      type uint64;
      description
        "number of stale ifh removed";
    }
    leaf total-platform-update-time {
      type uint64;
      description
        "total platform update time";
    }
    leaf total-time-in-gtrie-operations {
      type uint64;
      description
        "total time spent in gtrie operations";
    }
    leaf total-download-time {
      type uint64;
      description
        "total download time";
    }
    leaf clock-downlaod-time {
      type uint64;
      description
        "clock download time";
    }
    leaf cpu-download-time {
      type uint64;
      description
        "CPU download time";
    }
    leaf last-fib-shared-memory-reset-timestamp {
      type uint64;
      description
        "Last FIB shared memory reset time stamp";
    }
    leaf number-of-ifh-recycle {
      type uint32;
      description
        "Number of idbs that hit ifh recycle";
    }
    leaf number-of-idb-cleanup-after-ifh-recycle {
      type uint32;
      description
        "Number of idb cleaned up after hitting ifh
         recycle";
    }
    leaf number-of-management-interfaces {
      type uint32;
      description
        "Number of management interfaces";
    }
    leaf number-of-virtual-link-local-address-added {
      type uint32;
      description
        "NumberOfVirtualLinkLocalAddressAdded";
    }
    leaf number-of-virtual-link-local-address-deleted {
      type uint32;
      description
        "NumberOfVirtualLinkLocalAddressDeleted";
    }
    leaf number-of-virtual-link-local-address-dropped {
      type uint32;
      description
        "NumberOfVirtualLinkLocalAddressDropped";
    }
    leaf number-of-virtual-link-local-address-cached {
      type uint32;
      description
        "NumberOfVirtualLinkLocalAddressCached";
    }
    leaf cpuless-node-list-init {
      type boolean;
      description
        "cpuless node list init";
    }
    leaf cpuless-linecard-count {
      type uint32;
      description
        "count of cpuless line cards";
    }
    leaf prefer-aib-routes-over-rib-lsd-operational-state {
      type boolean;
      description
        "Prefer AIB routes over RIB/LSD operational state";
    }
    leaf prefer-aib-routes-over-rib-lsd-configured-state {
      type boolean;
      description
        "Prefer AIB routes over RIB/LSD configured state";
    }
    leaf proactive-arp-nd-feature {
      type boolean;
      description
        "Proactive-ARP-ND feature";
    }
    leaf xpl-loadinfo-is-enabled {
      type boolean;
      description
        "XPL loadinfo is enabled";
    }
    leaf fast-reroute-follow-bgp-pic-configured {
      type boolean;
      description
        "fast-reroute follow BGP-PIC configured";
    }
    leaf mpls-encapsulation-sharing-disabled {
      type boolean;
      description
        "MPLS encapsulation sharing disabled";
    }
    leaf consistent-hashing-auto-recovery {
      type boolean;
      description
        "Consistent-hashing auto-recovery";
    }
    leaf trace-buffer-multiplier {
      type uint32;
      description
        "The value of trace buffer multiplier";
    }
    leaf retry-syslog-timer {
      type uint32;
      description
        "The value of the retry syslog timer";
    }
    leaf bgp-hierarchical-load-balancing-mode {
      type uint32;
      description
        "BGP hierarchical load balancing mode";
    }
    leaf number-of-paths-for-hierarchical-load-balancing {
      type uint32;
      description
        "number of paths for hierarchical load balancing";
    }
    list cpuless-linecards {
      max-elements "20";
      description
        "list of cpuless line cards";
      leaf entry {
        type uint32;
        description
          "list of cpuless line cards";
      }
    }
    list per-protocol-statistic {
      key "protocol";
      description
        "Per protocol stats";
      uses FIB-SH-MISC-PROTO;
    }
    list deleted-route-timestamp {
      description
        "Timestamps of deleted routes";
      uses FIB-SH-ROUTE-DEL-TS;
    }
  }

  grouping FIB-SH-POLICY-RL-ENTRY {
    description
      "FIB Policy VXLAN VRF Rate Limit entry";
    leaf rate {
      type uint64;
      description
        "VVRL Policy Rate";
    }
    leaf table-id {
      type uint32;
      description
        "VVRL Table ID";
    }
    leaf vrf-name {
      type string;
      description
        "VVRL VRF Name";
    }
  }

  grouping FIB-SH-POLICY-SAF-ENTRY {
    description
      "FIB Policy Source-Address-Filtering entry";
    list saf-ip-address {
      description
        "SAF Policy IP address list";
      uses FIB-IP-ADDR-T-UNION;
    }
  }

  grouping FIB-SH-POLICY-TYPE-ENTRY {
    description
      "FIB SH POLICY TYPE ENTRY";
    container saf-policy {
      when "../type = 'saf'" {
        description
          "../type = 'SAF'";
      }
      description
        "SAF Policy";
      uses FIB-SH-POLICY-SAF-ENTRY;
    }
    container vxlan-vrf-rate-limit-policy {
      when "../type = 'vxlan-vrf-rate-limit'" {
        description
          "../type = 'VXLAN_VRF_RateLimit'";
      }
      description
        "VXLAN VRF Rate Limit Policy";
      uses FIB-SH-POLICY-RL-ENTRY;
    }
    leaf type {
      type Fib-sh-policy-bag;
      description
        "type";
    }
  }

  grouping FIB-SH-POLICY-ENTRY {
    description
      "FIB Policy";
    container object-base {
      description
        "Object Base";
      uses FIB-SH-FIB-OBJ-BASE;
    }
    container policy-entry {
      description
        "Policy Entry";
      uses FIB-SH-POLICY-TYPE-ENTRY;
    }
    leaf policy-name {
      type string;
      description
        "Policy Name";
    }
    leaf hardware {
      type yang:hex-string;
      description
        "Policy HW info";
    }
    leaf stat-id {
      type uint64;
      description
        "Stat Id";
    }
  }

  grouping FIB-COMMON-LTEP-NVE-TBL-STATS {
    description
      "FIB LTEP NVE table stats bag";
    container common-table-stats {
      description
        "Common FIB subtype table stats bag";
      uses FIB-COMMON-TBL-STATS-BAG;
    }
  }

  grouping FIB-VNI-INFO-ENTRY {
    description
      "FIB VNI_INFO entry";
    container destination-address {
      description
        "Destination address";
      uses FIB-IP-ADDR-T-UNION;
    }
    leaf vni-info-key-type {
      type Fib-vni-info-key-type-in-bag;
      description
        "VNI_Info Key Type";
    }
    leaf table-id {
      type uint32;
      description
        "EVNI Table Id";
    }
    leaf vni-id {
      type uint32;
      description
        "VNI_Info Id";
    }
    leaf vni-info-type {
      type Fib-vni-info-type-in-bag;
      description
        "VNI_Info Type";
    }
    leaf encap-id {
      type uint64;
      description
        "VNI_Info Encap Id";
    }
    leaf underlay-table-id {
      type uint32;
      description
        "Underlay Table Id";
    }
    leaf tunnel-type {
      type Fib-common-ipvpn-tunnel;
      description
        "Tunnel type";
    }
    leaf rtep-id {
      type uint64;
      description
        "RTEP Id";
    }
    leaf stat-id {
      type uint64;
      description
        "Stat Id";
    }
    leaf vni-interface {
      type xr:Interface-name;
      description
        "VNI Interface";
    }
    leaf src-mac-address {
      type yang:mac-address;
      description
        "Source Mac Address";
    }
    leaf dst-mac-address {
      type yang:mac-address;
      description
        "Destination Mac Address";
    }
    leaf hardware-info {
      type yang:hex-string;
      description
        "Hardware Info";
    }
  }

  grouping FIB-VXLAN-TEP-ENTRY {
    description
      "FIB VXLAN-TEP entry";
    container vni {
      description
        "vni";
      uses FIB-VNI-INFO-ENTRY;
    }
    container rtep {
      description
        "rtep";
      uses FIB-COMMON-RTEP-ENTRY;
    }
    leaf hardware-info {
      type yang:hex-string;
      description
        "Hardware Info";
    }
  }

  grouping FIB-COMMON-NHG-NAMED-TBL-STATS {
    description
      "FIB NHG Named table stats bag";
    container common-table-stats {
      description
        "Common FIB subtype table stats bag";
      uses FIB-COMMON-TBL-STATS-BAG;
    }
  }

  grouping FIB-RIB-NHG-ENTRY-INFO {
    description
      "FIB RIB NHG ENTRY INFO";
    leaf next-hop-group-id {
      type uint32;
      description
        "NextHop Group ID";
    }
    leaf next-hop-group-name {
      type string;
      description
        "NextHop Group Name";
    }
    leaf viability-events {
      type string;
      description
        "RIB Next-Hop-Group viability events string
         representation";
    }
    leaf nhgmbb-events {
      type string;
      description
        "RIB Next-Hop-Group MBB events string
         representation";
    }
  }

  grouping FIB-GRIBI-ENTRY-INFO {
    description
      "FIB GRIBI ENTRY INFO";
    leaf entry-transaction-id {
      type uint64;
      description
        "Next-Hop-Group transaction ID";
    }
    leaf nhg-id {
      type uint64;
      description
        "Next-Hop-Group object ID";
    }
    leaf nhg-vrf-id {
      type uint32;
      description
        "Next-Hop-Group VRF table ID";
    }
    leaf ack-status {
      type Fib-ack-status;
      description
        "Next-Hop-Group hardware acknowledgement status";
    }
    leaf ack-latency {
      type uint32;
      units "millisecond";
      description
        "Next-Hop-Group hardware acknowledgement latency
         in milliseconds";
    }
    leaf ack-events {
      type string;
      description
        "Next-Hop-Group ack events string representation";
    }
  }

  grouping FIB-SH-TBL-FIB-EXT-DET {
    description
      "FIB entry extension list information";
    leaf context-label-flag {
      type boolean;
      description
        "Context Label Exist";
    }
    leaf context-label {
      type uint32;
      description
        "Context Label";
    }
  }

  grouping FIB-SH-TBL-FIB-EXT-CMN-DET {
    description
      "FIB SH TBL FIB EXT CMN DET";
    container sfecd-le {
      when "../type = 'leaf-extension'" {
        description
          "../type = 'LeafExtension'";
      }
      description
        "sfecd le";
      uses FIB-SH-TBL-FIB-EXT-DET;
    }
    leaf type {
      type Fib-sh-tbl-fib-ext-bag;
      description
        "type";
    }
  }

  grouping MGMT-SRV6-ENDPOINT-BEHAVIOR {
    description
      "SRv6 Endpoint Behavior Info";
    leaf type {
      type Mgmt-srv6-endpoint;
      description
        "Behavior type";
    }
    leaf description {
      type string;
      description
        "Behavior description";
    }
  }

  grouping FIB-BAG-COUNTER {
    description
      "Basic fib statistics counter structure";
    leaf packet-count {
      type uint64;
      description
        "Packet count";
    }
    leaf byte-count {
      type uint64;
      description
        "Byte count";
    }
  }

  grouping FIB-SH-TBL-PATH-TEP-ENTRY {
    description
      "path TEP list for FIB table entries";
    container tunnel-destination-address {
      description
        "Tunnel Destination address";
      uses FIB-IP-ADDR-T-UNION;
    }
    container tunnel-source-address {
      description
        "Tunnel Source address";
      uses FIB-IP-ADDR-T-UNION;
    }
    leaf action {
      type uint32;
      description
        "Action";
    }
    leaf nh-table-id {
      type uint32;
      description
        "Next-hop table-id";
    }
    leaf nh-vrf-name {
      type string;
      description
        "Next-hop VRF name";
    }
  }

  grouping FIB-SH-TBL-SRV6-NEXT-LVL {
    description
      "SRv6 information for the next recursion level";
    list fib-sh-tbl-srv6-next-lvl {
      description
        "The SRv6 encapsulation information of the next
         recursion level or path";
      leaf srv6-encapsulation-behavior {
        type string;
        description
          "SRv6 Per-path Encapsulation Behavior";
      }
      leaf srv6-sid-list {
        type string;
        description
          "SRv6 SID list";
      }
      leaf srv6-packet-recycling-requested {
        type boolean;
        description
          "SRv6 Packet recycling is requested";
      }
    }
  }

  grouping FIB-SH-TBL-SRV6-RECYCLE {
    description
      "SRv6 packet recycle information for large SID
       stacks";
    list fib-sh-tbl-srv6-recycle {
      description
        "SRv6 packet recycling information";
      leaf internal-id {
        type string {
          length "0..52";
        }
        description
          "The internal ID containing more SID for packet
           reycling";
      }
      leaf srv6-sid-list-subset {
        type string;
        description
          "The subset of the SRv6 SID list of the current
           prefix";
      }
    }
  }

  grouping FIB-SH-TBL-PATH-SRV6-INFO {
    description
      "SRv6 path information for FIB table entries";
    container srv6-packet-recycling-information {
      description
        "SRv6 Packet recycling information";
      uses FIB-SH-TBL-SRV6-RECYCLE;
    }
    container next-recursion-level-srv6-information {
      description
        "SRv6 information of the next recursion level";
      uses FIB-SH-TBL-SRV6-NEXT-LVL;
    }
    leaf srv6-encapsulation-behavior {
      type string;
      description
        "SRv6 Per-path Encapsulation Behavior";
    }
    leaf srv6-sid-list {
      type string;
      description
        "SRv6 SID list";
    }
    leaf is-exact-route-requested {
      type boolean;
      description
        "Is show cef exact-route used?";
    }
    leaf srv6-evpn-ac-interface {
      type xr:Interface-name;
      description
        "SRv6 EVPN attached circuit interface";
    }
    leaf srv6-evpn-xconnect-id {
      type uint32;
      description
        "SRv6 EVPN xconnect ID";
    }
    leaf srv6-evpn-bridge-id {
      type uint32;
      description
        "SRv6 EVPN bridge ID";
    }
    leaf srv6-evpn-shg-id {
      type uint32;
      description
        "SRv6 EVPN shg ID";
    }
  }

  grouping FIB-SH-TBL-MPLS-LABEL-STACK {
    description
      "mpls label stack information for FIB table
       entries";
    leaf number-of-labels {
      type uint32;
      description
        "Total number of labels";
    }
    leaf out-interface {
      type xr:Interface-name;
      description
        "Outgoing Interface";
    }
    leaf nh-address {
      type string {
        length "0..52";
      }
      description
        "Next Hop address";
    }
    list lstack {
      max-elements "23";
      description
        "Label Stack";
      leaf entry {
        type uint32;
        description
          "Label Stack";
      }
    }
  }

  grouping FIB-SH-TBL-PATH-MPLS-INFO {
    description
      "mpls path information for FIB table entries";
    leaf local-lable {
      type uint32;
      description
        "LocalLable";
    }
    leaf recursive-fwd-chain {
      type boolean;
      description
        "RecursiveFwdChain";
    }
    leaf number-of-igp-paths {
      type uint32;
      description
        "NumberOfIGPPaths";
    }
    leaf remote-backup {
      type boolean;
      description
        "RemoteBackupPath";
    }
    list recursive-lbl-stack {
      description
        "Recursive Label(s)";
      leaf entry {
        type uint32;
        description
          "Recursive Label(s)";
      }
    }
    list igp-label-stack-array {
      description
        "igp label stack array";
      uses FIB-SH-TBL-MPLS-LABEL-STACK;
    }
  }

  grouping FIB-GRIBI-PATH-INFO {
    description
      "FIB GRIBI PATH INFO";
    leaf next-hop-id {
      type uint64;
      description
        "Next Hop Object ID";
    }
    leaf aft-object-type {
      type Fib-common-aft-nh;
      description
        "AFT Object type";
    }
    leaf aft-vrf-id {
      type uint32;
      description
        "AFT VRF table ID";
    }
  }

  grouping FIB-SH-TBL-NNH-PATH {
    description
      "Detailed Next Next Hop Information";
    leaf next-next-hop-index {
      type uint8;
      description
        "Next next hop index";
    }
    leaf next-next-hop-prefix {
      type string {
        length "0..52";
      }
      description
        "Next next hop prefix";
    }
    leaf next-next-hop-interface {
      type uint32;
      description
        "Next next hop interface index";
    }
  }

  grouping FIB-SH-IPENCAP-HDR-DET {
    description
      "Detailed IP Encap Header Description";
    leaf ip-encap-hdr-type {
      type Fib-sh-ipencap-hdr;
      description
        "Header Type";
    }
    leaf ip-encap-hdrp {
      type yang:hex-string;
      description
        "Static Header";
    }
    leaf ip-encap-hdr-dyn {
      type uint32;
      description
        "Dynamic Header Fields";
    }
  }

  grouping FIB-SH-IPENCAP-DET {
    description
      "Detailed IP Encap Description";
    leaf ip-encap-hdr-count {
      type uint8;
      description
        "Header Count";
    }
    leaf ip-encap-locks {
      type uint32;
      description
        "IPEncap Object Locks";
    }
    leaf ip-encap-transport-tbl {
      type uint32;
      description
        "Transport Table";
    }
    leaf ipe-transport-vrf-name {
      type string;
      description
        "Transport VRF name";
    }
    leaf ip-encap-transport-af {
      type uint32;
      description
        "Transport AF";
    }
    leaf ip-encap-payload-af {
      type uint32;
      description
        "Payload AF";
    }
    leaf ip-encap-payload-mtu {
      type uint16;
      description
        "Payload MTU";
    }
    leaf ip-encap-parent {
      type uint32;
      description
        "Pointer to parent";
    }
    leaf ip-encap-parent-type {
      type uint32;
      description
        "Parent type enumeration";
    }
    list ip-encap-hdr {
      description
        "Headers";
      uses FIB-SH-IPENCAP-HDR-DET;
    }
  }

  grouping FIB-SH-TBL-PATH-DET {
    description
      "Detailed path information for FIB table entries";
    container gribi-path-info {
      description
        "GRIBI path info";
      uses FIB-GRIBI-PATH-INFO;
    }
    leaf ip-address-to-recurse {
      type string {
        length "0..52";
      }
      description
        "IP address to recurse to";
    }
    leaf label-to-recurse {
      type uint32;
      description
        "Local label to recurse over";
    }
    leaf srv6-sid-to-recurse {
      type inet:ipv6-address;
      description
        "SRv6 SID to recurse over";
    }
    leaf detail-next-hop-prefix {
      type string {
        length "0..52";
      }
      description
        "Next hop prefix";
    }
    leaf next-hop-mask-length {
      type uint8;
      description
        "Next hop mask length";
    }
    leaf interface-associated-path {
      type xr:Interface-name;
      description
        "Interface associated with this path";
    }
    leaf next-hop-interface {
      type xr:Interface-name;
      description
        "Next hop interface";
    }
    leaf next-hop-vrf {
      type string;
      description
        "Next hop VRF";
    }
    leaf tunnle-endpoint-id {
      type uint32;
      description
        "Tunnel endpoint id";
    }
    leaf lisprlocid {
      type uint32;
      description
        "LISP RLOC ID";
    }
    leaf number-of-dependencies-this-path {
      type uint32;
      description
        "No. of dependents for this path";
    }
    leaf robin-reset-value {
      type uint8;
      description
        "Round robin reset value";
    }
    leaf recurse-prefix-object {
      type boolean;
      description
        "Is recursion object a leaf?";
    }
    leaf next-prefix-recursion {
      type string;
      description
        "Next prefix recursion in the path";
    }
    leaf next-prefix-length {
      type uint8;
      description
        "Next prefix length";
    }
    leaf recurse-prefix-object2 {
      type boolean;
      description
        "Recursion has two leaves (e.g. implicit-null
         path)";
    }
    leaf next-prefix-recursion2 {
      type string;
      description
        "Next prefix2 recursion in the path";
    }
    leaf next-prefix-length2 {
      type uint8;
      description
        "Next prefix2 length";
    }
    leaf detail-fib-adjacency-type {
      type Fib-adjacency-show;
      description
        "FIB entry adjacency type";
    }
    leaf current-path-flag {
      type boolean;
      description
        "Current path flag";
    }
    leaf recursive-path-information {
      type boolean;
      description
        "Recursive path information is available";
    }
    leaf external-adjacency {
      type boolean;
      description
        "Path is an external adjacency";
    }
    leaf fib-path-nh-information-type {
      type Fib-neh;
      description
        "FIB Nhinfo type";
    }
    leaf fib-path-nh-information-type-special {
      type Fib-neh-special;
      description
        "FIB Nhinfo type special";
    }
    leaf weight-of-path {
      type uint32;
      description
        "Path's Weight";
    }
    leaf tunnel-class {
      type uint8;
      description
        "Tunnel class of the path";
    }
    leaf tunnel-is-forward-class {
      type boolean;
      description
        "Flag to indicate if the Tunnel is forward class";
    }
    list spd-ip-encap {
      description
        "IP Encap";
      uses FIB-SH-IPENCAP-DET;
    }
    list next-next-hop {
      description
        "Next Next hop sets";
      uses FIB-SH-TBL-NNH-PATH;
    }
  }

  grouping FIB-SH-TBL-PATH {
    description
      "Brief path information for FIB table entries";
    list fib-sh-tbl-path {
      description
        "Next entry in the path";
      container more-detail-about-path {
        description
          "More detail about this path entry";
        uses FIB-SH-TBL-PATH-DET;
      }
      container mpls-information-for-path {
        description
          "mpls info for this path entry";
        uses FIB-SH-TBL-PATH-MPLS-INFO;
      }
      container srv6-information-for-path {
        description
          "SRv6 info for this path entry";
        uses FIB-SH-TBL-PATH-SRV6-INFO;
      }
      container per-path-counter {
        description
          "Per path counter";
        uses FIB-BAG-COUNTER;
      }
      leaf hardware-information {
        type yang:hex-string;
        description
          "Hardware info";
      }
      leaf brief-interface-handle {
        type xr:Interface-name;
        description
          "Interface handle";
      }
      leaf brief-next-hop-prefix {
        type string {
          length "0..52";
        }
        description
          "Next hop prefix";
      }
      leaf via-label-to-recurse {
        type uint32;
        description
          "Local label to recurse over";
      }
      leaf via-srv6-sid-to-recurse {
        type inet:ipv6-address;
        description
          "SRv6 SID to recurse over";
      }
      leaf via-nexthop-group {
        type inet:ipv6-address;
        description
          "Via NextHop Group - NHG";
      }
      leaf via-next-hop-group-name {
        type string;
        description
          "Via NextHop Group Name";
      }
      leaf brief-pnode-address {
        type string {
          length "0..52";
        }
        description
          "P-node address";
      }
      leaf brief-qnode-address {
        type string {
          length "0..52";
        }
        description
          "Q-node address";
      }
      leaf brief-lfa-protection-type {
        type Fib-update-path-lfa-protection;
        description
          "LFA protection type";
      }
      leaf resolved-path {
        type boolean;
        description
          "Resolved path";
      }
      leaf recursive-path {
        type boolean;
        description
          "Recursive path";
      }
      leaf packets-received-path {
        type boolean;
        description
          "Packets received on this path";
      }
      leaf attached-path {
        type boolean;
        description
          "Attached path";
      }
      leaf backup-path {
        type boolean;
        description
          "Backup path";
      }
      leaf best-external-path {
        type boolean;
        description
          "Best external path";
      }
      leaf protect-ignore {
        type boolean;
        description
          "Is protection ignored";
      }
      leaf path-dlb {
        type boolean;
        description
          "Is this the path used for DLB";
      }
      leaf via-nhg-path {
        type boolean;
        description
          "Path is over a NHG";
      }
      leaf path-flags {
        type uint32;
        description
          "Path flags";
      }
      leaf path-info-flags {
        type uint16;
        description
          "Path Info flags";
      }
      leaf path-index {
        type uint16;
        description
          "Path index";
      }
      leaf backup-index {
        type uint16;
        description
          "Backup path index";
      }
      leaf next-hop-index {
        type uint32;
        description
          "Next Hop Index";
      }
      leaf parent-interface-handle {
        type xr:Interface-name;
        description
          "Parent Interface Handle";
      }
      leaf recursionvia-len {
        type uint8;
        description
          "recursion via /N constraint";
      }
      leaf set-id {
        type uint8;
        description
          "ID of the path set";
      }
      leaf set-priority {
        type uint8;
        description
          "Priority of the path set";
      }
      list tep-entry {
        description
          "TEP encapsulation entries for this path entry";
        uses FIB-SH-TBL-PATH-TEP-ENTRY;
      }
    }
  }

  grouping FIB-ADDR-STR {
    description
      "FIB address";
    leaf address {
      type string {
        length "0..60";
      }
      description
        "address";
    }
  }

  grouping FIB-SH-TBL-LOADINFO-INT {
    description
      "Internal load sharing information arrays for FIB
       table entries";
    leaf level-of-loadinfos {
      type uint8;
      description
        "level of ldis";
    }
    leaf number-of-loadinfos {
      type uint8;
      description
        "no. of ldis";
    }
    leaf maximum-index-arrays {
      type uint32;
      description
        "Maximum index of the load sharing information
         arrays";
    }
    leaf maximum-slots {
      type uint32;
      description
        "Maximum slots";
    }
    leaf is-pbts-info-valid {
      type boolean;
      description
        "PBTS info valid flag";
    }
    leaf round-robin-disable {
      type boolean;
      description
        "Flag to indicate if the Round Robin is Disabled
         or not";
    }
    leaf number-of-loadinfo-next-hop-buckets {
      type uint16;
      description
        "Number of LDI next hop buckets";
    }
    leaf platform-hardware-information {
      type yang:hex-string;
      description
        "Platform Hardware info";
    }
    list path-indice {
      description
        "Path indices";
      leaf entry {
        type uint16;
        description
          "Path indices";
      }
    }
    list path-loadinfo-number {
      description
        "Path indices";
      leaf entry {
        type uint16;
        description
          "Path indices";
      }
    }
    list sanity-flag {
      description
        "Sanity flag";
      leaf entry {
        type boolean;
        description
          "Sanity flag";
      }
    }
    list interface-handle {
      description
        "Interface handle";
      leaf entry {
        type xr:Interface-name;
        description
          "Interface handle";
      }
    }
    list weights-of-path {
      description
        "Paths Weights";
      leaf entry {
        type uint32;
        description
          "Paths Weights";
      }
    }
    list normalized-weight {
      description
        "Normalized weights";
      leaf entry {
        type uint16;
        description
          "Normalized weights";
      }
    }
    list tunnel-class-value {
      description
        "Tunnel class value";
      leaf entry {
        type uint8;
        description
          "Tunnel class value";
      }
    }
    list pbts-class-offset {
      description
        "PBTS class offset";
      leaf entry {
        type uint16;
        description
          "PBTS class offset";
      }
    }
    list pbts-class-num-path {
      description
        "PBTS class num paths";
      leaf entry {
        type uint16;
        description
          "PBTS class num paths";
      }
    }
    list pbts-class-is-fallback-mapped {
      description
        "Does PBTS class fall back to drop or any class";
      leaf entry {
        type boolean;
        description
          "Does PBTS class fall back to drop or any class";
      }
    }
    list pbts-fallback-mapped-class {
      description
        "PBTS class falls back to class";
      leaf entry {
        type uint8;
        description
          "PBTS class falls back to class";
      }
    }
    list pbts-fallback-to-drop {
      description
        "PBTS class falls back to drop";
      leaf entry {
        type boolean;
        description
          "PBTS class falls back to drop";
      }
    }
    list tunnel-is-forward-class {
      description
        "Flag to indicate if the Tunnel is forward class";
      leaf entry {
        type boolean;
        description
          "Flag to indicate if the Tunnel is forward class";
      }
    }
    list adjacency-address {
      description
        "Adjacency address";
      uses FIB-ADDR-STR;
    }
  }

  grouping FIB-SH-TBL-LOADINFO-DET {
    description
      "Detailed load sharing information for FIB table
       entries";
    container loadinfo-internal-data {
      description
        "Loadinfo internal data";
      uses FIB-SH-TBL-LOADINFO-INT;
    }
    leaf packets-through-loadinfo {
      type uint64;
      description
        "Packets through this loadinfo";
    }
    leaf bytes-through-loadinfo {
      type uint64;
      units "byte";
      description
        "Bytes through this loadinfo";
    }
    leaf total-packets-through-loadinfo {
      type uint64;
      description
        "Total packets through this loadinfo";
    }
    leaf total-bytes-through-loadinfo {
      type uint64;
      units "byte";
      description
        "Total bytes through this loadinfo";
    }
    leaf prefix-of-owner {
      type uint32;
      description
        "Owner's Prefix";
    }
    leaf mask-length-of-owner {
      type uint32;
      description
        "Owner Prefix Mask length";
    }
    leaf loadinfo-reference-count {
      type uint16;
      description
        "Loadinfo reference count";
    }
    leaf per-dest-load-sharing-flag {
      type boolean;
      description
        "Flag to indicate if the Per destination load
         sharing flag is enabled";
    }
    leaf loadinfo-owner-deleted-flag {
      type boolean;
      description
        "Flag to indicate if the Loadinfo owner deleted
         flag is enabled";
    }
    leaf loadinfo-sanity-flag {
      type boolean;
      description
        "Flag to indicate if the Loadinfo sanity flag is
         enabled";
    }
    leaf is-owner {
      type boolean;
      description
        "Owner flag";
    }
  }

  grouping FIB-SH-TBL-FIB-DET {
    description
      "Detailed FIB table entry information";
    container loadshare-information {
      description
        "Detailed Loadshare info";
      uses FIB-SH-TBL-LOADINFO-DET;
    }
    leaf fib-entry-version {
      type uint64;
      description
        "FIB entry version number";
    }
    leaf per-prefix-accounting {
      type uint8;
      description
        "Per Prefix Accounting";
    }
    leaf load-sharing-type {
      type Fib-loadshare-show;
      description
        "Load sharing type";
    }
    leaf fib-entry-adjacency-type {
      type Fib-adjacency-show;
      description
        "FIB entry adjacency type";
    }
    leaf protocol-type {
      type uint32;
      description
        "FIB Protocol type";
    }
    leaf afi-fib-protocol-type {
      type uint32;
      description
        "AFI FIB protocol type";
    }
    leaf aib-l3-address {
      type yang:hex-string;
      description
        "AIB L3 Address";
    }
    leaf adjacency-address-length {
      type uint32;
      description
        "ADJ ADDR LEN";
    }
    leaf adjacency-interface-name {
      type xr:Interface-name;
      description
        "ADJ interface";
    }
    leaf fib-special-nh-info-type {
      type uint32;
      description
        "FIB Special NHINFO Type";
    }
    leaf fib-entry-adjacency-address {
      type yang:hex-string;
      description
        "FIB entry adj address";
    }
    leaf fib-entry-adjacency-interface {
      type uint32;
      description
        "FIB entry adjacency interface";
    }
    leaf packets-through-fib-entry {
      type uint64;
      description
        "Packets through this FIB entry";
    }
    leaf bytes-through-fib-entry {
      type uint64;
      units "byte";
      description
        "Bytes through this FIB entry";
    }
    leaf detailed-prefix-length {
      type uint32;
      description
        "Prefix length";
    }
    leaf prefix-protocol {
      type uint32;
      description
        "Prefix protocol";
    }
    leaf precedence-for-packets {
      type uint8;
      description
        "Precedence for packets to this entry";
    }
    leaf traffic-index-for-packets {
      type uint8;
      description
        "Traffic index for packets to this entry";
    }
    leaf switch-compontent-id {
      type uint32;
      description
        "Switch function compontent ID";
    }
    leaf fast-adjacency-flag {
      type boolean;
      description
        "Fast adjacency flag";
    }
    leaf illegal-fast-adjacency-flag {
      type boolean;
      description
        "Illegal fast adjacency flag";
    }
    leaf remote-adjacency-flag {
      type boolean;
      description
        "Remote adjacency flag";
    }
    leaf bgp-attribute-id {
      type uint32;
      description
        "BGP attribute id";
    }
    leaf bgp-local-attribute-id {
      type uint32;
      description
        "BGP local attribute id";
    }
    leaf bgp-attribute-local-preference {
      type uint32;
      description
        "BGP attribute local preference of the path";
    }
    leaf bgp-attribute-origin-as {
      type uint32;
      description
        "BGP attribute origin as";
    }
    leaf bgp-attribute-next-hop-as {
      type uint32;
      description
        "BGP attribute next hop as";
    }
    leaf path-string {
      type string;
      description
        "As path string";
    }
    leaf extcom-string {
      type yang:hex-string;
      description
        "extcom st";
    }
    leaf com-string {
      type yang:hex-string;
      description
        "com st";
    }
    leaf extended-community {
      type uint32;
      description
        "extended community";
    }
    leaf qos-group {
      type uint32;
      description
        "Quality of Service Group";
    }
    leaf mpls-forwarding-equivalence-class {
      type uint32;
      description
        "MPLS forwarding equivalence class";
    }
    leaf qppb-qos-group-and-ip-precedence {
      type uint32;
      description
        "QPPB quality of service group and IP precedence";
    }
    leaf flow-tag {
      type uint8;
      description
        "PBR flow-tag";
    }
    leaf forwarding-class-id {
      type uint8;
      description
        "SPP forwarding class ID";
    }
    leaf pl-time-of-last-update-in-msec {
      type uint64;
      description
        "The time of last update for PL in msec";
    }
    leaf loadinfo-time-of-last-update-in-msec {
      type uint64;
      description
        "The time of last update for LDI in msec";
    }
    leaf lw-loadinfo-time-of-last-update-in-msec {
      type uint64;
      description
        "The time of last update for LW-LDI in msec";
    }
    leaf encap-id {
      type uint64;
      description
        "Prefix EncapID";
    }
    leaf pl-timestamp-type {
      type uint32;
      description
        "The type of time-stamp on PL";
    }
    leaf resolve-over-table {
      type boolean;
      description
        "Resolved over Table";
    }
    leaf nh-table-id {
      type uint32;
      description
        "Next-hop table-id";
    }
    leaf nh-vrf-name {
      type string;
      description
        "Next-hop VRF name";
    }
  }

  grouping FIB-SH-TBL-FIB {
    description
      "Basic FIB table information";
    container detail-fib-entry-information {
      description
        "Detailed FIB entry information";
      uses FIB-SH-TBL-FIB-DET;
    }
    container fib-entry-path {
      description
        "FIB entry path details";
      uses FIB-SH-TBL-PATH;
    }
    container srv6-endpoint {
      description
        "SRv6 Endpoint behavior (if applicable)";
      uses MGMT-SRV6-ENDPOINT-BEHAVIOR;
    }
    container gribi {
      description
        "GRIBI Next-Hop-Group info";
      uses FIB-GRIBI-ENTRY-INFO;
    }
    container rib-nhg {
      description
        "RIB Next-Hop-Group info";
      uses FIB-RIB-NHG-ENTRY-INFO;
    }
    container per-prefix-counter {
      description
        "Per prefix counter";
      uses FIB-BAG-COUNTER;
    }
    leaf is-non-recursive {
      type boolean;
      description
        "IsNonRecursive Flag for the given prefix";
    }
    leaf is-unresolved {
      type boolean;
      description
        "Unresolved Flag for the given prefix";
    }
    leaf is-frr {
      type boolean;
      description
        "FRR Flag for the given prefix";
    }
    leaf protocol-type-fib-entry {
      type uint32;
      description
        "Proto type for this entry";
    }
    leaf label-type {
      type string {
        length "0..16";
      }
      description
        "Local Label type";
    }
    leaf path-count {
      type uint16;
      description
        "FIB Path Count";
    }
    leaf platform-hardware {
      type yang:hex-string;
      description
        "Platform Hardware info";
    }
    leaf number-of-references-to-path-list {
      type uint32;
      description
        "Number of references to the pathlist";
    }
    leaf path-list-flags {
      type uint32;
      description
        "The pathlist flags";
    }
    leaf path-list-source {
      type uint32;
      description
        "The pathlist source";
    }
    leaf number-of-references-to-loadinfo {
      type uint32;
      description
        "Number of references to the LDI";
    }
    leaf loadinfo-flags {
      type uint32;
      description
        "The LDI flags";
    }
    leaf loadinfo-external-flags {
      type uint32;
      description
        "The flags of ext assocaited with LDI ";
    }
    leaf pointer-external-loadinfo {
      type uint32;
      description
        "The pointer to the ext assocaited with LDI";
    }
    leaf exact-path-interface-name {
      type xr:Interface-name;
      description
        "exact-path interface name";
    }
    leaf exact-path-gre-interface-name {
      type xr:Interface-name;
      description
        "exact-path GRE physical interface name";
    }
    leaf exact-route-gre-phys-ifh-avail {
      type boolean;
      description
        "exact-route GRE phy ifh available";
    }
    leaf exact-route-result {
      type boolean;
      description
        "exact-route result";
    }
    leaf prefix-is-static-or-connected {
      type boolean;
      description
        "Prefix is static or connected";
    }
    leaf packet-should-receive {
      type boolean;
      description
        "Packet should always be received";
    }
    leaf prefix-connected {
      type boolean;
      description
        "Prefix is connected";
    }
    leaf prefix-for-adjancency {
      type boolean;
      description
        "Prefix is for an adjacency";
    }
    leaf prefix-for-pic-next-hop {
      type boolean;
      description
        "Prefix is for a PIC nexthop";
    }
    leaf purgable-after-purge-interval {
      type boolean;
      description
        "Purgable after the purge interval";
    }
    leaf broadcast-receive-flag {
      type boolean;
      description
        "Broadcast receive flag";
    }
    leaf broadcast-forward-flag {
      type boolean;
      description
        "Broadcast forward flag";
    }
    leaf zero-by-zero-route-as-default {
      type boolean;
      description
        "0/0 route added as default route";
    }
    leaf external-switch-triggered {
      type boolean;
      description
        "External switch function triggered";
    }
    leaf route-attribute-flag {
      type boolean;
      description
        "Route attributes summary flag";
    }
    leaf dummy-real-zero-route {
      type boolean;
      description
        "Dummy real zero route";
    }
    leaf lw-loadinfo-flag {
      type uint32;
      description
        "The LDI LW flags";
    }
    leaf lw-loadinfo-reference-counter {
      type uint32;
      description
        "The refcounter of LDI LW LDI";
    }
    leaf type-of-lw-loadinfo {
      type uint32;
      description
        "The type of LDI LW LDI";
    }
    leaf lspa-flags {
      type uint32;
      description
        "The LSPA flags";
    }
    leaf version-of-route {
      type uint64;
      description
        "The version of the route";
    }
    leaf fib-route-download-priority {
      type uint32;
      description
        "Priority at which the route was downloaded";
    }
    leaf time-of-last-update-in-msec {
      type uint64;
      description
        "The time of last update in msec";
    }
    leaf l2-subscriber-route {
      type boolean;
      description
        "Is L2 Subscriber route";
    }
    leaf l2-subscriber-xconnect-id {
      type uint32;
      description
        "XConnect-id associated with L2 subscriber";
    }
    leaf l2-subscriber-flags {
      type uint32;
      description
        "Flags associated with L2 subscriber";
    }
    leaf l2-subscriber-ip-protocol {
      type uint32;
      description
        "IP protocol associated with L2 subscriber";
    }
    leaf l2tpv3-cookie-length-bits {
      type uint32;
      description
        "L2TPv3 cookie length for L2 subscriber";
    }
    leaf route-for-external-reach-linecard-flag {
      type boolean;
      description
        "Route destined for Line Card that support
         External Reach only";
    }
    leaf route-source-not-preferred {
      type boolean;
      description
        "The source of this route is not preferred over
         other sources with the same prefix";
    }
    leaf route-is-sr-flag {
      type boolean;
      description
        "Route is a MPLS Segment-Routing prefix";
    }
    leaf route-is-srv6-headend {
      type boolean;
      description
        "This route is an SRv6 Head-end";
    }
    leaf route-is-srv6-endpoint {
      type boolean;
      description
        "This route is an SRv6 Endpoint";
    }
    leaf internal-i-droute {
      type boolean;
      description
        "Internal ID route";
    }
    leaf internal-id-route-type {
      type string;
      description
        "Internal ID route type";
    }
    leaf prefix-is-in-oor-state {
      type boolean;
      description
        "prefix is not installed in HW as platform
         out-of-resource";
    }
    leaf route-is-ribnhg {
      type boolean;
      description
        "Prefix is for RIB NextHop-Group";
    }
    leaf loadinfo-base-extended-flags {
      type uint16;
      description
        "LDI Base Extended Flags";
    }
    leaf lw-loadinfo-base-extended-flags {
      type uint16;
      description
        "LWLDI Base Extended Flags";
    }
    leaf transaction-id {
      type uint64;
      description
        "Route transaction ID";
    }
    leaf ack-status {
      type Fib-ack-status;
      description
        "Route hardware acknowledgement status";
    }
    leaf ack-latency {
      type uint32;
      units "millisecond";
      description
        "Route hardware acknowledgement latency in
         milliseconds";
    }
    leaf prefix-accounting-mode {
      type string {
        length "0..40";
      }
      description
        "Prefix accounting mode";
    }
    leaf ack-events {
      type string;
      description
        "Ack events string representation";
    }
    leaf is-loadinfo-collapsed {
      type boolean;
      description
        "LDI collapsed flag";
    }
    list extension-object {
      description
        "Leaf Extension Object List";
      uses FIB-SH-TBL-FIB-EXT-CMN-DET;
    }
  }

  grouping FIB-SH-TBL-FIB-INTERNAL {
    description
      "Internal FIB leaf information";
    leaf string-representation {
      type string;
      description
        "String Representation of a leaf";
    }
  }

  grouping FIB-COMMON-RTEP-ENTRY {
    description
      "FIB rtep entry";
    container destination-address {
      description
        "Destination address to forward the packet";
      uses FIB-IP-ADDR-T-UNION;
    }
    container tunnel-destination-address {
      description
        "Destination address of IP tunnel header";
      uses FIB-IP-ADDR-T-UNION;
    }
    container ltep {
      description
        "LTEP";
      uses FIB-COMMON-LTEP-ENTRY;
    }
    leaf tunnel-type {
      type Fib-common-ipvpn-tunnel;
      description
        "Tunnel type";
    }
    leaf destination-prefix-length {
      type uint8;
      description
        "Prefix length of Destination address";
    }
    leaf tunnel-destination-prefix-length {
      type uint8;
      description
        "Prefix length of Tunnel Destination";
    }
    leaf underlay-table-id {
      type uint32;
      description
        "Underlay Table Id";
    }
    leaf vxlan-overlay-table-id {
      type uint32;
      description
        "VxLAN Overlay Table Id";
    }
    leaf vxlan-e-vni-id {
      type uint32;
      description
        "VxLAN E-VNI Id";
    }
    leaf hardware-info {
      type yang:hex-string;
      description
        "Hardware Info";
    }
    leaf rtep-internal {
      type string;
      description
        "Internal representation of an RTEP Object";
    }
    leaf stat-id {
      type uint64;
      description
        "Stats ID";
    }
  }

  grouping FIB-IP-ADDR-T-UNION {
    description
      "FIB IP ADDR T UNION";
    leaf afi {
      type Fib-common-af-id;
      description
        "AFI";
    }
    leaf none {
      when "../afi = 'none'" {
        description
          "../AFI = 'None'";
      }
      type uint8;
      description
        "No address family";
    }
    leaf ipv4 {
      when "../afi = 'ipv4'" {
        description
          "../AFI = 'IPv4'";
      }
      type Fib-common-in-addr;
      description
        "IPv4 address type";
    }
    leaf ipv6 {
      when "../afi = 'ipv6'" {
        description
          "../AFI = 'IPv6'";
      }
      type Fib-common-in6-addr;
      description
        "IPv6 address type";
    }
  }

  grouping FIB-COMMON-LTEP-ENTRY {
    description
      "FIB LTEP Entry Info";
    container source-address {
      description
        "Source address";
      uses FIB-IP-ADDR-T-UNION;
    }
    container destination-address {
      description
        "Destination address";
      uses FIB-IP-ADDR-T-UNION;
    }
    leaf tunnel-type {
      type Fib-common-ipvpn-tunnel;
      description
        "Tunnel type";
    }
    leaf source-prefix-length {
      type uint8;
      description
        "Prefix length of Sounce address";
    }
    leaf destination-prefix-length {
      type uint8;
      description
        "Prefix length of Destination address";
    }
    leaf underlay-table-id {
      type uint32;
      description
        "Underlay table Id";
    }
    leaf hardware-info {
      type yang:hex-string;
      description
        "Hardware Info";
    }
    leaf ltep-internal {
      type string;
      description
        "Internal representation of an LTEP Object";
    }
    leaf stat-id {
      type uint64;
      description
        "Stats ID";
    }
    leaf vxlan-vni-id {
      type uint32;
      description
        "VXLAN VNI Id";
    }
  }

  grouping FIB-COMMON-TBL-SUBTYPE-STATS-BAG {
    description
      "FIB subtype table stats bag";
    leaf alloc-objects {
      type uint64;
      description
        "Number of allocated objects";
    }
    leaf freed-objects {
      type uint64;
      description
        "Number of freed objects";
    }
    leaf alloc-size {
      type uint64;
      description
        "Size of allocated objects";
    }
    leaf freed-size {
      type uint64;
      description
        "Size of freed objects";
    }
    leaf table-counters-flag {
      type uint32;
      description
        "Mask for counters array";
    }
    list table-counter {
      description
        "Array of table counters";
      leaf entry {
        type uint64;
        description
          "Array of table counters";
      }
    }
  }

  grouping FIB-COMMON-TBL-STATS-BAG {
    description
      "FIB table stats bag";
    list table-subtype-stat {
      description
        "Array to hold different subtype table stats";
      uses FIB-COMMON-TBL-SUBTYPE-STATS-BAG;
    }
  }

  grouping FIB-COMMON-GRIBI-TBL-STATS {
    description
      "FIB GRIBI table stats bag";
    container common-table-stats {
      description
        "Common FIB subtype table stats bag";
      uses FIB-COMMON-TBL-STATS-BAG;
    }
  }

  grouping EVT-HIST-ENTRY {
    description
      "Event history Entry";
    leaf evt-timestamp {
      type string;
      description
        "The timestamp of the event";
    }
    leaf evt-name {
      type string;
      description
        "Event name";
    }
    leaf evt-type {
      type uint8;
      description
        "Event type";
    }
    leaf evt-many {
      type boolean;
      description
        "Multiple instance flag";
    }
    leaf evt-sticky {
      type boolean;
      description
        "Sticky flag";
    }
    list evt-data {
      description
        "Optional data";
      leaf entry {
        type uint32;
        description
          "Optional data";
      }
    }
  }

  grouping EVT-HIST-INFO {
    description
      "Per object event history";
    leaf evt-class-name {
      type string;
      description
        "Class name string";
    }
    leaf evt-granularity-ms {
      type uint32;
      units "millisecond";
      description
        "Granularity of timestamps, in milliseconds";
    }
    list evt-entry {
      description
        "Array of event entries";
      uses EVT-HIST-ENTRY;
    }
  }

  grouping FIB-OBJECT-ENCAP-ID-CHILD {
    description
      "FIB Encap ID Object Child Information";
    container object-base {
      description
        "Object Base";
      uses FIB-SH-FIB-OBJ-BASE;
    }
    leaf key-string {
      type string;
      description
        "Object String Key";
    }
  }

  grouping FIB-OBJECT-ENCAP-ID-INFO {
    description
      "FIB Encap ID Object Information";
    container object-base {
      description
        "Object Base";
      uses FIB-SH-FIB-OBJ-BASE;
    }
    container encap-id-event-history {
      description
        "Encap ID Event History";
      uses EVT-HIST-INFO;
    }
    leaf encap-id {
      type uint64;
      description
        "Encap ID";
    }
    leaf key-string {
      type string;
      description
        "Encap Object Key";
    }
    leaf meta-data {
      type uint64;
      description
        "PD Meta Data";
    }
    list conflict-children {
      description
        "Conflict Children";
      uses FIB-OBJECT-ENCAP-ID-CHILD;
    }
    list non-conflict-children {
      description
        "NonConflict Children";
      uses FIB-OBJECT-ENCAP-ID-CHILD;
    }
  }

  grouping FIB-ENCAP-ID-SUMMARY {
    description
      "FIB Encap ID Summary";
    leaf number-of-encap-id {
      type uint32;
      description
        "Number of Encap ID";
    }
    leaf number-of-encap-id-conflict {
      type uint32;
      description
        "Number of Encap IDs have conflicts";
    }
    leaf number-of-conflict-child {
      type uint32;
      description
        "Number of Conflict Children";
    }
    leaf number-of-non-conflict-child {
      type uint32;
      description
        "Number of NonConflict Children";
    }
    leaf number-of-incomplete {
      type uint32;
      description
        "Number of incomplete Encap ID objects";
    }
    leaf number-of-pd-create {
      type uint32;
      description
        "Number of Encap ID objects have PD create";
    }
    leaf number-of-pd-modify {
      type uint32;
      description
        "Number of Encap ID objects have PD modify";
    }
    leaf number-of-pd-delete {
      type uint32;
      description
        "Number of Encap ID objects have PD delete";
    }
    leaf number-of-pd-sync-error {
      type uint32;
      description
        "Number of Encap ID objects have PD sync error";
    }
    leaf number-of-async-error {
      type uint32;
      description
        "Number of Encap ID objects have async error";
    }
    leaf number-of-oor-error {
      type uint32;
      description
        "Number of Encap ID objects have oor error";
    }
  }

  grouping FIB-UDP-PORT-GLBL-ENTRY {
    description
      "FIB UDP port global entry";
    leaf udp-port-global-flags {
      type uint32;
      description
        "UDP port global flags";
    }
    leaf tunnel-type-xr {
      type Fib-common-ipvpn-tunnel;
      description
        "Tunnel type";
    }
    leaf udp-port-ipv4 {
      type uint16;
      description
        "UDP port IPv4";
    }
    leaf udp-port-ipv6 {
      type uint16;
      description
        "UDP port IPv6";
    }
    leaf udp-port-mpls {
      type uint16;
      description
        "UDP port MPLS";
    }
    leaf policy-update-timestamp {
      type uint64;
      description
        "Policy update timestamp";
    }
    leaf platform-update-timestamp {
      type uint64;
      description
        "Platform update timestamp";
    }
  }

  grouping FIB-SH-FIB-OBJ-BASE {
    description
      "FIB object base information";
    leaf object-reference-count {
      type uint32;
      description
        "FIB Object Reference Count";
    }
    leaf object-flags {
      type uint32;
      description
        "FIB Object flags";
    }
    leaf object-type {
      type uint8;
      description
        "FIB Object type";
    }
    leaf object-timestamp {
      type uint64;
      description
        "FIB Object Timestamp in msec";
    }
    leaf object-pointer {
      type uint64;
      description
        "FIB Object pointer";
    }
    leaf object-id {
      type uint64;
      description
        "FIB Object ID";
    }
  }
}
