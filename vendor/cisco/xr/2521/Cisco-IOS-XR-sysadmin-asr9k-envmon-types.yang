module Cisco-IOS-XR-sysadmin-asr9k-envmon-types {
  namespace "http://www.cisco.com/ns/yang/Cisco-IOS-XR-sysadmin-asr9k-envmon-types";
  prefix envmon-types;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains definitions
     for the Calvados model objects.
     
     Copyright (c) 2012-2020 by Cisco Systems, Inc.
     All rights reserved.";

  revision 2025-03-27 {
    description
      "Enable the support for graceful shutdown disable option.
       2022-08-05
         Add gen2 common low power CLI.";
    semver:module-version "2.0.0";
  }
  revision 2019-04-15 {
    description
      "Establish semantic version baseline.";
    semver:module-version "1.0.0";
  }
  revision 2017-11-27 {
    description
      "Add graceful shutdown disable CLI.";
  }
  revision 2017-05-01 {
    description
      "Namespace change to comply with Cisco guidelines on namespace";
  }

  typedef num_pm {
    type uint32 {
      range "0..12";
    }
  }

  grouping fan-speed-group {
    leaf raise-fan-speed {
      type uint32 {
        range "0..100";
      }
      config false;
    }
  }

  grouping fan-ctrl-optics-group {
    leaf fan-ctrl-optics {
      type uint32 {
        range "0..1";
      }
      config false;
    }
  }

  grouping vin-uv-shut-group {
    container graceful-shutdown {
      leaf disable {
        type empty;
      }
    }
  }

  grouping gen2-common-lowpower-group {
    leaf gen2-common-lowpower {
      type uint32 {
        range "0..1";
      }
      config false;
    }
  }
}
