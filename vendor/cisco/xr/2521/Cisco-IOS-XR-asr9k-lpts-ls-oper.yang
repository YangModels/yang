module Cisco-IOS-XR-asr9k-lpts-ls-oper {
  namespace "http://cisco.com/ns/yang/Cisco-IOS-XR-asr9k-lpts-ls-oper";
  prefix asr9k-lpts-ls-oper;

  import Cisco-IOS-XR-types {
    prefix xr;
  }
  import cisco-semver {
    prefix semver;
  }
  include Cisco-IOS-XR-asr9k-lpts-ls-oper-sub1 {
    revision-date 2019-04-05;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR asr9k-lpts-ls package operational data.
     
     This module contains definitions
     for the following management objects:
       platform-lptsp-ifib-ls: ASR9K platform ifib operational data
       platform-lptsp-ifib-static-ls: ASR9K platform ifib operational
         data
     
     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  container platform-lptsp-ifib-ls {
    config false;
    description
      "ASR9K platform ifib operational data ";
    container nodes {
      description
        "List of nodes with platform specific lpts
         operation data";
      list node {
        key "node-name";
        description
          "Node with platform specific lpts data";
        container stats {
          description
            "pl_pifib stats";
          uses PL-PIFIB-SHOW-STATS;
        }
        container np-polices {
          description
            " Np policer ";
          list np-police {
            key "npu-id";
            description
              "Data for single policer entry";
            leaf npu-id {
              type uint32;
              description
                "NPU Identifier";
            }
            uses PL-PIFIB-SHOW-POLICER;
          }
        }
        container police-info {
          description
            "policer info for LC";
          uses PL-PIFIB-SHOW-POLICER;
        }
        container context-new {
          description
            "pl_pifib police data";
          uses PL-PIFIB-CONTEXT-INFO;
        }
        container context-database {
          description
            "pl_pifib police data";
          uses PL-PIFIB-CONTEXT-STATUS;
        }
        container police {
          description
            "pl_pifib police data";
          uses PL-PIFIB-SHOW-POLICER;
        }
        leaf node-name {
          type xr:Node-id;
          description
            "Node name";
        }
      }
    }
  }
  container platform-lptsp-ifib-static-ls {
    config false;
    description
      "ASR9K platform ifib operational data ";
    container node-statics {
      description
        "List of nodes with platform specific lpts
         operation data";
      list node-static {
        key "node-name";
        description
          "Node with platform specific lpts data";
        container stats {
          description
            "pl_pifib stats";
          uses PL-PIFIB-SHOW-STATS;
        }
        container police {
          description
            "pl_pifib police data";
          uses PL-PIFIB-SHOW-STATIC-POLICE;
        }
        leaf node-name {
          type xr:Node-id;
          description
            "Node name";
        }
      }
    }
  }
}
