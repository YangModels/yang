module Cisco-IOS-XR-appmgr-act {
  namespace "http://cisco.com/ns/yang/Cisco-IOS-XR-appmgr-act";
  prefix appmgr-act;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR action package configuration.
     
     Copyright (c) 2020-2023 by Cisco Systems, Inc.
     All rights reserved.";

  revision 2025-01-20 {
    description
      "Removing anchoring from yang pattern, as all Yang pattern statements are automatically anchored now.
       2022-11-11
         Support for enforcing signature verification before rpm install added
       2021-09-09
         Adding patterns and length for strings";
    semver:module-version "2.0.0";
  }
  revision 2021-08-15 {
    description
      "Support for process script actions added.";
    semver:module-version "1.1.0";
  }
  revision 2021-03-01 {
    description
      "Adding support for uninstall by source.";
    semver:module-version "1.0.0";
  }
  revision 2021-02-15 {
    description
      "Support for process script actions added.";
  }
  revision 2020-07-14 {
    description
      "Establish semantic version baseline.";
  }

  rpc appmgr-app-start {
    description
      "Start an application";
    input {
      leaf name {
        type string {
          length "1..255";
          pattern "[a-zA-Z0-9][a-zA-Z0-9_.-]+";
        }
        mandatory true;
        description
          "App name";
      }
    }
  }
  rpc appmgr-app-stop {
    description
      "Stop an application";
    input {
      leaf name {
        type string {
          length "1..255";
          pattern "[a-zA-Z0-9][a-zA-Z0-9_.-]+";
        }
        mandatory true;
        description
          "App name";
      }
    }
  }
  rpc appmgr-app-kill {
    description
      "Kill an application";
    input {
      leaf name {
        type string {
          length "1..255";
          pattern "[a-zA-Z0-9][a-zA-Z0-9_.-]+";
        }
        mandatory true;
        description
          "App name";
      }
    }
  }
  rpc appmgr-app-copy {
    description
      "Copy files/folders between an application and an XR filesystem";
    input {
      leaf source {
        type string;
        mandatory true;
        description
          "SOURCE-FILESYSTEM:PATH or SOURCE-APPLICATION:PATH (eg. harddisk:foo/bar or myapp:foo/bar)";
      }
      leaf destination {
        type string;
        mandatory true;
        description
          "DESTINATION-FILESYSTEM:PATH or DESTINATION-APPLICATION:PATH (eg. harddisk:foo/bar or myapp:foo/bar)";
      }
    }
  }
  rpc appmgr-package-install {
    description
      "Install an rpm without signature verification.";
    input {
      leaf rpm {
        type string;
        mandatory true;
        description
          "Path to package rpm";
      }
    }
  }
  rpc appmgr-package-install-verify {
    description
      "Install an rpm with signature verification enforced.";
    input {
      leaf rpm {
        type string;
        mandatory true;
        description
          "Path to package rpm";
      }
    }
  }
  rpc appmgr-package-uninstall {
    description
      "Uninstall a package.";
    input {
      leaf package {
        type string;
        mandatory true;
        description
          "Package name";
      }
    }
  }
  rpc appmgr-package-uninstall-source {
    description
      "Uninstall a package by source name.";
    input {
      leaf source {
        type string {
          length "1..255";
          pattern "[a-zA-Z0-9][a-zA-Z0-9_.-]+";
        }
        mandatory true;
        description
          "Source name";
      }
    }
  }
  rpc appmgr-process-script-activate {
    description
      "Activate a process-script";
    input {
      leaf name {
        type string {
          length "1..255";
          pattern "[a-zA-Z0-9][a-zA-Z0-9_.-]+";
        }
        mandatory true;
        description
          "Process script name";
      }
    }
  }
  rpc appmgr-process-script-deactivate {
    description
      "Deactivate a process-script";
    input {
      leaf name {
        type string {
          length "1..255";
          pattern "[a-zA-Z0-9][a-zA-Z0-9_.-]+";
        }
        mandatory true;
        description
          "Process script name";
      }
    }
  }
  rpc appmgr-process-script-start {
    description
      "Start a process-script";
    input {
      leaf name {
        type string {
          length "1..255";
          pattern "[a-zA-Z0-9][a-zA-Z0-9_.-]+";
        }
        mandatory true;
        description
          "Process script name";
      }
    }
  }
  rpc appmgr-process-script-stop {
    description
      "Stop a process-script";
    input {
      leaf name {
        type string {
          length "1..255";
          pattern "[a-zA-Z0-9][a-zA-Z0-9_.-]+";
        }
        mandatory true;
        description
          "Process script name";
      }
    }
  }
  rpc appmgr-process-script-kill {
    description
      "Kill a process-script";
    input {
      leaf name {
        type string {
          length "1..255";
          pattern "[a-zA-Z0-9][a-zA-Z0-9_.-]+";
        }
        mandatory true;
        description
          "Process script name";
      }
    }
  }
  rpc appmgr-process-script-restart {
    description
      "Restart a process-script";
    input {
      leaf name {
        type string {
          length "1..255";
          pattern "[a-zA-Z0-9][a-zA-Z0-9_.-]+";
        }
        mandatory true;
        description
          "Process script name";
      }
    }
  }
}
