module Cisco-IOS-XR-perf-meas-cfg {
  namespace "http://cisco.com/ns/yang/Cisco-IOS-XR-perf-meas-cfg";
  prefix perf-meas-cfg;

  import ietf-inet-types {
    prefix inet;
  }
  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR perf-meas package configuration.
     
     This module contains definitions
     for the following management objects:
       performance-measurement: The root of performance-measurement
         configuration
     
     Copyright (c) 2013-2020 by Cisco Systems, Inc.
     All rights reserved.";

  revision 2020-02-20 {
    description
      "Modifid type of service knobs from array to integer.";
    semver:module-version "3.0.0";
  }
  revision 2019-09-18 {
    description
      "Hid and disabled unsupported features for 7.1.1.";
    semver:module-version "2.0.0";
  }
  revision 2019-04-05 {
    description
      "Establish semantic version baseline.";
    semver:module-version "1.0.0";
  }
  revision 2017-10-17 {
    description
      "Revision Zero.";
  }
  revision 2015-11-09 {
    description
      "IOS XR 6.0 revision.";
  }

  typedef Pm-measurement-mode {
    type enumeration {
      enum "pm-measurement-mode-type-one-way" {
        value 0;
        description
          "One-way measurement collecting only timestamp1
           and 2";
      }
      enum "pm-measurement-mode-type-two-way" {
        value 1;
        description
          "two-way measurement collecting only timestamp1,
           2, 3 and 4";
      }
    }
    description
      "Pm measurement mode";
  }

  typedef Pm-protocol-and-encap {
    type enumeration {
      enum "pm-payload-protocol-type-pm-mpls" {
        value 1;
        description
          "Use RF6374 with MPLS Encapsulation";
      }
      enum "pm-payload-protocol-type-pm-udp" {
        value 2;
        description
          "Use RFC6374 with UDP Encapsulation (Deprecated)";
      }
      enum "pm-payload-protocol-type-twamp-light" {
        value 3;
        description
          "Use RFC5357";
      }
    }
    description
      "Pm protocol and encap";
  }

  typedef Pm-ip-address {
    type enumeration {
      enum "pm-ip-address-type-ipv4" {
        value 0;
        description
          "IPv4 nexthop address";
      }
      enum "pm-ip-address-type-ipv6" {
        value 1;
        description
          "IPv6 nexthop address";
      }
      enum "pm-ip-address-type-unknown" {
        value 2;
        description
          "unknown nexthop addrss type";
      }
    }
    description
      "Pm ip address";
  }

  grouping THRESHOLD-CROSSING-CHECK-MINIMUM-DELAY {
    description
      "Common node of delay-profile-rsvp-te,
       delay-profile-sr-policy";
    leaf threshold-crossing-check-minimum-delay {
      type boolean;
      description
        "Enable Minimum-delay Threshold-check.";
    }
  }

  grouping THRESHOLD-CROSSING-CHECK-AVERAGE-DELAY {
    description
      "Common node of delay-profile-rsvp-te,
       delay-profile-sr-policy";
    leaf threshold-crossing-check-average-delay {
      type boolean;
      description
        "Enable Average-delay Threshold-check.";
    }
  }

  grouping ADVERTISEMENT {
    description
      "Common node of delay-profile-interface,
       delay-profile-sr-policy, delay-profile-rsvp-te";
    container advertisement {
      description
        "Advertisement Profile";
      container accelerated {
        description
          "Accelerated Advertisement Profile";
        leaf threshold {
          type uint32 {
            range "0..100";
          }
          units "percentage";
          default "20";
          description
            "Accelerated advertisement threshold percentage";
        }
        leaf minimum-change {
          type uint32 {
            range "0..100000";
          }
          default "500";
          description
            "Accelerated advertisement minimum value in
             uSec";
        }
        leaf enable {
          type empty;
          description
            "Enable Accelerated Advertisement";
        }
      }
      container periodic {
        description
          "Periodic Advertisement Profile";
        leaf interval {
          type uint32 {
            range "30..3600";
          }
          units "second";
          default "120";
          description
            "Periodic advertisement and metric aggregation
             interval in seconds";
        }
        leaf threshold {
          type uint32 {
            range "0..100";
          }
          units "percentage";
          default "10";
          description
            "Periodic advertisement threshold percentage
             change (compared to last advertisement)";
        }
        leaf minimum-change {
          type uint32 {
            range "0..100000";
          }
          description
            "Periodic advertisement minimum change in uSec
             (compared to last advertisement)";
        }
        leaf disable {
          type empty;
          description
            "Enable Performance Measurement Periodic
             Advertisement";
        }
      }
    }
  }

  grouping THRESHOLD-CROSSING-CHECK-MAXIMUM-DELAY {
    description
      "Common node of delay-profile-rsvp-te,
       delay-profile-sr-policy";
    leaf threshold-crossing-check-maximum-delay {
      type boolean;
      description
        "Enable Maximum-delay Threshold-check.";
    }
  }

  container performance-measurement {
    description
      "The root of performance-measurement configuration";
    container protocol {
      description
        "PM protocols";
      container twamp-light {
        description
          "Twamp-light protocol";
        container delay-measurement {
          description
            "Delay measurement";
          container unauthenticated {
            description
              "Unauthenticated mode";
            leaf querier-destination-port {
              type uint32 {
                range "862..14999";
              }
              description
                "UDP port opened to process queries, support
                 reserved 862 port for TWAMP or 11000 to
                 14999";
            }
          }
        }
      }
      container pm-mpls {
        description
          "PM-MPLS protocol";
        container delay-measurement {
          description
            "Delay measurement";
          container unauthenticated {
            description
              "Unauthenticated mode";
          }
        }
      }
    }
    container delay-profile-rsvp-te {
      description
        "Performance-measurement RSVP-TE delay profile";
      container probe {
        description
          "PM Delay Profile Probe";
        container type-of-service {
          description
            "PM Delay Profile Type Of Service";
          leaf dscp-value {
            type uint32 {
              range "0..63";
            }
            description
              "DSCP value indicating TOS level used by
               protocol twamp-light";
          }
          leaf traffic-class-value {
            type uint32 {
              range "0..7";
            }
            description
              "Traffic Class value indicating TOS level used
               by protocol pm-mpls";
          }
        }
        container protocol {
          description
            "Protocol used for measurement probe messages";
          leaf protocol-type {
            type Pm-protocol-and-encap;
            description
              "Type of protocol";
          }
        }
        leaf burst-interval {
          type uint32 {
            range "30..15000";
          }
          description
            "The value for delay profile probe burst
             interval";
        }
        leaf measurement-mode {
          type Pm-measurement-mode;
          description
            "Configuration for measurement mode";
        }
        leaf computation-interval {
          type uint32 {
            range "1..3600";
          }
          units "second";
          description
            "The value for delay profile probe computation
             interval in seconds";
        }
      }
      uses THRESHOLD-CROSSING-CHECK-AVERAGE-DELAY;
      uses ADVERTISEMENT;
      uses THRESHOLD-CROSSING-CHECK-MAXIMUM-DELAY;
      uses THRESHOLD-CROSSING-CHECK-MINIMUM-DELAY;
    }
    container delay-profile-interface {
      description
        "Performance-measurement interface delay profile";
      container probe {
        description
          "PM Delay Profile Probe";
        container protocol {
          description
            "Protocol used for measurement probe messages";
          leaf protocol-type {
            type Pm-protocol-and-encap;
            description
              "Type of protocol";
          }
        }
        leaf measurement-mode {
          type Pm-measurement-mode;
          description
            "Configuration for measurement mode";
        }
        leaf burst-interval {
          type uint32 {
            range "30..15000";
          }
          default "3000";
          description
            "The value for delay profile burst interval in
             mSec";
        }
        leaf computation-interval {
          type uint32 {
            range "1..3600";
          }
          units "second";
          default "30";
          description
            "The value for delay profile probe computation
             interval in seconds";
        }
      }
      uses ADVERTISEMENT;
    }
    container delay-profile-sr-policy {
      description
        "Performance-measurement SR Policy delay profile";
      container probe {
        description
          "PM Delay Profile Probe";
        container type-of-service {
          description
            "PM Delay Profile Type Of Service";
          leaf dscp-value {
            type uint32 {
              range "0..63";
            }
            description
              "DSCP value indicating TOS level used by
               protocol twamp-light";
          }
          leaf traffic-class-value {
            type uint32 {
              range "0..7";
            }
            description
              "Traffic Class value indicating TOS level used
               by protocol pm-mpls";
          }
        }
        container sweep {
          description
            "Enable ECMP hashing by sweeping a field in the
             probe packet";
          container destination {
            description
              "Configuration for destination address
               sweeping range, only IPv4 address is
               supported. Used by IPv4, IPv6 and NULL
               endpoint SR Policy.";
            leaf address-type {
              type Pm-ip-address;
              description
                "Type of address (Only support
                 PM_IP_ADDRESS_TYPE_IPV4)";
            }
            leaf address {
              type inet:ip-address-no-zone;
              description
                "Starting address for destination sweeping";
            }
            leaf range {
              type uint32 {
                range "0..128";
              }
              description
                "Sweeping range";
            }
          }
        }
        container protocol {
          description
            "Protocol used for measurement probe messages";
          leaf protocol-type {
            type Pm-protocol-and-encap;
            description
              "Type of protocol";
          }
        }
        leaf computation-interval {
          type uint32 {
            range "1..3600";
          }
          units "second";
          description
            "The value for delay profile probe computation
             interval in seconds";
        }
        leaf measurement-mode {
          type Pm-measurement-mode;
          description
            "Configuration for measurement mode";
        }
        leaf burst-interval {
          type uint32 {
            range "30..15000";
          }
          description
            "The value for delay profile probe burst
             interval";
        }
      }
      uses THRESHOLD-CROSSING-CHECK-AVERAGE-DELAY;
      uses ADVERTISEMENT;
      uses THRESHOLD-CROSSING-CHECK-MAXIMUM-DELAY;
      uses THRESHOLD-CROSSING-CHECK-MINIMUM-DELAY;
    }
    container interfaces {
      description
        "Configure performance-measurement interfaces";
      list interface {
        key "interface-name";
        description
          "Configure a performance-measurement interface";
        container delay-measurement {
          description
            "Interface delay measurement";
          leaf enable-delay-measurement {
            type empty;
            description
              "Enable interface delay measurement";
          }
          leaf advertise-delay {
            type uint32 {
              range "1..16777215";
            }
            description
              "The value for interface delay measurement
               advertisement delay in uSec";
          }
        }
        container nexthop-address {
          description
            "PM Delay Profile Nexthop Address";
          leaf nexthop-address-type {
            type Pm-ip-address;
            description
              "Type of IP Address of nexthop";
          }
          leaf nexthop-address {
            type inet:ip-address-no-zone;
            description
              "Address of nexthop";
          }
        }
        leaf enable-interface {
          type empty;
          description
            "Enable interface submode";
        }
        leaf interface-name {
          type xr:Interface-name;
          description
            "Interface name";
        }
      }
    }
    leaf enable-performance-measurement {
      type empty;
      description
        "Enable the performance measurement feature";
    }
    leaf maximum-pps {
      type uint32 {
        range "1..25000";
      }
      units "packet/s";
      description
        "Maximum packets per second allowed";
    }
  }
}
