module Cisco-IOS-XR-ipv4-arp-act {
  namespace "http://cisco.com/ns/yang/Cisco-IOS-XR-ipv4-arp-act";
  prefix arp-act;

  import cisco-semver {
    prefix semver;
  }
  import Cisco-IOS-XR-types {
    prefix csc;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR action package configuration.
     
     Copyright (c) 2018-2019 by Cisco Systems, Inc.
     All rights reserved.";

  revision 2019-10-01 {
    description
      "Made changes to be RFC6087 compliant";
    semver:module-version "1.1.0";
  }
  revision 2019-04-05 {
    description
      "Establish semantic version baseline.";
    semver:module-version "1.0.0";
  }
  revision 2018-10-08 {
    description
      "IOS XR 6.1.1 revision.";
  }

  rpc clear-arp-api-stats-api {
    description
      "Clear ARP API stats API";
    input {
      leaf name {
        type string;
        mandatory true;
        description
          "Name of api";
      }
    }
    csc:xr-task "arp";
    csc:cli-command "clear arp api-stats api <name>";
  }
  rpc clear-arp-api-stats-location {
    description
      "Clear ARP API stats location";
    input {
      leaf node-location {
        type string;
        mandatory true;
        description
          "Node location";
        csc:cli-name "*";
      }
    }
    csc:xr-task "arp";
    csc:cli-command "clear arp api-stats location <node-location>";
  }
}
