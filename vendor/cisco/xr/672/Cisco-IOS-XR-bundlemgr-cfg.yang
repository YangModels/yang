module Cisco-IOS-XR-bundlemgr-cfg {
  namespace "http://cisco.com/ns/yang/Cisco-IOS-XR-bundlemgr-cfg";
  prefix bundlemgr-cfg;

  import ietf-inet-types {
    prefix inet;
  }
  import ietf-yang-types {
    prefix yang;
  }
  import Cisco-IOS-XR-types {
    prefix xr;
  }
  import cisco-semver {
    prefix semver;
  }
  import Cisco-IOS-XR-ifmgr-cfg {
    prefix a1;
  }
  import Cisco-IOS-XR-rgmgr-cfg {
    prefix a2;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR bundlemgr package configuration.
     
     This model is deprecated and is replaced by
     Cisco-IOS-XR-um-if-bundle-cfg.yang which will provide the
     compatible functionalities.
     
     This module contains definitions
     for the following management objects:
       lacp: Link Aggregation Control Protocol commands
     
     This YANG module augments the
       Cisco-IOS-XR-ifmgr-cfg,
       Cisco-IOS-XR-rgmgr-cfg,
     modules with configuration data.
     
     Copyright (c) 2013-2020 by Cisco Systems, Inc.
     All rights reserved.";

  revision 2020-02-05 {
    description
      "Lacp Period cli Long option added.";
    semver:module-version "1.1.0";
  }
  revision 2019-05-30 {
    description
      "64 bit bandwidth changes.";
    semver:module-version "1.0.0";
  }
  revision 2019-05-12 {
    description
      "Deprecated the native model, replaced by UM model.";
    semver:module-version "1.0.0";
  }
  revision 2019-04-05 {
    description
      "Establish semantic version baseline.";
  }
  revision 2017-05-01 {
    description
      "Fixing backward compatibility error in module.";
  }
  revision 2016-12-16 {
    description
      "Description updated.";
  }
  revision 2015-11-09 {
    description
      "IOS XR 6.0 revision.";
  }

  typedef Bfd-mode {
    type enumeration {
      enum "no-cfg" {
        value 0;
        description
          "BFD mode not configured on per-bundle basis";
      }
      enum "cisco" {
        value 1;
        description
          "BFD mode Cisco";
      }
      enum "ietf" {
        value 2;
        description
          "BFD mode IETF";
      }
    }
    description
      "Bfd mode";
  }

  typedef Churn-logging {
    type enumeration {
      enum "actor" {
        value 1;
        description
          "Logging for actor churn only";
      }
      enum "partner" {
        value 2;
        description
          "Logging for partner churn only";
      }
      enum "both" {
        value 3;
        description
          "Logging for actor and partner churn";
      }
    }
    description
      "Churn logging";
  }

  typedef Bundle-mode {
    type enumeration {
      enum "on" {
        value 0;
        description
          "On";
      }
      enum "active" {
        value 1;
        description
          "Active";
      }
      enum "passive" {
        value 2;
        description
          "Passive";
      }
    }
    description
      "Bundle mode";
  }

  typedef Bundle-minimum-bandwidth-range {
    type enumeration {
      enum "none" {
        value 0;
        description
          "None";
      }
      enum "kbps" {
        value 1;
        description
          "kbps";
      }
      enum "mbps" {
        value 2;
        description
          "mbps";
      }
      enum "gbps" {
        value 3;
        description
          "gbps";
      }
    }
    description
      "Bundle minimum bandwidth range";
  }

  typedef Period-short-enum {
    type union {
      type enumeration {
        enum "true" {
          value 1;
          description
            "Use the standard LACP short period (1s)";
        }
      }
      type uint32 {
        range "1..1000";
      }
    }
    description
      "Period short enum";
  }

  typedef Bundle-cisco-ext-types {
    type enumeration {
      enum "lon-signaling-off" {
        value 0;
        description
          "LON signaling disabled";
      }
      enum "lon-signaling-on" {
        value 1;
        description
          "LON signaling enabled";
      }
    }
    description
      "Bundle cisco ext types";
  }

  typedef Bundle-cisco-ext {
    type empty;
    description
      "Cisco extensions enabled";
  }

  typedef Bundle-maximum-active-links-mode {
    type enumeration {
      enum "default" {
        value 0;
        description
          "Default";
      }
      enum "hot-standby" {
        value 1;
        description
          "Hot standby";
      }
    }
    description
      "Bundle maximum active links mode";
  }

  typedef Mlacp-switchover {
    type enumeration {
      enum "brute-force" {
        value 1;
        description
          "Brute force shutdown";
      }
      enum "revertive" {
        value 2;
        description
          "Revertive behavior";
      }
    }
    description
      "Mlacp switchover";
  }

  typedef Bundle-load-balance {
    type enumeration {
      enum "default" {
        value 0;
        description
          "Default hash function used";
      }
      enum "efp-auto" {
        value 1;
        description
          "Send all traffic for this EFP over an
           automatically selected member";
      }
      enum "efp-value" {
        value 2;
        description
          "Send all traffic for this EFP over the member
           corresponding to the specified hash function";
      }
      enum "source-ip" {
        value 3;
        description
          "Load balance according to source IP address";
      }
      enum "destination-ip" {
        value 4;
        description
          "Load balance according to detination IP address";
      }
    }
    description
      "Bundle load balance";
  }

  typedef Bundle-port-activity {
    type enumeration {
      enum "on" {
        value 1;
        description
          "On";
      }
      enum "active" {
        value 2;
        description
          "Active";
      }
      enum "passive" {
        value 3;
        description
          "Passive";
      }
      enum "inherit" {
        value 4;
        description
          "Inherit";
      }
    }
    description
      "Bundle port activity";
  }

  typedef Mlacp-maximize-parameter {
    type enumeration {
      enum "links" {
        value 1;
        description
          "Maximize the number of operational links";
      }
      enum "bandwidth" {
        value 2;
        description
          "Maximize the operational bandwidth";
      }
    }
    description
      "Mlacp maximize parameter";
  }

  typedef Bundle-period {
    type union {
      type enumeration {
        enum "true" {
          value 1;
          description
            "Use the standard LACP short period (1s)";
        }
      }
      type uint32 {
        range "1..30000";
      }
    }
    description
      "Bundle period";
  }

  augment "/a1:interface-configurations/a1:interface-configuration" {
    description
      "This augment extends the configuration data of
       'Cisco-IOS-XR-ifmgr-cfg'";
    container bfd {
      status deprecated;
      description
        "This model is deprecated and is replaced by
         Cisco-IOS-XR-um-if-bundle-cfg.yang which will
         provide the compatible functionalities.  BFD
         over bundle members configuration";
      container address-family {
        description
          "Configuration of BFDoBM for all address
           families";
        container ipv6 {
          description
            "Configuration of BFDoBM for IPv6 address
             family";
          container ipv6-timers {
            description
              "Timers associated with BFDoBM";
            leaf ipv6-nbor-unconfig-timer {
              type uint32 {
                range "60..3600";
              }
              description
                "IPv6 Timer associated with aggressiveness on
                 BFD session peer being unconfigured";
            }
            leaf ipv6-start-timer {
              type uint32 {
                range "60..3600";
              }
              description
                "IPv6 Timer associated with aggressiveness on
                 BFD session creation";
            }
          }
          leaf ipv6-destination-address {
            type string;
            description
              "IPv6 Destination address for BFD sessions
               created by bundlemgr";
          }
          leaf ipv6-detection-multiplier {
            type uint32 {
              range "2..50";
            }
            description
              "IPv6 Detection multiplier for BFD sessions
               created by bundlemgr";
          }
          leaf ipv6-fast-detect {
            type empty;
            description
              "Configure to enable BFD over bundle members";
          }
          leaf ipv6-interval {
            type uint32 {
              range "3..30000";
            }
            description
              "IPV6 Hello interval for BFD sessions created
               by bundlemgr";
          }
        }
        container ipv4 {
          description
            "Configuration of BFDoBM for IPv4 address
             family";
          container echo {
            description
              "Container for Echo min-multiplier";
            leaf min-interval {
              type uint32 {
                range "15..2000";
              }
              description
                "Configure echo min-interval for bundle
                 interface";
            }
          }
          container timers {
            description
              "Timers associated with BFDoBM";
            leaf nbor-unconfig-timer {
              type uint32 {
                range "60..3600";
              }
              description
                "Timer associated with aggressiveness on BFD
                 session peer being unconfigured";
            }
            leaf start-timer {
              type uint32 {
                range "60..3600";
              }
              description
                "Timer associated with aggressiveness on BFD
                 session creation";
            }
          }
          leaf interval {
            type uint32 {
              range "3..30000";
            }
            description
              "Hello interval for BFD sessions created by
               bundlemgr";
          }
          leaf detection-multiplier {
            type uint32 {
              range "2..50";
            }
            description
              "Detection multiplier for BFD sessions created
               by bundlemgr";
          }
          leaf destination-address {
            type inet:ipv4-address-no-zone;
            description
              "Destination address for BFD sessions created
               by bundlemgr";
          }
          leaf fast-detect {
            type empty;
            description
              "Configure to enable BFD over bundle members";
          }
        }
      }
      leaf mode {
        type Bfd-mode;
        default "no-cfg";
        description
          "Configuration of BFDoBM mode [cisco|ietf]";
      }
    }
  }
  augment "/a1:interface-configurations/a1:interface-configuration" {
    description
      "This augment extends the configuration data of
       'Cisco-IOS-XR-ifmgr-cfg'";
    container bundle {
      status deprecated;
      description
        "This model is deprecated and is replaced by
         Cisco-IOS-XR-um-if-bundle-cfg.yang which will
         provide the compatible functionalities.  Generic
         per-bundle configuration";
      container bundle-load-balancing {
        description
          "Load-balance configuration";
        container hash-function {
          presence "Indicates a hash-function node is configured.";
          description
            "Enable loadbalancing on this Bundle / EFP";
          leaf hash-type {
            type Bundle-load-balance;
            mandatory true;
            description
              "The specified hash function to use";
          }
          leaf hash-value {
            type uint32 {
              range "1..64";
            }
            mandatory true;
            description
              "The loadbalance hash value selected. For
               non-EFP Value methods, this value must be set
               to 1.";
          }
        }
        leaf localize-links {
          type uint32 {
            range "1..64";
          }
          description
            "Set thresholds for forwarding bundle traffic
             within a rack";
        }
      }
      container minimum-active {
        description
          "Minimum criteria for a bundle to be active";
        container bandwidth {
          presence "Indicates a bandwidth node is configured.";
          description
            "Bandwidth (in kbps) needed to bring up a
             bundle";
          leaf min-bandwidth-range {
            type Bundle-minimum-bandwidth-range;
            mandatory true;
            description
              "Minimum Bandwidth Range";
          }
          leaf bandwidth {
            type uint32 {
              range "1..4294967295";
            }
            mandatory true;
            description
              "Bandwidth";
          }
        }
        leaf links {
          type uint32 {
            range "1..64";
          }
          default "1";
          description
            "Number of active links needed to bring up a
             bundle";
        }
      }
      container maximum-active {
        description
          "Set a limit on the number of links that can be
           active";
        container links {
          presence "Indicates a links node is configured.";
          description
            "Maximum number of active links in a bundle";
          leaf links {
            type uint32 {
              range "1..64";
            }
            mandatory true;
            description
              "Number of active links";
          }
          leaf max-active-links-mode {
            type Bundle-maximum-active-links-mode;
            description
              "Maximum active links mode";
          }
        }
      }
      leaf lacp-delay {
        type uint32 {
          range "1000..15000";
        }
        description
          "Set the lacp-delay timeout for members of this
           bundle";
      }
      leaf lacp-fallback {
        type uint32 {
          range "1..120";
        }
        default "5";
        description
          "Set the lacp-fallback timeout for this bundle";
      }
      leaf shutdown {
        type empty;
        description
          "Deactivate all member links (down to Standby
           state)";
      }
      leaf wait-while {
        type uint32 {
          range "0..2000";
        }
        default "2000";
        description
          "Set the wait-while timeout for members of this
           bundle";
      }
    }
  }
  augment "/a1:interface-configurations/a1:interface-configuration" {
    description
      "This augment extends the configuration data of
       'Cisco-IOS-XR-ifmgr-cfg'";
    container lacp {
      status deprecated;
      description
        "This model is deprecated and is replaced by
         Cisco-IOS-XR-um-if-bundle-cfg.yang which will
         provide the compatible functionalities.  Link
         Aggregation Control Protocol per-interface
         configuration (for bundle or member)";
      container cisco-extensions {
        presence "Indicates a cisco-extensions node is configured.";
        description
          "Enable bundle Cisco extensions";
        leaf cisco-ext {
          type Bundle-cisco-ext;
          mandatory true;
          description
            "Cisco extensions";
        }
        leaf cisco-ext-type {
          type Bundle-cisco-ext-types;
          description
            "Specific Cisco extension to enable / disable";
        }
      }
      container timeout {
        description
          "Set timeout values for LACP-related timers";
        leaf rx-default {
          type uint32 {
            range "0..3000";
          }
          description
            "Set the timeout between expired and defaulted
             states";
        }
        leaf actor-churn {
          type uint32 {
            range "0..120";
          }
          description
            "The time in milliseconds for which to run the
             timer";
        }
        leaf partner-churn {
          type uint32 {
            range "0..120";
          }
          description
            "Set the timeout to use before declaring
             partner churn";
        }
      }
      leaf system-priority {
        type uint32 {
          range "1..65535";
        }
        description
          "System priority for this bundle. Lower value is
           higher priority.";
      }
      leaf period {
        type Bundle-period;
        description
          "Lacp period for the bundle.";
      }
      leaf collector-max-delay {
        type uint32 {
          range "0..65535";
        }
        description
          "Collector Max Delay value to signal to the LACP
           partner";
      }
      leaf lacp-nonrevertive {
        type empty;
        description
          "Configure to enable lacp non-revertive mode";
      }
      leaf mode {
        type Bundle-mode;
        description
          "Lacp mode for the bundle.";
      }
      leaf fast-switchover {
        type empty;
        description
          "Configure to enable the fast-switchover mode";
      }
      leaf suppress-flaps {
        type uint32 {
          range "100..65535";
        }
        description
          "Suppress flaps on switchover for the specified
           period (in ms)";
      }
      leaf system-mac {
        type yang:mac-address;
        description
          "System identifier for this bundle.";
      }
      leaf period-short {
        type Period-short-enum;
        units "millisecond";
        description
          "LACP period to request from the partner (LACP
           standard short period, or rate in milliseconds
           for use with Cisco-specific extensions).
           Default is LACP standard long period (30s).";
      }
      leaf churn-logging {
        type Churn-logging;
        description
          "Log churn notifications on the specified
           system(s)";
      }
    }
  }
  augment "/a1:interface-configurations/a1:interface-configuration" {
    description
      "This augment extends the configuration data of
       'Cisco-IOS-XR-ifmgr-cfg'";
    container bundle-member {
      status deprecated;
      description
        "This model is deprecated and is replaced by
         Cisco-IOS-XR-um-if-bundle-cfg.yang which will
         provide the compatible functionalities.  Generic
         per-member configuration";
      container id {
        description
          "Add the port to an aggregated interface.";
        leaf bundle-id {
          type uint32 {
            range "1..65535";
          }
          description
            "Identifier of the bundle to add the port to.";
        }
        leaf port-activity {
          type Bundle-port-activity;
          description
            "Port Activity";
        }
      }
      leaf port-priority {
        type xr:Cisco-ios-xr-port-number;
        default "32768";
        description
          "Priority for this port. Lower value is higher
           priority.";
      }
    }
  }
  augment "/a1:interface-configurations/a1:interface-configuration" {
    description
      "This augment extends the configuration data of
       'Cisco-IOS-XR-ifmgr-cfg'";
    container mlacp {
      status deprecated;
      description
        "This model is deprecated and is replaced by
         Cisco-IOS-XR-um-if-bundle-cfg.yang which will
         provide the compatible functionalities.
         Multi-chassis LACP configuration";
      container maximize {
        presence "Indicates a maximize node is configured.";
        description
          "Set parameters to maximize between the mLACP
           peers";
        leaf maximize-by {
          type Mlacp-maximize-parameter;
          mandatory true;
          description
            "The paramenter which should be maximized";
        }
        leaf link-threshold {
          type uint32 {
            range "0..64";
          }
          description
            "The number of links below which to switch to
             the peer if it has more links available. Only
             applicable if maximizing by links. If 0, no
             threshold is applied.";
        }
        leaf bandwidth-threshold {
          type uint32 {
            range "0..4294967295";
          }
          description
            "The bandwidth (in kbps) below which to switch
             to the peer if it has more bandwidth available
             . Only applicable if maximizing by bandwidth.
             If 0, no threshold is applied.";
        }
      }
      leaf port-priority {
        type xr:Cisco-ios-xr-port-number;
        default "32768";
        description
          "The LACP port priority (lower value is higher
           priority)";
      }
      leaf recovery-delay {
        type uint32 {
          range "0..65535";
        }
        default "300";
        description
          "Set the delay before the bundle becomes active
           after recovery from failure";
      }
      leaf switchover-type {
        type Mlacp-switchover;
        description
          "Set the type of mLACP switchover to use for
           this bundle";
      }
      leaf iccp-group {
        type uint32 {
          range "1..4294967295";
        }
        description
          "Specify an ICCP Group in which this bundle
           should operate";
      }
    }
  }
  augment "/a2:redundancy-group-manager/a2:iccp/a2:iccp-groups/a2:iccp-group" {
    description
      "This augment extends the configuration data of
       'Cisco-IOS-XR-rgmgr-cfg'";
    container mlacp {
      status deprecated;
      description
        "This model is deprecated and is replaced by
         Cisco-IOS-XR-um-if-bundle-cfg.yang which will
         provide the compatible functionalities.
         Multi-chassis Link Aggregation Control Protocol
         commands";
      leaf connect-timeout {
        type uint32 {
          range "0..65534";
        }
        description
          "Number of seconds to wait before assuming mLACP
           peer is down.";
      }
      leaf system-mac {
        type yang:mac-address;
        description
          "Unique LACP identifier for this system.";
      }
      leaf node {
        type uint32 {
          range "0..7";
        }
        description
          "Unique identifier for this system in the ICCP
           Group.";
      }
      leaf system-priority {
        type uint32 {
          range "1..65535";
        }
        description
          "Priority for this system. Lower value is higher
           priority.";
      }
    }
  }
  container lacp {
    status deprecated;
    description
      "This model is deprecated and is replaced by
       Cisco-IOS-XR-um-if-bundle-cfg.yang which will
       provide the compatible functionalities.  Link
       Aggregation Control Protocol commands";
    leaf system-mac {
      type yang:mac-address;
      description
        "Unique identifier for this system.";
    }
    leaf system-priority {
      type uint32 {
        range "1..65535";
      }
      default "32768";
      description
        "Priority for this system. Lower value is higher
         priority.";
    }
  }
}
