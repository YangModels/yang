module Cisco-IOS-XR-accounting-cfg {
  namespace "http://cisco.com/ns/yang/Cisco-IOS-XR-accounting-cfg";
  prefix accounting-cfg;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR accounting package configuration.
     
     This module contains definitions
     for the following management objects:
       accounting: Global Accounting configuration commands
     
     Copyright (c) 2013-2019 by Cisco Systems, Inc.
     All rights reserved.";

  revision 2019-04-05 {
    description
      "Establish semantic version baseline.";
    semver:module-version "1.0.1";
  }
  revision 2017-05-31 {
    description
      "Fixing backward compatibility error in module.";
  }
  revision 2015-11-09 {
    description
      "IOS XR 6.0 revision.";
  }

  container accounting {
    description
      "Global Accounting configuration commands";
    container interfaces {
      description
        "Interfaces configuration";
      container mpls {
        description
          "Interfaces MPLS configuration";
        leaf enable {
          type empty;
          description
            "Enable accounting on MPLS";
        }
        leaf enable-v4rsvpte {
          type empty;
          description
            "Enable accounting on MPLS IPv4 RSVP TE";
        }
      }
      container segment-routing {
        description
          "Interfaces Segment Routing configuration";
        leaf enable {
          type empty;
          description
            "Enable accounting on Segment Routing";
        }
        leaf enable-mplsv4 {
          type empty;
          description
            "Enable accounting on Segment Routing MPLS IPv4";
        }
        leaf enable-mplsv6 {
          type empty;
          description
            "Enable accounting on Segment Routing MPLS IPv6";
        }
      }
      leaf enable {
        type empty;
        description
          "Enable accounting on Interfaces";
      }
    }
    leaf enable {
      type empty;
      description
        "Enable Accounting";
    }
  }
}
