submodule Cisco-IOS-XR-telemetry-model-driven-oper-sub1 {
  belongs-to Cisco-IOS-XR-telemetry-model-driven-oper {
    prefix Cisco-IOS-XR-telemetry-model-driven-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR telemetry-model-driven package operational data.
     
     Copyright (c) 2013-2020 by Cisco Systems, Inc.
     All rights reserved.";

  revision 2020-01-30 {
    description
      "Added compression leaf to destination container
       2020-01-10
         GRPC channel statistics added";
    semver:module-version "1.1.0";
  }
  revision 2019-04-05 {
    description
      "Establish semantic version baseline.";
    semver:module-version "1.0.1";
  }
  revision 2017-09-27 {
    description
      "Summary container added";
  }
  revision 2017-05-05 {
    description
      "Modified the type for the state variables";
  }
  revision 2017-05-01 {
    description
      "Fixing backward compatibility error in module.";
  }
  revision 2017-02-09 {
    description
      "Added DSCP";
  }
  revision 2017-01-30 {
    description
      "Initial 6.2.1 revision";
  }
  revision 2015-11-09 {
    description
      "IOS XR 6.0 revision.";
  }

  grouping TELEMETRY-SHOW-SUMMARY {
    description
      "Telemetry Summary information";
    leaf num-of-subscriptions {
      type uint32;
      description
        "Number of Subscriptions";
    }
    leaf num-of-active-subscriptions {
      type uint32;
      description
        "Number of Active Subscriptions";
    }
    leaf num-of-paused-subscriptions {
      type uint32;
      description
        "Number of Paused Subscriptions";
    }
    leaf num-of-destination-groups {
      type uint32;
      description
        "Number of Destination Groups";
    }
    leaf num-of-destinations {
      type uint32;
      description
        "Number of Destinations";
    }
    leaf num-of-tcp-dialouts {
      type uint32;
      description
        "Number of Tcp Dialout Destinations";
    }
    leaf num-of-udp-dialouts {
      type uint32;
      description
        "Number of Udp Dialout Destinations";
    }
    leaf num-of-grpc-tls-dialouts {
      type uint32;
      description
        "Number of GRPC TLS Dialout Destinations";
    }
    leaf num-of-grpc-non-tls-dialouts {
      type uint32;
      description
        "Number of GRPC Non-TLS Dialout Destinations";
    }
    leaf num-of-dialins {
      type uint32;
      description
        "Number of Dialin Destinations";
    }
    leaf num-of-active-destinations {
      type uint32;
      description
        "Number of Active Destinations";
    }
    leaf num-of-connected-sessions {
      type uint32;
      description
        "Number of Connected Sessions";
    }
    leaf num-of-connecting-sessions {
      type uint32;
      description
        "Number of Connecting Sessions";
    }
    leaf num-of-sensor-groups {
      type uint32;
      description
        "Number of Sensor Groups";
    }
    leaf num-of-unique-sensor-paths {
      type uint32;
      description
        "Number of Unique Sensor Paths";
    }
    leaf num-of-sensor-paths {
      type uint32;
      description
        "Number of Sensor Paths";
    }
    leaf num-of-not-resolved-sensor-paths {
      type uint32;
      description
        "Number of not resolved sensor paths";
    }
    leaf num-of-active-sensor-paths {
      type uint32;
      description
        "Number of Active Sensor Paths";
    }
    leaf max-sensor-paths {
      type uint32;
      description
        "Maximum Sensor Paths allowed";
    }
    leaf max-containers-per-path {
      type uint32;
      description
        "Max containers allowed per Sensor Path";
    }
  }
}
