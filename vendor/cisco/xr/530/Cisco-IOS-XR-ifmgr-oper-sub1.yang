submodule Cisco-IOS-XR-ifmgr-oper-sub1 {

  belongs-to Cisco-IOS-XR-ifmgr-oper {
    prefix Cisco-IOS-XR-ifmgr-oper;
  }

  /*** LINKAGE (IMPORTS / INCLUDES) ***/

  import Cisco-IOS-XR-types { prefix "xr"; }

  include Cisco-IOS-XR-ifmgr-oper-sub2 {
    revision-date 2013-07-22;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR ifmgr package operational data.

     Copyright (c) 2013-2014 by Cisco Systems, Inc.
     All rights reserved.";

  revision "2013-07-22" {
    description
      "Initial revision.";
  }


  grouping IMDS-IFATTR-BASE-INFO {
    description "Basic interface information";
    leaf interface {
      xr:xr-xml-map "imd:Interface";
      type xr:Interface-name;
      description "Interface";
    }
    leaf parent-interface {
      xr:xr-xml-map "imd:ParentInterface";
      type xr:Interface-name;
      description "Parent Interface";
    }
    leaf type {
      xr:xr-xml-map "imd:Type";
      type string;
      description "Interface type";
    }
    leaf state {
      xr:xr-xml-map "imd:State";
      type Im-state-enum;
      description "Operational state";
    }
    leaf actual-state {
      xr:xr-xml-map "imd:ActualState";
      type Im-state-enum;
      description
        "Operational state with no translation of error
        disable or shutdown";
    }
    leaf line-state {
      xr:xr-xml-map "imd:LineState";
      type Im-state-enum;
      description "Line protocol state";
    }
    leaf actual-line-state {
      xr:xr-xml-map "imd:ActualLineState";
      type Im-state-enum;
      description
        "Line protocol state with no translation of error
        disable or shutdown";
    }
    leaf encapsulation {
      xr:xr-xml-map "imd:Encapsulation";
      type string;
      description "Interface encapsulation";
    }
    leaf encapsulation-type-string {
      xr:xr-xml-map "imd:EncapsulationTypeString";
      type string {
        length "0..32";
      }
      description "Interface encapsulation description string";
    }
    leaf mtu {
      xr:xr-xml-map "imd:MTU";
      type uint32;
      units "byte";
      description "MTU in bytes";
    }
    leaf sub-interface-mtu-overhead {
      xr:xr-xml-map "imd:SubInterfaceMTUOverhead";
      type uint32;
      description "Subif MTU overhead";
    }
    leaf l2-transport {
      xr:xr-xml-map "imd:L2Transport";
      type boolean;
      description "L2 transport";
    }
    leaf bandwidth {
      xr:xr-xml-map "imd:Bandwidth";
      type uint32;
      description "Interface bandwidth (Kb/s)";
    }
  }
}
