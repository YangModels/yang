module Cisco-IOS-XR-man-netconf-cfg {

  /*** NAMESPACE / PREFIX DEFINITION ***/

  namespace "http://cisco.com/ns/yang/Cisco-IOS-XR-man-netconf-cfg";


  prefix "man-netconf-cfg";

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR man-netconf package configuration.

     This module contains definitions
     for the following management objects:
       netconf-yang: NETCONF YANG configuration commands

     Copyright (c) 2013-2014 by Cisco Systems, Inc.
     All rights reserved.";

  revision "2013-07-22" {
    description
      "Initial revision.";
  }


  container netconf-yang {
    xr:xr-xml-map "cfg_netconf:NETCONF_YANG";
    description "NETCONF YANG configuration commands";

    container agent {
      xr:xr-xml-map "cfg_netconf:Agent";
      description "NETCONF YANG agent configuration commands";

      container ssh {
        xr:xr-xml-map "cfg_netconf:SSH";
        description "NETCONF YANG agent over SSH connection";
        leaf enable {
          xr:xr-xml-map "cfg_netconf:Enable";
          xr:xr-cli-map "netconf-yang agent ssh ";
          type empty;
          description
            "Enable NETCONF YANG agent over SSH connection";
        }
      }
    }
  }
}
