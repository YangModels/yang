module Cisco-IOS-XR-rgmgr-oper {

  /*** NAMESPACE / PREFIX DEFINITION ***/

  namespace "http://cisco.com/ns/yang/Cisco-IOS-XR-rgmgr-oper";


  prefix "rgmgr-oper";

  /*** LINKAGE (IMPORTS / INCLUDES) ***/

  import Cisco-IOS-XR-types { prefix "xr"; }

  include Cisco-IOS-XR-rgmgr-oper-sub1 {
    revision-date 2013-07-22;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR rgmgr package operational data.

     This module contains definitions
     for the following management objects:
       redundancy-group-manager: Redundancy group manager operational
         data

     Copyright (c) 2013-2014 by Cisco Systems, Inc.
     All rights reserved.";

  revision "2013-07-22" {
    description
      "Initial revision.";
  }


  container redundancy-group-manager {
    xr:xr-xml-map "infra_rgmgr_oper:RedundancyGroupManager";
    config false;
    description "Redundancy group manager operational data";

    container controllers {
      xr:xr-xml-map "infra_rgmgr_oper:ControllerTable";
      description "Redundancy group manager data";

      list controller {
        xr:xr-xml-map "infra_rgmgr_oper:Controller";
        key "controller-name";
        description "Display redundancy group by controller name";
        leaf controller-name {
          xr:xr-xml-map "infra_rgmgr_oper:ControllerName";
          type xr:Interface-name;
          description "Controller name";
        }
        uses RGMGR-RED-GRP;
      }
    }
  }
}
