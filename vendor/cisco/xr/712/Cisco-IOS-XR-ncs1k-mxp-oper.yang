module Cisco-IOS-XR-ncs1k-mxp-oper {
  namespace "http://cisco.com/ns/yang/Cisco-IOS-XR-ncs1k-mxp-oper";
  prefix ncs1k-mxp-oper;

  import cisco-semver {
    prefix semver;
  }
  include Cisco-IOS-XR-ncs1k-mxp-oper-sub1 {
    revision-date 2019-04-05;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ncs1k-mxp package operational data.
     
     This module contains definitions
     for the following management objects:
       hw-module: mxp hw-module command chain
     
     Copyright (c) 2013-2019 by Cisco Systems, Inc.
     All rights reserved.";

  revision 2019-04-05 {
    description
      "Establish semantic version baseline.";
    semver:module-version "1.0.0";
  }
  revision 2018-06-20 {
    description
      "Modify the existing variable name.";
  }
  revision 2015-11-09 {
    description
      "IOS XR 6.0 revision.";
  }

  container hw-module {
    config false;
    description
      "mxp hw-module command chain";
    container slice-ids {
      description
        "Slice information";
      list slice-id {
        key "slice-num";
        description
          "Per slice num data";
        leaf slice-num {
          type uint32;
          description
            "Details associated with a particular slice
             number";
        }
        uses HW-MODULE-SLICE-INFO-B;
      }
    }
    container slice-all {
      description
        "Information for all slices";
      uses MXP-HWMOD-OP;
    }
  }
}
