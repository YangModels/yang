//*************  DO-NOT EDIT  **************
//*********** Auto-generated file ********** 

 module cisco-xr-openconfig-alarms-deviations {

  namespace "http://cisco.com/ns/yang/cisco-xr-openconfig-alarms-deviations";
  prefix  "oc-alarmsdevs";

  import openconfig-alarms { prefix oc-alarms; }
  import openconfig-platform { prefix oc-platform; }

  organization "Cisco Systems, Inc.";

  contact
    "Cisco Systems, Inc.
     Customer Service

     Postal: 170 West Tasman Drive
     San Jose, CA 95134

     Tel: +1 800 553-NETS

     E-mail: cs-yang@cisco.com";

  description
    "This module contains a set of deviations for 
 
     openconfig-alarms.yang@2018-01-16 

     on Cisco IOS-XR devices.

     Copyright (c) 2017, 2019-2020 by Cisco Systems, Inc.
     All rights reserved.";

  revision "2019-11-14" {
    description
      "Initial revision applicable to IOS-XR 6.4.1";
  }


  deviation /oc-platform:components/oc-platform:component/oc-platform:state/oc-alarms:equipment-failure {
    deviate not-supported;
  }

  deviation /oc-platform:components/oc-platform:component/oc-platform:state/oc-alarms:equipment-mismatch {
    deviate not-supported;
  }


}
//total deviations:2
