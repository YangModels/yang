module Cisco-IOS-XR-linux-xlnc-oper {
  namespace "http://cisco.com/ns/yang/Cisco-IOS-XR-linux-xlnc-oper";
  prefix linux-xlnc-oper;

  import Cisco-IOS-XR-types {
    prefix xr;
  }
  import cisco-semver {
    prefix semver;
  }
  include Cisco-IOS-XR-linux-xlnc-oper-sub1 {
    revision-date 2020-01-14;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR linux-xlnc package operational data.
     
     This module contains definitions
     for the following management objects:
       linux-networking: Linux Networking operational data
     
     Copyright (c) 2013-2020 by Cisco Systems, Inc.
     All rights reserved.";

  revision 2020-01-14 {
    description
      "Add error reporting for attempts to set the MAC address on linux-managed interfaces, where IOS XR does not support changing the MAC address.";
    semver:module-version "1.1.0";
  }
  revision 2019-04-05 {
    description
      "Establish semantic version baseline.";
    semver:module-version "1.1.0";
  }
  revision 2015-11-09 {
    description
      "IOS XR 6.0 revision.";
  }

  container linux-networking {
    config false;
    description
      "Linux Networking operational data";
    container global {
      description
        "Global operational data";
      container status {
        description
          "Linux Networking operational status";
        container inconsistencies-per-interfaces {
          description
            "Global inconsistencies table";
          list inconsistencies-per-interface {
            key "interface-name";
            description
              "Inconsistencies observed for a particular
               interface.";
            leaf interface-name {
              type xr:Interface-name;
              description
                "Interface name";
            }
            uses XLNC-BAG-INTERFACE-INCONSISTENCIES;
          }
        }
      }
    }
  }
}
