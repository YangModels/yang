submodule Cisco-IOS-XR-envmon-oper-sub1 {
  belongs-to Cisco-IOS-XR-envmon-oper {
    prefix Cisco-IOS-XR-envmon-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR envmon package operational data.
     
     Copyright (c) 2013-2019 by Cisco Systems, Inc.
     All rights reserved.";

  revision 2019-04-05 {
    description
      "Establish semantic version baseline.";
    semver:module-version "1.0.1";
  }
  revision 2015-11-09 {
    description
      "IOS XR 6.0 revision.";
  }

  grouping CONSUMER-PWR-INFO-B {
    description
      "Power Consumer Info";
    leaf node-name {
      type string;
      description
        "Name of the Node";
    }
    leaf node-type {
      type string;
      description
        "PID of the Entity";
    }
    leaf pwr-alctd {
      type uint32;
      description
        "Power Allocated";
    }
    leaf pwr-used {
      type uint32;
      description
        "Power Used";
    }
    leaf node-status {
      type string;
      description
        "Node Status";
    }
  }

  grouping CHASSIS-PWR-GRP-INFO-B {
    description
      "Group Level Power Info";
    leaf total-pwr-in {
      type uint64;
      description
        "Total Power Input in watts";
    }
    leaf total-pwr-out {
      type uint64;
      description
        "Total Power Output in watts";
    }
    leaf total-current-in-a {
      type string;
      description
        "Total Current Input A in amps";
    }
    leaf total-current-in-b {
      type string;
      description
        "Total Current Input B in amps";
    }
    leaf total-current-out {
      type string;
      description
        "Total Current Output in amps";
    }
    leaf total-output-capacity {
      type uint64;
      description
        "Total Output capacity in watts";
    }
  }

  grouping CHASSIS-PWR-INFO-B {
    description
      "Chassis Level Power Info";
    leaf total-pwr-required {
      type uint32;
      description
        "Total Power required";
    }
    leaf red-mode {
      type uint32;
      description
        "Redundancy Mode";
    }
    leaf total-pe-ms {
      type uint32;
      description
        "Total Number of PEMs";
    }
    leaf red-num-pe-ms {
      type uint32;
      description
        "Redundant Number of PEMs";
    }
    list grp-info {
      max-elements "3";
      description
        "Total Info Group Wise";
      uses CHASSIS-PWR-GRP-INFO-B;
    }
  }

  grouping PRODUCER-PWR-PEM-INFO-B {
    description
      "Power Producer PEM Info";
    leaf node-name {
      type string;
      description
        "Name of the Node";
    }
    leaf node-type {
      type string;
      description
        "PID of the PEM";
    }
    leaf num-feed {
      type uint32;
      description
        "Number of Feeds";
    }
    leaf voltage-in-a {
      type uint32;
      description
        "Input Voltage A";
    }
    leaf voltage-in-b {
      type uint32;
      description
        "Input Voltage B";
    }
    leaf voltage-out {
      type uint32;
      description
        "Output Voltage";
    }
    leaf current-in-a {
      type uint32;
      description
        "Input Current A";
    }
    leaf current-in-b {
      type uint32;
      description
        "Input Current B";
    }
    leaf current-out {
      type uint32;
      description
        "Output Current";
    }
    leaf node-status {
      type string;
      description
        "Node Status";
    }
  }

  grouping PRODUCER-PWR-PT-INFO-B {
    description
      "Power Producer PT Info";
    list pem-info-array {
      description
        "PEM Info Array";
      uses PRODUCER-PWR-PEM-INFO-B;
    }
  }
}
