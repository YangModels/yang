module Cisco-IOS-XR-sysadmin-obfl-clear {
  namespace "http://cisco.com/ns/yang/Cisco-IOS-XR-sysadmin-obfl-clear";
  prefix obflclear;

  import tailf-common {
    prefix tailf;
  }
  import cisco-semver {
    prefix semver;
  }

  organization
    "Cisco Systems Inc.";
  contact
    "Cisco Systems, Inc.
     Customer Service
     
     Postal: 170 West Tasman Drive
     San Jose, CA 95134
     
     Tel: +1 800 553-NETS
     
     E-mail: cs-yang@cisco.com";
  description
    "This module is for clearing OBFL data.
     
     Copyright (c) 2012-2020 by Cisco Systems, Inc.
     All rights reserved.";

  revision 2019-04-15 {
    description
      "Establish semantic version baseline.";
    semver:module-version "1.0.2";
  }
  revision 2017-07-31 {
    description
      "Changed namespace to follow Cisco guidelines on naming conventions";
  }
  revision 2016-10-12 {
    description
      "Unhide commands and configs. Moved to advanced-grp";
  }
  revision 2011-12-03 {
    description
      "Initial revision.";
  }

  grouping obflclear-grp {
    container logging {
      config false;
      container onboard {
        config false;
        list location {
          key "location";
          config false;
          leaf location {
            type string;
          }
          tailf:action "clear" {
            input {
              leaf all {
                type empty;
                mandatory true;
              }
            }
          }
        }
      }
    }
  }
}
