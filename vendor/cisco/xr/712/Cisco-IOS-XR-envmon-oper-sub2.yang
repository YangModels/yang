submodule Cisco-IOS-XR-envmon-oper-sub2 {
  belongs-to Cisco-IOS-XR-envmon-oper {
    prefix Cisco-IOS-XR-envmon-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR envmon package operational data.
     
     Copyright (c) 2013-2019 by Cisco Systems, Inc.
     All rights reserved.";

  revision 2019-04-05 {
    description
      "Establish semantic version baseline.";
    semver:module-version "1.0.1";
  }
  revision 2015-11-09 {
    description
      "IOS XR 6.0 revision.";
  }

  grouping SPI-ENVMON-SENSOR-DATA-B {
    description
      "Sensor Data structure";
    leaf sensor-value {
      type int32;
      description
        "Value of Sensor";
    }
    leaf critical-low-threshold {
      type int32;
      description
        "Critical Low Threshold Value, interpret -32768
         value as N/A";
    }
    leaf critical-high-threshold {
      type int32;
      description
        "Critical High Threshold Value, interpret -32768
         value as N/A";
    }
    leaf major-low-threshold {
      type int32;
      description
        "Major Low Threshold Value, interpret -32768
         value as N/A";
    }
    leaf major-high-threshold {
      type int32;
      description
        "Major High Threshold Value, interpret -32768
         value as N/A";
    }
    leaf minor-low-threshold {
      type int32;
      description
        "Minor Low Threshold Value, interpret -32768
         value as N/A";
    }
    leaf minor-high-threshold {
      type int32;
      description
        "Minor High Threshold Value, interpret -32768
         value as N/A";
    }
    leaf name-xr {
      type string;
      description
        "Name of Sensor";
    }
    leaf location {
      type string;
      description
        "Location of Sensor";
    }
    leaf fru-type {
      type string;
      description
        "FRU Type";
    }
    leaf status {
      type uint32;
      description
        "Sensor Operational Status";
    }
  }
}
