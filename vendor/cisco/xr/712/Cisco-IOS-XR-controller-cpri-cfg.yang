module Cisco-IOS-XR-controller-cpri-cfg {
  namespace "http://cisco.com/ns/yang/Cisco-IOS-XR-controller-cpri-cfg";
  prefix controller-cpri-cfg;

  import cisco-semver {
    prefix semver;
  }
  import Cisco-IOS-XR-ifmgr-cfg {
    prefix a1;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR controller-cpri package configuration.
     
     This YANG module augments the
       Cisco-IOS-XR-ifmgr-cfg
     module with configuration data.
     
     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  typedef Cpri-data-rate {
    type enumeration {
      enum "none" {
        value 0;
        description
          "None";
      }
      enum "614mb" {
        value 1;
        description
          "CPRI rate 614.4MB";
      }
      enum "1228mb" {
        value 2;
        description
          "CPRI rate 1228.8MB";
      }
      enum "2457mb" {
        value 3;
        description
          "CPRI rate 2457.6MB";
      }
      enum "3072mb" {
        value 4;
        description
          "CPRI rate 3072MB";
      }
      enum "4915mb" {
        value 5;
        description
          "CPRI rate 4915.2MB";
      }
      enum "6144mb" {
        value 6;
        description
          "CPRI rate 6144MB";
      }
      enum "9830mb" {
        value 7;
        description
          "CPRI rate 9830.4MB";
      }
      enum "8110mb" {
        value 8;
        description
          "CPRI rate 8110.08MB";
      }
      enum "10137mb" {
        value 9;
        description
          "CPRI rate 10137.6MB";
      }
      enum "12165mb" {
        value 10;
        description
          "CPRI rate 12165.12MB";
      }
      enum "24330mb" {
        value 11;
        description
          "CPRI rate 24330.24MB";
      }
    }
    description
      "Cpri data rate";
  }

  typedef Cpri-lpbk-mode {
    type enumeration {
      enum "line" {
        value 1;
        description
          "Line Loopback";
      }
      enum "internal" {
        value 4;
        description
          "Internal Loopback";
      }
    }
    description
      "Cpri lpbk mode";
  }

  typedef Cpri-sync-mode {
    type enumeration {
      enum "slave" {
        value 0;
        description
          "Slave";
      }
      enum "master" {
        value 1;
        description
          "Master";
      }
    }
    description
      "Cpri sync mode";
  }

  augment "/a1:interface-configurations/a1:interface-configuration" {
    description
      "This augment extends the configuration data of
       'Cisco-IOS-XR-ifmgr-cfg'";
    container cpri {
      description
        "CPRI port controller configuration";
      container negotiable-line-rates {
        description
          "Configure the CPRI rates that should used in
           line rate negotiation";
        leaf-list negotiable-line-rate {
          type Cpri-data-rate;
          max-elements "4";
          description
            "Array of CPRI line rates";
        }
      }
      container extended-loopback {
        description
          "Configure CPRI port extended loopback level and
           mode";
        leaf level {
          type uint32 {
            range "1..3";
          }
          description
            "ExtendedLoopbackLevel";
        }
        leaf mode {
          type Cpri-lpbk-mode;
          description
            "ExtendedLoopbackMode";
        }
      }
      leaf synchronization-mode {
        type Cpri-sync-mode;
        default "slave";
        description
          "Configure CPRI Synchronization mode";
      }
      leaf l1-startup-timer {
        type uint32;
        default "0";
        description
          "Configure L1 startup timer value";
      }
    }
  }
}
