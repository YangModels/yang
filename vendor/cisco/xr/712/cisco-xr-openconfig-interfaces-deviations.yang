module cisco-xr-openconfig-interfaces-deviations {

  prefix  "ocifdevs";

  namespace "http://cisco.com/ns/yang/cisco-xr-openconfig-interfaces-deviations";

  import openconfig-interfaces { prefix oc-if; }

  organization "Cisco Systems, Inc.";

  contact
    "Cisco Systems, Inc.
     Customer Service

     Postal: 170 West Tasman Drive
     San Jose, CA 95134

     Tel: +1 800 553-NETS

     E-mail: cs-yang@cisco.com";

  description
    "This module contains a set of deviations for 
 
     openconfig-interfaces.yang@2019-11-19 

     on Cisco IOS-XR devices.

     Copyright (c) 2017 by Cisco Systems, Inc.
     All rights reserved.";

  revision "2020-03-09" {
    description
      "Initial revision applicable to IOS-XR 6.4.1";
  }

  deviation /oc-if:interfaces/oc-if:interface/oc-if:config/oc-if:enabled {
    deviate delete {
        default true;
    }
  }

  deviation /oc-if:interfaces/oc-if:interface/oc-if:state/oc-if:enabled {
    deviate delete {
        default true;
    }
  }

  deviation /oc-if:interfaces/oc-if:interface/oc-if:config/oc-if:type {
    deviate not-supported;
  }

}
//total deviations:3
