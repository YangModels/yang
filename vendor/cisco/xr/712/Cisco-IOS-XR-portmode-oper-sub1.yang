submodule Cisco-IOS-XR-portmode-oper-sub1 {
  belongs-to Cisco-IOS-XR-portmode-oper {
    prefix Cisco-IOS-XR-portmode-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR portmode package operational data.
     
     Copyright (c) 2013-2019 by Cisco Systems, Inc.
     All rights reserved.";

  revision 2019-07-05 {
    description
      "Portmode Oper Yang and Oper Sub-Yang Model added.";
    semver:module-version "1.0.0";
  }
  revision 2019-04-05 {
    description
      "Establish semantic version baseline.";
  }
  revision 2015-11-09 {
    description
      "IOS XR 6.0 revision.";
  }

  typedef Port-mode-rate {
    type enumeration {
      enum "none" {
        value 0;
        description
          "None";
      }
      enum "port-mode-rate-oc3" {
        value 1;
        description
          "OC3";
      }
      enum "port-mode-rate-oc12" {
        value 2;
        description
          "OC12";
      }
      enum "port-mode-rate-oc48" {
        value 3;
        description
          "OC48";
      }
      enum "port-mode-rate-oc192" {
        value 4;
        description
          "OC192";
      }
      enum "port-mode-rate-oc768" {
        value 5;
        description
          "OC768";
      }
      enum "port-mode-rate-stm1" {
        value 6;
        description
          "STM1";
      }
      enum "port-mode-rate-stm4" {
        value 7;
        description
          "STM4";
      }
      enum "port-mode-rate-stm16" {
        value 8;
        description
          "STM16";
      }
      enum "port-mode-rate-stm64" {
        value 9;
        description
          "STM64";
      }
      enum "port-mode-rate-stm256" {
        value 10;
        description
          "STM256";
      }
      enum "port-mode-rate-100ge" {
        value 11;
        description
          "100GE";
      }
      enum "port-mode-rate-10ge" {
        value 12;
        description
          "10GE";
      }
      enum "port-mode-rate-40ge" {
        value 13;
        description
          "40GE";
      }
      enum "port-mode-rate-1ge" {
        value 14;
        description
          "1GE";
      }
      enum "port-mode-rate-25ge" {
        value 15;
        description
          "25GE";
      }
    }
    description
      "Port mode rate";
  }

  typedef Pt {
    type enumeration {
      enum "na" {
        value 0;
        description
          "NA";
      }
      enum "two-asynchronous-cbr-mapping" {
        value 2;
        description
          "02 (Asynchronous CBR mapping)";
      }
      enum "three-bit-synchronous-cbr-mapping" {
        value 3;
        description
          "03 (Bit synchronous CBR mapping)";
      }
      enum "five-gfp-mapping" {
        value 5;
        description
          "05 (GFP mapping)";
      }
      enum "six-virtual-concatenated-signal" {
        value 6;
        description
          "06 (Virtual Concatenated Signal)";
      }
      enum "seven-pc-scodeword-transparent-ethernet-mapping" {
        value 7;
        description
          "07 (PCS codeword transparent Ethernet mapping)";
      }
      enum "nine-gfp-mapping-into-opu2" {
        value 9;
        description
          "09 (GFP mapping into OPU2)";
      }
      enum "zero-astm1-mapping-into-opu0" {
        value 10;
        description
          "0A (STM1 mapping into OPU0)";
      }
      enum "zero-bstm4-mapping-into-opu0" {
        value 11;
        description
          "0B (STM4 mapping into OPU0)";
      }
      enum "twenty-odu-multiplex-structure-supporting-odt-ujk" {
        value 32;
        description
          "20 (ODU multiplex structure supporting ODTUjk)";
      }
      enum "twenty-one-odu-multiplex-structure-supporting-odt-ujk-and-odt-ukts" {
        value 33;
        description
          "21 (ODU multiplex structure supporting ODTUjk
           and ODTUk.ts)";
      }
      enum "traffic-dependent" {
        value 34;
        description
          "Traffic Dependent";
      }
    }
    description
      "Pt";
  }

  typedef Mapping {
    type enumeration {
      enum "none" {
        value 0;
        description
          "None mapping type";
      }
      enum "gfp-f" {
        value 1;
        description
          "GFP-F mapping type";
      }
      enum "amp" {
        value 2;
        description
          "AMP mapping type";
      }
      enum "bmp" {
        value 3;
        description
          "BMP mapping type";
      }
      enum "gmp" {
        value 4;
        description
          "GMP mapping type";
      }
      enum "wis" {
        value 5;
        description
          "WIS mapping type";
      }
      enum "gfp-f-ext" {
        value 6;
        description
          "GFP-F-Extended mapping type";
      }
    }
    description
      "Mapping";
  }

  typedef Framing {
    type enumeration {
      enum "none" {
        value 0;
        description
          "None framing type";
      }
      enum "opu0" {
        value 1;
        description
          "OPU0 framing type";
      }
      enum "opu1" {
        value 2;
        description
          "OPU1 framing type";
      }
      enum "opu1e" {
        value 3;
        description
          "OPU1e framing type";
      }
      enum "opu1f" {
        value 4;
        description
          "OPU1f framing type";
      }
      enum "opu2" {
        value 5;
        description
          "OPU2 framing type";
      }
      enum "opu2e" {
        value 6;
        description
          "OPU2e framing type";
      }
      enum "opu2f" {
        value 7;
        description
          "OPU2f framing type";
      }
      enum "opu3" {
        value 8;
        description
          "OPU3 framing type";
      }
      enum "opu3e1" {
        value 9;
        description
          "OPU3e1 framing type";
      }
      enum "opu3e2" {
        value 10;
        description
          "OPU3e2 framing type";
      }
      enum "opu4" {
        value 11;
        description
          "OPU4 framing type";
      }
      enum "opu-flex" {
        value 12;
        description
          "OPU Flex framing type";
      }
      enum "opuc2" {
        value 13;
        description
          "OPUC2 framing type";
      }
      enum "opuc4" {
        value 14;
        description
          "OPUC4 framing type";
      }
      enum "packet" {
        value 15;
        description
          "Packet framing type";
      }
    }
    description
      "Framing";
  }

  typedef Port-mode {
    type enumeration {
      enum "none" {
        value 0;
        description
          "None";
      }
      enum "ethernet" {
        value 1;
        description
          "Ethernet";
      }
      enum "sonet" {
        value 2;
        description
          "Sonet";
      }
      enum "fibre-channel" {
        value 3;
        description
          "Fibre Channel";
      }
      enum "otn" {
        value 4;
        description
          "OTN";
      }
      enum "sdh" {
        value 5;
        description
          "SDH";
      }
      enum "ethernet-packet" {
        value 6;
        description
          "Ethernet Packet";
      }
      enum "cpri" {
        value 7;
        description
          "CPRI";
      }
    }
    description
      "Port mode";
  }

  grouping PORTMODE-CAPABILITY-DETAILS {
    description
      "PortMode Capability";
    leaf port-num {
      type uint32;
      description
        "Port number";
    }
    leaf port-mode-type {
      type Port-mode;
      description
        "PortMode type";
    }
    leaf framing {
      type Framing;
      description
        "Framing type";
    }
    leaf mapping {
      type Mapping;
      description
        "Mapping type";
    }
    leaf pt-type {
      type Pt;
      description
        "Payload type";
    }
    leaf port-mode-rate {
      type Port-mode-rate;
      description
        "Portmode Rate";
    }
  }

  grouping PORTMODE-CAPABILITY-ALL {
    description
      "PortMode Capability All";
    list port-mode {
      description
        "PortMode";
      uses PORTMODE-CAPABILITY-DETAILS;
    }
  }

  grouping PORTMODE-DETAILS-ALL {
    description
      "PortMode All";
    list port-mode {
      description
        "PortMode";
      uses PORTMODE-DETAILS;
    }
  }

  grouping PORTMODE-DETAILS {
    description
      "PortMode";
    leaf port-num {
      type uint32;
      description
        "Port number";
    }
    leaf port-mode-type {
      type Port-mode;
      description
        "PortMode type";
    }
    leaf framing {
      type Framing;
      description
        "Framing type";
    }
    leaf mapping {
      type Mapping;
      description
        "Mapping type";
    }
    leaf pt-type {
      type Pt;
      description
        "Payload type";
    }
    leaf port-mode-rate {
      type Port-mode-rate;
      description
        "Portmode Rate";
    }
    leaf port-name {
      type string {
        length "0..65";
      }
      description
        "Interface Name";
    }
  }
}
