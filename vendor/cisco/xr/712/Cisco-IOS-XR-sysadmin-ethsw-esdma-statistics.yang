module Cisco-IOS-XR-sysadmin-ethsw-esdma-statistics {
  namespace "http://www.cisco.com/ns/yang/Cisco-IOS-XR-sysadmin-ethsw-esdma-statistics";
  prefix esdma_statistics;

  import Cisco-IOS-XR-sysadmin-ethsw-esdma-types {
    prefix esdma_types;
  }
  import cisco-semver {
    prefix semver;
  }

  organization
    "Cisco Systems Inc.";
  contact
    "Cisco Systems, Inc.
     Customer Service
     
     Postal: 170 West Tasman Drive
     San Jose, CA 95134
     
     Tel: +1 800 553-NETS
     
     E-mail: cs-yang@cisco.com";
  description
    "This module contains the YANG definitions
     for the Cisco IOS-XR SysAdmin
     'show controller switch statistics' commands.
     
     Copyright (c) 2011-2020 by Cisco Systems, Inc.
     All rights reserved.";

  revision 2019-04-15 {
    description
      "Establish semantic version baseline.";
    semver:module-version "1.0.0";
  }
  revision 2018-02-23 {
    description
      "Added a missing : for uniform output format";
  }
  revision 2017-05-01 {
    description
      "Namespace change to comply with Cisco guidelines on namespace";
  }
  revision 2016-07-06 {
    description
      "Initial revision with content extracted from esdma_cli.yang.";
  }

  grouping switch-statistics-group {
    container statistics {
      container summary-statistics {
        list location {
          key "rack card switch-id";
          leaf rack {
            type esdma_types:esdma-rack-num-enum;
          }
          leaf card {
            type esdma_types:esdma-cpu;
            description
              "Card that owns a switch of interest";
          }
          leaf switch-id {
            type esdma_types:esdma-switch-type-enum;
            description
              "Switch type";
          }
          leaf serial-num {
            type string;
            description
              "Rack serial number";
          }
          list port-iter {
            key "port";
            leaf port {
              type esdma_types:esdma-switch-port-type;
              description
                "Switch port";
            }
            leaf phys-state {
              type esdma_types:esdma-switch-port-state;
              description
                "Physical port state";
            }
            leaf state-changes {
              type uint32;
              description
                "Physical port state changes";
            }
            leaf sw-sum-tx-packets {
              type uint64;
              description
                "Packets transmitted on this switch port";
            }
            leaf sw-sum-rx-packets {
              type uint64;
              description
                "Indicates the port speed in bits per second";
            }
            leaf sw-sum-tx-drops-errors {
              type uint64;
              description
                "Indicates the number of transmitted packets that had an error or were dropped by the policer";
            }
            leaf sw-sum-rx-drops-errors {
              type uint64;
              description
                "Indicates the number of received packets that had an error or were dropped by the policer";
            }
            leaf connects-to {
              type string;
              description
                "Indicates what this port connects to";
            }
          }
        }
      }
      container detail {
        list location {
          key "rack card switch-id";
          leaf rack {
            type esdma_types:esdma-rack-num-enum;
          }
          leaf card {
            type esdma_types:esdma-cpu;
            description
              "Card that owns a switch of interest";
          }
          leaf switch-id {
            type esdma_types:esdma-switch-type-enum;
            description
              "Switch type";
          }
          list port-iter {
            key "port";
            leaf port {
              type esdma_types:esdma-switch-port-type;
              description
                "Switch port";
            }
            leaf phys-state {
              type esdma_types:esdma-switch-port-state;
              description
                "Physical port state";
            }
            leaf port-speed {
              type string;
              description
                "Indicates the port speed in bits per second";
            }
            leaf connects-to {
              type string;
              description
                "Indicates what this port connects to";
            }
            container counters {
              leaf sw-det-rx-ucast-packets {
                type uint64;
              }
              leaf sw-det-rx-mcast-packets {
                type uint64;
              }
              leaf sw-det-rx-bcast-packets {
                type uint64;
              }
              leaf sw-det-rx-flow-control {
                type uint64;
              }
              leaf sw-det-rx-good-octets {
                type uint64;
              }
              leaf sw-det-rx-bad-octets {
                type uint64;
              }
              leaf sw-det-rx-fifo-overrun {
                type uint64;
              }
              leaf sw-det-rx-undersize {
                type uint64;
              }
              leaf sw-det-rx-fragments {
                type uint64;
              }
              leaf sw-det-rx-oversize {
                type uint64;
              }
              leaf sw-det-rx-jabber {
                type uint64;
              }
              leaf sw-det-rx-errors {
                type uint64;
              }
              leaf sw-det-rx-bad-crc {
                type uint64;
              }
              leaf sw-det-rx-collisions {
                type uint64;
              }
              leaf sw-det-rx-policing-drops {
                type uint64;
              }
              leaf sw-det-tx-ucast-packets {
                type uint64;
              }
              leaf sw-det-tx-mcast-packets {
                type uint64;
              }
              leaf sw-det-tx-bcast-packets {
                type uint64;
              }
              leaf sw-det-tx-flow-control {
                type uint64;
              }
              leaf sw-det-tx-good-octets {
                type uint64;
              }
              leaf sw-det-tx-deferred {
                type uint64;
              }
              leaf sw-det-tx-fifo-unrun {
                type uint64;
              }
              leaf sw-det-tx-mult-collision {
                type uint64;
              }
              leaf sw-det-tx-excess-collision {
                type uint64;
              }
              leaf sw-det-tx-late-collisions {
                type uint64;
              }
              leaf sw-det-tx-policing-drops {
                type uint64;
              }
              leaf sw-det-txq-drops {
                type uint64;
              }
              leaf sw-det-rxtx-packets-64 {
                type uint64;
              }
              leaf sw-det-rxtx-packets-65-127 {
                type uint64;
              }
              leaf sw-det-rxtx-packets-128-255 {
                type uint64;
              }
              leaf sw-det-rxtx-packets-256-511 {
                type uint64;
              }
              leaf sw-det-rxtx-packets-512-1023 {
                type uint64;
              }
              leaf sw-det-rxtx-packets-1024-max {
                type uint64;
              }
            }
          }
        }
      }
    }
  }
}
