module Cisco-IOS-XR-qos-ma-bng-cfg {
  namespace "http://cisco.com/ns/yang/Cisco-IOS-XR-qos-ma-bng-cfg";
  prefix qos-ma-bng-cfg;

  import cisco-semver {
    prefix semver;
  }
  import Cisco-IOS-XR-subscriber-infra-tmplmgr-cfg {
    prefix a1;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR qos-ma-bng package configuration.
     
     This YANG module augments the
       Cisco-IOS-XR-subscriber-infra-tmplmgr-cfg
     module with configuration data.
     
     Copyright (c) 2013-2019 by Cisco Systems, Inc.
     All rights reserved.";

  revision 2019-04-05 {
    description
      "Establish semantic version baseline.";
    semver:module-version "1.0.1";
  }
  revision 2016-04-01 {
    description
      "Descriptions updated.";
  }
  revision 2015-11-09 {
    description
      "IOS XR 6.0 revision.";
  }

  typedef Qosl2-data-link {
    type enumeration {
      enum "aal5" {
        value 0;
        description
          "ATM adaption layer AAL5";
      }
    }
    description
      "Qosl2 data link";
  }

  typedef Qosl2-encap {
    type enumeration {
      enum "snap-pppoa" {
        value 1;
        description
          "snap-pppoa encap used between the DSLAM and CPE";
      }
      enum "mux-pppoa" {
        value 2;
        description
          "mux-pppoa encap used between the DSLAM and CPE";
      }
      enum "snap1483-routed" {
        value 3;
        description
          "snap-1483routed encap used between the DSLAM
           and CPE";
      }
      enum "mux1483-routed" {
        value 4;
        description
          "mux-1483routed encap used between the DSLAM and
           CPE";
      }
      enum "snap-rbe" {
        value 5;
        description
          "snap-rbe encap used between the DSLAM and CPE";
      }
      enum "snap-dot1qrbe" {
        value 6;
        description
          "snap-dot1q-rbe encap used between the DSLAM and
           CPE";
      }
      enum "mux-rbe" {
        value 7;
        description
          "mux-rbe encap used between the DSLAM and CPE";
      }
      enum "mux-dot1qrbe" {
        value 8;
        description
          "mux-dot1q-rbe encap used between the DSLAM and
           CPE";
      }
    }
    description
      "Qosl2 encap";
  }

  grouping QOS {
    description
      "Common node of ppp, ip-subscriber,
       subscriber-service";
    container qos {
      description
        "QoS dynamically applied configuration template";
      container service-policy {
        description
          "Service policy to be applied in ingress/egress
           direction";
        container input {
          presence "Indicates a input node is configured.";
          description
            "Subscriber ingress policy";
          leaf policy-name {
            type string;
            mandatory true;
            description
              "Name of policy-map";
          }
          leaf spi-name {
            type string;
            description
              "Name of the SPI";
          }
          leaf merge {
            type boolean;
            description
              "TRUE for merge enabled for service-policy
               applied on dynamic template.";
          }
          leaf merge-id {
            type uint32 {
              range "0..255";
            }
            description
              "Merge ID value";
          }
          leaf account-stats {
            type boolean;
            description
              "TRUE for account stats enabled for
               service-policy applied on dynamic template.
               Note: account stats not supported for
               subscriber type 'ppp' and 'ipsubscriber'.";
          }
        }
        container output {
          presence "Indicates a output node is configured.";
          description
            "Subscriber egress policy";
          leaf policy-name {
            type string;
            mandatory true;
            description
              "Name of policy-map";
          }
          leaf spi-name {
            type string;
            description
              "Name of the SPI";
          }
          leaf merge {
            type boolean;
            description
              "TRUE for merge enabled for service-policy
               applied on dynamic template.";
          }
          leaf merge-id {
            type uint32 {
              range "0..255";
            }
            description
              "Merge ID value";
          }
          leaf account-stats {
            type boolean;
            description
              "TRUE for account stats enabled for
               service-policy applied on dynamic template.
               Note: account stats not supported for
               subscriber type 'ppp' and 'ipsubscriber'.";
          }
        }
      }
      container account {
        description
          "QoS L2 overhead accounting";
        leaf aal {
          type Qosl2-data-link;
          must "../encapsulation and not(../user-defined or ../atm-cell-tax)";
          description
            "ATM adaptation layer AAL";
        }
        leaf encapsulation {
          type Qosl2-encap;
          must "../aal and not(../user-defined or ../atm-cell-tax)";
          description
            "Specify encapsulation type";
        }
        leaf atm-cell-tax {
          type empty;
          must "../user-defined and not(../aal or ../encapsulation)";
          description
            "ATM cell tax to L2 overhead";
        }
        leaf user-defined {
          type int32 {
            range "-63..63";
          }
          must "not(../aal or ../encapsulation)";
          description
            "Numeric L2 overhead offset";
        }
      }
      container output {
        description
          "QoS to be applied in egress direction";
        leaf minimum-bandwidth {
          type uint32 {
            range "1..4294967295";
          }
          units "kbit/s";
          description
            "Minimum bandwidth value for the subscriber (in
             kbps)";
        }
      }
    }
  }

  augment "/a1:dynamic-template/a1:subscriber-services/a1:subscriber-service" {
    description
      "This augment extends the configuration data of
       'Cisco-IOS-XR-subscriber-infra-tmplmgr-cfg'";
    uses QOS;
  }
  augment "/a1:dynamic-template/a1:ip-subscribers/a1:ip-subscriber" {
    description
      "This augment extends the configuration data of
       'Cisco-IOS-XR-subscriber-infra-tmplmgr-cfg'";
    uses QOS;
  }
  augment "/a1:dynamic-template/a1:ppps/a1:ppp" {
    description
      "This augment extends the configuration data of
       'Cisco-IOS-XR-subscriber-infra-tmplmgr-cfg'";
    uses QOS;
  }
}
