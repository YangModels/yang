submodule Cisco-IOS-XR-install-oper-sub1 {
  belongs-to Cisco-IOS-XR-install-oper {
    prefix Cisco-IOS-XR-install-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR install package operational data.
     
     Copyright (c) 2013-2020 by Cisco Systems, Inc.
     All rights reserved.";

  revision 2020-04-23 {
    description
      "Add categorization of installed software packages into Cisco and Non-Cisco
       2020-04-23
         Add categorization of installed software packages into Cisco and Non-Cisco
       2020-04-23
         Add categorization of installed software packages into Cisco and Non-Cisco";
    semver:module-version "1.2.0";
  }
  revision 2019-10-13 {
    description
      "NCS540L 7.1.1 release
       2019-10-12
       8000 series 7.0.11 release
       2019-08-13
       Common yang oper model for lindt and eXR install.";
    semver:module-version "1.1.0";
  }
  revision 2019-04-05 {
    description
      "Establish semantic version baseline.";
    semver:module-version "1.0.0";
  }
  revision 2015-11-09 {
    description
      "IOS XR 6.0 revision.";
  }

  typedef Inst-req-state {
    type enumeration {
      enum "in-progress" {
        value 0;
        description
          "In progress";
      }
      enum "success" {
        value 1;
        description
          "Success";
      }
      enum "failure" {
        value 2;
        description
          "Failure";
      }
    }
    description
      "Install request state type";
  }

  typedef Install-opt-string {
    type string;
    description
      "Install opt string";
  }

  grouping INST-REQUEST-BAG {
    description
      "Request result bag";
    leaf request {
      type string;
      description
        "The last user request";
    }
    leaf state {
      type Inst-req-state;
      description
        "The state of the last user request";
    }
    leaf timestamp {
      type string;
      description
        "The time the current state was entered";
    }
    leaf error {
      type string;
      description
        "String describing the error, if any";
    }
    leaf operation-id {
      type Install-opt-string;
      description
        "Operation ID of the ongoing or  previous
         completed install operation";
    }
  }

  grouping INST-TOP-LEVEL-PKG-TYPE {
    description
      "Install user-installable package type";
    leaf name {
      type string;
      description
        "Package name";
    }
    leaf architecture {
      type string;
      description
        "Architecture";
    }
    leaf version {
      type string;
      description
        "Version";
    }
    leaf release {
      type string;
      description
        "Release";
    }
    leaf epoch {
      type Install-opt-string;
      description
        "Epoch";
    }
    leaf xr-mandatory {
      type boolean;
      description
        "XR Mandatory";
    }
    leaf xr-optional {
      type boolean;
      description
        "XR Optional";
    }
    leaf gpg-key-id {
      type Install-opt-string;
      description
        "The GPG key ID at install time. A key ID of '0'
         indicates a package with no GPG signature.";
    }
  }

  grouping INST-SUMMARY-PACKAGES-BAG {
    description
      "Summary packages result bag";
    leaf xr-packages-hash {
      type string;
      description
        "Hash of XR packages";
    }
    list package {
      description
        "Packages";
      uses INST-TOP-LEVEL-PKG-TYPE;
    }
  }

  grouping INST-PACKAGES-BAG {
    description
      "Package result bag";
    list package {
      description
        "Packages";
      uses INST-PKG-TYPE;
    }
  }

  grouping INST-PKG-TYPE {
    description
      "Install package type";
    leaf name {
      type string;
      description
        "Package name";
    }
    leaf architecture {
      type string;
      description
        "Architecture";
    }
    leaf version {
      type string;
      description
        "Version";
    }
    leaf release {
      type string;
      description
        "Release";
    }
    leaf epoch {
      type Install-opt-string;
      description
        "Epoch";
    }
    leaf gpg-key-id {
      type Install-opt-string;
      description
        "The GPG key ID at install time. A key ID of '0'
         indicates a package with no GPG signature.";
    }
  }

  grouping INST-FIX-TYPE {
    description
      "INST FIX TYPE";
    leaf ddts {
      type string;
      description
        "DDTS id";
    }
    list package {
      description
        "Packages";
      uses INST-PKG-TYPE;
    }
  }

  grouping INST-FIXES-BAG {
    description
      "Install bag containing details of
       active/committed fixes";
    list fixes {
      description
        "Fixes";
      uses INST-FIX-TYPE;
    }
  }

  grouping INST-VER-PKG-TYPE {
    description
      "Install package type";
    leaf name {
      type string;
      description
        "Name";
    }
    leaf version {
      type string;
      description
        "Version";
    }
    leaf built-by {
      type string;
      description
        "User built by";
    }
    leaf built-on {
      type string;
      description
        "Time built";
    }
    leaf workspace {
      type string;
      description
        "Workspace built in";
    }
    leaf build-host {
      type string;
      description
        "Build host";
    }
  }

  grouping INST-VERSION-BAG {
    description
      "Install version bag";
    leaf label {
      type string;
      description
        "Label";
    }
    leaf copyright-info {
      type string;
      description
        "Copyright information";
    }
    leaf hardware-info {
      type string;
      description
        "Hardware information";
    }
    leaf uptime {
      type string;
      description
        "System uptime";
    }
    leaf location {
      type Install-opt-string;
      description
        "Prefix for the path where packages will be
         installed";
    }
    leaf processor {
      type Install-opt-string;
      description
        "Processor";
    }
    list package {
      description
        "Packages";
      uses INST-VER-PKG-TYPE;
    }
  }
}
