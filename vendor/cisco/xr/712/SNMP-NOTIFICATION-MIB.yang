module SNMP-NOTIFICATION-MIB {
  namespace "http://tail-f.com/ns/mibs/SNMP-NOTIFICATION-MIB/200210140000Z";
  prefix SNMP_NOTIFICATION_MIB;
  tailf:id "";
  tailf:snmp-mib-module-name "SNMP-NOTIFICATION-MIB";

  import ietf-yang-types {
    prefix yang;
  }
  import tailf-common {
    prefix tailf;
  }
  import SNMPv2-TC {
    prefix SNMPv2_TC;
  }
  import SNMP-TARGET-MIB {
    prefix SNMP_TARGET_MIB;
  }

  revision 2002-10-14 {
    description
      "";
  }

  container SNMP-NOTIFICATION-MIB {
    container snmpNotifyTable {
      list snmpNotifyEntry {
        key "snmpNotifyName";
        tailf:sort-order "snmp-implied";
        tailf:snmp-oid "1.3.6.1.6.3.13.1.1";
        leaf snmpNotifyName {
          type snmpNotifyNameType;
          tailf:snmp-oid "1.3.6.1.6.3.13.1.1.1.1";
        }
        leaf snmpNotifyTag {
          type SNMP_TARGET_MIB:SnmpTagValue;
          tailf:snmp-oid "1.3.6.1.6.3.13.1.1.1.2";
        }
        leaf snmpNotifyType {
          type snmpNotifyTypeType;
          tailf:snmp-oid "1.3.6.1.6.3.13.1.1.1.3";
          default "trap";
        }
        leaf snmpNotifyStorageType {
          type SNMPv2_TC:StorageType;
          tailf:snmp-oid "1.3.6.1.6.3.13.1.1.1.4";
          default "nonVolatile";
        }
      }
    }
    container snmpNotifyFilterProfileTable {
      tailf:hidden "full";
      presence "";
      list snmpNotifyFilterProfileEntry {
        key "snmpTargetParamsName";
        tailf:sort-order "snmp-implied";
        tailf:snmp-oid "1.3.6.1.6.3.13.1.2";
        leaf snmpTargetParamsName {
          type snmpTargetParamsNameType;
          tailf:snmp-oid "1.3.6.1.6.3.12.1.3.1.1";
        }
        leaf snmpNotifyFilterProfileName {
          type snmpNotifyFilterProfileNameType;
          tailf:snmp-oid "1.3.6.1.6.3.13.1.2.1.1";
        }
        leaf snmpNotifyFilterProfileStorType {
          type SNMPv2_TC:StorageType;
          tailf:snmp-oid "1.3.6.1.6.3.13.1.2.1.2";
          default "nonVolatile";
        }
      }
    }
    container snmpNotifyFilterTable {
      tailf:hidden "full";
      presence "";
      list snmpNotifyFilterEntry {
        key "snmpNotifyFilterProfileName snmpNotifyFilterSubtree";
        tailf:sort-order "snmp-implied";
        tailf:snmp-oid "1.3.6.1.6.3.13.1.3";
        leaf snmpNotifyFilterProfileName {
          type snmpNotifyFilterProfileNameType;
          tailf:snmp-oid "1.3.6.1.6.3.13.1.2.1.1";
        }
        leaf snmpNotifyFilterSubtree {
          type yang:object-identifier;
          tailf:snmp-oid "1.3.6.1.6.3.13.1.3.1.1";
        }
        leaf snmpNotifyFilterMask {
          type snmpNotifyFilterMaskType;
          tailf:snmp-oid "1.3.6.1.6.3.13.1.3.1.2";
        }
        leaf snmpNotifyFilterType {
          type snmpNotifyFilterTypeType;
          tailf:snmp-oid "1.3.6.1.6.3.13.1.3.1.3";
          default "included";
        }
        leaf snmpNotifyFilterStorageType {
          type SNMPv2_TC:StorageType;
          tailf:snmp-oid "1.3.6.1.6.3.13.1.3.1.4";
          default "nonVolatile";
        }
      }
    }
  }

  typedef snmpNotifyNameType {
    type string {
      length "1 .. 32";
    }
  }

  typedef snmpNotifyTypeType {
    type enumeration {
      enum "trap" {
        value 1;
      }
      enum "inform" {
        value 2;
      }
    }
  }

  typedef snmpTargetParamsNameType {
    type string {
      length "1 .. 32";
    }
  }

  typedef snmpNotifyFilterProfileNameType {
    type string {
      length "1 .. 32";
    }
  }

  typedef snmpNotifyFilterMaskType {
    type tailf:hex-list {
      pattern "(((([0-9A-Fa-f]{2}):){0,15}([0-9A-Fa-f]{2}))){0,1}";
      tailf:value-length "min .. 16";
    }
  }

  typedef snmpNotifyFilterTypeType {
    type enumeration {
      enum "included" {
        value 1;
      }
      enum "excluded" {
        value 2;
      }
    }
  }
}
