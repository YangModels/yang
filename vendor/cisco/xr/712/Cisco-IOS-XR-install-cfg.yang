module Cisco-IOS-XR-install-cfg {
  namespace "http://cisco.com/ns/yang/Cisco-IOS-XR-install-cfg";
  prefix install-cfg;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR install package configuration.
     
     This module contains definitions
     for the following management objects:
       install: Install configuration data
     
     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  container install {
    description
      "Install configuration data";
    container repositories {
      description
        "Table of repositories";
      list repository {
        key "id";
        description
          "Repository configuration";
        leaf url {
          type string {
            length "1..900";
          }
          description
            "Repository URL - path to local repository or
             ftp, http, or https path to remote repository,
             optionally containing the name of a VRF for
             the repository. Format one of: 
               ftp
             ://<server>[;<vrf>]/<path_to_repo> 
               http
             ://<server>[;<vrf>]/<path_to_repo> 
               https
             ://<server>[;<vrf>]/<path_to_repo> 
               file
             :///<path_to_repo>";
        }
        leaf description {
          type string {
            length "1..900";
          }
          description
            "Repository name or description";
        }
        leaf id {
          type string {
            length "1..80";
          }
          description
            "Repository identifier";
        }
      }
    }
  }
}
