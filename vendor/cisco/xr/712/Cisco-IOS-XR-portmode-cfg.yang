module Cisco-IOS-XR-portmode-cfg {
  namespace "http://cisco.com/ns/yang/Cisco-IOS-XR-portmode-cfg";
  prefix portmode-cfg;

  import cisco-semver {
    prefix semver;
  }
  import Cisco-IOS-XR-ifmgr-cfg {
    prefix a1;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR portmode package configuration.
     
     This YANG module augments the
       Cisco-IOS-XR-ifmgr-cfg
     module with configuration data.
     
     Copyright (c) 2013-2019 by Cisco Systems, Inc.
     All rights reserved.";

  revision 2019-07-05 {
    description
      "Portmode Config and Datatype Yang model added.";
    semver:module-version "1.0.0";
  }
  revision 2019-04-05 {
    description
      "Establish semantic version baseline.";
  }
  revision 2015-11-09 {
    description
      "IOS XR 6.0 revision.";
  }

  typedef Port-mode-mapping {
    type enumeration {
      enum "none" {
        value 0;
        description
          "No mapping";
      }
      enum "gfp-f" {
        value 1;
        description
          "GFP_F mapping";
      }
      enum "amp" {
        value 2;
        description
          "AMP mapping";
      }
      enum "bmp" {
        value 3;
        description
          "BMP mapping";
      }
      enum "gmp" {
        value 4;
        description
          "GMP mapping";
      }
      enum "wis" {
        value 5;
        description
          "WIS mapping";
      }
      enum "gfp-f-ext" {
        value 6;
        description
          "GFP_F_EXT mapping";
      }
    }
    description
      "Port mode mapping";
  }

  typedef Port-mode-rate {
    type enumeration {
      enum "none" {
        value 0;
        description
          "No Rate";
      }
      enum "oc3" {
        value 1;
        description
          "OC3 Rate";
      }
      enum "oc12" {
        value 2;
        description
          "OC12 Rate";
      }
      enum "oc48" {
        value 3;
        description
          "OC48 Rate";
      }
      enum "oc192" {
        value 4;
        description
          "OC192 Rate";
      }
      enum "oc768" {
        value 5;
        description
          "OC768 Rate";
      }
      enum "stm1" {
        value 6;
        description
          "STM1 Rate";
      }
      enum "stm4" {
        value 7;
        description
          "STM4 Rate";
      }
      enum "stm16" {
        value 8;
        description
          "STM16 Rate";
      }
      enum "stm64" {
        value 9;
        description
          "STM64 Rate";
      }
      enum "stm256" {
        value 10;
        description
          "STM256 Rate";
      }
      enum "100ge" {
        value 11;
        description
          "100GE Rate";
      }
      enum "10ge" {
        value 12;
        description
          "10GE Rate";
      }
      enum "40ge" {
        value 13;
        description
          "40GE Rate";
      }
      enum "1ge" {
        value 14;
        description
          "1GE Rate";
      }
      enum "25ge" {
        value 15;
        description
          "25GE Rate";
      }
    }
    description
      "Port mode rate";
  }

  typedef Port-mode-types {
    type enumeration {
      enum "invalid" {
        value 0;
        description
          "Invalid portmode";
      }
      enum "ethernet" {
        value 1;
        description
          "Ethernet portmode type";
      }
      enum "sonet" {
        value 2;
        description
          "Sonet portmode type";
      }
      enum "fc" {
        value 3;
        description
          "FC portmode type";
      }
      enum "otn" {
        value 4;
        description
          "OTN portmode type";
      }
      enum "sdh" {
        value 5;
        description
          "SDH portmode type";
      }
      enum "cpri" {
        value 7;
        description
          "CPRI portmode type";
      }
    }
    description
      "Port mode types";
  }

  typedef Port-mode-framing {
    type enumeration {
      enum "none" {
        value 0;
        description
          "No framing";
      }
      enum "opu0" {
        value 1;
        description
          "OPU0 framing";
      }
      enum "opu1" {
        value 2;
        description
          "OPU1 framing";
      }
      enum "opu1e" {
        value 3;
        description
          "OPU1e framing";
      }
      enum "opu1f" {
        value 4;
        description
          "OPU1f framing";
      }
      enum "opu2" {
        value 5;
        description
          "OPU2 framing";
      }
      enum "opu2e" {
        value 6;
        description
          "OPU2e framing";
      }
      enum "opu2f" {
        value 7;
        description
          "OPU2f framing";
      }
      enum "opu3" {
        value 8;
        description
          "OPU3 framing";
      }
      enum "opu3e1" {
        value 9;
        description
          "OPU3e1 framing";
      }
      enum "opu3e2" {
        value 10;
        description
          "OPU3e2 framing";
      }
      enum "opu4" {
        value 11;
        description
          "OPU4 framing";
      }
      enum "opu-flex" {
        value 12;
        description
          "OPUFlex framing";
      }
      enum "opuc2" {
        value 13;
        description
          "OPUC2 framing";
      }
      enum "opuc4" {
        value 14;
        description
          "OPUC4 framing";
      }
      enum "packet" {
        value 15;
        description
          "Packet framing";
      }
    }
    description
      "Port mode framing";
  }

  augment "/a1:interface-configurations/a1:interface-configuration" {
    description
      "This augment extends the configuration data of
       'Cisco-IOS-XR-ifmgr-cfg'";
    container port-mode {
      description
        "Portmode configuration";
      container lane-numbers {
        description
          "Breakout Configuration";
        list lane-number {
          key "lane-no";
          description
            "Lane number for breakout configuration";
          leaf lane-no {
            type uint32 {
              range "1..10";
            }
            description
              "LANE NO";
          }
          leaf rate {
            type Port-mode-rate;
            description
              "PortMode rate";
          }
          leaf mapping {
            type Port-mode-mapping;
            description
              "PortMode mapping types";
          }
          leaf framing {
            type Port-mode-framing;
            description
              "PortMode framing types";
          }
          leaf type {
            type Port-mode-types;
            description
              "PortMode types";
          }
        }
      }
      container info {
        description
          "PortMode configuration";
        leaf rate {
          type Port-mode-rate;
          description
            "PortMode rate";
        }
        leaf mapping {
          type Port-mode-mapping;
          description
            "PortMode mapping types";
        }
        leaf framing {
          type Port-mode-framing;
          description
            "PortMode framing types";
        }
        leaf type {
          type Port-mode-types;
          description
            "PortMode types";
        }
      }
    }
  }
}
