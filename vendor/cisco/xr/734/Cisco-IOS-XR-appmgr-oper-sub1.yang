submodule Cisco-IOS-XR-appmgr-oper-sub1 {
  belongs-to Cisco-IOS-XR-appmgr-oper {
    prefix Cisco-IOS-XR-appmgr-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR appmgr package operational data.
     
     Copyright (c) 2013-2021 by Cisco Systems, Inc.
     All rights reserved.";

  revision 2021-05-15 {
    description
      "Unused application types removed
       2021-03-01
         Adding information about installed packages
       2021-02-15
         Support for process scripts.";
    semver:module-version "2.0.0";
  }
  revision 2019-04-05 {
    description
      "Establish semantic version baseline.";
    semver:module-version "1.0.0";
  }
  revision 2015-11-09 {
    description
      "IOS XR 6.0 revision.";
  }

  typedef Appmgr-app-state {
    type enumeration {
      enum "deactivated" {
        value 1;
        description
          "Deactivated";
      }
      enum "activated" {
        value 2;
        description
          "Activated";
      }
      enum "error" {
        value 4;
        description
          "Error";
      }
    }
    description
      "Appmgr application state";
  }

  typedef Appmgr-app {
    type enumeration {
      enum "docker" {
        value 1;
        description
          "Docker";
      }
    }
    description
      "Appmgr application type";
  }

  typedef Appmgr-daemon-state {
    type enumeration {
      enum "not-started" {
        value 1;
        description
          "Not Started";
      }
      enum "start-requested" {
        value 2;
        description
          "Start Requested";
      }
      enum "started" {
        value 3;
        description
          "Started";
      }
      enum "stop-requested" {
        value 4;
        description
          "Stop Requested";
      }
      enum "stopped" {
        value 5;
        description
          "Stopped";
      }
      enum "kill-requested" {
        value 6;
        description
          "Kill Requested";
      }
      enum "killed" {
        value 7;
        description
          "Killed";
      }
      enum "exit-success" {
        value 8;
        description
          "Exit Success";
      }
      enum "exit-failure" {
        value 9;
        description
          "Exit Failure";
      }
    }
    description
      "Appmgr process script state";
  }

  typedef String1 {
    type string;
    description
      "String1";
  }

  typedef Appmgr-restart-policy {
    type enumeration {
      enum "never" {
        value 1;
        description
          "Never";
      }
      enum "on-failure" {
        value 2;
        description
          "On Failure";
      }
      enum "always" {
        value 3;
        description
          "Always";
      }
      enum "unless-stopped" {
        value 4;
        description
          "Unless Stopped";
      }
      enum "unless-errored" {
        value 5;
        description
          "Unless Errored";
      }
    }
    description
      "Appmgr restart policy";
  }

  typedef Package {
    type string;
    description
      "Package";
  }

  grouping VRF-RELAY-INFO {
    description
      "VRF Forwarding Relay information.";
    leaf name {
      type string;
      description
        "Container Name";
    }
    leaf status {
      type string;
      description
        "Vrf Forwarding Relay status.";
    }
    leaf error-info {
      type string;
      description
        "Vrf Forwarding Relay error information.";
    }
    leaf src-vrf {
      type string;
      description
        "Source VRF.";
    }
    leaf src-port {
      type string;
      description
        "Source Port.";
    }
    leaf dest-vrf {
      type string;
      description
        "Destination VRF.";
    }
    leaf dest-port {
      type string;
      description
        "Destination Port.";
    }
    leaf ip-range {
      type string;
      description
        "IP address range";
    }
  }

  grouping DOCKER-INFO {
    description
      "Docker container info";
    leaf id {
      type string;
      description
        "Container ID";
    }
    leaf image {
      type string;
      description
        "Image ID";
    }
    leaf command {
      type string;
      description
        "Quoted command";
    }
    leaf created-at {
      type string;
      description
        "Time when the container was created";
    }
    leaf running-for {
      type string;
      description
        "Elapsed time since the container was started.";
    }
    leaf ports {
      type string;
      description
        "Exposed ports.";
    }
    leaf status {
      type string;
      description
        "Container status.";
    }
    leaf size {
      type string;
      description
        "Container disk size.";
    }
    leaf names {
      type string;
      description
        "Container names.";
    }
    leaf labels {
      type string;
      description
        "All labels assigned to the container.";
    }
    leaf mounts {
      type string;
      description
        "Names of the volumes mounted in this container.";
    }
    leaf networks {
      type string;
      description
        "Names of the networks attached to this container
         .";
    }
    leaf local-volumes {
      type string;
      description
        "Names of the local volumes mounted in this
         container";
    }
    list vrf-relay-info {
      description
        "VRF forwarding relay information";
      uses VRF-RELAY-INFO;
    }
  }

  grouping APPMGR-VAR-INFO {
    description
      "Appmgr App Variable Info";
    container docker-info {
      when "../type = 'docker'" {
        description
          "../Type = 'Docker'";
      }
      description
        "Details of docker applications";
      uses DOCKER-INFO;
    }
    leaf type {
      type Appmgr-app;
      description
        "Type";
    }
  }

  grouping APPMGR-APP-INFO {
    description
      "Information about an Application managed by the
       App Mgr";
    container var-info {
      description
        "App Variable Info";
      uses APPMGR-VAR-INFO;
    }
    leaf name {
      type string;
      description
        "Application name";
    }
    leaf type {
      type Appmgr-app;
      description
        "Application type";
    }
    leaf source {
      type string;
      description
        "Application source";
    }
    leaf config-state {
      type Appmgr-app-state;
      description
        "Application config state";
    }
    leaf error-info {
      type string;
      description
        "App Error Info";
    }
  }

  grouping BAG-DOCKER-STATS {
    description
      "Docker stats output";
    leaf container {
      type string;
      description
        "Container name or ID (user input)";
    }
    leaf name {
      type string;
      description
        "Container name";
    }
    leaf id {
      type string;
      description
        "Container ID";
    }
    leaf cpu-perc {
      type string;
      units "percentage";
      description
        "CPU percentage";
    }
    leaf mem-usage {
      type string;
      description
        "Memory usage";
    }
    leaf net-io {
      type string;
      description
        "Network IO";
    }
    leaf block-io {
      type string;
      description
        "Block IO";
    }
    leaf mem-perc {
      type string;
      units "percentage";
      description
        "Memory percentage";
    }
    leaf pids {
      type string;
      description
        "Number of PIDs";
    }
  }

  grouping APPMGR-VAR-STATS {
    description
      "Appmgr App Variable Stats";
    container docker-stats {
      when "../type = 'docker'" {
        description
          "../Type = 'Docker'";
      }
      description
        "Stats for docker applications";
      uses BAG-DOCKER-STATS;
    }
    leaf type {
      type Appmgr-app;
      description
        "Type";
    }
  }

  grouping APPMGR-APP-STATS {
    description
      "Stats for an Application managed by the App Mgr";
    container var-stats {
      description
        "App Variable Stats";
      uses APPMGR-VAR-STATS;
    }
  }

  grouping APPMGR-DAEMON-CONFIG {
    description
      "Appmgr process script configuration";
    leaf executable {
      type string;
      description
        "Executable Name";
    }
    leaf run-args {
      type string;
      description
        "Run Arguments";
    }
    leaf restart-policy {
      type Appmgr-restart-policy;
      description
        "Restart Policy";
    }
    leaf max-retries {
      type uint16 {
        range "1..10";
      }
      description
        "Maximum Restarts";
    }
  }

  grouping APPMGR-DAEMON-EXEC-INFO {
    description
      "Appmgr process script running information";
    leaf executable {
      type string;
      description
        "Executable Name";
    }
    leaf run-args {
      type string;
      description
        "Run Arguments";
    }
    leaf restart-policy {
      type Appmgr-restart-policy;
      description
        "Restart Policy";
    }
    leaf max-retries {
      type uint16 {
        range "1..10";
      }
      description
        "Maximum Restarts";
    }
    leaf restarts {
      type uint16;
      description
        "Restarts";
    }
    leaf last-started-time {
      type String1;
      description
        "Last Started Time";
    }
    leaf checksum {
      type String1;
      description
        "Executable's checksum";
    }
    leaf log-location {
      type String1;
      description
        "Log Location";
    }
    leaf last-exit-code {
      type int32;
      description
        "Last Exit Code";
    }
  }

  grouping APPMGR-DAEMON-INFO {
    description
      "Information about a process script managed by the
       App Mgr";
    container execution-info {
      description
        "Execution Info";
      uses APPMGR-DAEMON-EXEC-INFO;
    }
    container config {
      description
        "Registered Configuration";
      uses APPMGR-DAEMON-CONFIG;
    }
    leaf name {
      type string;
      description
        "Application name";
    }
    leaf status {
      type Appmgr-daemon-state;
      description
        "Application status";
    }
    leaf is-activated {
      type boolean;
      description
        "Is App Activated";
    }
    leaf is-cfg-pending {
      type boolean;
      description
        "Is Configuration Pending";
    }
  }

  grouping APPMGR-SOURCE {
    description
      "Information about an installed source.";
    leaf name-xr {
      type string;
      description
        "Source name";
    }
    leaf file {
      type string;
      description
        "Source file";
    }
    leaf package {
      type Package;
      description
        "Parent package";
    }
  }

  grouping APPMGR-PACKAGES {
    description
      "Installed packages";
    leaf-list package {
      type Package;
      description
        "Packages";
    }
  }
}
