module Cisco-IOS-XR-asr9k-qos-oper {
  namespace "http://cisco.com/ns/yang/Cisco-IOS-XR-asr9k-qos-oper";
  prefix asr9k-qos-oper;

  import Cisco-IOS-XR-types {
    prefix xr;
  }
  import cisco-semver {
    prefix semver;
  }
  include Cisco-IOS-XR-asr9k-qos-oper-sub2 {
    revision-date 2021-04-09;
  }
  include Cisco-IOS-XR-asr9k-qos-oper-sub1 {
    revision-date 2021-04-09;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR asr9k-qos package operational data.
     
     This module contains definitions
     for the following management objects:
       platform-qos: QoS ASR9K platform operational data
     
     Copyright (c) 2013-2021 by Cisco Systems, Inc.
     All rights reserved.";

  revision 2021-04-09 {
    description
      "pi changes to support wred drop probability";
    semver:module-version "1.1.0";
  }
  revision 2020-12-23 {
    description
      "Introduced an CLI to show qos performance stats";
    semver:module-version "1.0.0";
  }
  revision 2019-09-30 {
    description
      "YANG support for PWHE interface";
  }
  revision 2019-04-05 {
    description
      "Establish semantic version baseline.";
  }
  revision 2015-11-09 {
    description
      "IOS XR 6.0 revision.";
  }

  grouping NV-SATELLITE-INPUT {
    description
      "Common node of nv-satellite-interface,
       satellite-id, member-interface";
    container nv-satellite-input {
      description
        "A piece of Satellite QoS policy-map operational
         data for input";
      uses NV-SAT-STATISTICS;
    }
  }

  grouping DETAILS {
    description
      "Common node of output, input, member-interface,
       pin-interface";
    container details {
      description
        "QoS policy direction egress";
      uses QOS-SHOW-EA-POLICY;
    }
  }

  grouping STATISTICS {
    description
      "Common node of input, output, policy-name";
    container statistics {
      description
        "Policy-map statistics operational data for an
         interface";
      uses QOS-STATS;
    }
  }

  grouping INTERFACE {
    description
      "Common node of interface-table,
       nv-interface-table";
    list interface {
      key "interface-name";
      description
        "QoS policy-map operational data for a particular
         interface";
      leaf interface-name {
        type xr:Interface-name;
        description
          "Name of the interface";
      }
      uses MEMBER-INTERFACE-TABLE;
      uses SATELLITE-ID-TABLE;
      uses INPUT;
      uses OUTPUT;
    }
  }

  grouping INPUT {
    description
      "Common node of shared-policy-instance,
       member-interface, interface";
    container input {
      description
        "A piece of QoS policy-map operational data for
         an interface";
      uses STATISTICS;
      uses POLICY-NAME-TABLE;
    }
  }

  grouping MEMBER-INTERFACE-TABLE {
    description
      "Common node of interface, nv-satellite-interface,
       shared-policy-instance";
    container member-interfaces {
      description
        "QoS policy-map member interface table";
      list member-interface {
        key "interface-name";
        description
          "QoS policy-map member interface statistics";
        leaf interface-name {
          type xr:Interface-name;
          description
            "Name of member interface";
        }
        uses SATELLITE-ID-TABLE;
        uses INPUT;
        uses NV-SATELLITE-INPUT;
        uses OUTPUT;
        uses NV-SATELLITE-OUTPUT;
      }
    }
  }

  grouping QOS-ASR9K-OPER-MEMBER-INTERFACE-TABLE {
    description
      "Common node of interface, nv-satellite-interface,
       shared-policy-instanceCommon node of
       bundle-output, bundle-input";
    container member-interfaces {
      description
        "QoS list of member interfaces";
      list member-interface {
        key "interface-name";
        description
          "QoS interface name";
        leaf interface-name {
          type xr:Interface-name;
          description
            "Memeber interface";
        }
        uses DETAILS;
      }
    }
  }

  grouping POLICY-NAME-TABLE {
    description
      "Common node of input, output";
    container policy-names {
      description
        "Policy-map statistics operational data for an
         interface";
      list policy-name {
        key "service-policy-name";
        description
          "Policy-map statistics operational data for an
           interface";
        leaf service-policy-name {
          type xr:Cisco-ios-xr-string;
          description
            "Name of the policy";
        }
        uses STATISTICS;
      }
    }
  }

  grouping NV-SATELLITE-OUTPUT {
    description
      "Common node of nv-satellite-interface,
       satellite-id, member-interface";
    container nv-satellite-output {
      description
        "A piece of Satellite QoS policy-map operational
         data for an interface";
      uses NV-SAT-STATISTICS;
    }
  }

  grouping OUTPUT {
    description
      "Common node of shared-policy-instance,
       member-interface, interface";
    container output {
      description
        "A piece of QoS policy-map operational data for
         an interface";
      uses STATISTICS;
      uses POLICY-NAME-TABLE;
    }
  }

  grouping NV-SAT-STATISTICS {
    description
      "Common node of nv-satellite-input,
       nv-satellite-output";
    container nv-sat-statistics {
      description
        "Policy-map statistics operational data for
         satellite interface";
      uses QOS-STATS;
    }
  }

  grouping SATELLITE-ID-TABLE {
    description
      "Common node of interface, member-interface";
    container satellite-ids {
      description
        "Satellite ID information";
      list satellite-id {
        key "nv-satellite-id";
        description
          "Satellite ID information";
        leaf nv-satellite-id {
          type uint32;
          description
            "Satellite ID";
        }
        uses NV-SATELLITE-INPUT;
        uses NV-SATELLITE-OUTPUT;
      }
    }
  }

  grouping PIN-INTERFACE-TABLE {
    description
      "Common node of pwhe-output, pwhe-input";
    container pin-interfaces {
      description
        "QoS list of member interfaces";
      list pin-interface {
        key "interface-name";
        description
          "QoS interface name";
        leaf interface-name {
          type xr:Interface-name;
          description
            "Memeber interface";
        }
        uses DETAILS;
      }
    }
  }

  container platform-qos {
    config false;
    description
      "QoS ASR9K platform operational data ";
    container nodes {
      description
        "List of nodes with platform specific QoS
         configuration";
      list node {
        key "node-name";
        description
          "Node with platform specific QoS configuration";
        container capability {
          description
            "QoS system capability";
          uses QOS-EA-CAPABILITY;
        }
        container pwhe-interfaces {
          description
            "QoS list of Pwhe interfaces";
          list pwhe-interface {
            key "interface-name";
            description
              "QoS interface name";
            container pwhe-output {
              description
                "QoS policy direction output";
              uses PIN-INTERFACE-TABLE;
            }
            container pwhe-input {
              description
                "QoS policy direction output";
              uses PIN-INTERFACE-TABLE;
            }
            leaf interface-name {
              type xr:Interface-name;
              description
                "Pwhe interface name";
            }
          }
        }
        container interfaces {
          description
            "QoS list of interfaces";
          list interface {
            key "interface-name";
            description
              "QoS interface name";
            container input {
              description
                "QoS policy direction ingress";
              uses DETAILS;
            }
            container output {
              description
                "QoS policy direction egress";
              uses DETAILS;
            }
            leaf interface-name {
              type xr:Interface-name;
              description
                "The name of the interface";
            }
          }
        }
        container bundle-interfaces {
          description
            "QoS list of bundle interfaces";
          list bundle-interface {
            key "interface-name";
            description
              "QoS interface name";
            container bundle-output {
              description
                "QoS policy direction output";
              uses QOS-ASR9K-OPER-MEMBER-INTERFACE-TABLE;
            }
            container bundle-input {
              description
                "QoS policy direction output";
              uses QOS-ASR9K-OPER-MEMBER-INTERFACE-TABLE;
            }
            leaf interface-name {
              type xr:Interface-name;
              description
                "Bundle interface name";
            }
          }
        }
        container performance {
          description
            "QoS system performance";
          uses QOS-EA-PERF-STATS;
        }
        leaf node-name {
          type xr:Node-id;
          description
            "Node name";
        }
      }
    }
  }
}
