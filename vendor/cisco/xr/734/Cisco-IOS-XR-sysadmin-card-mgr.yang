module Cisco-IOS-XR-sysadmin-card-mgr {
  namespace "http://www.cisco.com/ns/yang/Cisco-IOS-XR-sysadmin-card-mgr";
  prefix card_mgr;

  import Cisco-IOS-XR-sysadmin-show-trace {
    prefix show_trace;
  }
  import Cisco-IOS-XR-sysadmin-types {
    prefix calvados;
  }
  import cisco-semver {
    prefix semver;
  }

  organization
    "Cisco Systems Inc.";
  contact
    "Cisco Systems, Inc.
     Customer Service
     
     Postal: 170 West Tasman Drive
     San Jose, CA 95134
     
     Tel: +1 800 553-NETS
     
     E-mail: cs-yang@cisco.com";
  description
    "The 'card_mgr' module provides support for access to detail card HW information like power status, card state, inventory info, etc.
     
     Copyright (c) 2012-2020 by Cisco Systems, Inc.
     All rights reserved.";

  revision 2019-04-15 {
    description
      "Establish semantic version baseline.";
    semver:module-version "1.0.0";
  }
  revision 2018-04-09 {
    description
      "Required changes for ConfD 6.4.5";
  }
  revision 2017-05-01 {
    description
      "Namespace change to comply with Cisco guidelines on namespace";
  }
  revision 2015-03-29 {
    description
      "Initial revision.";
  }

  typedef startHexOffset {
    type string;
    description
      "Start address in Hex between 0x0 and 0x400";
  }

  typedef endHexOffset {
    type string;
    description
      "End address in Hex between 0x0 and 0x400";
  }

  typedef HexOffset {
    type string;
    description
      "Address in Hex between 0x0 and 0x400";
  }

  grouping card_mgr-group {
    description
      "Card Manager module information";
    container card_mgr {
      description
        "Card Manager module information";
      uses show_trace:traceable;
      uses inventory-group;
      uses event-hist-group;
      uses notif-hist-group;
      uses oir-hist-group;
      uses iofpga-group;
      uses bootldr-group;
    }
  }

  grouping inventory-group {
    description
      "Card inventory Group";
    container inventory {
      config false;
      description
        "Card inventory information";
      uses inventory-summary-group;
      uses inventory-detail-group;
    }
  }

  grouping inventory-summary-group {
    description
      "Card Inventory Summary Group";
    container summary {
      config false;
      description
        "Card inventory summary";
      list card_mgr_inv_summary {
        key "location";
        description
          "Card Manager Inventory Summary";
        leaf location {
          type string;
          mandatory true;
          description
            "Card location";
        }
        leaf card_mgr_inv_PID_string {
          type string;
          description
            "Card inventory PID";
        }
        leaf card_mgr_inv_slot_number {
          type uint32;
          description
            "Card inventory BP ID";
        }
        leaf card_mgr_inv_serial_number {
          type string;
          description
            "Card inventory Serial Number";
        }
        leaf card_mgr_inv_hw_version {
          type string;
          description
            "Card inventory HW Ver";
        }
        leaf card_mgr_inv_card_state {
          type string;
          description
            "Card inventory Card State";
        }
      }
    }
  }

  grouping inventory-detail-group {
    description
      "Card Manager Inventory Detail Group";
    container detail {
      config false;
      description
        "Card Manager inventory detail information";
      list card_mgr_inv_detail {
        key "location";
        description
          "Card location";
        leaf location {
          type string;
          description
            "Card location";
        }
        container card_mgr_inv_detail_list {
          description
            "card_mgr inventory detail list";
          leaf-list card_mgr_inv_detail_values {
            type string;
            description
              "card_mgr inventory detail value";
          }
        }
      }
    }
  }

  grouping event-hist-group {
    description
      "Card Event History Group";
    container event-history {
      config false;
      description
        "Card Event History";
      container brief {
        config false;
        description
          "Show all events in brief format";
        uses event-hist-group-brief;
      }
      container detail {
        config false;
        description
          "Show all events with additional detail information";
        uses event-hist-group-detail;
      }
    }
  }

  grouping event-hist-group-brief {
    description
      "Card Event History Group Brief";
    list location {
      key "location";
      description
        "Select Location";
      leaf location {
        type string;
        description
          "Location";
      }
      container card_event_hist_brief {
        description
          "Card Event History Brief";
        leaf-list card_event_hist_brief_values {
          type string;
          description
            "Card Event History Brief Values";
        }
      }
    }
  }

  grouping event-hist-group-detail {
    description
      "Card Event History Group Detail";
    list location {
      key "location";
      description
        "Select Location";
      leaf location {
        type string;
        description
          "Location";
      }
      container card_event_hist_detail {
        description
          "Card Event History Detail";
        leaf-list card_event_hist_detail_values {
          type string;
          description
            "Card Event History Detail Values";
        }
      }
    }
  }

  grouping notif-hist-group {
    description
      "Card State Notification History Group";
    container notif-history {
      config false;
      description
        "Card State Notification History";
      container brief {
        config false;
        description
          "Show all state notifications in brief format";
        uses notif-hist-group-brief;
      }
      container detail {
        config false;
        description
          "Show all state notifications with additional detail information";
        uses notif-hist-group-detail;
      }
    }
  }

  grouping notif-hist-group-brief {
    description
      "Notify Histroy Group Brief";
    list location {
      key "location";
      description
        "Select Location";
      leaf location {
        type string;
        description
          "Location";
      }
      container card_notif_hist_brief {
        description
          "Notify Histroy Brief";
        leaf-list card_notif_hist_brief_values {
          type string;
          description
            "Notify Histroy Brief Values";
        }
      }
    }
  }

  grouping notif-hist-group-detail {
    description
      "Notify Histroy Group Detail";
    list location {
      key "location";
      description
        "Select Location";
      leaf location {
        type string;
        description
          "Location";
      }
      container card_notif_hist_detail {
        description
          "Notify Histroy Detail";
        leaf-list card_notif_hist_detail_values {
          type string;
          description
            "Notify Histroy Detail Values";
        }
      }
    }
  }

  grouping oir-hist-group {
    description
      "Cards OIR History Group";
    container oir-history {
      config false;
      description
        "Cards OIR History";
      list rack {
        key "rack";
        description
          "Select Rack";
        leaf rack {
          type string;
          description
            "Rack";
        }
        container card_oir_hist {
          description
            "Cards OIR History";
          leaf-list card_oir_events {
            type string;
            description
              "Cards OIR Events";
          }
        }
      }
    }
  }

  grouping iofpga-group {
    description
      "IOFPGA Information Group";
    container iofpga {
      config false;
      description
        "IOFPGA information";
      uses iofpga-register-group;
      uses iofpga-flash-group;
    }
  }

  grouping iofpga-register-group {
    description
      "IOFPGA Register Information Group";
    container register {
      config false;
      description
        "IOFPGA Register information";
      uses cpu-register-group;
      uses mb-register-group;
      uses dc-register-group;
    }
  }

  grouping cpu-register-group {
    description
      "CPU-IOFPGA Register Information Group";
    container cpu {
      config false;
      description
        "CPU-IOFPGA Register information";
      list register_location {
        key "register_location";
        config false;
        description
          "Card location";
        leaf register_location {
          type string;
          description
            "Location";
        }
        uses iofpga-block-number-group;
        uses iofpga-offset-group;
        uses iofpga-address-group;
      }
    }
  }

  grouping mb-register-group {
    description
      "Mother Board(MB)-IOFPGA Register Information Group";
    container mb {
      config false;
      description
        "Mother Board(MB)-IOFPGA Register information";
      list register_location {
        key "register_location";
        config false;
        description
          "Card location";
        leaf register_location {
          type string;
          description
            "Location";
        }
        uses iofpga-block-number-group;
        uses iofpga-offset-group;
        uses iofpga-address-group;
      }
    }
  }

  grouping dc-register-group {
    description
      "Daughter Card(DC)-IOFPGA Register Information Group";
    container dc {
      config false;
      description
        "Daughter Card(DC)-IOFPGA Register information";
      list register_location {
        key "register_location";
        config false;
        description
          "Card location";
        leaf register_location {
          type string;
          description
            "Location";
        }
        uses iofpga-block-number-group;
        uses iofpga-offset-group;
        uses iofpga-address-group;
      }
    }
  }

  grouping iofpga-block-number-group {
    description
      "IOFPGA Block Number Group";
    list iofpga_block_number {
      key "iofpga_block_num";
      config false;
      description
        "Register Group ID";
      leaf iofpga_block_num {
        type uint32;
        description
          "GP";
      }
      leaf block_location {
        type string;
        description
          "Location";
      }
      leaf iofpga_block_nm {
        type string;
        description
          "Block NM";
      }
      list iofpga_register_number {
        key "index";
        description
          "Register Number";
        leaf index {
          type uint32;
          description
            "Register IDX";
        }
        leaf iofpga_register_name {
          type string;
          description
            "Register Name";
        }
        list iofpga_data {
          description
            "IOFPGA DATA";
          leaf name {
            type string;
            description
              "Register Name";
          }
          leaf offset {
            type uint32;
            description
              "Register Offset";
          }
          leaf value {
            type uint32;
            description
              "Register Value";
          }
        }
      }
    }
  }

  grouping iofpga-offset-group {
    description
      "IOFPGA Offset Group";
    list iofpga_offset {
      key "hex_offset";
      config false;
      description
        "Register Offset Address";
      leaf hex_offset {
        type HexOffset;
        description
          "Register Hex Offset";
      }
      list iofpga_reg_offset_data {
        description
          "Register Offset Data";
        leaf iofpga_reg_off_addr {
          type uint32;
          description
            "Register Offset Address";
        }
        leaf reg_off_value {
          type string;
          description
            "Register Offset Value";
        }
      }
    }
  }

  grouping iofpga-address-group {
    description
      "IOFPGA Address Group";
    list iofpga_address {
      key "start_hex_addr end_hex_addr";
      config false;
      description
        "Register Range to fetch data";
      leaf start_hex_addr {
        type startHexOffset;
        description
          "Register Start Hex Address";
      }
      leaf end_hex_addr {
        type endHexOffset;
        description
          "Register End Hex Address";
      }
      list iofpga_reg_range_addr_list {
        key "iofpga_reg_range_addr";
        description
          "Register Range Hex Address";
        leaf iofpga_reg_range_addr {
          type uint32;
          description
            "Register Offset";
        }
        list iofpga_reg_data {
          description
            "Register Data";
          leaf iofpga_reg_addr {
            type uint32;
            description
              "Register Address";
          }
          leaf reg_value {
            type string;
            description
              "Register Value";
          }
        }
      }
    }
  }

  grouping iofpga-flash-group {
    description
      "IOFPGA SPI Flash Group";
    container flash {
      config false;
      description
        "IOFPGA SPI flash information";
      uses iofpga-flash-info-group;
      uses iofpga-flash-status-group;
    }
  }

  grouping iofpga-flash-info-group {
    description
      "IOFPGA SPI Flash Information Group";
    container info {
      config false;
      description
        "IOFPGA SPI flash content";
      list flash_location {
        key "flash_location";
        description
          "Select Location";
        leaf flash_location {
          type calvados:location-id;
          description
            "IOFPGA Flash Location";
        }
        container iofpga_flash_info {
          description
            "IOFPGA Flash Information";
          leaf-list iofpga_flash_info_values {
            type string;
            description
              "IOFPGA Flash Information Values";
          }
        }
      }
    }
  }

  grouping iofpga-flash-status-group {
    description
      "IOFPGA SPI Flash Status Group";
    container status {
      config false;
      description
        "IOFPGA SPI flash status";
      list flash_location {
        key "flash_location";
        description
          "IOFPGA Flash Location";
        leaf flash_location {
          type calvados:location-id;
          description
            "IOFPGA Flash Location ID";
        }
        container iofpga_flash_status {
          description
            "IOFPGA Flash Status";
          leaf-list iofpga_flash_status_values {
            type string;
            description
              "IOFPGA Flash Status Values";
          }
        }
      }
    }
  }

  grouping bootldr-group {
    description
      "Bootloader Group";
    container bootloader {
      config false;
      description
        "Bootloader information";
      uses bootldr-flash-group;
    }
  }

  grouping bootldr-flash-group {
    description
      "Bootloader SPI Flash Group";
    container flash {
      config false;
      description
        "Bootloader SPI flash information";
      uses bootldr-flash-info-group;
      uses bootldr-flash-status-group;
    }
  }

  grouping bootldr-flash-info-group {
    description
      "Bootloader SPI Flash Information Group";
    container info {
      config false;
      description
        "Bootloader SPI flash content";
      list flash_location {
        key "flash_location";
        description
          "Select Location";
        leaf flash_location {
          type calvados:location-id;
          description
            "Location ID";
        }
        container bootldr_flash_info {
          description
            "Bootloader Flash Information";
          leaf-list bootldr_flash_info_values {
            type string;
            description
              "Bootloader Flash Information Values";
          }
        }
      }
    }
  }

  grouping bootldr-flash-status-group {
    description
      "Bootloader SPI Flash Group";
    container status {
      config false;
      description
        "Bootloader SPI flash status";
      list flash_location {
        key "flash_location";
        description
          "Select Location";
        leaf flash_location {
          type calvados:location-id;
          description
            "Location ID";
        }
        container bootldr_flash_status {
          description
            "Bootloader flash status";
          leaf-list bootldr_flash_status_values {
            type string;
            description
              "Bootloader Flash Status Values";
          }
        }
      }
    }
  }
}
