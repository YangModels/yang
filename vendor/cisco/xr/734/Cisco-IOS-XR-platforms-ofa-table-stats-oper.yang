module Cisco-IOS-XR-platforms-ofa-table-stats-oper {
  namespace "http://cisco.com/ns/yang/Cisco-IOS-XR-platforms-ofa-table-stats-oper";
  prefix platforms-ofa-table-stats-oper;

  import Cisco-IOS-XR-types {
    prefix xr;
  }
  import cisco-semver {
    prefix semver;
  }
  include Cisco-IOS-XR-platforms-ofa-table-stats-oper-sub1 {
    revision-date 2021-11-04;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR platforms-ofa-table-stats package operational data.
     
     This module contains definitions
     for the following management objects:
       ofa: OFA Data
     
     Copyright (c) 2013-2021 by Cisco Systems, Inc.
     All rights reserved.";

  revision 2021-11-04 {
    description
      "Declaring NBC due to enum ordering changes inside the OFA table enum IosSetYangSchemaRev Cisco-IOS-XR-platforms-ofa-table-stats-oper
       2021-07-07
         Added Quaratine DB counters to ofa table stats";
    semver:module-version "3.0.0";
  }
  revision 2020-06-19 {
    description
      "Bwalk Error Counters";
    semver:module-version "2.0.0";
  }
  revision 2019-12-14 {
    description
      "Added the Yang Model for ofa sw resources";
    semver:module-version "1.1.0";
  }
  revision 2019-06-06 {
    description
      "Added the Yang Model for ofa sw resources";
    semver:module-version "1.0.0";
  }
  revision 2019-04-05 {
    description
      "Establish semantic version baseline.";
  }
  revision 2015-11-09 {
    description
      "IOS XR 6.0 revision.";
  }

  typedef Ofa-table {
    type enumeration {
      enum "test-if" {
        value 0;
        description
          "test if";
      }
      enum "test-if-with-create-reject" {
        value 1;
        description
          "testifwithcreatereject";
      }
      enum "test-nh" {
        value 2;
        description
          "test nh";
      }
      enum "test-global-discard" {
        value 3;
        description
          "testglobaldiscard";
      }
      enum "test-nhg" {
        value 4;
        description
          "test nhg";
      }
      enum "test-rt" {
        value 5;
        description
          "test rt";
      }
      enum "test-dynhg" {
        value 6;
        description
          "testdynhg";
      }
      enum "test-async-nhg" {
        value 7;
        description
          "testasyncnhg";
      }
      enum "test-async-nhgstats" {
        value 8;
        description
          "testasyncnhgstats";
      }
      enum "test-ip-punt-policy" {
        value 9;
        description
          "test ippuntpolicy";
      }
      enum "test-punt" {
        value 10;
        description
          "test punt";
      }
      enum "test-punt-policy-stats" {
        value 11;
        description
          "testpuntpolicystats";
      }
      enum "test-async-update" {
        value 12;
        description
          "testasyncupdate";
      }
      enum "test-async-barrier-with-knob" {
        value 13;
        description
          "testasyncbarrierwithknob";
      }
      enum "test-async-barrier-with-outknob" {
        value 14;
        description
          "testasyncbarrierwithoutknob";
      }
      enum "test-o-fast-ats" {
        value 15;
        description
          "testofastats";
      }
      enum "test-o-fast-ats1" {
        value 16;
        description
          "testofastats1";
      }
      enum "test-o-fast-ats2" {
        value 17;
        description
          "testofastats2";
      }
      enum "test-dpastats1" {
        value 18;
        description
          "testdpastats1";
      }
      enum "test-dpastats2" {
        value 19;
        description
          "testdpastats2";
      }
      enum "test-srvgrid" {
        value 20;
        description
          "testsrvgrid";
      }
      enum "test-ddel-q" {
        value 21;
        description
          "test ddel q";
      }
      enum "test-mco-list" {
        value 22;
        description
          "testmcolist";
      }
      enum "test-syncmco-list" {
        value 23;
        description
          "testsyncmcolist";
      }
      enum "test-syncmctblstats" {
        value 24;
        description
          "testsyncmctblstats";
      }
      enum "test-dddp" {
        value 25;
        description
          "testdddp";
      }
      enum "test-grid1" {
        value 26;
        description
          "testgrid1";
      }
      enum "sys" {
        value 27;
        description
          "sys";
      }
      enum "npu" {
        value 28;
        description
          "npu";
      }
      enum "npu-host-port" {
        value 29;
        description
          "npuhostport";
      }
      enum "npuhwid" {
        value 30;
        description
          "npuhwid";
      }
      enum "optics-port" {
        value 31;
        description
          "opticsport";
      }
      enum "gi-port" {
        value 32;
        description
          "giport";
      }
      enum "l1-port" {
        value 33;
        description
          "l1port";
      }
      enum "mac-port" {
        value 34;
        description
          "macport";
      }
      enum "l2-port" {
        value 35;
        description
          "l2port";
      }
      enum "eth-port" {
        value 36;
        description
          "ethport";
      }
      enum "eth-ports-tats" {
        value 37;
        description
          "ethportstats";
      }
      enum "l2intf" {
        value 38;
        description
          "l2intf";
      }
      enum "l2if" {
        value 39;
        description
          "l2if";
      }
      enum "mplspwe-port" {
        value 40;
        description
          "mplspweport";
      }
      enum "mplspwe-port-o-list" {
        value 41;
        description
          "mplspweport olist";
      }
      enum "mhpwe-port" {
        value 42;
        description
          "mhpweport";
      }
      enum "l2xc" {
        value 43;
        description
          "l2xc";
      }
      enum "l2vpnstats" {
        value 44;
        description
          "l2vpnstats";
      }
      enum "l1-ports-tats" {
        value 45;
        description
          "l1portstats";
      }
      enum "mac-ports-tats" {
        value 46;
        description
          "macportstats";
      }
      enum "l3intf" {
        value 47;
        description
          "l3intf";
      }
      enum "l3if" {
        value 48;
        description
          "l3if";
      }
      enum "l3intfrxstats" {
        value 49;
        description
          "l3intfrxstats";
      }
      enum "ip-route" {
        value 50;
        description
          "iproute";
      }
      enum "ip6-route" {
        value 51;
        description
          "ip6route";
      }
      enum "punt-policy-stats" {
        value 52;
        description
          "puntpolicystats";
      }
      enum "lpts-policy-stats" {
        value 53;
        description
          "lptspolicystats";
      }
      enum "tep" {
        value 54;
        description
          "tep";
      }
      enum "ip-punt-policy" {
        value 55;
        description
          "ippuntpolicy";
      }
      enum "ip6-punt-policy" {
        value 56;
        description
          "ip6puntpolicy";
      }
      enum "iplpts-policy" {
        value 57;
        description
          "iplptspolicy";
      }
      enum "ip6lpts-policy" {
        value 58;
        description
          "ip6lptspolicy";
      }
      enum "isis-punt-policy" {
        value 59;
        description
          "isispuntpolicy";
      }
      enum "isislpts-policy" {
        value 60;
        description
          "isislptspolicy";
      }
      enum "nh-group" {
        value 61;
        description
          "nhgroup";
      }
      enum "ipnh-group" {
        value 62;
        description
          "ipnhgroup";
      }
      enum "ip6nh-group" {
        value 63;
        description
          "ip6nhgroup";
      }
      enum "ipnh" {
        value 64;
        description
          "ipnh";
      }
      enum "ip6nh" {
        value 65;
        description
          "ip6nh";
      }
      enum "ipvrf" {
        value 66;
        description
          "ipvrf";
      }
      enum "vrfid" {
        value 67;
        description
          "vrfid";
      }
      enum "mplsnh" {
        value 68;
        description
          "mplsnh";
      }
      enum "lspnh" {
        value 69;
        description
          "lspnh";
      }
      enum "mpls-label" {
        value 70;
        description
          "mplslabel";
      }
      enum "punt" {
        value 71;
        description
          "punt";
      }
      enum "punt-police-r" {
        value 72;
        description
          "puntpolicer";
      }
      enum "lpts-police-r" {
        value 73;
        description
          "lptspolicer";
      }
      enum "punt-lpts-police-r" {
        value 74;
        description
          "puntlptspolicer";
      }
      enum "punt-stats" {
        value 75;
        description
          "puntstats";
      }
      enum "tm-port" {
        value 76;
        description
          "tmport";
      }
      enum "span-session" {
        value 77;
        description
          "spansession";
      }
      enum "police-rstats" {
        value 78;
        description
          "policerstats";
      }
      enum "tm-ports-tats" {
        value 79;
        description
          "tmportstats";
      }
      enum "voq-grp" {
        value 80;
        description
          "voqgrp";
      }
      enum "l3intftxstats" {
        value 81;
        description
          "l3intftxstats";
      }
      enum "mplstetxstats" {
        value 82;
        description
          "mplstetxstats";
      }
      enum "mplslblstats" {
        value 83;
        description
          "mplslblstats";
      }
      enum "police-r" {
        value 84;
        description
          "policer";
      }
      enum "l2intfrxstats" {
        value 85;
        description
          "l2intfrxstats";
      }
      enum "l2intftxstats" {
        value 86;
        description
          "l2intftxstats";
      }
      enum "pbr-tt-ipv4" {
        value 87;
        description
          "pbr tt ipv4";
      }
      enum "pbr-tt-ipv6" {
        value 88;
        description
          "pbr tt ipv6";
      }
      enum "bfdhwoff" {
        value 89;
        description
          "bfdhwoff";
      }
      enum "bfdoff" {
        value 90;
        description
          "bfdoff";
      }
      enum "bfdoffstats" {
        value 91;
        description
          "bfdoffstats";
      }
      enum "global" {
        value 92;
        description
          "global";
      }
      enum "lag-port" {
        value 93;
        description
          "lagport";
      }
      enum "agg-port" {
        value 94;
        description
          "aggport";
      }
      enum "agg-member" {
        value 95;
        description
          "aggmember";
      }
      enum "qos-profile" {
        value 96;
        description
          "qosprofile";
      }
      enum "acl-profile" {
        value 97;
        description
          "acl profile";
      }
      enum "tmrate-profile" {
        value 98;
        description
          "tmrateprofile";
      }
      enum "ipacl" {
        value 99;
        description
          "ipacl";
      }
      enum "ip6acl" {
        value 100;
        description
          "ip6acl";
      }
      enum "sched-tree" {
        value 101;
        description
          "schedtree";
      }
      enum "tmcos" {
        value 102;
        description
          "tmcos";
      }
      enum "statsagg" {
        value 103;
        description
          "statsagg";
      }
      enum "nhprotect" {
        value 104;
        description
          "nhprotect";
      }
      enum "sampler" {
        value 105;
        description
          "sampler";
      }
      enum "l2qos" {
        value 106;
        description
          "l2qos";
      }
      enum "peer-qos" {
        value 107;
        description
          "peerqos";
      }
      enum "ipqos" {
        value 108;
        description
          "ipqos";
      }
      enum "ip6qos" {
        value 109;
        description
          "ip6qos";
      }
      enum "mplsqos" {
        value 110;
        description
          "mplsqos";
      }
      enum "qos-group" {
        value 111;
        description
          "qosgroup";
      }
      enum "qosid" {
        value 112;
        description
          "qosid";
      }
      enum "extlif" {
        value 113;
        description
          "extlif";
      }
      enum "elif" {
        value 114;
        description
          "elif";
      }
      enum "ingaclstats" {
        value 115;
        description
          "ingaclstats";
      }
      enum "egraclstats" {
        value 116;
        description
          "egraclstats";
      }
      enum "edpl" {
        value 117;
        description
          "edpl";
      }
      enum "l2protect" {
        value 118;
        description
          "l2protect";
      }
      enum "sat" {
        value 119;
        description
          "sat";
      }
      enum "satstats" {
        value 120;
        description
          "satstats";
      }
      enum "cfmoam-profile-def" {
        value 121;
        description
          "cfmoamprofiledef";
      }
      enum "cfmmaid" {
        value 122;
        description
          "cfmmaid";
      }
      enum "cfmdefmps" {
        value 123;
        description
          "cfmdefmps";
      }
      enum "cfmofflmep" {
        value 124;
        description
          "cfmofflmep";
      }
      enum "cfmoffrmep" {
        value 125;
        description
          "cfmoffrmep";
      }
      enum "cfmnonoff" {
        value 126;
        description
          "cfmnonoff";
      }
      enum "cfmhwoffrxstats" {
        value 127;
        description
          "cfmhwoffrxstats";
      }
      enum "ipmc-route" {
        value 128;
        description
          "ipmcroute";
      }
      enum "l2ipmc-route" {
        value 129;
        description
          "l2ipmcroute";
      }
      enum "ipmco-list" {
        value 130;
        description
          "ipmcolist";
      }
      enum "l2mco-list" {
        value 131;
        description
          "l2mcolist";
      }
      enum "meshmc" {
        value 132;
        description
          "meshmc";
      }
      enum "l2-bridge" {
        value 133;
        description
          "l2bridge";
      }
      enum "l2-bridge-port" {
        value 134;
        description
          "l2bridgeport";
      }
      enum "l2-bridge-vni" {
        value 135;
        description
          "l2bridgevni";
      }
      enum "l2-bridge-vnidecap" {
        value 136;
        description
          "l2bridgevnidecap";
      }
      enum "l2-bridge-mac" {
        value 137;
        description
          "l2bridgemac";
      }
      enum "l2brmac" {
        value 138;
        description
          "l2brmac";
      }
      enum "ip-tunnel-decap" {
        value 139;
        description
          "iptunneldecap";
      }
      enum "l2vlan-range" {
        value 140;
        description
          "l2vlanrange";
      }
      enum "ip-tunnel-encap" {
        value 141;
        description
          "iptunnelencap";
      }
      enum "iptnl-encap" {
        value 142;
        description
          "iptnlencap";
      }
      enum "iptnldecap" {
        value 143;
        description
          "iptnldecap";
      }
      enum "iptnlnh" {
        value 144;
        description
          "iptnlnh";
      }
      enum "rawget" {
        value 145;
        description
          "rawget";
      }
      enum "ip6mc-route" {
        value 146;
        description
          "ip6mcroute";
      }
      enum "ip6mc-comp-grp" {
        value 147;
        description
          "ip6mc comp grp";
      }
      enum "l2evpnact-remote-peer-id" {
        value 148;
        description
          "l2evpnactremotepeerid";
      }
      enum "l2evpnact-local-shl" {
        value 149;
        description
          "l2evpnactlocalshl";
      }
      enum "l2evpnact-remote-shl" {
        value 150;
        description
          "l2evpnactremoteshl";
      }
      enum "evpn-iml-range" {
        value 151;
        description
          "evpn imlrange";
      }
      enum "l2-bridge-o-list" {
        value 152;
        description
          "l2bridgeolist";
      }
      enum "l2-bridge-vnio-list" {
        value 153;
        description
          "l2bridgevniolist";
      }
      enum "l2acl" {
        value 154;
        description
          "l2acl";
      }
      enum "l2evpn-nh" {
        value 155;
        description
          "l2evpn nh";
      }
      enum "l2-bridge-port-sc" {
        value 156;
        description
          "l2bridgeport sc";
      }
      enum "l3intfmctxstats" {
        value 157;
        description
          "l3intfmctxstats";
      }
      enum "tidl-sample" {
        value 158;
        description
          "tidl sample";
      }
      enum "tidl-ref-sample" {
        value 159;
        description
          "tidl ref sample";
      }
      enum "ipacl-prefix" {
        value 160;
        description
          "ipaclprefix";
      }
      enum "ip6acl-prefix" {
        value 161;
        description
          "ip6aclprefix";
      }
      enum "ipacl-port" {
        value 162;
        description
          "ipaclport";
      }
      enum "scaleacl" {
        value 163;
        description
          "scaleacl";
      }
      enum "ipmcf-hop" {
        value 164;
        description
          "ipmcfhop";
      }
      enum "bundle-swoff" {
        value 165;
        description
          "bundle swoff";
      }
      enum "mcidswoff" {
        value 166;
        description
          "mcidswoff";
      }
      enum "dest-map" {
        value 167;
        description
          "destmap";
      }
      enum "l2-bridge-port-pw" {
        value 168;
        description
          "l2bridgeport pw";
      }
      enum "l2evpnact-local-shlstats" {
        value 169;
        description
          "l2evpnactlocalshlstats";
      }
      enum "test-hidden" {
        value 170;
        description
          "testhidden";
      }
      enum "test-local" {
        value 171;
        description
          "testlocal";
      }
      enum "test-repeated" {
        value 172;
        description
          "testrepeated";
      }
      enum "limd" {
        value 173;
        description
          "limd";
      }
      enum "litap" {
        value 174;
        description
          "litap";
      }
      enum "l3ifstats" {
        value 175;
        description
          "l3ifstats";
      }
      enum "mplsstats" {
        value 176;
        description
          "mplsstats";
      }
      enum "sr-test-ats" {
        value 177;
        description
          "srtestats";
      }
      enum "srteifstats" {
        value 178;
        description
          "srteifstats";
      }
      enum "exception-nh" {
        value 179;
        description
          "exceptionnh";
      }
      enum "srv6-global" {
        value 180;
        description
          "srv6 global";
      }
      enum "srv6sid" {
        value 181;
        description
          "srv6sid";
      }
      enum "srv6nh" {
        value 182;
        description
          "srv6nh";
      }
      enum "sr6sid" {
        value 183;
        description
          "sr6sid";
      }
      enum "sr6nh" {
        value 184;
        description
          "sr6nh";
      }
      enum "redirect-vrf" {
        value 185;
        description
          "redirectvrf";
      }
      enum "test-xtf" {
        value 186;
        description
          "test xtf";
      }
      enum "ippbr" {
        value 187;
        description
          "ippbr";
      }
      enum "ippbrstats" {
        value 188;
        description
          "ippbrstats";
      }
      enum "mpls-mdt-bud" {
        value 189;
        description
          "mplsmdtbud";
      }
      enum "mpls-label-rxstats" {
        value 190;
        description
          "mplslabelrxstats";
      }
      enum "l2mac-static" {
        value 191;
        description
          "l2macstatic";
      }
      enum "dot1x" {
        value 192;
        description
          "dot1x";
      }
      enum "iprte" {
        value 193;
        description
          "iprte";
      }
      enum "ip6rte" {
        value 194;
        description
          "ip6rte";
      }
      enum "llnh" {
        value 195;
        description
          "llnh";
      }
      enum "urpfintf" {
        value 196;
        description
          "urpfintf";
      }
      enum "ipmcrxstats" {
        value 197;
        description
          "ipmcrxstats";
      }
      enum "mplsrte" {
        value 198;
        description
          "mplsrte";
      }
      enum "protectnh" {
        value 199;
        description
          "protectnh";
      }
      enum "ipllnh" {
        value 200;
        description
          "ipllnh";
      }
      enum "ip6llnh" {
        value 201;
        description
          "ip6llnh";
      }
      enum "macnh" {
        value 202;
        description
          "macnh";
      }
      enum "qos-match-stats" {
        value 203;
        description
          "qosmatchstats";
      }
      enum "ofal2xc" {
        value 204;
        description
          "ofal2xc";
      }
      enum "ofamplspwe-port" {
        value 205;
        description
          "ofamplspweport";
      }
      enum "pwenh" {
        value 206;
        description
          "pwenh";
      }
      enum "pwenh-group" {
        value 207;
        description
          "pwenhgroup";
      }
      enum "ipmcrte" {
        value 208;
        description
          "ipmcrte";
      }
      enum "ip6mcrte" {
        value 209;
        description
          "ip6mcrte";
      }
      enum "ipmcr-test-ats" {
        value 210;
        description
          "ipmcrtestats";
      }
      enum "ip6mcr-test-ats" {
        value 211;
        description
          "ip6mcrtestats";
      }
      enum "transport-nh" {
        value 212;
        description
          "transportnh";
      }
      enum "port-range" {
        value 213;
        description
          "portrange";
      }
      enum "bvi-port" {
        value 214;
        description
          "bviport";
      }
      enum "mcid" {
        value 215;
        description
          "mcid";
      }
      enum "mc-gid" {
        value 216;
        description
          "mc gid";
      }
      enum "mcgidole" {
        value 217;
        description
          "mcgidole";
      }
      enum "mco-list" {
        value 218;
        description
          "mcolist";
      }
      enum "test-da" {
        value 219;
        description
          "testda";
      }
      enum "test-ca" {
        value 220;
        description
          "testca";
      }
      enum "test-ba" {
        value 221;
        description
          "testba";
      }
      enum "test-aa" {
        value 222;
        description
          "testaa";
      }
      enum "test-async-aa" {
        value 223;
        description
          "testasyncaa";
      }
      enum "test-reliable-notif" {
        value 224;
        description
          "testreliablenotif";
      }
      enum "test-de" {
        value 225;
        description
          "testde";
      }
      enum "test-ce" {
        value 226;
        description
          "testce";
      }
      enum "test-be" {
        value 227;
        description
          "testbe";
      }
      enum "test-db" {
        value 228;
        description
          "testdb";
      }
      enum "test-cb" {
        value 229;
        description
          "testcb";
      }
      enum "test-bb" {
        value 230;
        description
          "testbb";
      }
      enum "test-df" {
        value 231;
        description
          "testdf";
      }
      enum "test-cf" {
        value 232;
        description
          "testcf";
      }
      enum "test-bf" {
        value 233;
        description
          "testbf";
      }
      enum "test-af" {
        value 234;
        description
          "testaf";
      }
      enum "test-cz" {
        value 235;
        description
          "testcz";
      }
      enum "test-ax" {
        value 236;
        description
          "testax";
      }
      enum "test-ay" {
        value 237;
        description
          "testay";
      }
      enum "test-ef" {
        value 238;
        description
          "testef";
      }
      enum "test-ff" {
        value 239;
        description
          "testff";
      }
      enum "test-gf" {
        value 240;
        description
          "testgf";
      }
      enum "test-eastwestscheduling" {
        value 241;
        description
          "testeastwestscheduling";
      }
      enum "test-transnh" {
        value 242;
        description
          "testtransnh";
      }
      enum "test-eth-port" {
        value 243;
        description
          "testethport";
      }
      enum "test-eastwest" {
        value 244;
        description
          "testeastwest";
      }
      enum "test-ifstats" {
        value 245;
        description
          "testifstats";
      }
      enum "test-async-oor" {
        value 246;
        description
          "testasyncoor";
      }
      enum "test-syncmcas-too-r" {
        value 247;
        description
          "testsyncmcastoor";
      }
      enum "test-syncdeviceoor" {
        value 248;
        description
          "testsyncdeviceoor";
      }
      enum "test-az" {
        value 249;
        description
          "testaz";
      }
      enum "test-by" {
        value 250;
        description
          "testby";
      }
      enum "police-r-group" {
        value 251;
        description
          "policergroup";
      }
      enum "meter-profile" {
        value 252;
        description
          "meterprofile";
      }
      enum "acl-mirror" {
        value 253;
        description
          "acl mirror";
      }
      enum "meter-action-profile" {
        value 254;
        description
          "meteractionprofile";
      }
      enum "voqrm" {
        value 255;
        description
          "voqrm";
      }
      enum "port-wfq-profile" {
        value 256;
        description
          "portwfqprofile";
      }
      enum "rpfif" {
        value 257;
        description
          "rpfif";
      }
      enum "brmac" {
        value 258;
        description
          "brmac";
      }
      enum "br-static-mac" {
        value 259;
        description
          "brstaticmac";
      }
      enum "xconnect" {
        value 260;
        description
          "xconnect";
      }
      enum "bridge" {
        value 261;
        description
          "bridge";
      }
      enum "pwe-port" {
        value 262;
        description
          "pweport";
      }
      enum "olist" {
        value 263;
        description
          "olist";
      }
      enum "lsmprotect" {
        value 264;
        description
          "lsmprotect";
      }
      enum "monitor-session" {
        value 265;
        description
          "monitorsession";
      }
      enum "monitor-session-stats" {
        value 266;
        description
          "monitorsessionstats";
      }
      enum "mplsmcast" {
        value 267;
        description
          "mplsmcast";
      }
      enum "l2ifstats" {
        value 268;
        description
          "l2ifstats";
      }
      enum "imlnh" {
        value 269;
        description
          "imlnh";
      }
      enum "evinh" {
        value 270;
        description
          "evinh";
      }
      enum "member-list" {
        value 271;
        description
          "memberlist";
      }
      enum "test-oor" {
        value 272;
        description
          "testoor";
      }
      enum "hwre-source-s-oor" {
        value 273;
        description
          "hwresources oor";
      }
      enum "qospfcstats" {
        value 274;
        description
          "qospfcstats";
      }
      enum "pfctc" {
        value 275;
        description
          "pfctc";
      }
      enum "pfc-watchdog" {
        value 276;
        description
          "pfc watchdog";
      }
      enum "qos-shared" {
        value 277;
        description
          "qosshared";
      }
      enum "ecntxstats" {
        value 278;
        description
          "ecntxstats";
      }
      enum "tm-remote-credit" {
        value 279;
        description
          "tmremotecredit";
      }
      enum "ipmcole" {
        value 280;
        description
          "ipmcole";
      }
      enum "ip6mcole" {
        value 281;
        description
          "ip6mcole";
      }
      enum "pbr" {
        value 282;
        description
          "pbr";
      }
      enum "pbrstats" {
        value 283;
        description
          "pbrstats";
      }
      enum "punt-stormcontrol" {
        value 284;
        description
          "puntstormcontrol";
      }
      enum "ip6mcrxstats" {
        value 285;
        description
          "ip6mcrxstats";
      }
      enum "ipmctxintf" {
        value 286;
        description
          "ipmctxintf";
      }
      enum "ipmc-mdt-encap" {
        value 287;
        description
          "ipmcmdtencap";
      }
      enum "ipmc-mdt-decap" {
        value 288;
        description
          "ipmcmdtdecap";
      }
      enum "op2tap" {
        value 289;
        description
          "op2tap";
      }
      enum "mplsole" {
        value 290;
        description
          "mplsole";
      }
      enum "syncrpc" {
        value 291;
        description
          "syncrpc";
      }
      enum "tnlstats" {
        value 292;
        description
          "tnlstats";
      }
      enum "l2dhcp" {
        value 293;
        description
          "l2dhcp";
      }
      enum "pbrsbf" {
        value 294;
        description
          "pbrsbf";
      }
      enum "statsrpc" {
        value 295;
        description
          "statsrpc";
      }
      enum "oglpts" {
        value 296;
        description
          "oglpts";
      }
      enum "oglpts-prefix" {
        value 297;
        description
          "oglptsprefix";
      }
      enum "og6lpts-prefix" {
        value 298;
        description
          "og6lptsprefix";
      }
      enum "stormcontrol" {
        value 299;
        description
          "stormcontrol";
      }
      enum "acl-police-r" {
        value 300;
        description
          "aclpolicer";
      }
      enum "acl-police-rstats" {
        value 301;
        description
          "aclpolicerstats";
      }
      enum "aclkey-profile" {
        value 302;
        description
          "aclkeyprofile";
      }
      enum "acl-action-profile" {
        value 303;
        description
          "aclactionprofile";
      }
      enum "macllnh" {
        value 304;
        description
          "macllnh";
      }
      enum "dot1x-mac" {
        value 305;
        description
          "dot1x mac";
      }
    }
    description
      "Ofa table";
  }

  container ofa {
    config false;
    description
      "OFA Data";
    container stats {
      description
        "OFA Stats Data";
      container nodes {
        description
          "OFA data for available nodes";
        list node {
          key "node-name";
          description
            "OFA operational data for a particular node";
          container table-datas {
            description
              "OFA Resources table";
            list table-data {
              key "resource";
              description
                "OFA Resources table";
              leaf resource {
                type Ofa-table;
                description
                  "Resource type";
              }
              uses OFA-NPD-SYSDB-TABLE-RESOURCE;
            }
          }
          leaf node-name {
            type xr:Node-id;
            description
              "Node ID";
          }
        }
      }
    }
  }
}
