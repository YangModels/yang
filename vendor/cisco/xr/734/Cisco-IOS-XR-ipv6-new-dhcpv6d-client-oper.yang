module Cisco-IOS-XR-ipv6-new-dhcpv6d-client-oper {
  namespace "http://cisco.com/ns/yang/Cisco-IOS-XR-ipv6-new-dhcpv6d-client-oper";
  prefix ipv6-new-dhcpv6d-client-oper;

  import Cisco-IOS-XR-types {
    prefix xr;
  }
  import cisco-semver {
    prefix semver;
  }
  include Cisco-IOS-XR-ipv6-new-dhcpv6d-client-oper-sub1 {
    revision-date 2020-09-17;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ipv6-new-dhcpv6d-client package operational data.
     
     This module contains definitions
     for the following management objects:
       dhcpv6-client: DHCPv6 client operational data
     
     Copyright (c) 2013-2020 by Cisco Systems, Inc.
     All rights reserved.";

  revision 2020-09-17 {
    description
      "Added prefix-len option for dhcpv6 client";
    semver:module-version "1.0.0";
  }
  revision 2019-11-16 {
    description
      "Added Support for DHCPv6 Client.";
  }
  revision 2019-04-05 {
    description
      "Establish semantic version baseline.";
  }
  revision 2015-11-09 {
    description
      "IOS XR 6.0 revision.";
  }

  container dhcpv6-client {
    config false;
    description
      "DHCPv6 client operational data";
    container interfaces {
      description
        "DHCPv6 client particular interface name";
      list interface {
        key "interface-name";
        description
          "Interface name";
        container ipv6-binding {
          description
            "Single DHCPv6 client binding";
          uses DHCPV6-CLIENT-EDM-BAG;
        }
        container ipv6-statistics {
          description
            "DHCPv6 client binding statistics";
          uses DHCPV6-CLIENT-EDM-STATS-BAG;
        }
        leaf interface-name {
          type xr:Interface-name;
          description
            "The name of the interface";
        }
      }
    }
    container nodes {
      description
        "DHCPv6 client list of nodes";
      list node {
        key "node-name";
        description
          "DHCPv6 client particular node name";
        container clients {
          description
            "DHCPv6 client table";
          list client {
            key "interface-name";
            description
              "Single DHCPv6 client binding";
            leaf interface-name {
              type xr:Interface-name;
              description
                "The name of the interface";
            }
            uses DHCPV6-CLIENT-EDM-BAG;
          }
        }
        container client-stats {
          description
            "DHCPv6 client statistics table";
          list client-stat {
            key "interface-name";
            description
              "DHCPv6 client binding statistics";
            leaf interface-name {
              type xr:Interface-name;
              description
                "The name of the interface";
            }
            uses DHCPV6-CLIENT-EDM-STATS-BAG;
          }
        }
        leaf node-name {
          type xr:Node-id;
          description
            "Node name";
        }
      }
    }
  }
}
