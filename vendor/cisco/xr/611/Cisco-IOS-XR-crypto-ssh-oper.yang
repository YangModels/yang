module Cisco-IOS-XR-crypto-ssh-oper {

  /*** NAMESPACE / PREFIX DEFINITION ***/

  namespace "http://cisco.com/ns/yang/Cisco-IOS-XR-crypto-ssh-oper";


  prefix "crypto-ssh-oper";

  /*** LINKAGE (IMPORTS / INCLUDES) ***/

  import Cisco-IOS-XR-types { prefix "xr"; }

  include Cisco-IOS-XR-crypto-ssh-oper-sub1 {
    revision-date 2015-06-02;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR crypto-ssh package operational data.

     This module contains definitions
     for the following management objects:
       ssh1: Crypto Secure Shell(SSH) data
       ssh: ssh

     Copyright (c) 2013-2016 by Cisco Systems, Inc.
     All rights reserved.";

  revision "2015-06-02" {
    description
      "IOS XR 5.3.2 revision.";
  }

  revision "2015-01-07" {
    description
      "IOS XR 5.3.1 revision.";
  }


  container ssh1 {
    xr:xr-xml-map "crypto_ssh_oper:SSH1";
    config false;
    description "Crypto Secure Shell(SSH) data";

    container kex {
      xr:xr-xml-map "crypto_ssh_oper:Kex";
      description "key exchange method data";

      container nodes {
        xr:xr-xml-map "crypto_ssh_oper:NodeTable";
        description "Node-specific ssh session details";

        list node {
          xr:xr-xml-map "crypto_ssh_oper:Node";
          key "node-name";
          description "SSH session details for a particular node";
          leaf node-name {
            xr:xr-xml-map "crypto_ssh_oper:NodeName";
            type xr:Node-id;
            description "Node name";
          }
          uses SSH-SESSION-DETAIL;
        }
      }
    }
  }

  container ssh {
    xr:xr-xml-map "crypto_ssh_oper:SSH";
    config false;
    description "ssh";

    container session {
      xr:xr-xml-map "crypto_ssh_oper:Session";
      description "Crypto SSH session";

      container brief {
        xr:xr-xml-map "crypto_ssh_oper:Brief";
        description "SSH session brief information";
        uses SSH-SESSION-BRIEF;
      }

      container detail {
        xr:xr-xml-map "crypto_ssh_oper:Detail";
        description "SSH session detail information";
        uses SSH-SESSION-DETAIL;
      }
    }
  }
}
