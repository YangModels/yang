module Cisco-IOS-XR-manageability-object-tracking-cfg {

  /*** NAMESPACE / PREFIX DEFINITION ***/

  namespace "http://cisco.com/ns/yang"+
    "/Cisco-IOS-XR-manageability-object-tracking-cfg";


  prefix "manageability-object-tracking-cfg";

  /*** LINKAGE (IMPORTS / INCLUDES) ***/

  import ietf-inet-types { prefix "inet"; }

  import Cisco-IOS-XR-types { prefix "xr"; }

  import Cisco-IOS-XR-manageability-object-tracking-datatypes {
    prefix "dt1";
  }

  import Cisco-IOS-XR-ifmgr-cfg { prefix "a1"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR manageability-object-tracking package configuration.

     This module contains definitions
     for the following management objects:
       object-trackings: Object Tracking configuration

     This YANG module augments the
       Cisco-IOS-XR-ifmgr-cfg
     module with configuration data.

     Copyright (c) 2013-2016 by Cisco Systems, Inc.
     All rights reserved.";

  revision "2015-11-09" {
    description
      "IOS XR 6.0 revision.";
  }


  grouping OBJECT {
    description
      "Common node of threshold-weight-object,
      threshold-percentage-object";

    list object {
      xr:xr-xml-map "manageability-object-tracking_cfg:Object";
      key "object";
      description "Track name object";
      leaf object-weight {
        xr:xr-xml-map "manageability-object-tracking_cfg:ObjectWeig"+
          "ht";
        type int32;
        default "1";
        description "Weight of object";
      }
      leaf object {
        xr:xr-xml-map "manageability-object-tracking_cfg:Object";
        type dt1:Object-tracking-name-string;
        description "Object name";
      }
    }
  }

  grouping THRESHOLD-LIMITS {
    description
      "Common node of threshold-weight,
      threshold-percentage";

    container threshold-limits {
      xr:xr-xml-map "manageability-object-tracking_cfg:ThresholdLim"+
        "its";
      description "Threshold Limits";

      container threshold-up-values {
        xr:xr-xml-map "manageability-object-tracking_cfg:ThresholdU"+
          "p";
        description
          "Threshold limit at which track is set to UP
          state";

        list threshold-up-value {
          xr:xr-xml-map "manageability-object-tracking_cfg:Threshol"+
            "dUpValue";
          key "up";
          description
            "Threshold limit at which track is set to UP
            state";
          leaf threshold-down {
            xr:xr-xml-map "manageability-object-tracking_cfg:Thresh"+
              "oldDown";
            type int32;
            default "0";
            description
              "Threshold limit at which track is set to Down
              state";
          }
          leaf up {
            xr:xr-xml-map "manageability-object-tracking_cfg:Up";
            type int32;
            description "Up value";
          }
        }
      }
    }
  }

  container object-trackings {
    xr:xr-xml-map "manageability-object-tracking_cfg:ObjectTracking"+
      "Table";
    description "Object Tracking configuration";

    list object-tracking {
      xr:xr-xml-map "manageability-object-tracking_cfg:ObjectTracki"+
        "ng";
      key "track-name";
      description "Track name - maximum 32 characters";

      container type-interface {
        xr:xr-xml-map "manageability-object-tracking_cfg:TypeInterf"+
          "ace";
        description "Track type line-protocol";
        leaf interface {
          xr:xr-xml-map "manageability-object-tracking_cfg:Interfac"+
            "e";
          type xr:Interface-name;
          description "The name of the interface";
        }
      }

      container type-list {
        xr:xr-xml-map "manageability-object-tracking_cfg:TypeList";
        description "Track type boolean list";

        container threshold-weight {
          xr:xr-xml-map "manageability-object-tracking_cfg:Threshol"+
            "dWeight";
          description "Track type threshold weight";
          uses THRESHOLD-LIMITS;
        }

        container threshold-percentage-object {
          xr:xr-xml-map "manageability-object-tracking_cfg:Threshol"+
            "dPercentageObject";
          description "Track type threshold percentage";
          uses OBJECT;
        }

        container threshold-percentage {
          xr:xr-xml-map "manageability-object-tracking_cfg:Threshol"+
            "dPercentage";
          description "Track type threshold percentage";
          uses THRESHOLD-LIMITS;
        }

        container threshold-weight-object {
          xr:xr-xml-map "manageability-object-tracking_cfg:Threshol"+
            "dWeightObject";
          description "Track type threshold weight";
          uses OBJECT;
        }
      }

      container type-route {
        xr:xr-xml-map "manageability-object-tracking_cfg:TypeRoute";
        description "Track type route ipv4";

        container ip-address {
          xr:xr-xml-map "manageability-object-tracking_cfg:IPAddres"+
            "s";
          presence "enable ip-address";
          description "set track IPv4 address";
          leaf address {
            xr:xr-xml-map "manageability-object-tracking_cfg:Addres"+
              "s";
            type inet:ipv4-address-no-zone;
            description "IP address";
          }
          leaf mask {
            xr:xr-xml-map "manageability-object-tracking_cfg:Mask";
            type inet:ipv4-address-no-zone;
            description "Mask";
          }
        }
        leaf vrf {
          xr:xr-xml-map "manageability-object-tracking_cfg:VRF";
          type xr:Cisco-ios-xr-string {
            length "0..32";
          }
          description "VRF tag - use 'default' for the DEFAULT vrf";
        }
      }

      container type-boolean-list {
        xr:xr-xml-map "manageability-object-tracking_cfg:TypeBoolea"+
          "nList";
        description "Track type boolean list";

        container or-objects {
          xr:xr-xml-map "manageability-object-tracking_cfg:OrObject"+
            "Table";
          description "Track type boolean or list";

          list or-object {
            xr:xr-xml-map "manageability-object-tracking_cfg:OrObje"+
              "ct";
            key "object";
            description "Track name - maximum 32 characters";
            leaf object-sign {
              xr:xr-xml-map "manageability-object-tracking_cfg:Obje"+
                "ctSign";
              type dt1:Object-tracking-boolean-sign;
              description
                "Tracked Object sign (with or without not)";
            }
            leaf object {
              xr:xr-xml-map "manageability-object-tracking_cfg:Obje"+
                "ct";
              type dt1:Object-tracking-name-string;
              description "Object name";
            }
          }
        }

        container and-objects {
          xr:xr-xml-map "manageability-object-tracking_cfg:AndObjec"+
            "tTable";
          description "Track type boolean and list";

          list and-object {
            xr:xr-xml-map "manageability-object-tracking_cfg:AndObj"+
              "ect";
            key "object-name";
            description "Track name - maximum 32 characters";
            leaf object-sign {
              xr:xr-xml-map "manageability-object-tracking_cfg:Obje"+
                "ctSign";
              type dt1:Object-tracking-boolean-sign;
              description
                "Tracked Object sign (with or without not)";
            }
            leaf object-name {
              xr:xr-xml-map "manageability-object-tracking_cfg:Obje"+
                "ctName";
              type dt1:Object-tracking-name-string;
              description "Object name";
            }
          }
        }
      }
      leaf delay-up {
        xr:xr-xml-map "manageability-object-tracking_cfg:DelayUp";
        xr:xr-cli-map "track <string> delay up <number> ";
        type dt1:Object-tracking-delay;
        units "second";
        description "Delay up in seconds";
      }
      leaf enable {
        xr:xr-xml-map "manageability-object-tracking_cfg:Enable";
        type empty;
        description "Enable the Track";
      }
      leaf delay-down {
        xr:xr-xml-map "manageability-object-tracking_cfg:DelayDown";
        xr:xr-cli-map "track <string> delay down <number> ";
        type dt1:Object-tracking-delay;
        units "second";
        description "Track delay down time";
      }
      leaf type-interface-enable {
        xr:xr-xml-map "manageability-object-tracking_cfg:TypeInterf"+
          "aceEnable";
        type empty;
        description "Enable track type Interface";
      }
      leaf type-route-enable {
        xr:xr-xml-map "manageability-object-tracking_cfg:TypeRouteE"+
          "nable";
        type empty;
        description "Enable track type Route";
      }
      leaf type-boolean-list-and-enable {
        xr:xr-xml-map "manageability-object-tracking_cfg:TypeBoolea"+
          "nListAndEnable";
        type empty;
        description "Enable track type boolean list and";
      }
      leaf type-boolean-list-or-enable {
        xr:xr-xml-map "manageability-object-tracking_cfg:TypeBoolea"+
          "nListOrEnable";
        type empty;
        description "Enable track type boolean list or";
      }
      leaf track-name {
        xr:xr-xml-map "manageability-object-tracking_cfg:TrackName";
        type dt1:Object-tracking-name-string;
        description "Track name";
      }
    }
  }

  augment "/a1:interface-configurations/a1:interface-configuration" {
    leaf track-name {
      xr:xr-xml-map "manageability-object-tracking_interface_cfg:Tr"+
        "ackName";
      type dt1:Object-tracking-name-string;
      description "Track Name";
    }
    description
      "This augment extends the configuration data of
      'Cisco-IOS-XR-ifmgr-cfg'";
  }
}
