module Cisco-IOS-XR-ipv4-arp-cfg {

  /*** NAMESPACE / PREFIX DEFINITION ***/

  namespace "http://cisco.com/ns/yang/Cisco-IOS-XR-ipv4-arp-cfg";


  prefix "ipv4-arp-cfg";

  /*** LINKAGE (IMPORTS / INCLUDES) ***/

  import ietf-inet-types { prefix "inet"; }

  import ietf-yang-types { prefix "yang"; }

  import Cisco-IOS-XR-types { prefix "xr"; }

  import Cisco-IOS-XR-ifmgr-cfg { prefix "a1"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ipv4-arp package configuration.

     This module contains definitions
     for the following management objects:
       arp: ARP configuraiton
       arpgmp: arpgmp
       arp-redundancy: arp redundancy

     This YANG module augments the
       Cisco-IOS-XR-ifmgr-cfg
     module with configuration data.

     Copyright (c) 2013-2016 by Cisco Systems, Inc.
     All rights reserved.";

  revision "2015-11-09" {
    description
      "IOS XR 6.0 revision.";
  }

  typedef Arp-entry {
    type enumeration {
      enum static {
        value 0;
        description "Static ARP entry type";
      }
      enum alias {
        value 1;
        description "Alias ARP entry type";
      }
    }
    description "Arp entry";
  }
  typedef Arp-encap {
    type enumeration {
      enum arpa {
        value 1;
        description "Encapsulation type ARPA";
      }
      enum srp {
        value 4;
        description "Encapsulation type SRP";
      }
      enum srpa {
        value 5;
        description "Encapsulation type SRPA";
      }
      enum srpb {
        value 6;
        description "Encapsulation type SRPB";
      }
    }
    description "Arp encap";
  }

  container arp {
    xr:xr-xml-map "arp_cfg:ARP";
    description "ARP configuraiton";
    leaf max-entries {
      xr:xr-xml-map "arp_cfg:MaxEntries";
      xr:xr-cli-map "max-entries <number> ";
      type uint32 {
        range "1..256000";
      }
      description
        "Configure maximum number of safe ARP entries per
        line card";
    }
    leaf inner-cos {
      xr:xr-xml-map "arp_cfg:InnerCos";
      xr:xr-cli-map "inner-cos <number> ";
      type uint32 {
        range "0..7";
      }
      description "Configure inner cos values for arp packets";
    }
    leaf outer-cos {
      xr:xr-xml-map "arp_cfg:OuterCos";
      xr:xr-cli-map "outer-cos <number> ";
      type uint32 {
        range "0..7";
      }
      description "Configure outer cos values for arp packets";
    }
  }

  container arpgmp {
    xr:xr-xml-map "arp_cfg:ARPGMP";
    description "arpgmp";

    list vrf {
      xr:xr-xml-map "arp_cfg:VRF";
      key "vrf-name";
      description
        "Per VRF configuration, for the default VRF use
        'default'";

      container entries {
        xr:xr-xml-map "arp_cfg:EntryTable";
        description "ARP static and alias entry configuration";

        list entry {
          xr:xr-xml-map "arp_cfg:Entry";
          xr:xr-cli-map "arp [vrf <string>] <IPv4 address> <MAC add"+
            "ress> <enum> [alias] [interface <interface>] ";
          key "address";
          description
            "ARP static and alias entry configuration item";
          leaf address {
            xr:xr-xml-map "arp_cfg:Address";
            type inet:ipv4-address-no-zone;
            description "IP Address";
          }
          leaf mac-address {
            xr:xr-xml-map "arp_cfg:MACAddress";
            type yang:mac-address;
            description "MAC Address";
          }
          leaf encapsulation {
            xr:xr-xml-map "arp_cfg:Encapsulation";
            type Arp-encap;
            description "Encapsulation type";
          }
          leaf entry-type {
            xr:xr-xml-map "arp_cfg:EntryType";
            type Arp-entry;
            description "Entry type";
          }
          leaf interface {
            xr:xr-xml-map "arp_cfg:interface";
            type xr:Interface-name;
            description "Interface name";
          }
        }
      }
      leaf vrf-name {
        xr:xr-xml-map "arp_cfg:VRFName";
        type xr:Cisco-ios-xr-string;
        description "VRF name";
      }
    }
  }

  container arp-redundancy {
    xr:xr-xml-map "arp_cfg:ARPRedundancy";
    description "arp redundancy";

    container redundancy {
      xr:xr-xml-map "arp_cfg:Redundancy";
      presence "Indicates a redundancy node is configured.";
      description "Configure parameter for ARP Geo redundancy";

      container groups {
        xr:xr-xml-map "arp_cfg:GroupTable";
        description "Table of Group";

        list group {
          xr:xr-xml-map "arp_cfg:Group";
          key "group-id";
          description "None";

          container peers {
            xr:xr-xml-map "arp_cfg:PeerTable";
            description "Table of Peer";

            list peer {
              xr:xr-xml-map "arp_cfg:Peer";
              key "prefix-string";
              description "None";
              leaf prefix-string {
                xr:xr-xml-map "arp_cfg:PrefixString";
                type inet:ip-address-no-zone;
                description "Neighbor IPv4 address";
              }
            }
          }

          container interface-list {
            xr:xr-xml-map "arp_cfg:InterfaceList";
            presence "Indicates a interface-list node is"+
              " configured.";
            description "List of Interfaces for this Group";

            container interfaces {
              xr:xr-xml-map "arp_cfg:InterfaceTable";
              description "Table of Interface";

              list interface {
                xr:xr-xml-map "arp_cfg:Interface";
                xr:xr-cli-map "redundancy group <number> interface-"+
                  "list interface <interface> id <number> ";
                key "interface-name";
                description "Interface for this Group";
                leaf interface-name {
                  xr:xr-xml-map "arp_cfg:InterfaceName";
                  type xr:Interface-name;
                  description "Interface name";
                }
                leaf interface-id {
                  xr:xr-xml-map "arp_cfg:InterfaceID";
                  type uint32 {
                    range "1..65535";
                  }
                  mandatory true;
                  description "Interface Id for the interface";
                }
              }
            }
            leaf enable {
              xr:xr-xml-map "arp_cfg:Enable";
              type empty;
              mandatory true;
              description
                "Enable List of Interfaces for this Group.
                Deletion of this object also causes deletion
                of all associated objects under
                InterfaceList.";
            }
          }
          leaf source-interface {
            xr:xr-xml-map "arp_cfg:SourceInterface";
            xr:xr-cli-map "redundancy group <number> source-interfa"+
              "ce <interface> ";
            type xr:Interface-name;
            description "Interface name";
          }
          leaf group-id {
            xr:xr-xml-map "arp_cfg:GroupID";
            type uint32 {
              range "1..32";
            }
            description "Group ID";
          }
        }
      }
      leaf enable {
        xr:xr-xml-map "arp_cfg:Enable";
        type empty;
        mandatory true;
        description
          "Enable Configure parameter for ARP Geo
          redundancy. Deletion of this object also causes
          deletion of all associated objects under
          ArpRedundancy.";
      }
    }
  }

  augment "/a1:interface-configurations/a1:interface-configuration" {

    container dagrs {
      xr:xr-xml-map "dagr_cfg:DAGRTable";
      description
        "Direct-Attached Gateway Redundancy configuration";

      list dagr {
        xr:xr-xml-map "dagr_cfg:DAGR";
        key "ip-addr";
        description "The DAGR entry being configured";

        container sub {
          xr:xr-xml-map "dagr_cfg:Sub";
          description "DAGR Submode configuration";

          container metric {
            xr:xr-xml-map "dagr_cfg:Metric";
            description "Set Route Metric";
            leaf metric-norm {
              xr:xr-xml-map "dagr_cfg:MetricNorm";
              type uint32 {
                range "0..256";
              }
              default "100";
              description "Normal Route Metric";
            }
            leaf metric-prio {
              xr:xr-xml-map "dagr_cfg:MetricPrio";
              type uint32 {
                range "0..256";
              }
              default "90";
              description "Priority Route Metric";
            }
          }

          container timers {
            xr:xr-xml-map "dagr_cfg:Timers";
            description "Set Query Timers";
            leaf query-time {
              xr:xr-xml-map "dagr_cfg:QueryTime";
              type uint32 {
                range "1..10000";
              }
              default "1";
              description "Query Timeout";
            }
            leaf sby-time {
              xr:xr-xml-map "dagr_cfg:SbyTime";
              type uint32 {
                range "1..10000";
              }
              default "20";
              description "Standby Query Timeout";
            }
          }

          container distance {
            xr:xr-xml-map "dagr_cfg:Distance";
            description "Set Route Distance";
            leaf dist-norm {
              xr:xr-xml-map "dagr_cfg:DistNorm";
              type uint32 {
                range "0..256";
              }
              default "150";
              description "Normal Route Distance";
            }
            leaf dist-prio {
              xr:xr-xml-map "dagr_cfg:DistPrio";
              type uint32 {
                range "0..256";
              }
              default "5";
              description "Priority Route Distance";
            }
          }
          leaf priority-timeout {
            xr:xr-xml-map "dagr_cfg:PriorityTimeout";
            type uint32 {
              range "1..10000";
            }
            default "20";
            description "Priority Timeout value";
          }
        }
        leaf enter {
          xr:xr-xml-map "dagr_cfg:Enter";
          type empty;
          description "DAGR Group Enter item";
        }
        leaf ip-addr {
          xr:xr-xml-map "dagr_cfg:IPAddr";
          type inet:ipv4-address-no-zone;
          description "DAGR Peer IPv4 address";
        }
      }
    }
    description
      "This augment extends the configuration data of
      'Cisco-IOS-XR-ifmgr-cfg'";
  }

  augment "/a1:interface-configurations/a1:interface-configuration" {

    container ipv4arp {
      xr:xr-xml-map "ipv4_arp_interface_cfg:IPV4ARP";
      description "Configure Address Resolution Protocol";
      leaf learning-local {
        xr:xr-xml-map "ipv4_arp_interface_cfg:LearningLocal";
        type empty;
        description
          "Enable the dynamic learning of ARP entries(for
          local subnet) on the interface";
      }
      leaf gratuitous-ignore {
        xr:xr-xml-map "ipv4_arp_interface_cfg:GratuitousIgnore";
        type empty;
        description
          "Ignore the receipt of Gratuitous ARP packets on
          the interface";
      }
      leaf proxy-arp {
        xr:xr-xml-map "ipv4_arp_interface_cfg:ProxyARP";
        type empty;
        description "Proxy ARP configuration";
      }
      leaf purge-delay {
        xr:xr-xml-map "ipv4_arp_interface_cfg:PurgeDelay";
        type uint32 {
          range "1..65535";
        }
        description
          "Time to delay purging arp entries when the
          interface goes down";
      }
      leaf learning-disable {
        xr:xr-xml-map "ipv4_arp_interface_cfg:LearningDisable";
        type empty;
        description
          "Disable the dynamic learning of ARP entries on
          the interface";
      }
      leaf local-proxy-arp {
        xr:xr-xml-map "ipv4_arp_interface_cfg:LocalProxyARP";
        type empty;
        description "Local Proxy ARP configuration";
      }
      leaf timeout {
        xr:xr-xml-map "ipv4_arp_interface_cfg:Timeout";
        type uint32 {
          range "30..2144448000";
        }
        units "second";
        description "Number of seconds for ARP cache timeout";
      }
    }
    description
      "This augment extends the configuration data of
      'Cisco-IOS-XR-ifmgr-cfg'";
  }
}
