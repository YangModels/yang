module Cisco-IOS-XR-manageability-perfmgmt-cfg {

  /*** NAMESPACE / PREFIX DEFINITION ***/

  namespace "http://cisco.com/ns/yang"+
    "/Cisco-IOS-XR-manageability-perfmgmt-cfg";


  prefix "manageability-perfmgmt-cfg";

  /*** LINKAGE (IMPORTS / INCLUDES) ***/

  import ietf-inet-types { prefix "inet"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR manageability-perfmgmt package configuration.

     This module contains definitions
     for the following management objects:
       perf-mgmt: Performance Management configuration & operations

     Copyright (c) 2013-2016 by Cisco Systems, Inc.
     All rights reserved.";

  revision "2015-11-09" {
    description
      "IOS XR 6.0 revision.";
  }

  typedef Pm-threshold-val-range {
    type uint32 {
      range "0..65536";
    }
    description "Pm threshold val range";
  }
  typedef Pm-threshold-val-range-counter32 {
    type uint32 {
      range "0..4294967295";
    }
    description "Pm threshold val range counter32";
  }
  typedef Pm-threshold-rearm {
    type enumeration {
      enum always {
        value 0;
        description "Rearm Always";
      }
      enum window {
        value 1;
        description "Rearm after window of sampling periods";
      }
      enum toggle {
        value 2;
        description
          "Rearm after the first period when condition is
          not met";
      }
    }
    description "Pm threshold rearm";
  }
  typedef Pm-threshold-op {
    type enumeration {
      enum eq {
        value 1;
        description "Equal to";
      }
      enum ne {
        value 2;
        description "Not equal to";
      }
      enum lt {
        value 3;
        description "Less than";
      }
      enum le {
        value 4;
        description "Less than or equal to";
      }
      enum gt {
        value 5;
        description "Greater than";
      }
      enum ge {
        value 6;
        description "Greater than or equal to";
      }
      enum rg {
        value 7;
        description "Not in Range";
      }
    }
    description "Pm threshold op";
  }
  typedef Pid-range {
    type uint32 {
      range "0..4294967295";
    }
    description "Pid range";
  }
  typedef Pm-threshold-rearm-window {
    type uint32 {
      range "1..100";
    }
    description "Pm threshold rearm window";
  }

  grouping REG-EXP-GROUP {
    description
      "Common node of basic-counter-interface-template,
      generic-counter-interface-template,
      data-rate-interface-template";
    leaf reg-exp-group {
      xr:xr-xml-map "manageability_perf_thresh_cfg:RegExpGroup";
      type xr:Cisco-ios-xr-string {
        length "0..32";
      }
      description "Enable instance filtering by regular expression";
    }
  }

  grouping OUTPUT-LS-REQUESTS {
    description
      "Common node of ospfv2-protocol-template,
      ospfv3-protocol-template";

    container output-ls-requests {
      xr:xr-xml-map "manageability_perf_thresh_cfg:OutputLSRequests";
      presence "enable output-ls-requests";
      description "Number of LS Requests sent";
      leaf operator {
        xr:xr-xml-map "manageability_perf_thresh_cfg:Operator";
        type Pm-threshold-op;
        description "Operator";
      }
      leaf value {
        xr:xr-xml-map "manageability_perf_thresh_cfg:Value";
        type Pm-threshold-val-range-counter32;
        description
          "Threshold value (or start range value for
          operator RG)";
      }
      leaf end-range-value {
        xr:xr-xml-map "manageability_perf_thresh_cfg:EndRangeValue";
        type Pm-threshold-val-range-counter32;
        description
          "Threshold end range value (for operator RG, set
          to 0 otherwise)";
      }
      leaf percent {
        xr:xr-xml-map "manageability_perf_thresh_cfg:Percent";
        type boolean;
        description
          "Set to TRUE if Specified threshold values are
          in percent";
      }
      leaf rearm-type {
        xr:xr-xml-map "manageability_perf_thresh_cfg:RearmType";
        type Pm-threshold-rearm;
        description "Configure the Rearm type";
      }
      leaf rearm-window {
        xr:xr-xml-map "manageability_perf_thresh_cfg:RearmWindow";
        type Pm-threshold-rearm-window;
        description
          "Configure the rearm window size (for rearm type
          Window)";
      }
    }
  }

  grouping OSPF-INSTANCE-TABLE {
    description "Common node of ospfv2-protocol, ospfv3-protocol";

    container ospf-instances {
      xr:xr-xml-map "manageability_perf_enable_monitor_cfg:OSPFInst"+
        "anceTable";
      description "Monitor an instance";

      list ospf-instance {
        xr:xr-xml-map "manageability_perf_enable_monitor_cfg:OSPFIn"+
          "stance";
        key "instance-name";
        description "Instance being monitored";
        leaf instance-name {
          xr:xr-xml-map "manageability_perf_enable_monitor_cfg:Inst"+
            "anceName";
          type xr:Cisco-ios-xr-string;
          description "OSPF Instance Name";
        }
        uses MANAGEABILITY-PERF-ENABLE-MONITOR-CFG-TEMPLATE-NAME;
      }
    }
  }

  grouping INPUT-DB-DS {
    description
      "Common node of ospfv2-protocol-template,
      ospfv3-protocol-template";

    container input-db-ds {
      xr:xr-xml-map "manageability_perf_thresh_cfg:InputDBDs";
      presence "enable input-db-ds";
      description "Number of DBD packets received";
      leaf operator {
        xr:xr-xml-map "manageability_perf_thresh_cfg:Operator";
        type Pm-threshold-op;
        description "Operator";
      }
      leaf value {
        xr:xr-xml-map "manageability_perf_thresh_cfg:Value";
        type Pm-threshold-val-range-counter32;
        description
          "Threshold value (or start range value for
          operator RG)";
      }
      leaf end-range-value {
        xr:xr-xml-map "manageability_perf_thresh_cfg:EndRangeValue";
        type Pm-threshold-val-range-counter32;
        description
          "Threshold end range value (for operator RG, set
          to 0 otherwise)";
      }
      leaf percent {
        xr:xr-xml-map "manageability_perf_thresh_cfg:Percent";
        type boolean;
        description
          "Set to TRUE if Specified threshold values are
          in percent";
      }
      leaf rearm-type {
        xr:xr-xml-map "manageability_perf_thresh_cfg:RearmType";
        type Pm-threshold-rearm;
        description "Configure the Rearm type";
      }
      leaf rearm-window {
        xr:xr-xml-map "manageability_perf_thresh_cfg:RearmWindow";
        type Pm-threshold-rearm-window;
        description
          "Configure the rearm window size (for rearm type
          Window)";
      }
    }
  }

  grouping NODE-ALL {
    description
      "Common node of cpu-node, memory-node,
      process-node";

    container node-all {
      xr:xr-xml-map "manageability_perf_enable_stats_cfg:NodeAll";
      description "All the the nodes";
      uses TEMPLATE-NAME;
    }
  }

  grouping MANAGEABILITY-PERF-ENABLE-THRESH-CFG-NODE-ALL {
    description
      "Common node of cpu-node, memory-node,
      process-nodeCommon node of cpu-node, memory-node,
      process-node";

    container node-all {
      xr:xr-xml-map "manageability_perf_enable_thresh_cfg:NodeAll";
      description "All the the nodes";
      uses MANAGEABILITY-PERF-ENABLE-THRESH-CFG-TEMPLATE-NAME;
    }
  }

  grouping INPUT-LSA-ACKS-LSA {
    description
      "Common node of ospfv2-protocol-template,
      ospfv3-protocol-template";

    container input-lsa-acks-lsa {
      xr:xr-xml-map "manageability_perf_thresh_cfg:InputLSAAcksLSA";
      presence "enable input-lsa-acks-lsa";
      description "Number of LSA received in LSA Acknowledgements";
      leaf operator {
        xr:xr-xml-map "manageability_perf_thresh_cfg:Operator";
        type Pm-threshold-op;
        description "Operator";
      }
      leaf value {
        xr:xr-xml-map "manageability_perf_thresh_cfg:Value";
        type Pm-threshold-val-range-counter32;
        description
          "Threshold value (or start range value for
          operator RG)";
      }
      leaf end-range-value {
        xr:xr-xml-map "manageability_perf_thresh_cfg:EndRangeValue";
        type Pm-threshold-val-range-counter32;
        description
          "Threshold end range value (for operator RG, set
          to 0 otherwise)";
      }
      leaf percent {
        xr:xr-xml-map "manageability_perf_thresh_cfg:Percent";
        type boolean;
        description
          "Set to TRUE if Specified threshold values are
          in percent";
      }
      leaf rearm-type {
        xr:xr-xml-map "manageability_perf_thresh_cfg:RearmType";
        type Pm-threshold-rearm;
        description "Configure the Rearm type";
      }
      leaf rearm-window {
        xr:xr-xml-map "manageability_perf_thresh_cfg:RearmWindow";
        type Pm-threshold-rearm-window;
        description
          "Configure the rearm window size (for rearm type
          Window)";
      }
    }
  }

  grouping OUTPUT-DB-DS-LSA {
    description
      "Common node of ospfv2-protocol-template,
      ospfv3-protocol-template";

    container output-db-ds-lsa {
      xr:xr-xml-map "manageability_perf_thresh_cfg:OutputDBDsLSA";
      presence "enable output-db-ds-lsa";
      description "Number of LSA sent in DBD packets";
      leaf operator {
        xr:xr-xml-map "manageability_perf_thresh_cfg:Operator";
        type Pm-threshold-op;
        description "Operator";
      }
      leaf value {
        xr:xr-xml-map "manageability_perf_thresh_cfg:Value";
        type Pm-threshold-val-range-counter32;
        description
          "Threshold value (or start range value for
          operator RG)";
      }
      leaf end-range-value {
        xr:xr-xml-map "manageability_perf_thresh_cfg:EndRangeValue";
        type Pm-threshold-val-range-counter32;
        description
          "Threshold end range value (for operator RG, set
          to 0 otherwise)";
      }
      leaf percent {
        xr:xr-xml-map "manageability_perf_thresh_cfg:Percent";
        type boolean;
        description
          "Set to TRUE if Specified threshold values are
          in percent";
      }
      leaf rearm-type {
        xr:xr-xml-map "manageability_perf_thresh_cfg:RearmType";
        type Pm-threshold-rearm;
        description "Configure the Rearm type";
      }
      leaf rearm-window {
        xr:xr-xml-map "manageability_perf_thresh_cfg:RearmWindow";
        type Pm-threshold-rearm-window;
        description
          "Configure the rearm window size (for rearm type
          Window)";
      }
    }
  }

  grouping TEMPLATE-NAME {
    description
      "Common node of ospfv2-protocol, ospfv3-protocol,
      bgp, node, node-all, ldp-mpls,
      data-rate-interface, generic-counter-interface,
      basic-counter-interface";
    leaf template-name {
      xr:xr-xml-map "manageability_perf_enable_stats_cfg:TemplateNa"+
        "me";
      xr:xr-cli-map "(apply)|(enable) generic-counters (<string>)|("+
        "default) ";
      xr:xr-cli-map "bgp ";
      xr:xr-cli-map "ospf v2protocol ";
      xr:xr-cli-map "ospf v3protocol ";
      xr:xr-cli-map "cpu location all ";
      xr:xr-cli-map "cpu location <location> ";
      xr:xr-cli-map "(apply)|(enable) basic-counters (<string>)|(de"+
        "fault) ";
      xr:xr-cli-map "process location all ";
      xr:xr-cli-map "process location <location> ";
      xr:xr-cli-map "(apply)|(enable) data-rates (<string>)|(defaul"+
        "t) ";
      xr:xr-cli-map "memory location all ";
      xr:xr-cli-map "memory location <location> ";
      xr:xr-cli-map "(apply)|(enable) ldp (<string>)|(default) ";
      type string;
      description "Template name";
    }
  }

  grouping MANAGEABILITY-PERF-ENABLE-THRESH-CFG-TEMPLATE-NAME {
    description
      "Common node of ospfv2-protocol, ospfv3-protocol,
      bgp, node, node-all, ldp-mpls,
      data-rate-interface, generic-counter-interface,
      basic-counter-interfaceCommon node of
      ospfv2-protocol, ospfv3-protocol, node, node-all,
      ldp-mpls, data-rate-interface,
      generic-counter-interface,
      basic-counter-interface, bgp";
    leaf template-name {
      xr:xr-xml-map "manageability_perf_enable_thresh_cfg:TemplateN"+
        "ame";
      xr:xr-cli-map "ospf v3protocol ";
      xr:xr-cli-map "bgp ";
      xr:xr-cli-map "(apply)|(enable) data-rates (<string>)|(defaul"+
        "t) ";
      xr:xr-cli-map "ospf v2protocol ";
      xr:xr-cli-map "(apply)|(enable) memory location <location> (<"+
        "string>)|(default) ";
      xr:xr-cli-map "(apply)|(enable) memory location all (<string>"+
        ")|(default) ";
      xr:xr-cli-map "(apply)|(enable) generic-counters (<string>)|("+
        "default) ";
      xr:xr-cli-map "(apply)|(enable) cpu location <location> (<str"+
        "ing>)|(default) ";
      xr:xr-cli-map "(apply)|(enable) cpu location all (<string>)|("+
        "default) ";
      xr:xr-cli-map "(apply)|(enable) ldp (<string>)|(default) ";
      xr:xr-cli-map "(apply)|(enable) process location <location> ("+
        "<string>)|(default) ";
      xr:xr-cli-map "(apply)|(enable) process location all (<string"+
        ">)|(default) ";
      xr:xr-cli-map "(apply)|(enable) basic-counters (<string>)|(de"+
        "fault) ";
      type string;
      description "Template name";
    }
  }

  grouping MANAGEABILITY-PERF-ENABLE-MONITOR-CFG-TEMPLATE-NAME {
    description
      "Common node of ospfv2-protocol, ospfv3-protocol,
      bgp, node, node-all, ldp-mpls,
      data-rate-interface, generic-counter-interface,
      basic-counter-interfaceCommon node of
      ospfv2-protocol, ospfv3-protocol, node, node-all,
      ldp-mpls, data-rate-interface,
      generic-counter-interface,
      basic-counter-interface, bgpCommon node of
      ospf-instance, session, pid, node, interface,
      neighbor";
    leaf template-name {
      xr:xr-xml-map "manageability_perf_enable_monitor_cfg:Template"+
        "Name";
      xr:xr-cli-map "(apply)|(enable) ldp <IPv4 address> (<string>)"+
        "|(default) ";
      xr:xr-cli-map "(apply)|(enable) v3protocol <string> (<string>"+
        ")|(default) ";
      xr:xr-cli-map "(apply)|(enable) generic-counters <interface> "+
        "(<string>)|(default) ";
      xr:xr-cli-map "(apply)|(enable) process location <location> p"+
        "rocess <number> (<string>)|(default) ";
      xr:xr-cli-map "(apply)|(enable) basic-counters <interface> (<"+
        "string>)|(default) ";
      xr:xr-cli-map "(apply)|(enable) memory location <location> (<"+
        "string>)|(default) ";
      xr:xr-cli-map "(apply)|(enable) v2protocol <string> (<string>"+
        ")|(default) ";
      xr:xr-cli-map "(apply)|(enable) cpu location <location> (<str"+
        "ing>)|(default) ";
      xr:xr-cli-map "(apply)|(enable) bgp <IPv4 address> (<string>)"+
        "|(default) ";
      xr:xr-cli-map "(apply)|(enable) data-rates <interface> (<stri"+
        "ng>)|(default) ";
      type string;
      description "Template name";
    }
  }

  grouping TEMPLATE-TABLE {
    description
      "Common node of ospfv2-protocol, ospfv3-protocol,
      bgp, generic-counter-interface,
      basic-counter-interface, data-rate-interface,
      ldp-mpls, cpu-node, memory-node, process-node";

    container templates {
      xr:xr-xml-map "manageability_perf_stats_cfg:TemplateTable";
      description "Template name";

      list template {
        xr:xr-xml-map "manageability_perf_stats_cfg:Template";
        key "template-name";
        description "A template instance";
        leaf reg-exp-group {
          xr:xr-xml-map "manageability_perf_stats_cfg:RegExpGroup";
          xr:xr-cli-map "generic-counters (template <string>)|(defa"+
            "ult) regular-expression <string> ";
          xr:xr-cli-map "basic-counters (template <string>)|(defaul"+
            "t) regular-expression <string> ";
          xr:xr-cli-map "data-rates (template <string>)|(default) r"+
            "egular-expression <string> ";
          type xr:Cisco-ios-xr-string {
            length "0..32";
          }
          description
            "Enable instance filtering by regular
            expression";
        }
        leaf history-persistent {
          xr:xr-xml-map "manageability_perf_stats_cfg:HistoryPersis"+
            "tent";
          xr:xr-cli-map "generic-counters (template <string>)|(defa"+
            "ult) history-persistent ";
          xr:xr-cli-map "process (template <string>)|(default) hist"+
            "ory-persistent ";
          xr:xr-cli-map "basic-counters (template <string>)|(defaul"+
            "t) history-persistent ";
          xr:xr-cli-map "v3protocol (template <string>)|(default) h"+
            "istory-persistent ";
          xr:xr-cli-map "cpu (template <string>)|(default) history-"+
            "persistent ";
          xr:xr-cli-map "data-rates (template <string>)|(default) h"+
            "istory-persistent ";
          xr:xr-cli-map "memory (template <string>)|(default) histo"+
            "ry-persistent ";
          xr:xr-cli-map "ldp (template <string>)|(default) history-"+
            "persistent ";
          xr:xr-cli-map "bgp (template <string>)|(default) history-"+
            "persistent ";
          xr:xr-cli-map "v2protocol (template <string>)|(default) h"+
            "istory-persistent ";
          type empty;
          description "Enable persistent history statistics";
        }
        leaf vrf-group {
          xr:xr-xml-map "manageability_perf_stats_cfg:VRFGroup";
          xr:xr-cli-map "generic-counters (template <string>)|(defa"+
            "ult) vrf-group <string> ";
          xr:xr-cli-map "data-rates (template <string>)|(default) v"+
            "rf-group <string> ";
          type xr:Cisco-ios-xr-string {
            length "0..32";
          }
          description
            "VRF group configured in regular expression to
            be applied";
        }
        leaf sample-interval {
          xr:xr-xml-map "manageability_perf_stats_cfg:SampleInterva"+
            "l";
          xr:xr-cli-map "generic-counters (template <string>)|(defa"+
            "ult) sample-interval <number> ";
          xr:xr-cli-map "process (template <string>)|(default) samp"+
            "le-interval <number> ";
          xr:xr-cli-map "basic-counters (template <string>)|(defaul"+
            "t) sample-interval <number> ";
          xr:xr-cli-map "v3protocol (template <string>)|(default) s"+
            "ample-interval <number> ";
          xr:xr-cli-map "cpu (template <string>)|(default) sample-i"+
            "nterval <number> ";
          xr:xr-cli-map "data-rates (template <string>)|(default) s"+
            "ample-interval <number> ";
          xr:xr-cli-map "memory (template <string>)|(default) sampl"+
            "e-interval <number> ";
          xr:xr-cli-map "ldp (template <string>)|(default) sample-i"+
            "nterval <number> ";
          xr:xr-cli-map "bgp (template <string>)|(default) sample-i"+
            "nterval <number> ";
          xr:xr-cli-map "v2protocol (template <string>)|(default) s"+
            "ample-interval <number> ";
          type uint32 {
            range "1..60";
          }
          units "minute";
          description "Frequency of each sample in minutes";
        }
        leaf sample-size {
          xr:xr-xml-map "manageability_perf_stats_cfg:SampleSize";
          xr:xr-cli-map "generic-counters (template <string>)|(defa"+
            "ult) sample-size <number> ";
          xr:xr-cli-map "process (template <string>)|(default) samp"+
            "le-size <number> ";
          xr:xr-cli-map "basic-counters (template <string>)|(defaul"+
            "t) sample-size <number> ";
          xr:xr-cli-map "v3protocol (template <string>)|(default) s"+
            "ample-size <number> ";
          xr:xr-cli-map "cpu (template <string>)|(default) sample-s"+
            "ize <number> ";
          xr:xr-cli-map "data-rates (template <string>)|(default) s"+
            "ample-size <number> ";
          xr:xr-cli-map "memory (template <string>)|(default) sampl"+
            "e-size <number> ";
          xr:xr-cli-map "ldp (template <string>)|(default) sample-s"+
            "ize <number> ";
          xr:xr-cli-map "bgp (template <string>)|(default) sample-s"+
            "ize <number> ";
          xr:xr-cli-map "v2protocol (template <string>)|(default) s"+
            "ample-size <number> ";
          type uint32 {
            range "1..60";
          }
          description "Number of samples to be taken";
        }
        leaf template-name {
          xr:xr-xml-map "manageability_perf_stats_cfg:TemplateName";
          type xr:Cisco-ios-xr-string;
          description "Template Name";
        }
      }
    }
  }

  grouping SAMPLE-INTERVAL {
    description
      "Common node of data-rate-interface-template,
      ldp-mpls-template, cpu-node-template,
      memory-node-template, process-node-template";
    leaf sample-interval {
      xr:xr-xml-map "manageability_perf_thresh_cfg:SampleInterval";
      type uint32 {
        range "1..60";
      }
      units "minute";
      description "Frequency of sampling in minutes";
    }
  }

  grouping MANAGEABILITY-PERF-THRESH-CFG-SAMPLE-INTERVAL {
    description
      "Common node of data-rate-interface-template,
      ldp-mpls-template, cpu-node-template,
      memory-node-template, process-node-templateCommon
      node of ospfv2-protocol-template,
      ospfv3-protocol-template, bgp-template,
      basic-counter-interface-template,
      generic-counter-interface-template";
    leaf sample-interval {
      xr:xr-xml-map "manageability_perf_thresh_cfg:SampleInterval";
      type uint32 {
        range "1..60";
      }
      units "minute";
      description "Frequency of sampling in minutes";
    }
  }

  grouping INPUT-PACKETS {
    description
      "Common node of ospfv2-protocol-template,
      ospfv3-protocol-template";

    container input-packets {
      xr:xr-xml-map "manageability_perf_thresh_cfg:InputPackets";
      presence "enable input-packets";
      description "Total number of packets received";
      leaf operator {
        xr:xr-xml-map "manageability_perf_thresh_cfg:Operator";
        type Pm-threshold-op;
        description "Operator";
      }
      leaf value {
        xr:xr-xml-map "manageability_perf_thresh_cfg:Value";
        type Pm-threshold-val-range-counter32;
        description
          "Threshold value (or start range value for
          operator RG)";
      }
      leaf end-range-value {
        xr:xr-xml-map "manageability_perf_thresh_cfg:EndRangeValue";
        type Pm-threshold-val-range-counter32;
        description
          "Threshold end range value (for operator RG, set
          to 0 otherwise)";
      }
      leaf percent {
        xr:xr-xml-map "manageability_perf_thresh_cfg:Percent";
        type boolean;
        description
          "Set to TRUE if Specified threshold values are
          in percent";
      }
      leaf rearm-type {
        xr:xr-xml-map "manageability_perf_thresh_cfg:RearmType";
        type Pm-threshold-rearm;
        description "Configure the Rearm type";
      }
      leaf rearm-window {
        xr:xr-xml-map "manageability_perf_thresh_cfg:RearmWindow";
        type Pm-threshold-rearm-window;
        description
          "Configure the rearm window size (for rearm type
          Window)";
      }
    }
  }

  grouping INPUT-LSA-UPDATES-LSA {
    description
      "Common node of ospfv2-protocol-template,
      ospfv3-protocol-template";

    container input-lsa-updates-lsa {
      xr:xr-xml-map "manageability_perf_thresh_cfg:InputLSAUpdatesL"+
        "SA";
      presence "enable input-lsa-updates-lsa";
      description "Number of LSA received in LSA Updates";
      leaf operator {
        xr:xr-xml-map "manageability_perf_thresh_cfg:Operator";
        type Pm-threshold-op;
        description "Operator";
      }
      leaf value {
        xr:xr-xml-map "manageability_perf_thresh_cfg:Value";
        type Pm-threshold-val-range-counter32;
        description
          "Threshold value (or start range value for
          operator RG)";
      }
      leaf end-range-value {
        xr:xr-xml-map "manageability_perf_thresh_cfg:EndRangeValue";
        type Pm-threshold-val-range-counter32;
        description
          "Threshold end range value (for operator RG, set
          to 0 otherwise)";
      }
      leaf percent {
        xr:xr-xml-map "manageability_perf_thresh_cfg:Percent";
        type boolean;
        description
          "Set to TRUE if Specified threshold values are
          in percent";
      }
      leaf rearm-type {
        xr:xr-xml-map "manageability_perf_thresh_cfg:RearmType";
        type Pm-threshold-rearm;
        description "Configure the Rearm type";
      }
      leaf rearm-window {
        xr:xr-xml-map "manageability_perf_thresh_cfg:RearmWindow";
        type Pm-threshold-rearm-window;
        description
          "Configure the rearm window size (for rearm type
          Window)";
      }
    }
  }

  grouping VRF-GROUP {
    description
      "Common node of basic-counter-interface-template,
      generic-counter-interface-template,
      data-rate-interface-template";
    leaf vrf-group {
      xr:xr-xml-map "manageability_perf_thresh_cfg:VRFGroup";
      type xr:Cisco-ios-xr-string {
        length "0..32";
      }
      description
        "Enable instance filtering by VRF name regular
        expression ";
    }
  }

  grouping OUTPUT-LSA-UPDATES-LSA {
    description
      "Common node of ospfv2-protocol-template,
      ospfv3-protocol-template";

    container output-lsa-updates-lsa {
      xr:xr-xml-map "manageability_perf_thresh_cfg:OutputLSAUpdates"+
        "LSA";
      presence "enable output-lsa-updates-lsa";
      description "Number of LSA sent in LSA Updates";
      leaf operator {
        xr:xr-xml-map "manageability_perf_thresh_cfg:Operator";
        type Pm-threshold-op;
        description "Operator";
      }
      leaf value {
        xr:xr-xml-map "manageability_perf_thresh_cfg:Value";
        type Pm-threshold-val-range-counter32;
        description
          "Threshold value (or start range value for
          operator RG)";
      }
      leaf end-range-value {
        xr:xr-xml-map "manageability_perf_thresh_cfg:EndRangeValue";
        type Pm-threshold-val-range-counter32;
        description
          "Threshold end range value (for operator RG, set
          to 0 otherwise)";
      }
      leaf percent {
        xr:xr-xml-map "manageability_perf_thresh_cfg:Percent";
        type boolean;
        description
          "Set to TRUE if Specified threshold values are
          in percent";
      }
      leaf rearm-type {
        xr:xr-xml-map "manageability_perf_thresh_cfg:RearmType";
        type Pm-threshold-rearm;
        description "Configure the Rearm type";
      }
      leaf rearm-window {
        xr:xr-xml-map "manageability_perf_thresh_cfg:RearmWindow";
        type Pm-threshold-rearm-window;
        description
          "Configure the rearm window size (for rearm type
          Window)";
      }
    }
  }

  grouping INPUT-LSA-ACKS {
    description
      "Common node of ospfv2-protocol-template,
      ospfv3-protocol-template";

    container input-lsa-acks {
      xr:xr-xml-map "manageability_perf_thresh_cfg:InputLSAAcks";
      presence "enable input-lsa-acks";
      description "Number of LSA Acknowledgements received";
      leaf operator {
        xr:xr-xml-map "manageability_perf_thresh_cfg:Operator";
        type Pm-threshold-op;
        description "Operator";
      }
      leaf value {
        xr:xr-xml-map "manageability_perf_thresh_cfg:Value";
        type Pm-threshold-val-range-counter32;
        description
          "Threshold value (or start range value for
          operator RG)";
      }
      leaf end-range-value {
        xr:xr-xml-map "manageability_perf_thresh_cfg:EndRangeValue";
        type Pm-threshold-val-range-counter32;
        description
          "Threshold end range value (for operator RG, set
          to 0 otherwise)";
      }
      leaf percent {
        xr:xr-xml-map "manageability_perf_thresh_cfg:Percent";
        type boolean;
        description
          "Set to TRUE if Specified threshold values are
          in percent";
      }
      leaf rearm-type {
        xr:xr-xml-map "manageability_perf_thresh_cfg:RearmType";
        type Pm-threshold-rearm;
        description "Configure the Rearm type";
      }
      leaf rearm-window {
        xr:xr-xml-map "manageability_perf_thresh_cfg:RearmWindow";
        type Pm-threshold-rearm-window;
        description
          "Configure the rearm window size (for rearm type
          Window)";
      }
    }
  }

  grouping INPUT-LSA-UPDATES {
    description
      "Common node of ospfv2-protocol-template,
      ospfv3-protocol-template";

    container input-lsa-updates {
      xr:xr-xml-map "manageability_perf_thresh_cfg:InputLSAUpdates";
      presence "enable input-lsa-updates";
      description "Number of LSA Updates received";
      leaf operator {
        xr:xr-xml-map "manageability_perf_thresh_cfg:Operator";
        type Pm-threshold-op;
        description "Operator";
      }
      leaf value {
        xr:xr-xml-map "manageability_perf_thresh_cfg:Value";
        type Pm-threshold-val-range-counter32;
        description
          "Threshold value (or start range value for
          operator RG)";
      }
      leaf end-range-value {
        xr:xr-xml-map "manageability_perf_thresh_cfg:EndRangeValue";
        type Pm-threshold-val-range-counter32;
        description
          "Threshold end range value (for operator RG, set
          to 0 otherwise)";
      }
      leaf percent {
        xr:xr-xml-map "manageability_perf_thresh_cfg:Percent";
        type boolean;
        description
          "Set to TRUE if Specified threshold values are
          in percent";
      }
      leaf rearm-type {
        xr:xr-xml-map "manageability_perf_thresh_cfg:RearmType";
        type Pm-threshold-rearm;
        description "Configure the Rearm type";
      }
      leaf rearm-window {
        xr:xr-xml-map "manageability_perf_thresh_cfg:RearmWindow";
        type Pm-threshold-rearm-window;
        description
          "Configure the rearm window size (for rearm type
          Window)";
      }
    }
  }

  grouping OUTPUT-LSA-ACKS-LSA {
    description
      "Common node of ospfv2-protocol-template,
      ospfv3-protocol-template";

    container output-lsa-acks-lsa {
      xr:xr-xml-map "manageability_perf_thresh_cfg:OutputLSAAcksLSA";
      presence "enable output-lsa-acks-lsa";
      description "Number of LSA sent in LSA Acknowledgements";
      leaf operator {
        xr:xr-xml-map "manageability_perf_thresh_cfg:Operator";
        type Pm-threshold-op;
        description "Operator";
      }
      leaf value {
        xr:xr-xml-map "manageability_perf_thresh_cfg:Value";
        type Pm-threshold-val-range-counter32;
        description
          "Threshold value (or start range value for
          operator RG)";
      }
      leaf end-range-value {
        xr:xr-xml-map "manageability_perf_thresh_cfg:EndRangeValue";
        type Pm-threshold-val-range-counter32;
        description
          "Threshold end range value (for operator RG, set
          to 0 otherwise)";
      }
      leaf percent {
        xr:xr-xml-map "manageability_perf_thresh_cfg:Percent";
        type boolean;
        description
          "Set to TRUE if Specified threshold values are
          in percent";
      }
      leaf rearm-type {
        xr:xr-xml-map "manageability_perf_thresh_cfg:RearmType";
        type Pm-threshold-rearm;
        description "Configure the Rearm type";
      }
      leaf rearm-window {
        xr:xr-xml-map "manageability_perf_thresh_cfg:RearmWindow";
        type Pm-threshold-rearm-window;
        description
          "Configure the rearm window size (for rearm type
          Window)";
      }
    }
  }

  grouping INTERFACE-TABLE {
    description
      "Common node of generic-counters, basic-counters,
      data-rates";

    container interfaces {
      xr:xr-xml-map "manageability_perf_enable_monitor_cfg:Interfac"+
        "eTable";
      description "Monitor an Interface";

      list interface {
        xr:xr-xml-map "manageability_perf_enable_monitor_cfg:Interf"+
          "ace";
        key "interface-name";
        description "Interface being Monitored";
        leaf interface-name {
          xr:xr-xml-map "manageability_perf_enable_monitor_cfg:Inte"+
            "rfaceName";
          type xr:Interface-name;
          description "Interface Name";
        }
        uses MANAGEABILITY-PERF-ENABLE-MONITOR-CFG-TEMPLATE-NAME;
      }
    }
  }

  grouping OUTPUT-PACKETS {
    description
      "Common node of ospfv2-protocol-template,
      ospfv3-protocol-template";

    container output-packets {
      xr:xr-xml-map "manageability_perf_thresh_cfg:OutputPackets";
      presence "enable output-packets";
      description "Total number of packets sent";
      leaf operator {
        xr:xr-xml-map "manageability_perf_thresh_cfg:Operator";
        type Pm-threshold-op;
        description "Operator";
      }
      leaf value {
        xr:xr-xml-map "manageability_perf_thresh_cfg:Value";
        type Pm-threshold-val-range-counter32;
        description
          "Threshold value (or start range value for
          operator RG)";
      }
      leaf end-range-value {
        xr:xr-xml-map "manageability_perf_thresh_cfg:EndRangeValue";
        type Pm-threshold-val-range-counter32;
        description
          "Threshold end range value (for operator RG, set
          to 0 otherwise)";
      }
      leaf percent {
        xr:xr-xml-map "manageability_perf_thresh_cfg:Percent";
        type boolean;
        description
          "Set to TRUE if Specified threshold values are
          in percent";
      }
      leaf rearm-type {
        xr:xr-xml-map "manageability_perf_thresh_cfg:RearmType";
        type Pm-threshold-rearm;
        description "Configure the Rearm type";
      }
      leaf rearm-window {
        xr:xr-xml-map "manageability_perf_thresh_cfg:RearmWindow";
        type Pm-threshold-rearm-window;
        description
          "Configure the rearm window size (for rearm type
          Window)";
      }
    }
  }

  grouping OUTPUT-LSA-UPDATES {
    description
      "Common node of ospfv2-protocol-template,
      ospfv3-protocol-template";

    container output-lsa-updates {
      xr:xr-xml-map "manageability_perf_thresh_cfg:OutputLSAUpdates";
      presence "enable output-lsa-updates";
      description "Number of LSA Updates sent";
      leaf operator {
        xr:xr-xml-map "manageability_perf_thresh_cfg:Operator";
        type Pm-threshold-op;
        description "Operator";
      }
      leaf value {
        xr:xr-xml-map "manageability_perf_thresh_cfg:Value";
        type Pm-threshold-val-range-counter32;
        description
          "Threshold value (or start range value for
          operator RG)";
      }
      leaf end-range-value {
        xr:xr-xml-map "manageability_perf_thresh_cfg:EndRangeValue";
        type Pm-threshold-val-range-counter32;
        description
          "Threshold end range value (for operator RG, set
          to 0 otherwise)";
      }
      leaf percent {
        xr:xr-xml-map "manageability_perf_thresh_cfg:Percent";
        type boolean;
        description
          "Set to TRUE if Specified threshold values are
          in percent";
      }
      leaf rearm-type {
        xr:xr-xml-map "manageability_perf_thresh_cfg:RearmType";
        type Pm-threshold-rearm;
        description "Configure the Rearm type";
      }
      leaf rearm-window {
        xr:xr-xml-map "manageability_perf_thresh_cfg:RearmWindow";
        type Pm-threshold-rearm-window;
        description
          "Configure the rearm window size (for rearm type
          Window)";
      }
    }
  }

  grouping OUTPUT-HELLO-PACKETS {
    description
      "Common node of ospfv2-protocol-template,
      ospfv3-protocol-template";

    container output-hello-packets {
      xr:xr-xml-map "manageability_perf_thresh_cfg:OutputHelloPacke"+
        "ts";
      presence "enable output-hello-packets";
      description "Total number of packets sent";
      leaf operator {
        xr:xr-xml-map "manageability_perf_thresh_cfg:Operator";
        type Pm-threshold-op;
        description "Operator";
      }
      leaf value {
        xr:xr-xml-map "manageability_perf_thresh_cfg:Value";
        type Pm-threshold-val-range-counter32;
        description
          "Threshold value (or start range value for
          operator RG)";
      }
      leaf end-range-value {
        xr:xr-xml-map "manageability_perf_thresh_cfg:EndRangeValue";
        type Pm-threshold-val-range-counter32;
        description
          "Threshold end range value (for operator RG, set
          to 0 otherwise)";
      }
      leaf percent {
        xr:xr-xml-map "manageability_perf_thresh_cfg:Percent";
        type boolean;
        description
          "Set to TRUE if Specified threshold values are
          in percent";
      }
      leaf rearm-type {
        xr:xr-xml-map "manageability_perf_thresh_cfg:RearmType";
        type Pm-threshold-rearm;
        description "Configure the Rearm type";
      }
      leaf rearm-window {
        xr:xr-xml-map "manageability_perf_thresh_cfg:RearmWindow";
        type Pm-threshold-rearm-window;
        description
          "Configure the rearm window size (for rearm type
          Window)";
      }
    }
  }

  grouping NODE-TABLE {
    description "Common node of memory, cpu";

    container nodes {
      xr:xr-xml-map "manageability_perf_enable_monitor_cfg:NodeTabl"+
        "e";
      description "Node specification";

      list node {
        xr:xr-xml-map "manageability_perf_enable_monitor_cfg:Node";
        key "node-id";
        description "Node instance";
        leaf node-id {
          xr:xr-xml-map "manageability_perf_enable_monitor_cfg:Node"+
            "ID";
          type xr:Node-id;
          description "Node ID";
        }
        uses MANAGEABILITY-PERF-ENABLE-MONITOR-CFG-TEMPLATE-NAME;
      }
    }
  }

  grouping MANAGEABILITY-PERF-ENABLE-THRESH-CFG-NODE-TABLE {
    description
      "Common node of memory, cpuCommon node of cpu-node
      , memory-node, process-node";

    container nodes {
      xr:xr-xml-map "manageability_perf_enable_thresh_cfg:NodeTable";
      description "Node specification";

      list node {
        xr:xr-xml-map "manageability_perf_enable_thresh_cfg:Node";
        key "node-id";
        description "Node instance";
        leaf node-id {
          xr:xr-xml-map "manageability_perf_enable_thresh_cfg:NodeI"+
            "D";
          type xr:Node-id;
          description "Node ID";
        }
        uses MANAGEABILITY-PERF-ENABLE-THRESH-CFG-TEMPLATE-NAME;
      }
    }
  }

  grouping MANAGEABILITY-PERF-ENABLE-STATS-CFG-NODE-TABLE {
    description
      "Common node of memory, cpuCommon node of cpu-node
      , memory-node, process-nodeCommon node of
      cpu-node, memory-node, process-node";

    container nodes {
      xr:xr-xml-map "manageability_perf_enable_stats_cfg:NodeTable";
      description "Node specification";

      list node {
        xr:xr-xml-map "manageability_perf_enable_stats_cfg:Node";
        key "node-id";
        description "Node instance";
        leaf node-id {
          xr:xr-xml-map "manageability_perf_enable_stats_cfg:NodeID";
          type xr:Node-id;
          description "Node ID";
        }
        uses TEMPLATE-NAME;
      }
    }
  }

  grouping OUTPUT-DB-DS {
    description
      "Common node of ospfv2-protocol-template,
      ospfv3-protocol-template";

    container output-db-ds {
      xr:xr-xml-map "manageability_perf_thresh_cfg:OutputDBDs";
      presence "enable output-db-ds";
      description "Number of DBD packets sent";
      leaf operator {
        xr:xr-xml-map "manageability_perf_thresh_cfg:Operator";
        type Pm-threshold-op;
        description "Operator";
      }
      leaf value {
        xr:xr-xml-map "manageability_perf_thresh_cfg:Value";
        type Pm-threshold-val-range-counter32;
        description
          "Threshold value (or start range value for
          operator RG)";
      }
      leaf end-range-value {
        xr:xr-xml-map "manageability_perf_thresh_cfg:EndRangeValue";
        type Pm-threshold-val-range-counter32;
        description
          "Threshold end range value (for operator RG, set
          to 0 otherwise)";
      }
      leaf percent {
        xr:xr-xml-map "manageability_perf_thresh_cfg:Percent";
        type boolean;
        description
          "Set to TRUE if Specified threshold values are
          in percent";
      }
      leaf rearm-type {
        xr:xr-xml-map "manageability_perf_thresh_cfg:RearmType";
        type Pm-threshold-rearm;
        description "Configure the Rearm type";
      }
      leaf rearm-window {
        xr:xr-xml-map "manageability_perf_thresh_cfg:RearmWindow";
        type Pm-threshold-rearm-window;
        description
          "Configure the rearm window size (for rearm type
          Window)";
      }
    }
  }

  grouping INPUT-LS-REQUESTS-LSA {
    description
      "Common node of ospfv2-protocol-template,
      ospfv3-protocol-template";

    container input-ls-requests-lsa {
      xr:xr-xml-map "manageability_perf_thresh_cfg:InputLSRequestsL"+
        "SA";
      presence "enable input-ls-requests-lsa";
      description "Number of LSA received in LS Requests";
      leaf operator {
        xr:xr-xml-map "manageability_perf_thresh_cfg:Operator";
        type Pm-threshold-op;
        description "Operator";
      }
      leaf value {
        xr:xr-xml-map "manageability_perf_thresh_cfg:Value";
        type Pm-threshold-val-range-counter32;
        description
          "Threshold value (or start range value for
          operator RG)";
      }
      leaf end-range-value {
        xr:xr-xml-map "manageability_perf_thresh_cfg:EndRangeValue";
        type Pm-threshold-val-range-counter32;
        description
          "Threshold end range value (for operator RG, set
          to 0 otherwise)";
      }
      leaf percent {
        xr:xr-xml-map "manageability_perf_thresh_cfg:Percent";
        type boolean;
        description
          "Set to TRUE if Specified threshold values are
          in percent";
      }
      leaf rearm-type {
        xr:xr-xml-map "manageability_perf_thresh_cfg:RearmType";
        type Pm-threshold-rearm;
        description "Configure the Rearm type";
      }
      leaf rearm-window {
        xr:xr-xml-map "manageability_perf_thresh_cfg:RearmWindow";
        type Pm-threshold-rearm-window;
        description
          "Configure the rearm window size (for rearm type
          Window)";
      }
    }
  }

  grouping OUTPUT-LS-REQUESTS-LSA {
    description
      "Common node of ospfv2-protocol-template,
      ospfv3-protocol-template";

    container output-ls-requests-lsa {
      xr:xr-xml-map "manageability_perf_thresh_cfg:OutputLSRequests"+
        "LSA";
      presence "enable output-ls-requests-lsa";
      description "Number of LSA sent in LS Requests";
      leaf operator {
        xr:xr-xml-map "manageability_perf_thresh_cfg:Operator";
        type Pm-threshold-op;
        description "Operator";
      }
      leaf value {
        xr:xr-xml-map "manageability_perf_thresh_cfg:Value";
        type Pm-threshold-val-range-counter32;
        description
          "Threshold value (or start range value for
          operator RG)";
      }
      leaf end-range-value {
        xr:xr-xml-map "manageability_perf_thresh_cfg:EndRangeValue";
        type Pm-threshold-val-range-counter32;
        description
          "Threshold end range value (for operator RG, set
          to 0 otherwise)";
      }
      leaf percent {
        xr:xr-xml-map "manageability_perf_thresh_cfg:Percent";
        type boolean;
        description
          "Set to TRUE if Specified threshold values are
          in percent";
      }
      leaf rearm-type {
        xr:xr-xml-map "manageability_perf_thresh_cfg:RearmType";
        type Pm-threshold-rearm;
        description "Configure the Rearm type";
      }
      leaf rearm-window {
        xr:xr-xml-map "manageability_perf_thresh_cfg:RearmWindow";
        type Pm-threshold-rearm-window;
        description
          "Configure the rearm window size (for rearm type
          Window)";
      }
    }
  }

  grouping OUTPUT-LSA-ACKS {
    description
      "Common node of ospfv2-protocol-template,
      ospfv3-protocol-template";

    container output-lsa-acks {
      xr:xr-xml-map "manageability_perf_thresh_cfg:OutputLSAAcks";
      presence "enable output-lsa-acks";
      description "Number of LSA Acknowledgements sent";
      leaf operator {
        xr:xr-xml-map "manageability_perf_thresh_cfg:Operator";
        type Pm-threshold-op;
        description "Operator";
      }
      leaf value {
        xr:xr-xml-map "manageability_perf_thresh_cfg:Value";
        type Pm-threshold-val-range-counter32;
        description
          "Threshold value (or start range value for
          operator RG)";
      }
      leaf end-range-value {
        xr:xr-xml-map "manageability_perf_thresh_cfg:EndRangeValue";
        type Pm-threshold-val-range-counter32;
        description
          "Threshold end range value (for operator RG, set
          to 0 otherwise)";
      }
      leaf percent {
        xr:xr-xml-map "manageability_perf_thresh_cfg:Percent";
        type boolean;
        description
          "Set to TRUE if Specified threshold values are
          in percent";
      }
      leaf rearm-type {
        xr:xr-xml-map "manageability_perf_thresh_cfg:RearmType";
        type Pm-threshold-rearm;
        description "Configure the Rearm type";
      }
      leaf rearm-window {
        xr:xr-xml-map "manageability_perf_thresh_cfg:RearmWindow";
        type Pm-threshold-rearm-window;
        description
          "Configure the rearm window size (for rearm type
          Window)";
      }
    }
  }

  grouping INPUT-DB-DS-LSA {
    description
      "Common node of ospfv2-protocol-template,
      ospfv3-protocol-template";

    container input-db-ds-lsa {
      xr:xr-xml-map "manageability_perf_thresh_cfg:InputDBDsLSA";
      presence "enable input-db-ds-lsa";
      description "Number of LSA received in DBD packets";
      leaf operator {
        xr:xr-xml-map "manageability_perf_thresh_cfg:Operator";
        type Pm-threshold-op;
        description "Operator";
      }
      leaf value {
        xr:xr-xml-map "manageability_perf_thresh_cfg:Value";
        type Pm-threshold-val-range-counter32;
        description
          "Threshold value (or start range value for
          operator RG)";
      }
      leaf end-range-value {
        xr:xr-xml-map "manageability_perf_thresh_cfg:EndRangeValue";
        type Pm-threshold-val-range-counter32;
        description
          "Threshold end range value (for operator RG, set
          to 0 otherwise)";
      }
      leaf percent {
        xr:xr-xml-map "manageability_perf_thresh_cfg:Percent";
        type boolean;
        description
          "Set to TRUE if Specified threshold values are
          in percent";
      }
      leaf rearm-type {
        xr:xr-xml-map "manageability_perf_thresh_cfg:RearmType";
        type Pm-threshold-rearm;
        description "Configure the Rearm type";
      }
      leaf rearm-window {
        xr:xr-xml-map "manageability_perf_thresh_cfg:RearmWindow";
        type Pm-threshold-rearm-window;
        description
          "Configure the rearm window size (for rearm type
          Window)";
      }
    }
  }

  grouping INPUT-LS-REQUESTS {
    description
      "Common node of ospfv2-protocol-template,
      ospfv3-protocol-template";

    container input-ls-requests {
      xr:xr-xml-map "manageability_perf_thresh_cfg:InputLSRequests";
      presence "enable input-ls-requests";
      description "Number of LS Requests received";
      leaf operator {
        xr:xr-xml-map "manageability_perf_thresh_cfg:Operator";
        type Pm-threshold-op;
        description "Operator";
      }
      leaf value {
        xr:xr-xml-map "manageability_perf_thresh_cfg:Value";
        type Pm-threshold-val-range-counter32;
        description
          "Threshold value (or start range value for
          operator RG)";
      }
      leaf end-range-value {
        xr:xr-xml-map "manageability_perf_thresh_cfg:EndRangeValue";
        type Pm-threshold-val-range-counter32;
        description
          "Threshold end range value (for operator RG, set
          to 0 otherwise)";
      }
      leaf percent {
        xr:xr-xml-map "manageability_perf_thresh_cfg:Percent";
        type boolean;
        description
          "Set to TRUE if Specified threshold values are
          in percent";
      }
      leaf rearm-type {
        xr:xr-xml-map "manageability_perf_thresh_cfg:RearmType";
        type Pm-threshold-rearm;
        description "Configure the Rearm type";
      }
      leaf rearm-window {
        xr:xr-xml-map "manageability_perf_thresh_cfg:RearmWindow";
        type Pm-threshold-rearm-window;
        description
          "Configure the rearm window size (for rearm type
          Window)";
      }
    }
  }

  grouping INPUT-HELLO-PACKETS {
    description
      "Common node of ospfv2-protocol-template,
      ospfv3-protocol-template";

    container input-hello-packets {
      xr:xr-xml-map "manageability_perf_thresh_cfg:InputHelloPacket"+
        "s";
      presence "enable input-hello-packets";
      description "Number of Hello packets received";
      leaf operator {
        xr:xr-xml-map "manageability_perf_thresh_cfg:Operator";
        type Pm-threshold-op;
        description "Operator";
      }
      leaf value {
        xr:xr-xml-map "manageability_perf_thresh_cfg:Value";
        type Pm-threshold-val-range-counter32;
        description
          "Threshold value (or start range value for
          operator RG)";
      }
      leaf end-range-value {
        xr:xr-xml-map "manageability_perf_thresh_cfg:EndRangeValue";
        type Pm-threshold-val-range-counter32;
        description
          "Threshold end range value (for operator RG, set
          to 0 otherwise)";
      }
      leaf percent {
        xr:xr-xml-map "manageability_perf_thresh_cfg:Percent";
        type boolean;
        description
          "Set to TRUE if Specified threshold values are
          in percent";
      }
      leaf rearm-type {
        xr:xr-xml-map "manageability_perf_thresh_cfg:RearmType";
        type Pm-threshold-rearm;
        description "Configure the Rearm type";
      }
      leaf rearm-window {
        xr:xr-xml-map "manageability_perf_thresh_cfg:RearmWindow";
        type Pm-threshold-rearm-window;
        description
          "Configure the rearm window size (for rearm type
          Window)";
      }
    }
  }

  container perf-mgmt {
    xr:xr-xml-map "manageability_perf_cfg_common:PerfMgmt";
    description "Performance Management configuration & operations";

    container resources {
      xr:xr-xml-map "manageability_perf_cfg_common:Resources";
      description "Resources configuration";

      container tftp-resources {
        xr:xr-xml-map "manageability_perf_cfg_common:TFTPResources";
        presence "Indicates a tftp-resources node is configured.";
        description
          "Configure the TFTP server IP address and
          directory name";
        leaf server-address {
          xr:xr-xml-map "manageability_perf_cfg_common:ServerAddres"+
            "s";
          type inet:ipv4-address-no-zone;
          mandatory true;
          description "IP address of the TFTP server";
        }
        leaf directory {
          xr:xr-xml-map "manageability_perf_cfg_common:Directory";
          type string;
          mandatory true;
          description "Directory name on TFTP server";
        }
        leaf vrf-name {
          xr:xr-xml-map "manageability_perf_cfg_common:VRFName";
          type xr:Cisco-ios-xr-string {
            length "0..32";
          }
          description "VRF name";
        }
      }

      container dump-local {
        xr:xr-xml-map "manageability_perf_cfg_common:DumpLocal";
        description "Configure local dump parameters";
        leaf enable {
          xr:xr-xml-map "manageability_perf_cfg_common:Enable";
          xr:xr-cli-map "resources dump local ";
          type empty;
          description "Enable data dump onto local filesystem";
        }
      }

      container memory-resources {
        xr:xr-xml-map "manageability_perf_cfg_common:MemoryResource"+
          "s";
        description
          "Configure the memory usage limits of
          performance management";
        leaf max-limit {
          xr:xr-xml-map "manageability_perf_cfg_common:MaxLimit";
          type int32;
          units "kilobyte";
          description
            "Maximum limit for memory usage (Kbytes) for
            data buffers";
        }
        leaf min-reserved {
          xr:xr-xml-map "manageability_perf_cfg_common:MinReserved";
          type int32;
          units "kilobyte";
          description
            "Specify a minimum free memory (Kbytes) to be
            ensured before allowing a collection request";
        }
      }
    }

    container statistics {
      xr:xr-xml-map "manageability_perf_stats_cfg:Statistics";
      description "Templates for collection of statistics";

      container generic-counter-interface {
        xr:xr-xml-map "manageability_perf_stats_cfg:GenericCounterI"+
          "nterface";
        description
          "Interface Generic GenericCounter collection
          templates";
        uses TEMPLATE-TABLE;
      }

      container process-node {
        xr:xr-xml-map "manageability_perf_stats_cfg:ProcessNode";
        description "Node Process collection templates";
        uses TEMPLATE-TABLE;
      }

      container basic-counter-interface {
        xr:xr-xml-map "manageability_perf_stats_cfg:BasicCounterInt"+
          "erface";
        description "Interface BasicCounter collection templates";
        uses TEMPLATE-TABLE;
      }

      container ospfv3-protocol {
        xr:xr-xml-map "manageability_perf_stats_cfg:OSPFv3Protocol";
        description "OSPF v3 Protocol collection templates";
        uses TEMPLATE-TABLE;
      }

      container cpu-node {
        xr:xr-xml-map "manageability_perf_stats_cfg:CPUNode";
        description "Node CPU collection templates";
        uses TEMPLATE-TABLE;
      }

      container data-rate-interface {
        xr:xr-xml-map "manageability_perf_stats_cfg:DataRateInterfa"+
          "ce";
        description "Interface DataRate collection templates";
        uses TEMPLATE-TABLE;
      }

      container memory-node {
        xr:xr-xml-map "manageability_perf_stats_cfg:MemoryNode";
        description "Node Memory collection templates";
        uses TEMPLATE-TABLE;
      }

      container ldp-mpls {
        xr:xr-xml-map "manageability_perf_stats_cfg:LDP_MPLS";
        description "MPLS LDP collection templates";
        uses TEMPLATE-TABLE;
      }

      container bgp {
        xr:xr-xml-map "manageability_perf_stats_cfg:BGP";
        description "BGP collection templates";
        uses TEMPLATE-TABLE;
      }

      container ospfv2-protocol {
        xr:xr-xml-map "manageability_perf_stats_cfg:OSPFv2Protocol";
        description "OSPF v2 Protocol collection templates";
        uses TEMPLATE-TABLE;
      }
    }

    container enable {
      xr:xr-xml-map "manageability_perf_cfg_common:Enable";
      description
        "Start data collection and/or threshold
        monitoring";

      container threshold {
        xr:xr-xml-map "manageability_perf_enable_thresh_cfg:Thresho"+
          "ld";
        description
          "Start threshold monitoring using a defined
          template";

        container ospfv3-protocol {
          xr:xr-xml-map "manageability_perf_enable_thresh_cfg:OSPFv"+
            "3Protocol";
          description "Threshold monitoring for OSPF v3 Protocol";
          uses MANAGEABILITY-PERF-ENABLE-THRESH-CFG-TEMPLATE-NAME;
        }

        container bgp {
          xr:xr-xml-map "manageability_perf_enable_thresh_cfg:BGP";
          description "Threshold monitoring for BGP";
          uses MANAGEABILITY-PERF-ENABLE-THRESH-CFG-TEMPLATE-NAME;
        }

        container data-rate-interface {
          xr:xr-xml-map "manageability_perf_enable_thresh_cfg:DataR"+
            "ateInterface";
          description
            "Threshold monitoring for Interface  data-rates";
          uses MANAGEABILITY-PERF-ENABLE-THRESH-CFG-TEMPLATE-NAME;
        }

        container ospfv2-protocol {
          xr:xr-xml-map "manageability_perf_enable_thresh_cfg:OSPFv"+
            "2Protocol";
          description "Threshold monitoring for OSPF v2 Protocol";
          uses MANAGEABILITY-PERF-ENABLE-THRESH-CFG-TEMPLATE-NAME;
        }

        container memory-node {
          xr:xr-xml-map "manageability_perf_enable_thresh_cfg:Memor"+
            "yNode";
          description "Threshold monitoring for memory";
          uses MANAGEABILITY-PERF-ENABLE-THRESH-CFG-NODE-TABLE;
          uses MANAGEABILITY-PERF-ENABLE-THRESH-CFG-NODE-ALL;
        }

        container generic-counter-interface {
          xr:xr-xml-map "manageability_perf_enable_thresh_cfg:Gener"+
            "icCounterInterface";
          description
            "Threshold monitoring for Interface
            generic-counters";
          uses MANAGEABILITY-PERF-ENABLE-THRESH-CFG-TEMPLATE-NAME;
        }

        container cpu-node {
          xr:xr-xml-map "manageability_perf_enable_thresh_cfg:CPUNo"+
            "de";
          description "Threshold monitoring for CPU";
          uses MANAGEABILITY-PERF-ENABLE-THRESH-CFG-NODE-TABLE;
          uses MANAGEABILITY-PERF-ENABLE-THRESH-CFG-NODE-ALL;
        }

        container ldp-mpls {
          xr:xr-xml-map "manageability_perf_enable_thresh_cfg:LDP_M"+
            "PLS";
          description "Threshold monitoring for LDP";
          uses MANAGEABILITY-PERF-ENABLE-THRESH-CFG-TEMPLATE-NAME;
        }

        container process-node {
          xr:xr-xml-map "manageability_perf_enable_thresh_cfg:Proce"+
            "ssNode";
          description "Threshold monitoring for process";
          uses MANAGEABILITY-PERF-ENABLE-THRESH-CFG-NODE-TABLE;
          uses MANAGEABILITY-PERF-ENABLE-THRESH-CFG-NODE-ALL;
        }

        container basic-counter-interface {
          xr:xr-xml-map "manageability_perf_enable_thresh_cfg:Basic"+
            "CounterInterface";
          description
            "Threshold monitoring for Interface
            basic-counters";
          uses MANAGEABILITY-PERF-ENABLE-THRESH-CFG-TEMPLATE-NAME;
        }
      }

      container statistics {
        xr:xr-xml-map "manageability_perf_enable_stats_cfg:Statisti"+
          "cs";
        description
          "Start periodic collection using a defined a
          template";

        container generic-counter-interface {
          xr:xr-xml-map "manageability_perf_enable_stats_cfg:Generi"+
            "cCounterInterface";
          description "Statistics collection for generic-counters";
          uses TEMPLATE-NAME;
        }

        container bgp {
          xr:xr-xml-map "manageability_perf_enable_stats_cfg:BGP";
          description "Data collection for BGP";
          uses TEMPLATE-NAME;
        }

        container ospfv2-protocol {
          xr:xr-xml-map "manageability_perf_enable_stats_cfg:OSPFv2"+
            "Protocol";
          description "Data collection for OSPF v2 Protocol";
          uses TEMPLATE-NAME;
        }

        container ospfv3-protocol {
          xr:xr-xml-map "manageability_perf_enable_stats_cfg:OSPFv3"+
            "Protocol";
          description "Data collection for OSPF v3 Protocol";
          uses TEMPLATE-NAME;
        }

        container cpu-node {
          xr:xr-xml-map "manageability_perf_enable_stats_cfg:CPUNod"+
            "e";
          description "Collection for CPU";
          uses NODE-ALL;
          uses MANAGEABILITY-PERF-ENABLE-STATS-CFG-NODE-TABLE;
        }

        container basic-counter-interface {
          xr:xr-xml-map "manageability_perf_enable_stats_cfg:BasicC"+
            "ounterInterface";
          description "Statistics collection for basic-counters";
          uses TEMPLATE-NAME;
        }

        container process-node {
          xr:xr-xml-map "manageability_perf_enable_stats_cfg:Proces"+
            "sNode";
          description "Collection for process";
          uses NODE-ALL;
          uses MANAGEABILITY-PERF-ENABLE-STATS-CFG-NODE-TABLE;
        }

        container data-rate-interface {
          xr:xr-xml-map "manageability_perf_enable_stats_cfg:DataRa"+
            "teInterface";
          description "Statistics collection for generic-counters";
          uses TEMPLATE-NAME;
        }

        container memory-node {
          xr:xr-xml-map "manageability_perf_enable_stats_cfg:Memory"+
            "Node";
          description "Collection for memory";
          uses NODE-ALL;
          uses MANAGEABILITY-PERF-ENABLE-STATS-CFG-NODE-TABLE;
        }

        container ldp-mpls {
          xr:xr-xml-map "manageability_perf_enable_stats_cfg:LDP_MP"+
            "LS";
          description "Collection for labels distribution protocol";
          uses TEMPLATE-NAME;
        }
      }

      container monitor-enable {
        xr:xr-xml-map "manageability_perf_enable_monitor_cfg:Monito"+
          "rEnable";
        description
          "Start data collection for a monitored instance";

        container ldp-mpls {
          xr:xr-xml-map "manageability_perf_enable_monitor_cfg:LDP_"+
            "MPLS";
          description "Monitoring for LDP";

          container sessions {
            xr:xr-xml-map "manageability_perf_enable_monitor_cfg:Se"+
              "ssionTable";
            description "LDP session specification";

            list session {
              xr:xr-xml-map "manageability_perf_enable_monitor_cfg:"+
                "Session";
              key "session";
              description "IP address of the LDP Session";
              leaf session {
                xr:xr-xml-map "manageability_perf_enable_monitor_cf"+
                  "g:session";
                type inet:ipv4-address-no-zone;
                description "IP address of the LDP Session";
              }
              uses "MANAGEABILITY-PERF-ENABLE"+
                "-MONITOR-CFG-TEMPLATE-NAME";
            }
          }
        }

        container ospfv3-protocol {
          xr:xr-xml-map "manageability_perf_enable_monitor_cfg:OSPF"+
            "v3Protocol";
          description "Monitor OSPF v3 Protocol";
          uses OSPF-INSTANCE-TABLE;
        }

        container generic-counters {
          xr:xr-xml-map "manageability_perf_enable_monitor_cfg:Gene"+
            "ricCounters";
          description "Monitoring for generic-counters";
          uses INTERFACE-TABLE;
        }

        container process {
          xr:xr-xml-map "manageability_perf_enable_monitor_cfg:Proc"+
            "ess";
          description "Collection for a single process";

          container process-nodes {
            xr:xr-xml-map "manageability_perf_enable_monitor_cfg:Pr"+
              "ocessNodeTable";
            description "Node specification";

            list process-node {
              xr:xr-xml-map "manageability_perf_enable_monitor_cfg:"+
                "ProcessNode";
              key "node-id";
              description "Node instance";

              container pids {
                xr:xr-xml-map "manageability_perf_enable_monitor_cf"+
                  "g:PIDTable";
                description "Process ID specification";

                list pid {
                  xr:xr-xml-map "manageability_perf_enable_monitor_"+
                    "cfg:PID";
                  key "pid";
                  description
                    "Specify an existing template for data
                    collection";
                  leaf pid {
                    xr:xr-xml-map "manageability_perf_enable_monito"+
                      "r_cfg:PID";
                    type Pid-range;
                    description "Specify Process ID";
                  }
                  uses "MANAGEABILITY-PERF-ENABLE"+
                    "-MONITOR-CFG-TEMPLATE-NAME";
                }
              }
              leaf node-id {
                xr:xr-xml-map "manageability_perf_enable_monitor_cf"+
                  "g:NodeID";
                type xr:Node-id;
                description "Node ID";
              }
            }
          }
        }

        container basic-counters {
          xr:xr-xml-map "manageability_perf_enable_monitor_cfg:Basi"+
            "cCounters";
          description "Monitoring for basic-counters";
          uses INTERFACE-TABLE;
        }

        container memory {
          xr:xr-xml-map "manageability_perf_enable_monitor_cfg:Memo"+
            "ry";
          description "Collection for memory";
          uses NODE-TABLE;
        }

        container ospfv2-protocol {
          xr:xr-xml-map "manageability_perf_enable_monitor_cfg:OSPF"+
            "v2Protocol";
          description "Monitor OSPF v2 Protocol";
          uses OSPF-INSTANCE-TABLE;
        }

        container cpu {
          xr:xr-xml-map "manageability_perf_enable_monitor_cfg:CPU";
          description "Collection for CPU";
          uses NODE-TABLE;
        }

        container bgp {
          xr:xr-xml-map "manageability_perf_enable_monitor_cfg:BGP";
          description "Monitor BGP protocol";

          container neighbors {
            xr:xr-xml-map "manageability_perf_enable_monitor_cfg:Ne"+
              "ighborTable";
            description "Monitor BGP protocol for a BGP peer";

            list neighbor {
              xr:xr-xml-map "manageability_perf_enable_monitor_cfg:"+
                "Neighbor";
              key "peer-address";
              description "Neighbor being monitored";
              leaf peer-address {
                xr:xr-xml-map "manageability_perf_enable_monitor_cf"+
                  "g:PeerAddress";
                type inet:ipv4-address-no-zone;
                description "IP address of the Neighbor";
              }
              uses "MANAGEABILITY-PERF-ENABLE"+
                "-MONITOR-CFG-TEMPLATE-NAME";
            }
          }
        }

        container data-rates {
          xr:xr-xml-map "manageability_perf_enable_monitor_cfg:Data"+
            "Rates";
          description "Monitoring for data-rates";
          uses INTERFACE-TABLE;
        }
      }
    }

    container reg-exp-groups {
      xr:xr-xml-map "manageability_perf_cfg_common:RegExpGroupTable";
      description "Configure regular expression group";

      list reg-exp-group {
        xr:xr-xml-map "manageability_perf_cfg_common:RegExpGroup";
        key "reg-exp-group-name";
        description "Specify regular expression group name";

        container reg-exps {
          xr:xr-xml-map "manageability_perf_cfg_common:RegExpTable";
          description "Configure regular expression";

          list reg-exp {
            xr:xr-xml-map "manageability_perf_cfg_common:RegExp";
            xr:xr-cli-map "regular-expression <string> index <numbe"+
              "r> <text> ";
            key "reg-exp-index";
            description "Specify regular expression index number";
            leaf reg-exp-index {
              xr:xr-xml-map "manageability_perf_cfg_common:RegExpIn"+
                "dex";
              type uint32 {
                range "1..100";
              }
              description "Regular expression index number";
            }
            leaf reg-exp-string {
              xr:xr-xml-map "manageability_perf_cfg_common:RegExpSt"+
                "ring";
              type string {
                length "0..128";
              }
              mandatory true;
              description "Regular expression string to match";
            }
          }
        }
        leaf reg-exp-group-name {
          xr:xr-xml-map "manageability_perf_cfg_common:RegExpGroupN"+
            "ame";
          type xr:Cisco-ios-xr-string {
            length "0..32";
          }
          description "Regular expression group name";
        }
      }
    }

    container threshold {
      xr:xr-xml-map "manageability_perf_thresh_cfg:Threshold";
      description "Container for threshold templates";

      container generic-counter-interface {
        xr:xr-xml-map "manageability_perf_thresh_cfg:GenericCounter"+
          "Interface";
        description
          "Interface Generic Counter threshold
          configuration";

        container generic-counter-interface-templates {
          xr:xr-xml-map "manageability_perf_thresh_cfg:GenericCount"+
            "erInterfaceTemplateTable";
          description
            "Interface Generic Counter threshold templates";

          list generic-counter-interface-template {
            xr:xr-xml-map "manageability_perf_thresh_cfg:GenericCou"+
              "nterInterfaceTemplate";
            key "template-name";
            description
              "Interface Generic Counter threshold template
              instance";

            container in-octets {
              xr:xr-xml-map "manageability_perf_thresh_cfg:InOctets";
              presence "enable in-octets";
              description "Number of inbound octets/bytes";
              leaf operator {
                xr:xr-xml-map "manageability_perf_thresh_cfg:Operat"+
                  "or";
                type Pm-threshold-op;
                description "Operator";
              }
              leaf value {
                xr:xr-xml-map "manageability_perf_thresh_cfg:Value";
                type Pm-threshold-val-range-counter32;
                description
                  "Threshold value (or start range value for
                  operator RG)";
              }
              leaf end-range-value {
                xr:xr-xml-map "manageability_perf_thresh_cfg:EndRan"+
                  "geValue";
                type Pm-threshold-val-range-counter32;
                description
                  "Threshold end range value (for operator RG,
                  set to 0 otherwise)";
              }
              leaf percent {
                xr:xr-xml-map "manageability_perf_thresh_cfg:Percen"+
                  "t";
                type boolean;
                description
                  "Set to TRUE if Specified threshold values
                  are in percent";
              }
              leaf rearm-type {
                xr:xr-xml-map "manageability_perf_thresh_cfg:RearmT"+
                  "ype";
                type Pm-threshold-rearm;
                description "Configure the Rearm type";
              }
              leaf rearm-window {
                xr:xr-xml-map "manageability_perf_thresh_cfg:RearmW"+
                  "indow";
                type Pm-threshold-rearm-window;
                description
                  "Configure the rearm window size (for rearm
                  type Window)";
              }
            }

            container in-ucast-pkts {
              xr:xr-xml-map "manageability_perf_thresh_cfg:InUcastP"+
                "kts";
              presence "enable in-ucast-pkts";
              description "Number of inbound unicast packets";
              leaf operator {
                xr:xr-xml-map "manageability_perf_thresh_cfg:Operat"+
                  "or";
                type Pm-threshold-op;
                description "Operator";
              }
              leaf value {
                xr:xr-xml-map "manageability_perf_thresh_cfg:Value";
                type Pm-threshold-val-range-counter32;
                description
                  "Threshold value (or start range value for
                  operator RG)";
              }
              leaf end-range-value {
                xr:xr-xml-map "manageability_perf_thresh_cfg:EndRan"+
                  "geValue";
                type Pm-threshold-val-range-counter32;
                description
                  "Threshold end range value (for operator RG,
                  set to 0 otherwise)";
              }
              leaf percent {
                xr:xr-xml-map "manageability_perf_thresh_cfg:Percen"+
                  "t";
                type boolean;
                description
                  "Set to TRUE if Specified threshold values
                  are in percent";
              }
              leaf rearm-type {
                xr:xr-xml-map "manageability_perf_thresh_cfg:RearmT"+
                  "ype";
                type Pm-threshold-rearm;
                description "Configure the Rearm type";
              }
              leaf rearm-window {
                xr:xr-xml-map "manageability_perf_thresh_cfg:RearmW"+
                  "indow";
                type Pm-threshold-rearm-window;
                description
                  "Configure the rearm window size (for rearm
                  type Window)";
              }
            }

            container out-ucast-pkts {
              xr:xr-xml-map "manageability_perf_thresh_cfg:OutUcast"+
                "Pkts";
              presence "enable out-ucast-pkts";
              description "Number of outbound unicast packets";
              leaf operator {
                xr:xr-xml-map "manageability_perf_thresh_cfg:Operat"+
                  "or";
                type Pm-threshold-op;
                description "Operator";
              }
              leaf value {
                xr:xr-xml-map "manageability_perf_thresh_cfg:Value";
                type Pm-threshold-val-range-counter32;
                description
                  "Threshold value (or start range value for
                  operator RG)";
              }
              leaf end-range-value {
                xr:xr-xml-map "manageability_perf_thresh_cfg:EndRan"+
                  "geValue";
                type Pm-threshold-val-range-counter32;
                description
                  "Threshold end range value (for operator RG,
                  set to 0 otherwise)";
              }
              leaf percent {
                xr:xr-xml-map "manageability_perf_thresh_cfg:Percen"+
                  "t";
                type boolean;
                description
                  "Set to TRUE if Specified threshold values
                  are in percent";
              }
              leaf rearm-type {
                xr:xr-xml-map "manageability_perf_thresh_cfg:RearmT"+
                  "ype";
                type Pm-threshold-rearm;
                description "Configure the Rearm type";
              }
              leaf rearm-window {
                xr:xr-xml-map "manageability_perf_thresh_cfg:RearmW"+
                  "indow";
                type Pm-threshold-rearm-window;
                description
                  "Configure the rearm window size (for rearm
                  type Window)";
              }
            }

            container out-broadcast-pkts {
              xr:xr-xml-map "manageability_perf_thresh_cfg:OutBroad"+
                "castPkts";
              presence "enable out-broadcast-pkts";
              description "Number of outbound broadcast packets";
              leaf operator {
                xr:xr-xml-map "manageability_perf_thresh_cfg:Operat"+
                  "or";
                type Pm-threshold-op;
                description "Operator";
              }
              leaf value {
                xr:xr-xml-map "manageability_perf_thresh_cfg:Value";
                type Pm-threshold-val-range-counter32;
                description
                  "Threshold value (or start range value for
                  operator RG)";
              }
              leaf end-range-value {
                xr:xr-xml-map "manageability_perf_thresh_cfg:EndRan"+
                  "geValue";
                type Pm-threshold-val-range-counter32;
                description
                  "Threshold end range value (for operator RG,
                  set to 0 otherwise)";
              }
              leaf percent {
                xr:xr-xml-map "manageability_perf_thresh_cfg:Percen"+
                  "t";
                type boolean;
                description
                  "Set to TRUE if Specified threshold values
                  are in percent";
              }
              leaf rearm-type {
                xr:xr-xml-map "manageability_perf_thresh_cfg:RearmT"+
                  "ype";
                type Pm-threshold-rearm;
                description "Configure the Rearm type";
              }
              leaf rearm-window {
                xr:xr-xml-map "manageability_perf_thresh_cfg:RearmW"+
                  "indow";
                type Pm-threshold-rearm-window;
                description
                  "Configure the rearm window size (for rearm
                  type Window)";
              }
            }

            container out-multicast-pkts {
              xr:xr-xml-map "manageability_perf_thresh_cfg:OutMulti"+
                "castPkts";
              presence "enable out-multicast-pkts";
              description "Number of outbound multicast packets";
              leaf operator {
                xr:xr-xml-map "manageability_perf_thresh_cfg:Operat"+
                  "or";
                type Pm-threshold-op;
                description "Operator";
              }
              leaf value {
                xr:xr-xml-map "manageability_perf_thresh_cfg:Value";
                type Pm-threshold-val-range-counter32;
                description
                  "Threshold value (or start range value for
                  operator RG)";
              }
              leaf end-range-value {
                xr:xr-xml-map "manageability_perf_thresh_cfg:EndRan"+
                  "geValue";
                type Pm-threshold-val-range-counter32;
                description
                  "Threshold end range value (for operator RG,
                  set to 0 otherwise)";
              }
              leaf percent {
                xr:xr-xml-map "manageability_perf_thresh_cfg:Percen"+
                  "t";
                type boolean;
                description
                  "Set to TRUE if Specified threshold values
                  are in percent";
              }
              leaf rearm-type {
                xr:xr-xml-map "manageability_perf_thresh_cfg:RearmT"+
                  "ype";
                type Pm-threshold-rearm;
                description "Configure the Rearm type";
              }
              leaf rearm-window {
                xr:xr-xml-map "manageability_perf_thresh_cfg:RearmW"+
                  "indow";
                type Pm-threshold-rearm-window;
                description
                  "Configure the rearm window size (for rearm
                  type Window)";
              }
            }

            container input-overrun {
              xr:xr-xml-map "manageability_perf_thresh_cfg:InputOve"+
                "rrun";
              presence "enable input-overrun";
              description
                "Number of inbound packets with overrun
                errors";
              leaf operator {
                xr:xr-xml-map "manageability_perf_thresh_cfg:Operat"+
                  "or";
                type Pm-threshold-op;
                description "Operator";
              }
              leaf value {
                xr:xr-xml-map "manageability_perf_thresh_cfg:Value";
                type Pm-threshold-val-range-counter32;
                description
                  "Threshold value (or start range value for
                  operator RG)";
              }
              leaf end-range-value {
                xr:xr-xml-map "manageability_perf_thresh_cfg:EndRan"+
                  "geValue";
                type Pm-threshold-val-range-counter32;
                description
                  "Threshold end range value (for operator RG,
                  set to 0 otherwise)";
              }
              leaf percent {
                xr:xr-xml-map "manageability_perf_thresh_cfg:Percen"+
                  "t";
                type boolean;
                description
                  "Set to TRUE if Specified threshold values
                  are in percent";
              }
              leaf rearm-type {
                xr:xr-xml-map "manageability_perf_thresh_cfg:RearmT"+
                  "ype";
                type Pm-threshold-rearm;
                description "Configure the Rearm type";
              }
              leaf rearm-window {
                xr:xr-xml-map "manageability_perf_thresh_cfg:RearmW"+
                  "indow";
                type Pm-threshold-rearm-window;
                description
                  "Configure the rearm window size (for rearm
                  type Window)";
              }
            }

            container out-octets {
              xr:xr-xml-map "manageability_perf_thresh_cfg:OutOctet"+
                "s";
              presence "enable out-octets";
              description "Number of outbound octets/bytes";
              leaf operator {
                xr:xr-xml-map "manageability_perf_thresh_cfg:Operat"+
                  "or";
                type Pm-threshold-op;
                description "Operator";
              }
              leaf value {
                xr:xr-xml-map "manageability_perf_thresh_cfg:Value";
                type Pm-threshold-val-range-counter32;
                description
                  "Threshold value (or start range value for
                  operator RG)";
              }
              leaf end-range-value {
                xr:xr-xml-map "manageability_perf_thresh_cfg:EndRan"+
                  "geValue";
                type Pm-threshold-val-range-counter32;
                description
                  "Threshold end range value (for operator RG,
                  set to 0 otherwise)";
              }
              leaf percent {
                xr:xr-xml-map "manageability_perf_thresh_cfg:Percen"+
                  "t";
                type boolean;
                description
                  "Set to TRUE if Specified threshold values
                  are in percent";
              }
              leaf rearm-type {
                xr:xr-xml-map "manageability_perf_thresh_cfg:RearmT"+
                  "ype";
                type Pm-threshold-rearm;
                description "Configure the Rearm type";
              }
              leaf rearm-window {
                xr:xr-xml-map "manageability_perf_thresh_cfg:RearmW"+
                  "indow";
                type Pm-threshold-rearm-window;
                description
                  "Configure the rearm window size (for rearm
                  type Window)";
              }
            }

            container output-underrun {
              xr:xr-xml-map "manageability_perf_thresh_cfg:OutputUn"+
                "derrun";
              presence "enable output-underrun";
              description
                "Number of outbound packets with underrun
                errors";
              leaf operator {
                xr:xr-xml-map "manageability_perf_thresh_cfg:Operat"+
                  "or";
                type Pm-threshold-op;
                description "Operator";
              }
              leaf value {
                xr:xr-xml-map "manageability_perf_thresh_cfg:Value";
                type Pm-threshold-val-range-counter32;
                description
                  "Threshold value (or start range value for
                  operator RG)";
              }
              leaf end-range-value {
                xr:xr-xml-map "manageability_perf_thresh_cfg:EndRan"+
                  "geValue";
                type Pm-threshold-val-range-counter32;
                description
                  "Threshold end range value (for operator RG,
                  set to 0 otherwise)";
              }
              leaf percent {
                xr:xr-xml-map "manageability_perf_thresh_cfg:Percen"+
                  "t";
                type boolean;
                description
                  "Set to TRUE if Specified threshold values
                  are in percent";
              }
              leaf rearm-type {
                xr:xr-xml-map "manageability_perf_thresh_cfg:RearmT"+
                  "ype";
                type Pm-threshold-rearm;
                description "Configure the Rearm type";
              }
              leaf rearm-window {
                xr:xr-xml-map "manageability_perf_thresh_cfg:RearmW"+
                  "indow";
                type Pm-threshold-rearm-window;
                description
                  "Configure the rearm window size (for rearm
                  type Window)";
              }
            }

            container input-total-errors {
              xr:xr-xml-map "manageability_perf_thresh_cfg:InputTot"+
                "alErrors";
              presence "enable input-total-errors";
              description
                "Number of inbound incorrect packets
                discarded";
              leaf operator {
                xr:xr-xml-map "manageability_perf_thresh_cfg:Operat"+
                  "or";
                type Pm-threshold-op;
                description "Operator";
              }
              leaf value {
                xr:xr-xml-map "manageability_perf_thresh_cfg:Value";
                type Pm-threshold-val-range-counter32;
                description
                  "Threshold value (or start range value for
                  operator RG)";
              }
              leaf end-range-value {
                xr:xr-xml-map "manageability_perf_thresh_cfg:EndRan"+
                  "geValue";
                type Pm-threshold-val-range-counter32;
                description
                  "Threshold end range value (for operator RG,
                  set to 0 otherwise)";
              }
              leaf percent {
                xr:xr-xml-map "manageability_perf_thresh_cfg:Percen"+
                  "t";
                type boolean;
                description
                  "Set to TRUE if Specified threshold values
                  are in percent";
              }
              leaf rearm-type {
                xr:xr-xml-map "manageability_perf_thresh_cfg:RearmT"+
                  "ype";
                type Pm-threshold-rearm;
                description "Configure the Rearm type";
              }
              leaf rearm-window {
                xr:xr-xml-map "manageability_perf_thresh_cfg:RearmW"+
                  "indow";
                type Pm-threshold-rearm-window;
                description
                  "Configure the rearm window size (for rearm
                  type Window)";
              }
            }

            container output-total-drops {
              xr:xr-xml-map "manageability_perf_thresh_cfg:OutputTo"+
                "talDrops";
              presence "enable output-total-drops";
              description
                "Number of outbound correct packets discarded";
              leaf operator {
                xr:xr-xml-map "manageability_perf_thresh_cfg:Operat"+
                  "or";
                type Pm-threshold-op;
                description "Operator";
              }
              leaf value {
                xr:xr-xml-map "manageability_perf_thresh_cfg:Value";
                type Pm-threshold-val-range-counter32;
                description
                  "Threshold value (or start range value for
                  operator RG)";
              }
              leaf end-range-value {
                xr:xr-xml-map "manageability_perf_thresh_cfg:EndRan"+
                  "geValue";
                type Pm-threshold-val-range-counter32;
                description
                  "Threshold end range value (for operator RG,
                  set to 0 otherwise)";
              }
              leaf percent {
                xr:xr-xml-map "manageability_perf_thresh_cfg:Percen"+
                  "t";
                type boolean;
                description
                  "Set to TRUE if Specified threshold values
                  are in percent";
              }
              leaf rearm-type {
                xr:xr-xml-map "manageability_perf_thresh_cfg:RearmT"+
                  "ype";
                type Pm-threshold-rearm;
                description "Configure the Rearm type";
              }
              leaf rearm-window {
                xr:xr-xml-map "manageability_perf_thresh_cfg:RearmW"+
                  "indow";
                type Pm-threshold-rearm-window;
                description
                  "Configure the rearm window size (for rearm
                  type Window)";
              }
            }

            container input-crc {
              xr:xr-xml-map "manageability_perf_thresh_cfg:InputCRC";
              presence "enable input-crc";
              description
                "Number of inbound packets discarded with
                incorrect CRC";
              leaf operator {
                xr:xr-xml-map "manageability_perf_thresh_cfg:Operat"+
                  "or";
                type Pm-threshold-op;
                description "Operator";
              }
              leaf value {
                xr:xr-xml-map "manageability_perf_thresh_cfg:Value";
                type Pm-threshold-val-range-counter32;
                description
                  "Threshold value (or start range value for
                  operator RG)";
              }
              leaf end-range-value {
                xr:xr-xml-map "manageability_perf_thresh_cfg:EndRan"+
                  "geValue";
                type Pm-threshold-val-range-counter32;
                description
                  "Threshold end range value (for operator RG,
                  set to 0 otherwise)";
              }
              leaf percent {
                xr:xr-xml-map "manageability_perf_thresh_cfg:Percen"+
                  "t";
                type boolean;
                description
                  "Set to TRUE if Specified threshold values
                  are in percent";
              }
              leaf rearm-type {
                xr:xr-xml-map "manageability_perf_thresh_cfg:RearmT"+
                  "ype";
                type Pm-threshold-rearm;
                description "Configure the Rearm type";
              }
              leaf rearm-window {
                xr:xr-xml-map "manageability_perf_thresh_cfg:RearmW"+
                  "indow";
                type Pm-threshold-rearm-window;
                description
                  "Configure the rearm window size (for rearm
                  type Window)";
              }
            }

            container in-broadcast-pkts {
              xr:xr-xml-map "manageability_perf_thresh_cfg:InBroadc"+
                "astPkts";
              presence "enable in-broadcast-pkts";
              description "Number of inbound broadcast packets";
              leaf operator {
                xr:xr-xml-map "manageability_perf_thresh_cfg:Operat"+
                  "or";
                type Pm-threshold-op;
                description "Operator";
              }
              leaf value {
                xr:xr-xml-map "manageability_perf_thresh_cfg:Value";
                type Pm-threshold-val-range-counter32;
                description
                  "Threshold value (or start range value for
                  operator RG)";
              }
              leaf end-range-value {
                xr:xr-xml-map "manageability_perf_thresh_cfg:EndRan"+
                  "geValue";
                type Pm-threshold-val-range-counter32;
                description
                  "Threshold end range value (for operator RG,
                  set to 0 otherwise)";
              }
              leaf percent {
                xr:xr-xml-map "manageability_perf_thresh_cfg:Percen"+
                  "t";
                type boolean;
                description
                  "Set to TRUE if Specified threshold values
                  are in percent";
              }
              leaf rearm-type {
                xr:xr-xml-map "manageability_perf_thresh_cfg:RearmT"+
                  "ype";
                type Pm-threshold-rearm;
                description "Configure the Rearm type";
              }
              leaf rearm-window {
                xr:xr-xml-map "manageability_perf_thresh_cfg:RearmW"+
                  "indow";
                type Pm-threshold-rearm-window;
                description
                  "Configure the rearm window size (for rearm
                  type Window)";
              }
            }

            container in-multicast-pkts {
              xr:xr-xml-map "manageability_perf_thresh_cfg:InMultic"+
                "astPkts";
              presence "enable in-multicast-pkts";
              description "Number of inbound multicast packets";
              leaf operator {
                xr:xr-xml-map "manageability_perf_thresh_cfg:Operat"+
                  "or";
                type Pm-threshold-op;
                description "Operator";
              }
              leaf value {
                xr:xr-xml-map "manageability_perf_thresh_cfg:Value";
                type Pm-threshold-val-range-counter32;
                description
                  "Threshold value (or start range value for
                  operator RG)";
              }
              leaf end-range-value {
                xr:xr-xml-map "manageability_perf_thresh_cfg:EndRan"+
                  "geValue";
                type Pm-threshold-val-range-counter32;
                description
                  "Threshold end range value (for operator RG,
                  set to 0 otherwise)";
              }
              leaf percent {
                xr:xr-xml-map "manageability_perf_thresh_cfg:Percen"+
                  "t";
                type boolean;
                description
                  "Set to TRUE if Specified threshold values
                  are in percent";
              }
              leaf rearm-type {
                xr:xr-xml-map "manageability_perf_thresh_cfg:RearmT"+
                  "ype";
                type Pm-threshold-rearm;
                description "Configure the Rearm type";
              }
              leaf rearm-window {
                xr:xr-xml-map "manageability_perf_thresh_cfg:RearmW"+
                  "indow";
                type Pm-threshold-rearm-window;
                description
                  "Configure the rearm window size (for rearm
                  type Window)";
              }
            }

            container out-packets {
              xr:xr-xml-map "manageability_perf_thresh_cfg:OutPacke"+
                "ts";
              presence "enable out-packets";
              description "Number of outbound packets";
              leaf operator {
                xr:xr-xml-map "manageability_perf_thresh_cfg:Operat"+
                  "or";
                type Pm-threshold-op;
                description "Operator";
              }
              leaf value {
                xr:xr-xml-map "manageability_perf_thresh_cfg:Value";
                type Pm-threshold-val-range-counter32;
                description
                  "Threshold value (or start range value for
                  operator RG)";
              }
              leaf end-range-value {
                xr:xr-xml-map "manageability_perf_thresh_cfg:EndRan"+
                  "geValue";
                type Pm-threshold-val-range-counter32;
                description
                  "Threshold end range value (for operator RG,
                  set to 0 otherwise)";
              }
              leaf percent {
                xr:xr-xml-map "manageability_perf_thresh_cfg:Percen"+
                  "t";
                type boolean;
                description
                  "Set to TRUE if Specified threshold values
                  are in percent";
              }
              leaf rearm-type {
                xr:xr-xml-map "manageability_perf_thresh_cfg:RearmT"+
                  "ype";
                type Pm-threshold-rearm;
                description "Configure the Rearm type";
              }
              leaf rearm-window {
                xr:xr-xml-map "manageability_perf_thresh_cfg:RearmW"+
                  "indow";
                type Pm-threshold-rearm-window;
                description
                  "Configure the rearm window size (for rearm
                  type Window)";
              }
            }

            container output-total-errors {
              xr:xr-xml-map "manageability_perf_thresh_cfg:OutputTo"+
                "talErrors";
              presence "enable output-total-errors";
              description
                "Number of outbound incorrect packets
                discarded";
              leaf operator {
                xr:xr-xml-map "manageability_perf_thresh_cfg:Operat"+
                  "or";
                type Pm-threshold-op;
                description "Operator";
              }
              leaf value {
                xr:xr-xml-map "manageability_perf_thresh_cfg:Value";
                type Pm-threshold-val-range-counter32;
                description
                  "Threshold value (or start range value for
                  operator RG)";
              }
              leaf end-range-value {
                xr:xr-xml-map "manageability_perf_thresh_cfg:EndRan"+
                  "geValue";
                type Pm-threshold-val-range-counter32;
                description
                  "Threshold end range value (for operator RG,
                  set to 0 otherwise)";
              }
              leaf percent {
                xr:xr-xml-map "manageability_perf_thresh_cfg:Percen"+
                  "t";
                type boolean;
                description
                  "Set to TRUE if Specified threshold values
                  are in percent";
              }
              leaf rearm-type {
                xr:xr-xml-map "manageability_perf_thresh_cfg:RearmT"+
                  "ype";
                type Pm-threshold-rearm;
                description "Configure the Rearm type";
              }
              leaf rearm-window {
                xr:xr-xml-map "manageability_perf_thresh_cfg:RearmW"+
                  "indow";
                type Pm-threshold-rearm-window;
                description
                  "Configure the rearm window size (for rearm
                  type Window)";
              }
            }

            container in-packets {
              xr:xr-xml-map "manageability_perf_thresh_cfg:InPacket"+
                "s";
              presence "enable in-packets";
              description "Number of inbound packets";
              leaf operator {
                xr:xr-xml-map "manageability_perf_thresh_cfg:Operat"+
                  "or";
                type Pm-threshold-op;
                description "Operator";
              }
              leaf value {
                xr:xr-xml-map "manageability_perf_thresh_cfg:Value";
                type Pm-threshold-val-range-counter32;
                description
                  "Threshold value (or start range value for
                  operator RG)";
              }
              leaf end-range-value {
                xr:xr-xml-map "manageability_perf_thresh_cfg:EndRan"+
                  "geValue";
                type Pm-threshold-val-range-counter32;
                description
                  "Threshold end range value (for operator RG,
                  set to 0 otherwise)";
              }
              leaf percent {
                xr:xr-xml-map "manageability_perf_thresh_cfg:Percen"+
                  "t";
                type boolean;
                description
                  "Set to TRUE if Specified threshold values
                  are in percent";
              }
              leaf rearm-type {
                xr:xr-xml-map "manageability_perf_thresh_cfg:RearmT"+
                  "ype";
                type Pm-threshold-rearm;
                description "Configure the Rearm type";
              }
              leaf rearm-window {
                xr:xr-xml-map "manageability_perf_thresh_cfg:RearmW"+
                  "indow";
                type Pm-threshold-rearm-window;
                description
                  "Configure the rearm window size (for rearm
                  type Window)";
              }
            }

            container input-unknown-proto {
              xr:xr-xml-map "manageability_perf_thresh_cfg:InputUnk"+
                "nownProto";
              presence "enable input-unknown-proto";
              description
                "Number of inbound packets discarded with
                unknown protocol";
              leaf operator {
                xr:xr-xml-map "manageability_perf_thresh_cfg:Operat"+
                  "or";
                type Pm-threshold-op;
                description "Operator";
              }
              leaf value {
                xr:xr-xml-map "manageability_perf_thresh_cfg:Value";
                type Pm-threshold-val-range-counter32;
                description
                  "Threshold value (or start range value for
                  operator RG)";
              }
              leaf end-range-value {
                xr:xr-xml-map "manageability_perf_thresh_cfg:EndRan"+
                  "geValue";
                type Pm-threshold-val-range-counter32;
                description
                  "Threshold end range value (for operator RG,
                  set to 0 otherwise)";
              }
              leaf percent {
                xr:xr-xml-map "manageability_perf_thresh_cfg:Percen"+
                  "t";
                type boolean;
                description
                  "Set to TRUE if Specified threshold values
                  are in percent";
              }
              leaf rearm-type {
                xr:xr-xml-map "manageability_perf_thresh_cfg:RearmT"+
                  "ype";
                type Pm-threshold-rearm;
                description "Configure the Rearm type";
              }
              leaf rearm-window {
                xr:xr-xml-map "manageability_perf_thresh_cfg:RearmW"+
                  "indow";
                type Pm-threshold-rearm-window;
                description
                  "Configure the rearm window size (for rearm
                  type Window)";
              }
            }

            container input-queue-drops {
              xr:xr-xml-map "manageability_perf_thresh_cfg:InputQue"+
                "ueDrops";
              presence "enable input-queue-drops";
              description "Number of input queue drops";
              leaf operator {
                xr:xr-xml-map "manageability_perf_thresh_cfg:Operat"+
                  "or";
                type Pm-threshold-op;
                description "Operator";
              }
              leaf value {
                xr:xr-xml-map "manageability_perf_thresh_cfg:Value";
                type Pm-threshold-val-range-counter32;
                description
                  "Threshold value (or start range value for
                  operator RG)";
              }
              leaf end-range-value {
                xr:xr-xml-map "manageability_perf_thresh_cfg:EndRan"+
                  "geValue";
                type Pm-threshold-val-range-counter32;
                description
                  "Threshold end range value (for operator RG,
                  set to 0 otherwise)";
              }
              leaf percent {
                xr:xr-xml-map "manageability_perf_thresh_cfg:Percen"+
                  "t";
                type boolean;
                description
                  "Set to TRUE if Specified threshold values
                  are in percent";
              }
              leaf rearm-type {
                xr:xr-xml-map "manageability_perf_thresh_cfg:RearmT"+
                  "ype";
                type Pm-threshold-rearm;
                description "Configure the Rearm type";
              }
              leaf rearm-window {
                xr:xr-xml-map "manageability_perf_thresh_cfg:RearmW"+
                  "indow";
                type Pm-threshold-rearm-window;
                description
                  "Configure the rearm window size (for rearm
                  type Window)";
              }
            }

            container input-total-drops {
              xr:xr-xml-map "manageability_perf_thresh_cfg:InputTot"+
                "alDrops";
              presence "enable input-total-drops";
              description
                "Number of inbound correct packets discarded";
              leaf operator {
                xr:xr-xml-map "manageability_perf_thresh_cfg:Operat"+
                  "or";
                type Pm-threshold-op;
                description "Operator";
              }
              leaf value {
                xr:xr-xml-map "manageability_perf_thresh_cfg:Value";
                type Pm-threshold-val-range-counter32;
                description
                  "Threshold value (or start range value for
                  operator RG)";
              }
              leaf end-range-value {
                xr:xr-xml-map "manageability_perf_thresh_cfg:EndRan"+
                  "geValue";
                type Pm-threshold-val-range-counter32;
                description
                  "Threshold end range value (for operator RG,
                  set to 0 otherwise)";
              }
              leaf percent {
                xr:xr-xml-map "manageability_perf_thresh_cfg:Percen"+
                  "t";
                type boolean;
                description
                  "Set to TRUE if Specified threshold values
                  are in percent";
              }
              leaf rearm-type {
                xr:xr-xml-map "manageability_perf_thresh_cfg:RearmT"+
                  "ype";
                type Pm-threshold-rearm;
                description "Configure the Rearm type";
              }
              leaf rearm-window {
                xr:xr-xml-map "manageability_perf_thresh_cfg:RearmW"+
                  "indow";
                type Pm-threshold-rearm-window;
                description
                  "Configure the rearm window size (for rearm
                  type Window)";
              }
            }

            container input-frame {
              xr:xr-xml-map "manageability_perf_thresh_cfg:InputFra"+
                "me";
              presence "enable input-frame";
              description
                "Number of inbound packets with framing
                errors";
              leaf operator {
                xr:xr-xml-map "manageability_perf_thresh_cfg:Operat"+
                  "or";
                type Pm-threshold-op;
                description "Operator";
              }
              leaf value {
                xr:xr-xml-map "manageability_perf_thresh_cfg:Value";
                type Pm-threshold-val-range-counter32;
                description
                  "Threshold value (or start range value for
                  operator RG)";
              }
              leaf end-range-value {
                xr:xr-xml-map "manageability_perf_thresh_cfg:EndRan"+
                  "geValue";
                type Pm-threshold-val-range-counter32;
                description
                  "Threshold end range value (for operator RG,
                  set to 0 otherwise)";
              }
              leaf percent {
                xr:xr-xml-map "manageability_perf_thresh_cfg:Percen"+
                  "t";
                type boolean;
                description
                  "Set to TRUE if Specified threshold values
                  are in percent";
              }
              leaf rearm-type {
                xr:xr-xml-map "manageability_perf_thresh_cfg:RearmT"+
                  "ype";
                type Pm-threshold-rearm;
                description "Configure the Rearm type";
              }
              leaf rearm-window {
                xr:xr-xml-map "manageability_perf_thresh_cfg:RearmW"+
                  "indow";
                type Pm-threshold-rearm-window;
                description
                  "Configure the rearm window size (for rearm
                  type Window)";
              }
            }
            leaf template-name {
              xr:xr-xml-map "manageability_perf_thresh_cfg:Template"+
                "Name";
              type xr:Cisco-ios-xr-string;
              description "Template Name";
            }
            uses MANAGEABILITY-PERF-THRESH-CFG-SAMPLE-INTERVAL;
            uses REG-EXP-GROUP;
            uses VRF-GROUP;
          }
        }
      }

      container ldp-mpls {
        xr:xr-xml-map "manageability_perf_thresh_cfg:LDP_MPLS";
        description "MPLS LDP threshold configuration";

        container ldp-mpls-templates {
          xr:xr-xml-map "manageability_perf_thresh_cfg:LDP_MPLSTemp"+
            "lateTable";
          description "MPLS LDP threshold templates";

          list ldp-mpls-template {
            xr:xr-xml-map "manageability_perf_thresh_cfg:LDP_MPLSTe"+
              "mplate";
            key "template-name";
            description "MPLS LDP threshold template instance";

            container address-withdraw-msgs-rcvd {
              xr:xr-xml-map "manageability_perf_thresh_cfg:AddressW"+
                "ithdrawMsgsRcvd";
              presence "enable address-withdraw-msgs-rcvd";
              description
                "Number of Address Withdraw messages received";
              leaf operator {
                xr:xr-xml-map "manageability_perf_thresh_cfg:Operat"+
                  "or";
                type Pm-threshold-op;
                description "Operator";
              }
              leaf value {
                xr:xr-xml-map "manageability_perf_thresh_cfg:Value";
                type int32;
                description
                  "Threshold value (or start range value for
                  operator RG)";
              }
              leaf end-range-value {
                xr:xr-xml-map "manageability_perf_thresh_cfg:EndRan"+
                  "geValue";
                type int32;
                description
                  "Threshold end range value (for operator RG,
                  set to 0 otherwise)";
              }
              leaf percent {
                xr:xr-xml-map "manageability_perf_thresh_cfg:Percen"+
                  "t";
                type boolean;
                description
                  "Set to TRUE if Specified threshold values
                  are in percent";
              }
              leaf rearm-type {
                xr:xr-xml-map "manageability_perf_thresh_cfg:RearmT"+
                  "ype";
                type Pm-threshold-rearm;
                description "Configure the Rearm type";
              }
              leaf rearm-window {
                xr:xr-xml-map "manageability_perf_thresh_cfg:RearmW"+
                  "indow";
                type Pm-threshold-rearm-window;
                description
                  "Configure the rearm window size (for rearm
                  type Window)";
              }
            }

            container label-withdraw-msgs-rcvd {
              xr:xr-xml-map "manageability_perf_thresh_cfg:LabelWit"+
                "hdrawMsgsRcvd";
              presence "enable label-withdraw-msgs-rcvd";
              description
                "Number of Label Withdraw messages received";
              leaf operator {
                xr:xr-xml-map "manageability_perf_thresh_cfg:Operat"+
                  "or";
                type Pm-threshold-op;
                description "Operator";
              }
              leaf value {
                xr:xr-xml-map "manageability_perf_thresh_cfg:Value";
                type int32;
                description
                  "Threshold value (or start range value for
                  operator RG)";
              }
              leaf end-range-value {
                xr:xr-xml-map "manageability_perf_thresh_cfg:EndRan"+
                  "geValue";
                type int32;
                description
                  "Threshold end range value (for operator RG,
                  set to 0 otherwise)";
              }
              leaf percent {
                xr:xr-xml-map "manageability_perf_thresh_cfg:Percen"+
                  "t";
                type boolean;
                description
                  "Set to TRUE if Specified threshold values
                  are in percent";
              }
              leaf rearm-type {
                xr:xr-xml-map "manageability_perf_thresh_cfg:RearmT"+
                  "ype";
                type Pm-threshold-rearm;
                description "Configure the Rearm type";
              }
              leaf rearm-window {
                xr:xr-xml-map "manageability_perf_thresh_cfg:RearmW"+
                  "indow";
                type Pm-threshold-rearm-window;
                description
                  "Configure the rearm window size (for rearm
                  type Window)";
              }
            }

            container address-withdraw-msgs-sent {
              xr:xr-xml-map "manageability_perf_thresh_cfg:AddressW"+
                "ithdrawMsgsSent";
              presence "enable address-withdraw-msgs-sent";
              description
                "Number of Address Withdraw messages sent";
              leaf operator {
                xr:xr-xml-map "manageability_perf_thresh_cfg:Operat"+
                  "or";
                type Pm-threshold-op;
                description "Operator";
              }
              leaf value {
                xr:xr-xml-map "manageability_perf_thresh_cfg:Value";
                type int32;
                description
                  "Threshold value (or start range value for
                  operator RG)";
              }
              leaf end-range-value {
                xr:xr-xml-map "manageability_perf_thresh_cfg:EndRan"+
                  "geValue";
                type int32;
                description
                  "Threshold end range value (for operator RG,
                  set to 0 otherwise)";
              }
              leaf percent {
                xr:xr-xml-map "manageability_perf_thresh_cfg:Percen"+
                  "t";
                type boolean;
                description
                  "Set to TRUE if Specified threshold values
                  are in percent";
              }
              leaf rearm-type {
                xr:xr-xml-map "manageability_perf_thresh_cfg:RearmT"+
                  "ype";
                type Pm-threshold-rearm;
                description "Configure the Rearm type";
              }
              leaf rearm-window {
                xr:xr-xml-map "manageability_perf_thresh_cfg:RearmW"+
                  "indow";
                type Pm-threshold-rearm-window;
                description
                  "Configure the rearm window size (for rearm
                  type Window)";
              }
            }

            container label-withdraw-msgs-sent {
              xr:xr-xml-map "manageability_perf_thresh_cfg:LabelWit"+
                "hdrawMsgsSent";
              presence "enable label-withdraw-msgs-sent";
              description "Number of Label Withdraw messages sent";
              leaf operator {
                xr:xr-xml-map "manageability_perf_thresh_cfg:Operat"+
                  "or";
                type Pm-threshold-op;
                description "Operator";
              }
              leaf value {
                xr:xr-xml-map "manageability_perf_thresh_cfg:Value";
                type int32;
                description
                  "Threshold value (or start range value for
                  operator RG)";
              }
              leaf end-range-value {
                xr:xr-xml-map "manageability_perf_thresh_cfg:EndRan"+
                  "geValue";
                type int32;
                description
                  "Threshold end range value (for operator RG,
                  set to 0 otherwise)";
              }
              leaf percent {
                xr:xr-xml-map "manageability_perf_thresh_cfg:Percen"+
                  "t";
                type boolean;
                description
                  "Set to TRUE if Specified threshold values
                  are in percent";
              }
              leaf rearm-type {
                xr:xr-xml-map "manageability_perf_thresh_cfg:RearmT"+
                  "ype";
                type Pm-threshold-rearm;
                description "Configure the Rearm type";
              }
              leaf rearm-window {
                xr:xr-xml-map "manageability_perf_thresh_cfg:RearmW"+
                  "indow";
                type Pm-threshold-rearm-window;
                description
                  "Configure the rearm window size (for rearm
                  type Window)";
              }
            }

            container notification-msgs-rcvd {
              xr:xr-xml-map "manageability_perf_thresh_cfg:Notifica"+
                "tionMsgsRcvd";
              presence "enable notification-msgs-rcvd";
              description
                "Number of Notification messages received";
              leaf operator {
                xr:xr-xml-map "manageability_perf_thresh_cfg:Operat"+
                  "or";
                type Pm-threshold-op;
                description "Operator";
              }
              leaf value {
                xr:xr-xml-map "manageability_perf_thresh_cfg:Value";
                type int32;
                description
                  "Threshold value (or start range value for
                  operator RG)";
              }
              leaf end-range-value {
                xr:xr-xml-map "manageability_perf_thresh_cfg:EndRan"+
                  "geValue";
                type int32;
                description
                  "Threshold end range value (for operator RG,
                  set to 0 otherwise)";
              }
              leaf percent {
                xr:xr-xml-map "manageability_perf_thresh_cfg:Percen"+
                  "t";
                type boolean;
                description
                  "Set to TRUE if Specified threshold values
                  are in percent";
              }
              leaf rearm-type {
                xr:xr-xml-map "manageability_perf_thresh_cfg:RearmT"+
                  "ype";
                type Pm-threshold-rearm;
                description "Configure the Rearm type";
              }
              leaf rearm-window {
                xr:xr-xml-map "manageability_perf_thresh_cfg:RearmW"+
                  "indow";
                type Pm-threshold-rearm-window;
                description
                  "Configure the rearm window size (for rearm
                  type Window)";
              }
            }

            container total-msgs-rcvd {
              xr:xr-xml-map "manageability_perf_thresh_cfg:TotalMsg"+
                "sRcvd";
              presence "enable total-msgs-rcvd";
              description "Total number of messages received";
              leaf operator {
                xr:xr-xml-map "manageability_perf_thresh_cfg:Operat"+
                  "or";
                type Pm-threshold-op;
                description "Operator";
              }
              leaf value {
                xr:xr-xml-map "manageability_perf_thresh_cfg:Value";
                type Pm-threshold-val-range;
                description
                  "Threshold value (or start range value for
                  operator RG)";
              }
              leaf end-range-value {
                xr:xr-xml-map "manageability_perf_thresh_cfg:EndRan"+
                  "geValue";
                type Pm-threshold-val-range;
                description
                  "Threshold end range value (for operator RG,
                  set to 0 otherwise)";
              }
              leaf percent {
                xr:xr-xml-map "manageability_perf_thresh_cfg:Percen"+
                  "t";
                type boolean;
                description
                  "Set to TRUE if Specified threshold values
                  are in percent";
              }
              leaf rearm-type {
                xr:xr-xml-map "manageability_perf_thresh_cfg:RearmT"+
                  "ype";
                type Pm-threshold-rearm;
                description "Configure the Rearm type";
              }
              leaf rearm-window {
                xr:xr-xml-map "manageability_perf_thresh_cfg:RearmW"+
                  "indow";
                type Pm-threshold-rearm-window;
                description
                  "Configure the rearm window size (for rearm
                  type Window)";
              }
            }

            container notification-msgs-sent {
              xr:xr-xml-map "manageability_perf_thresh_cfg:Notifica"+
                "tionMsgsSent";
              presence "enable notification-msgs-sent";
              description "Number of Notification messages sent";
              leaf operator {
                xr:xr-xml-map "manageability_perf_thresh_cfg:Operat"+
                  "or";
                type Pm-threshold-op;
                description "Operator";
              }
              leaf value {
                xr:xr-xml-map "manageability_perf_thresh_cfg:Value";
                type int32;
                description
                  "Threshold value (or start range value for
                  operator RG)";
              }
              leaf end-range-value {
                xr:xr-xml-map "manageability_perf_thresh_cfg:EndRan"+
                  "geValue";
                type int32;
                description
                  "Threshold end range value (for operator RG,
                  set to 0 otherwise)";
              }
              leaf percent {
                xr:xr-xml-map "manageability_perf_thresh_cfg:Percen"+
                  "t";
                type boolean;
                description
                  "Set to TRUE if Specified threshold values
                  are in percent";
              }
              leaf rearm-type {
                xr:xr-xml-map "manageability_perf_thresh_cfg:RearmT"+
                  "ype";
                type Pm-threshold-rearm;
                description "Configure the Rearm type";
              }
              leaf rearm-window {
                xr:xr-xml-map "manageability_perf_thresh_cfg:RearmW"+
                  "indow";
                type Pm-threshold-rearm-window;
                description
                  "Configure the rearm window size (for rearm
                  type Window)";
              }
            }

            container total-msgs-sent {
              xr:xr-xml-map "manageability_perf_thresh_cfg:TotalMsg"+
                "sSent";
              presence "enable total-msgs-sent";
              description "Total number of messages sent";
              leaf operator {
                xr:xr-xml-map "manageability_perf_thresh_cfg:Operat"+
                  "or";
                type Pm-threshold-op;
                description "Operator";
              }
              leaf value {
                xr:xr-xml-map "manageability_perf_thresh_cfg:Value";
                type int32;
                description
                  "Threshold value (or start range value for
                  operator RG)";
              }
              leaf end-range-value {
                xr:xr-xml-map "manageability_perf_thresh_cfg:EndRan"+
                  "geValue";
                type int32;
                description
                  "Threshold end range value (for operator RG,
                  set to 0 otherwise)";
              }
              leaf percent {
                xr:xr-xml-map "manageability_perf_thresh_cfg:Percen"+
                  "t";
                type boolean;
                description
                  "Set to TRUE if Specified threshold values
                  are in percent";
              }
              leaf rearm-type {
                xr:xr-xml-map "manageability_perf_thresh_cfg:RearmT"+
                  "ype";
                type Pm-threshold-rearm;
                description "Configure the Rearm type";
              }
              leaf rearm-window {
                xr:xr-xml-map "manageability_perf_thresh_cfg:RearmW"+
                  "indow";
                type Pm-threshold-rearm-window;
                description
                  "Configure the rearm window size (for rearm
                  type Window)";
              }
            }

            container label-release-msgs-rcvd {
              xr:xr-xml-map "manageability_perf_thresh_cfg:LabelRel"+
                "easeMsgsRcvd";
              presence "enable label-release-msgs-rcvd";
              description
                "Number of LAbel Release messages received";
              leaf operator {
                xr:xr-xml-map "manageability_perf_thresh_cfg:Operat"+
                  "or";
                type Pm-threshold-op;
                description "Operator";
              }
              leaf value {
                xr:xr-xml-map "manageability_perf_thresh_cfg:Value";
                type int32;
                description
                  "Threshold value (or start range value for
                  operator RG)";
              }
              leaf end-range-value {
                xr:xr-xml-map "manageability_perf_thresh_cfg:EndRan"+
                  "geValue";
                type int32;
                description
                  "Threshold end range value (for operator RG,
                  set to 0 otherwise)";
              }
              leaf percent {
                xr:xr-xml-map "manageability_perf_thresh_cfg:Percen"+
                  "t";
                type boolean;
                description
                  "Set to TRUE if Specified threshold values
                  are in percent";
              }
              leaf rearm-type {
                xr:xr-xml-map "manageability_perf_thresh_cfg:RearmT"+
                  "ype";
                type Pm-threshold-rearm;
                description "Configure the Rearm type";
              }
              leaf rearm-window {
                xr:xr-xml-map "manageability_perf_thresh_cfg:RearmW"+
                  "indow";
                type Pm-threshold-rearm-window;
                description
                  "Configure the rearm window size (for rearm
                  type Window)";
              }
            }

            container init-msgs-rcvd {
              xr:xr-xml-map "manageability_perf_thresh_cfg:InitMsgs"+
                "Rcvd";
              presence "enable init-msgs-rcvd";
              description "Number of Init messages received";
              leaf operator {
                xr:xr-xml-map "manageability_perf_thresh_cfg:Operat"+
                  "or";
                type Pm-threshold-op;
                description "Operator";
              }
              leaf value {
                xr:xr-xml-map "manageability_perf_thresh_cfg:Value";
                type int32;
                description
                  "Threshold value (or start range value for
                  operator RG)";
              }
              leaf end-range-value {
                xr:xr-xml-map "manageability_perf_thresh_cfg:EndRan"+
                  "geValue";
                type int32;
                description
                  "Threshold end range value (for operator RG,
                  set to 0 otherwise)";
              }
              leaf percent {
                xr:xr-xml-map "manageability_perf_thresh_cfg:Percen"+
                  "t";
                type boolean;
                description
                  "Set to TRUE if Specified threshold values
                  are in percent";
              }
              leaf rearm-type {
                xr:xr-xml-map "manageability_perf_thresh_cfg:RearmT"+
                  "ype";
                type Pm-threshold-rearm;
                description "Configure the Rearm type";
              }
              leaf rearm-window {
                xr:xr-xml-map "manageability_perf_thresh_cfg:RearmW"+
                  "indow";
                type Pm-threshold-rearm-window;
                description
                  "Configure the rearm window size (for rearm
                  type Window)";
              }
            }

            container label-release-msgs-sent {
              xr:xr-xml-map "manageability_perf_thresh_cfg:LabelRel"+
                "easeMsgsSent";
              presence "enable label-release-msgs-sent";
              description "Number of Label Release messages sent";
              leaf operator {
                xr:xr-xml-map "manageability_perf_thresh_cfg:Operat"+
                  "or";
                type Pm-threshold-op;
                description "Operator";
              }
              leaf value {
                xr:xr-xml-map "manageability_perf_thresh_cfg:Value";
                type int32;
                description
                  "Threshold value (or start range value for
                  operator RG)";
              }
              leaf end-range-value {
                xr:xr-xml-map "manageability_perf_thresh_cfg:EndRan"+
                  "geValue";
                type int32;
                description
                  "Threshold end range value (for operator RG,
                  set to 0 otherwise)";
              }
              leaf percent {
                xr:xr-xml-map "manageability_perf_thresh_cfg:Percen"+
                  "t";
                type boolean;
                description
                  "Set to TRUE if Specified threshold values
                  are in percent";
              }
              leaf rearm-type {
                xr:xr-xml-map "manageability_perf_thresh_cfg:RearmT"+
                  "ype";
                type Pm-threshold-rearm;
                description "Configure the Rearm type";
              }
              leaf rearm-window {
                xr:xr-xml-map "manageability_perf_thresh_cfg:RearmW"+
                  "indow";
                type Pm-threshold-rearm-window;
                description
                  "Configure the rearm window size (for rearm
                  type Window)";
              }
            }

            container init-msgs-sent {
              xr:xr-xml-map "manageability_perf_thresh_cfg:InitMsgs"+
                "Sent";
              presence "enable init-msgs-sent";
              description "Number of Init messages sent";
              leaf operator {
                xr:xr-xml-map "manageability_perf_thresh_cfg:Operat"+
                  "or";
                type Pm-threshold-op;
                description "Operator";
              }
              leaf value {
                xr:xr-xml-map "manageability_perf_thresh_cfg:Value";
                type int32;
                description
                  "Threshold value (or start range value for
                  operator RG)";
              }
              leaf end-range-value {
                xr:xr-xml-map "manageability_perf_thresh_cfg:EndRan"+
                  "geValue";
                type int32;
                description
                  "Threshold end range value (for operator RG,
                  set to 0 otherwise)";
              }
              leaf percent {
                xr:xr-xml-map "manageability_perf_thresh_cfg:Percen"+
                  "t";
                type boolean;
                description
                  "Set to TRUE if Specified threshold values
                  are in percent";
              }
              leaf rearm-type {
                xr:xr-xml-map "manageability_perf_thresh_cfg:RearmT"+
                  "ype";
                type Pm-threshold-rearm;
                description "Configure the Rearm type";
              }
              leaf rearm-window {
                xr:xr-xml-map "manageability_perf_thresh_cfg:RearmW"+
                  "indow";
                type Pm-threshold-rearm-window;
                description
                  "Configure the rearm window size (for rearm
                  type Window)";
              }
            }

            container label-mapping-msgs-rcvd {
              xr:xr-xml-map "manageability_perf_thresh_cfg:LabelMap"+
                "pingMsgsRcvd";
              presence "enable label-mapping-msgs-rcvd";
              description
                "Number of Label Mapping messages received";
              leaf operator {
                xr:xr-xml-map "manageability_perf_thresh_cfg:Operat"+
                  "or";
                type Pm-threshold-op;
                description "Operator";
              }
              leaf value {
                xr:xr-xml-map "manageability_perf_thresh_cfg:Value";
                type int32;
                description
                  "Threshold value (or start range value for
                  operator RG)";
              }
              leaf end-range-value {
                xr:xr-xml-map "manageability_perf_thresh_cfg:EndRan"+
                  "geValue";
                type int32;
                description
                  "Threshold end range value (for operator RG,
                  set to 0 otherwise)";
              }
              leaf percent {
                xr:xr-xml-map "manageability_perf_thresh_cfg:Percen"+
                  "t";
                type boolean;
                description
                  "Set to TRUE if Specified threshold values
                  are in percent";
              }
              leaf rearm-type {
                xr:xr-xml-map "manageability_perf_thresh_cfg:RearmT"+
                  "ype";
                type Pm-threshold-rearm;
                description "Configure the Rearm type";
              }
              leaf rearm-window {
                xr:xr-xml-map "manageability_perf_thresh_cfg:RearmW"+
                  "indow";
                type Pm-threshold-rearm-window;
                description
                  "Configure the rearm window size (for rearm
                  type Window)";
              }
            }

            container keepalive-msgs-rcvd {
              xr:xr-xml-map "manageability_perf_thresh_cfg:Keepaliv"+
                "eMsgsRcvd";
              presence "enable keepalive-msgs-rcvd";
              description "Number of Keepalive messages received";
              leaf operator {
                xr:xr-xml-map "manageability_perf_thresh_cfg:Operat"+
                  "or";
                type Pm-threshold-op;
                description "Operator";
              }
              leaf value {
                xr:xr-xml-map "manageability_perf_thresh_cfg:Value";
                type int32;
                description
                  "Threshold value (or start range value for
                  operator RG)";
              }
              leaf end-range-value {
                xr:xr-xml-map "manageability_perf_thresh_cfg:EndRan"+
                  "geValue";
                type int32;
                description
                  "Threshold end range value (for operator RG,
                  set to 0 otherwise)";
              }
              leaf percent {
                xr:xr-xml-map "manageability_perf_thresh_cfg:Percen"+
                  "t";
                type boolean;
                description
                  "Set to TRUE if Specified threshold values
                  are in percent";
              }
              leaf rearm-type {
                xr:xr-xml-map "manageability_perf_thresh_cfg:RearmT"+
                  "ype";
                type Pm-threshold-rearm;
                description "Configure the Rearm type";
              }
              leaf rearm-window {
                xr:xr-xml-map "manageability_perf_thresh_cfg:RearmW"+
                  "indow";
                type Pm-threshold-rearm-window;
                description
                  "Configure the rearm window size (for rearm
                  type Window)";
              }
            }

            container label-mapping-msgs-sent {
              xr:xr-xml-map "manageability_perf_thresh_cfg:LabelMap"+
                "pingMsgsSent";
              presence "enable label-mapping-msgs-sent";
              description "Number of Label Mapping messages sent";
              leaf operator {
                xr:xr-xml-map "manageability_perf_thresh_cfg:Operat"+
                  "or";
                type Pm-threshold-op;
                description "Operator";
              }
              leaf value {
                xr:xr-xml-map "manageability_perf_thresh_cfg:Value";
                type int32;
                description
                  "Threshold value (or start range value for
                  operator RG)";
              }
              leaf end-range-value {
                xr:xr-xml-map "manageability_perf_thresh_cfg:EndRan"+
                  "geValue";
                type int32;
                description
                  "Threshold end range value (for operator RG,
                  set to 0 otherwise)";
              }
              leaf percent {
                xr:xr-xml-map "manageability_perf_thresh_cfg:Percen"+
                  "t";
                type boolean;
                description
                  "Set to TRUE if Specified threshold values
                  are in percent";
              }
              leaf rearm-type {
                xr:xr-xml-map "manageability_perf_thresh_cfg:RearmT"+
                  "ype";
                type Pm-threshold-rearm;
                description "Configure the Rearm type";
              }
              leaf rearm-window {
                xr:xr-xml-map "manageability_perf_thresh_cfg:RearmW"+
                  "indow";
                type Pm-threshold-rearm-window;
                description
                  "Configure the rearm window size (for rearm
                  type Window)";
              }
            }

            container keepalive-msgs-sent {
              xr:xr-xml-map "manageability_perf_thresh_cfg:Keepaliv"+
                "eMsgsSent";
              presence "enable keepalive-msgs-sent";
              description "Number of Keepalive messages sent";
              leaf operator {
                xr:xr-xml-map "manageability_perf_thresh_cfg:Operat"+
                  "or";
                type Pm-threshold-op;
                description "Operator";
              }
              leaf value {
                xr:xr-xml-map "manageability_perf_thresh_cfg:Value";
                type int32;
                description
                  "Threshold value (or start range value for
                  operator RG)";
              }
              leaf end-range-value {
                xr:xr-xml-map "manageability_perf_thresh_cfg:EndRan"+
                  "geValue";
                type int32;
                description
                  "Threshold end range value (for operator RG,
                  set to 0 otherwise)";
              }
              leaf percent {
                xr:xr-xml-map "manageability_perf_thresh_cfg:Percen"+
                  "t";
                type boolean;
                description
                  "Set to TRUE if Specified threshold values
                  are in percent";
              }
              leaf rearm-type {
                xr:xr-xml-map "manageability_perf_thresh_cfg:RearmT"+
                  "ype";
                type Pm-threshold-rearm;
                description "Configure the Rearm type";
              }
              leaf rearm-window {
                xr:xr-xml-map "manageability_perf_thresh_cfg:RearmW"+
                  "indow";
                type Pm-threshold-rearm-window;
                description
                  "Configure the rearm window size (for rearm
                  type Window)";
              }
            }

            container address-msgs-rcvd {
              xr:xr-xml-map "manageability_perf_thresh_cfg:AddressM"+
                "sgsRcvd";
              presence "enable address-msgs-rcvd";
              description "Number of Address messages received";
              leaf operator {
                xr:xr-xml-map "manageability_perf_thresh_cfg:Operat"+
                  "or";
                type Pm-threshold-op;
                description "Operator";
              }
              leaf value {
                xr:xr-xml-map "manageability_perf_thresh_cfg:Value";
                type int32;
                description
                  "Threshold value (or start range value for
                  operator RG)";
              }
              leaf end-range-value {
                xr:xr-xml-map "manageability_perf_thresh_cfg:EndRan"+
                  "geValue";
                type int32;
                description
                  "Threshold end range value (for operator RG,
                  set to 0 otherwise)";
              }
              leaf percent {
                xr:xr-xml-map "manageability_perf_thresh_cfg:Percen"+
                  "t";
                type boolean;
                description
                  "Set to TRUE if Specified threshold values
                  are in percent";
              }
              leaf rearm-type {
                xr:xr-xml-map "manageability_perf_thresh_cfg:RearmT"+
                  "ype";
                type Pm-threshold-rearm;
                description "Configure the Rearm type";
              }
              leaf rearm-window {
                xr:xr-xml-map "manageability_perf_thresh_cfg:RearmW"+
                  "indow";
                type Pm-threshold-rearm-window;
                description
                  "Configure the rearm window size (for rearm
                  type Window)";
              }
            }

            container address-msgs-sent {
              xr:xr-xml-map "manageability_perf_thresh_cfg:AddressM"+
                "sgsSent";
              presence "enable address-msgs-sent";
              description "Number of Address messages sent";
              leaf operator {
                xr:xr-xml-map "manageability_perf_thresh_cfg:Operat"+
                  "or";
                type Pm-threshold-op;
                description "Operator";
              }
              leaf value {
                xr:xr-xml-map "manageability_perf_thresh_cfg:Value";
                type int32;
                description
                  "Threshold value (or start range value for
                  operator RG)";
              }
              leaf end-range-value {
                xr:xr-xml-map "manageability_perf_thresh_cfg:EndRan"+
                  "geValue";
                type int32;
                description
                  "Threshold end range value (for operator RG,
                  set to 0 otherwise)";
              }
              leaf percent {
                xr:xr-xml-map "manageability_perf_thresh_cfg:Percen"+
                  "t";
                type boolean;
                description
                  "Set to TRUE if Specified threshold values
                  are in percent";
              }
              leaf rearm-type {
                xr:xr-xml-map "manageability_perf_thresh_cfg:RearmT"+
                  "ype";
                type Pm-threshold-rearm;
                description "Configure the Rearm type";
              }
              leaf rearm-window {
                xr:xr-xml-map "manageability_perf_thresh_cfg:RearmW"+
                  "indow";
                type Pm-threshold-rearm-window;
                description
                  "Configure the rearm window size (for rearm
                  type Window)";
              }
            }
            leaf template-name {
              xr:xr-xml-map "manageability_perf_thresh_cfg:Template"+
                "Name";
              type xr:Cisco-ios-xr-string;
              description "Template Name";
            }
            uses SAMPLE-INTERVAL;
          }
        }
      }

      container basic-counter-interface {
        xr:xr-xml-map "manageability_perf_thresh_cfg:BasicCounterIn"+
          "terface";
        description
          "Interface Basic Counter threshold configuration";

        container basic-counter-interface-templates {
          xr:xr-xml-map "manageability_perf_thresh_cfg:BasicCounter"+
            "InterfaceTemplateTable";
          description "Interface Basic Counter threshold templates";

          list basic-counter-interface-template {
            xr:xr-xml-map "manageability_perf_thresh_cfg:BasicCount"+
              "erInterfaceTemplate";
            key "template-name";
            description
              "Interface Basic Counter threshold template
              instance";

            container in-octets {
              xr:xr-xml-map "manageability_perf_thresh_cfg:InOctets";
              presence "enable in-octets";
              description "Number of inbound octets/bytes";
              leaf operator {
                xr:xr-xml-map "manageability_perf_thresh_cfg:Operat"+
                  "or";
                type Pm-threshold-op;
                description "Operator";
              }
              leaf value {
                xr:xr-xml-map "manageability_perf_thresh_cfg:Value";
                type Pm-threshold-val-range-counter32;
                description
                  "Threshold value (or start range value for
                  operator RG)";
              }
              leaf end-range-value {
                xr:xr-xml-map "manageability_perf_thresh_cfg:EndRan"+
                  "geValue";
                type Pm-threshold-val-range-counter32;
                description
                  "Threshold end range value (for operator RG,
                  set to 0 otherwise)";
              }
              leaf percent {
                xr:xr-xml-map "manageability_perf_thresh_cfg:Percen"+
                  "t";
                type boolean;
                description
                  "Set to TRUE if Specified threshold values
                  are in percent";
              }
              leaf rearm-type {
                xr:xr-xml-map "manageability_perf_thresh_cfg:RearmT"+
                  "ype";
                type Pm-threshold-rearm;
                description "Configure the Rearm type";
              }
              leaf rearm-window {
                xr:xr-xml-map "manageability_perf_thresh_cfg:RearmW"+
                  "indow";
                type Pm-threshold-rearm-window;
                description
                  "Configure the rearm window size (for rearm
                  type Window)";
              }
            }

            container out-octets {
              xr:xr-xml-map "manageability_perf_thresh_cfg:OutOctet"+
                "s";
              presence "enable out-octets";
              description "Number of outbound octets/bytes";
              leaf operator {
                xr:xr-xml-map "manageability_perf_thresh_cfg:Operat"+
                  "or";
                type Pm-threshold-op;
                description "Operator";
              }
              leaf value {
                xr:xr-xml-map "manageability_perf_thresh_cfg:Value";
                type Pm-threshold-val-range-counter32;
                description
                  "Threshold value (or start range value for
                  operator RG)";
              }
              leaf end-range-value {
                xr:xr-xml-map "manageability_perf_thresh_cfg:EndRan"+
                  "geValue";
                type Pm-threshold-val-range-counter32;
                description
                  "Threshold end range value (for operator RG,
                  set to 0 otherwise)";
              }
              leaf percent {
                xr:xr-xml-map "manageability_perf_thresh_cfg:Percen"+
                  "t";
                type boolean;
                description
                  "Set to TRUE if Specified threshold values
                  are in percent";
              }
              leaf rearm-type {
                xr:xr-xml-map "manageability_perf_thresh_cfg:RearmT"+
                  "ype";
                type Pm-threshold-rearm;
                description "Configure the Rearm type";
              }
              leaf rearm-window {
                xr:xr-xml-map "manageability_perf_thresh_cfg:RearmW"+
                  "indow";
                type Pm-threshold-rearm-window;
                description
                  "Configure the rearm window size (for rearm
                  type Window)";
              }
            }

            container output-queue-drops {
              xr:xr-xml-map "manageability_perf_thresh_cfg:OutputQu"+
                "eueDrops";
              presence "enable output-queue-drops";
              description "Number of outbound queue drops";
              leaf operator {
                xr:xr-xml-map "manageability_perf_thresh_cfg:Operat"+
                  "or";
                type Pm-threshold-op;
                description "Operator";
              }
              leaf value {
                xr:xr-xml-map "manageability_perf_thresh_cfg:Value";
                type Pm-threshold-val-range-counter32;
                description
                  "Threshold value (or start range value for
                  operator RG)";
              }
              leaf end-range-value {
                xr:xr-xml-map "manageability_perf_thresh_cfg:EndRan"+
                  "geValue";
                type Pm-threshold-val-range-counter32;
                description
                  "Threshold end range value (for operator RG,
                  set to 0 otherwise)";
              }
              leaf percent {
                xr:xr-xml-map "manageability_perf_thresh_cfg:Percen"+
                  "t";
                type boolean;
                description
                  "Set to TRUE if Specified threshold values
                  are in percent";
              }
              leaf rearm-type {
                xr:xr-xml-map "manageability_perf_thresh_cfg:RearmT"+
                  "ype";
                type Pm-threshold-rearm;
                description "Configure the Rearm type";
              }
              leaf rearm-window {
                xr:xr-xml-map "manageability_perf_thresh_cfg:RearmW"+
                  "indow";
                type Pm-threshold-rearm-window;
                description
                  "Configure the rearm window size (for rearm
                  type Window)";
              }
            }

            container input-total-errors {
              xr:xr-xml-map "manageability_perf_thresh_cfg:InputTot"+
                "alErrors";
              presence "enable input-total-errors";
              description
                "Number of inbound incorrect packets
                discarded";
              leaf operator {
                xr:xr-xml-map "manageability_perf_thresh_cfg:Operat"+
                  "or";
                type Pm-threshold-op;
                description "Operator";
              }
              leaf value {
                xr:xr-xml-map "manageability_perf_thresh_cfg:Value";
                type Pm-threshold-val-range-counter32;
                description
                  "Threshold value (or start range value for
                  operator RG)";
              }
              leaf end-range-value {
                xr:xr-xml-map "manageability_perf_thresh_cfg:EndRan"+
                  "geValue";
                type Pm-threshold-val-range-counter32;
                description
                  "Threshold end range value (for operator RG,
                  set to 0 otherwise)";
              }
              leaf percent {
                xr:xr-xml-map "manageability_perf_thresh_cfg:Percen"+
                  "t";
                type boolean;
                description
                  "Set to TRUE if Specified threshold values
                  are in percent";
              }
              leaf rearm-type {
                xr:xr-xml-map "manageability_perf_thresh_cfg:RearmT"+
                  "ype";
                type Pm-threshold-rearm;
                description "Configure the Rearm type";
              }
              leaf rearm-window {
                xr:xr-xml-map "manageability_perf_thresh_cfg:RearmW"+
                  "indow";
                type Pm-threshold-rearm-window;
                description
                  "Configure the rearm window size (for rearm
                  type Window)";
              }
            }

            container output-total-drops {
              xr:xr-xml-map "manageability_perf_thresh_cfg:OutputTo"+
                "talDrops";
              presence "enable output-total-drops";
              description
                "Number of outbound correct packets discarded";
              leaf operator {
                xr:xr-xml-map "manageability_perf_thresh_cfg:Operat"+
                  "or";
                type Pm-threshold-op;
                description "Operator";
              }
              leaf value {
                xr:xr-xml-map "manageability_perf_thresh_cfg:Value";
                type Pm-threshold-val-range-counter32;
                description
                  "Threshold value (or start range value for
                  operator RG)";
              }
              leaf end-range-value {
                xr:xr-xml-map "manageability_perf_thresh_cfg:EndRan"+
                  "geValue";
                type Pm-threshold-val-range-counter32;
                description
                  "Threshold end range value (for operator RG,
                  set to 0 otherwise)";
              }
              leaf percent {
                xr:xr-xml-map "manageability_perf_thresh_cfg:Percen"+
                  "t";
                type boolean;
                description
                  "Set to TRUE if Specified threshold values
                  are in percent";
              }
              leaf rearm-type {
                xr:xr-xml-map "manageability_perf_thresh_cfg:RearmT"+
                  "ype";
                type Pm-threshold-rearm;
                description "Configure the Rearm type";
              }
              leaf rearm-window {
                xr:xr-xml-map "manageability_perf_thresh_cfg:RearmW"+
                  "indow";
                type Pm-threshold-rearm-window;
                description
                  "Configure the rearm window size (for rearm
                  type Window)";
              }
            }

            container out-packets {
              xr:xr-xml-map "manageability_perf_thresh_cfg:OutPacke"+
                "ts";
              presence "enable out-packets";
              description "Number of outbound packets";
              leaf operator {
                xr:xr-xml-map "manageability_perf_thresh_cfg:Operat"+
                  "or";
                type Pm-threshold-op;
                description "Operator";
              }
              leaf value {
                xr:xr-xml-map "manageability_perf_thresh_cfg:Value";
                type Pm-threshold-val-range-counter32;
                description
                  "Threshold value (or start range value for
                  operator RG)";
              }
              leaf end-range-value {
                xr:xr-xml-map "manageability_perf_thresh_cfg:EndRan"+
                  "geValue";
                type Pm-threshold-val-range-counter32;
                description
                  "Threshold end range value (for operator RG,
                  set to 0 otherwise)";
              }
              leaf percent {
                xr:xr-xml-map "manageability_perf_thresh_cfg:Percen"+
                  "t";
                type boolean;
                description
                  "Set to TRUE if Specified threshold values
                  are in percent";
              }
              leaf rearm-type {
                xr:xr-xml-map "manageability_perf_thresh_cfg:RearmT"+
                  "ype";
                type Pm-threshold-rearm;
                description "Configure the Rearm type";
              }
              leaf rearm-window {
                xr:xr-xml-map "manageability_perf_thresh_cfg:RearmW"+
                  "indow";
                type Pm-threshold-rearm-window;
                description
                  "Configure the rearm window size (for rearm
                  type Window)";
              }
            }

            container output-total-errors {
              xr:xr-xml-map "manageability_perf_thresh_cfg:OutputTo"+
                "talErrors";
              presence "enable output-total-errors";
              description
                "Number of outbound incorrect packets
                discarded";
              leaf operator {
                xr:xr-xml-map "manageability_perf_thresh_cfg:Operat"+
                  "or";
                type Pm-threshold-op;
                description "Operator";
              }
              leaf value {
                xr:xr-xml-map "manageability_perf_thresh_cfg:Value";
                type Pm-threshold-val-range-counter32;
                description
                  "Threshold value (or start range value for
                  operator RG)";
              }
              leaf end-range-value {
                xr:xr-xml-map "manageability_perf_thresh_cfg:EndRan"+
                  "geValue";
                type Pm-threshold-val-range-counter32;
                description
                  "Threshold end range value (for operator RG,
                  set to 0 otherwise)";
              }
              leaf percent {
                xr:xr-xml-map "manageability_perf_thresh_cfg:Percen"+
                  "t";
                type boolean;
                description
                  "Set to TRUE if Specified threshold values
                  are in percent";
              }
              leaf rearm-type {
                xr:xr-xml-map "manageability_perf_thresh_cfg:RearmT"+
                  "ype";
                type Pm-threshold-rearm;
                description "Configure the Rearm type";
              }
              leaf rearm-window {
                xr:xr-xml-map "manageability_perf_thresh_cfg:RearmW"+
                  "indow";
                type Pm-threshold-rearm-window;
                description
                  "Configure the rearm window size (for rearm
                  type Window)";
              }
            }

            container in-packets {
              xr:xr-xml-map "manageability_perf_thresh_cfg:InPacket"+
                "s";
              presence "enable in-packets";
              description "Number of inbound packets";
              leaf operator {
                xr:xr-xml-map "manageability_perf_thresh_cfg:Operat"+
                  "or";
                type Pm-threshold-op;
                description "Operator";
              }
              leaf value {
                xr:xr-xml-map "manageability_perf_thresh_cfg:Value";
                type Pm-threshold-val-range-counter32;
                description
                  "Threshold value (or start range value for
                  operator RG)";
              }
              leaf end-range-value {
                xr:xr-xml-map "manageability_perf_thresh_cfg:EndRan"+
                  "geValue";
                type Pm-threshold-val-range-counter32;
                description
                  "Threshold end range value (for operator RG,
                  set to 0 otherwise)";
              }
              leaf percent {
                xr:xr-xml-map "manageability_perf_thresh_cfg:Percen"+
                  "t";
                type boolean;
                description
                  "Set to TRUE if Specified threshold values
                  are in percent";
              }
              leaf rearm-type {
                xr:xr-xml-map "manageability_perf_thresh_cfg:RearmT"+
                  "ype";
                type Pm-threshold-rearm;
                description "Configure the Rearm type";
              }
              leaf rearm-window {
                xr:xr-xml-map "manageability_perf_thresh_cfg:RearmW"+
                  "indow";
                type Pm-threshold-rearm-window;
                description
                  "Configure the rearm window size (for rearm
                  type Window)";
              }
            }

            container input-queue-drops {
              xr:xr-xml-map "manageability_perf_thresh_cfg:InputQue"+
                "ueDrops";
              presence "enable input-queue-drops";
              description "Number of input queue drops";
              leaf operator {
                xr:xr-xml-map "manageability_perf_thresh_cfg:Operat"+
                  "or";
                type Pm-threshold-op;
                description "Operator";
              }
              leaf value {
                xr:xr-xml-map "manageability_perf_thresh_cfg:Value";
                type Pm-threshold-val-range-counter32;
                description
                  "Threshold value (or start range value for
                  operator RG)";
              }
              leaf end-range-value {
                xr:xr-xml-map "manageability_perf_thresh_cfg:EndRan"+
                  "geValue";
                type Pm-threshold-val-range-counter32;
                description
                  "Threshold end range value (for operator RG,
                  set to 0 otherwise)";
              }
              leaf percent {
                xr:xr-xml-map "manageability_perf_thresh_cfg:Percen"+
                  "t";
                type boolean;
                description
                  "Set to TRUE if Specified threshold values
                  are in percent";
              }
              leaf rearm-type {
                xr:xr-xml-map "manageability_perf_thresh_cfg:RearmT"+
                  "ype";
                type Pm-threshold-rearm;
                description "Configure the Rearm type";
              }
              leaf rearm-window {
                xr:xr-xml-map "manageability_perf_thresh_cfg:RearmW"+
                  "indow";
                type Pm-threshold-rearm-window;
                description
                  "Configure the rearm window size (for rearm
                  type Window)";
              }
            }

            container input-total-drops {
              xr:xr-xml-map "manageability_perf_thresh_cfg:InputTot"+
                "alDrops";
              presence "enable input-total-drops";
              description
                "Number of inbound correct packets discarded";
              leaf operator {
                xr:xr-xml-map "manageability_perf_thresh_cfg:Operat"+
                  "or";
                type Pm-threshold-op;
                description "Operator";
              }
              leaf value {
                xr:xr-xml-map "manageability_perf_thresh_cfg:Value";
                type Pm-threshold-val-range-counter32;
                description
                  "Threshold value (or start range value for
                  operator RG)";
              }
              leaf end-range-value {
                xr:xr-xml-map "manageability_perf_thresh_cfg:EndRan"+
                  "geValue";
                type Pm-threshold-val-range-counter32;
                description
                  "Threshold end range value (for operator RG,
                  set to 0 otherwise)";
              }
              leaf percent {
                xr:xr-xml-map "manageability_perf_thresh_cfg:Percen"+
                  "t";
                type boolean;
                description
                  "Set to TRUE if Specified threshold values
                  are in percent";
              }
              leaf rearm-type {
                xr:xr-xml-map "manageability_perf_thresh_cfg:RearmT"+
                  "ype";
                type Pm-threshold-rearm;
                description "Configure the Rearm type";
              }
              leaf rearm-window {
                xr:xr-xml-map "manageability_perf_thresh_cfg:RearmW"+
                  "indow";
                type Pm-threshold-rearm-window;
                description
                  "Configure the rearm window size (for rearm
                  type Window)";
              }
            }
            leaf template-name {
              xr:xr-xml-map "manageability_perf_thresh_cfg:Template"+
                "Name";
              type xr:Cisco-ios-xr-string;
              description "Template Name";
            }
            uses MANAGEABILITY-PERF-THRESH-CFG-SAMPLE-INTERVAL;
            uses REG-EXP-GROUP;
            uses VRF-GROUP;
          }
        }
      }

      container bgp {
        xr:xr-xml-map "manageability_perf_thresh_cfg:BGP";
        description "BGP threshold configuration";

        container bgp-templates {
          xr:xr-xml-map "manageability_perf_thresh_cfg:BGPTemplateT"+
            "able";
          description "BGP threshold templates";

          list bgp-template {
            xr:xr-xml-map "manageability_perf_thresh_cfg:BGPTemplat"+
              "e";
            key "template-name";
            description "BGP threshold template instance";

            container output-update-messages {
              xr:xr-xml-map "manageability_perf_thresh_cfg:OutputUp"+
                "dateMessages";
              presence "enable output-update-messages";
              description "Number of update messages sent";
              leaf operator {
                xr:xr-xml-map "manageability_perf_thresh_cfg:Operat"+
                  "or";
                type Pm-threshold-op;
                description "Operator";
              }
              leaf value {
                xr:xr-xml-map "manageability_perf_thresh_cfg:Value";
                type Pm-threshold-val-range-counter32;
                description
                  "Threshold value (or start range value for
                  operator RG)";
              }
              leaf end-range-value {
                xr:xr-xml-map "manageability_perf_thresh_cfg:EndRan"+
                  "geValue";
                type Pm-threshold-val-range-counter32;
                description
                  "Threshold end range value (for operator RG,
                  set to 0 otherwise)";
              }
              leaf percent {
                xr:xr-xml-map "manageability_perf_thresh_cfg:Percen"+
                  "t";
                type boolean;
                description
                  "Set to TRUE if Specified threshold values
                  are in percent";
              }
              leaf rearm-type {
                xr:xr-xml-map "manageability_perf_thresh_cfg:RearmT"+
                  "ype";
                type Pm-threshold-rearm;
                description "Configure the Rearm type";
              }
              leaf rearm-window {
                xr:xr-xml-map "manageability_perf_thresh_cfg:RearmW"+
                  "indow";
                type Pm-threshold-rearm-window;
                description
                  "Configure the rearm window size (for rearm
                  type Window)";
              }
            }

            container errors-received {
              xr:xr-xml-map "manageability_perf_thresh_cfg:ErrorsRe"+
                "ceived";
              presence "enable errors-received";
              description "Number of error notifications received";
              leaf operator {
                xr:xr-xml-map "manageability_perf_thresh_cfg:Operat"+
                  "or";
                type Pm-threshold-op;
                description "Operator";
              }
              leaf value {
                xr:xr-xml-map "manageability_perf_thresh_cfg:Value";
                type Pm-threshold-val-range-counter32;
                description
                  "Threshold value (or start range value for
                  operator RG)";
              }
              leaf end-range-value {
                xr:xr-xml-map "manageability_perf_thresh_cfg:EndRan"+
                  "geValue";
                type Pm-threshold-val-range-counter32;
                description
                  "Threshold end range value (for operator RG,
                  set to 0 otherwise)";
              }
              leaf percent {
                xr:xr-xml-map "manageability_perf_thresh_cfg:Percen"+
                  "t";
                type boolean;
                description
                  "Set to TRUE if Specified threshold values
                  are in percent";
              }
              leaf rearm-type {
                xr:xr-xml-map "manageability_perf_thresh_cfg:RearmT"+
                  "ype";
                type Pm-threshold-rearm;
                description "Configure the Rearm type";
              }
              leaf rearm-window {
                xr:xr-xml-map "manageability_perf_thresh_cfg:RearmW"+
                  "indow";
                type Pm-threshold-rearm-window;
                description
                  "Configure the rearm window size (for rearm
                  type Window)";
              }
            }

            container conn-established {
              xr:xr-xml-map "manageability_perf_thresh_cfg:ConnEsta"+
                "blished";
              presence "enable conn-established";
              description
                "Number of times the connection was
                established";
              leaf operator {
                xr:xr-xml-map "manageability_perf_thresh_cfg:Operat"+
                  "or";
                type Pm-threshold-op;
                description "Operator";
              }
              leaf value {
                xr:xr-xml-map "manageability_perf_thresh_cfg:Value";
                type Pm-threshold-val-range-counter32;
                description
                  "Threshold value (or start range value for
                  operator RG)";
              }
              leaf end-range-value {
                xr:xr-xml-map "manageability_perf_thresh_cfg:EndRan"+
                  "geValue";
                type Pm-threshold-val-range-counter32;
                description
                  "Threshold end range value (for operator RG,
                  set to 0 otherwise)";
              }
              leaf percent {
                xr:xr-xml-map "manageability_perf_thresh_cfg:Percen"+
                  "t";
                type boolean;
                description
                  "Set to TRUE if Specified threshold values
                  are in percent";
              }
              leaf rearm-type {
                xr:xr-xml-map "manageability_perf_thresh_cfg:RearmT"+
                  "ype";
                type Pm-threshold-rearm;
                description "Configure the Rearm type";
              }
              leaf rearm-window {
                xr:xr-xml-map "manageability_perf_thresh_cfg:RearmW"+
                  "indow";
                type Pm-threshold-rearm-window;
                description
                  "Configure the rearm window size (for rearm
                  type Window)";
              }
            }

            container output-messages {
              xr:xr-xml-map "manageability_perf_thresh_cfg:OutputMe"+
                "ssages";
              presence "enable output-messages";
              description "Number of messages sent";
              leaf operator {
                xr:xr-xml-map "manageability_perf_thresh_cfg:Operat"+
                  "or";
                type Pm-threshold-op;
                description "Operator";
              }
              leaf value {
                xr:xr-xml-map "manageability_perf_thresh_cfg:Value";
                type Pm-threshold-val-range-counter32;
                description
                  "Threshold value (or start range value for
                  operator RG)";
              }
              leaf end-range-value {
                xr:xr-xml-map "manageability_perf_thresh_cfg:EndRan"+
                  "geValue";
                type Pm-threshold-val-range-counter32;
                description
                  "Threshold end range value (for operator RG,
                  set to 0 otherwise)";
              }
              leaf percent {
                xr:xr-xml-map "manageability_perf_thresh_cfg:Percen"+
                  "t";
                type boolean;
                description
                  "Set to TRUE if Specified threshold values
                  are in percent";
              }
              leaf rearm-type {
                xr:xr-xml-map "manageability_perf_thresh_cfg:RearmT"+
                  "ype";
                type Pm-threshold-rearm;
                description "Configure the Rearm type";
              }
              leaf rearm-window {
                xr:xr-xml-map "manageability_perf_thresh_cfg:RearmW"+
                  "indow";
                type Pm-threshold-rearm-window;
                description
                  "Configure the rearm window size (for rearm
                  type Window)";
              }
            }

            container conn-dropped {
              xr:xr-xml-map "manageability_perf_thresh_cfg:ConnDrop"+
                "ped";
              presence "enable conn-dropped";
              description
                "Number of times the connection was dropped";
              leaf operator {
                xr:xr-xml-map "manageability_perf_thresh_cfg:Operat"+
                  "or";
                type Pm-threshold-op;
                description "Operator";
              }
              leaf value {
                xr:xr-xml-map "manageability_perf_thresh_cfg:Value";
                type Pm-threshold-val-range-counter32;
                description
                  "Threshold value (or start range value for
                  operator RG)";
              }
              leaf end-range-value {
                xr:xr-xml-map "manageability_perf_thresh_cfg:EndRan"+
                  "geValue";
                type Pm-threshold-val-range-counter32;
                description
                  "Threshold end range value (for operator RG,
                  set to 0 otherwise)";
              }
              leaf percent {
                xr:xr-xml-map "manageability_perf_thresh_cfg:Percen"+
                  "t";
                type boolean;
                description
                  "Set to TRUE if Specified threshold values
                  are in percent";
              }
              leaf rearm-type {
                xr:xr-xml-map "manageability_perf_thresh_cfg:RearmT"+
                  "ype";
                type Pm-threshold-rearm;
                description "Configure the Rearm type";
              }
              leaf rearm-window {
                xr:xr-xml-map "manageability_perf_thresh_cfg:RearmW"+
                  "indow";
                type Pm-threshold-rearm-window;
                description
                  "Configure the rearm window size (for rearm
                  type Window)";
              }
            }

            container input-update-messages {
              xr:xr-xml-map "manageability_perf_thresh_cfg:InputUpd"+
                "ateMessages";
              presence "enable input-update-messages";
              description "Number of update messages received";
              leaf operator {
                xr:xr-xml-map "manageability_perf_thresh_cfg:Operat"+
                  "or";
                type Pm-threshold-op;
                description "Operator";
              }
              leaf value {
                xr:xr-xml-map "manageability_perf_thresh_cfg:Value";
                type Pm-threshold-val-range-counter32;
                description
                  "Threshold value (or start range value for
                  operator RG)";
              }
              leaf end-range-value {
                xr:xr-xml-map "manageability_perf_thresh_cfg:EndRan"+
                  "geValue";
                type Pm-threshold-val-range-counter32;
                description
                  "Threshold end range value (for operator RG,
                  set to 0 otherwise)";
              }
              leaf percent {
                xr:xr-xml-map "manageability_perf_thresh_cfg:Percen"+
                  "t";
                type boolean;
                description
                  "Set to TRUE if Specified threshold values
                  are in percent";
              }
              leaf rearm-type {
                xr:xr-xml-map "manageability_perf_thresh_cfg:RearmT"+
                  "ype";
                type Pm-threshold-rearm;
                description "Configure the Rearm type";
              }
              leaf rearm-window {
                xr:xr-xml-map "manageability_perf_thresh_cfg:RearmW"+
                  "indow";
                type Pm-threshold-rearm-window;
                description
                  "Configure the rearm window size (for rearm
                  type Window)";
              }
            }

            container errors-sent {
              xr:xr-xml-map "manageability_perf_thresh_cfg:ErrorsSe"+
                "nt";
              presence "enable errors-sent";
              description "Number of error notifications sent";
              leaf operator {
                xr:xr-xml-map "manageability_perf_thresh_cfg:Operat"+
                  "or";
                type Pm-threshold-op;
                description "Operator";
              }
              leaf value {
                xr:xr-xml-map "manageability_perf_thresh_cfg:Value";
                type Pm-threshold-val-range-counter32;
                description
                  "Threshold value (or start range value for
                  operator RG)";
              }
              leaf end-range-value {
                xr:xr-xml-map "manageability_perf_thresh_cfg:EndRan"+
                  "geValue";
                type Pm-threshold-val-range-counter32;
                description
                  "Threshold end range value (for operator RG,
                  set to 0 otherwise)";
              }
              leaf percent {
                xr:xr-xml-map "manageability_perf_thresh_cfg:Percen"+
                  "t";
                type boolean;
                description
                  "Set to TRUE if Specified threshold values
                  are in percent";
              }
              leaf rearm-type {
                xr:xr-xml-map "manageability_perf_thresh_cfg:RearmT"+
                  "ype";
                type Pm-threshold-rearm;
                description "Configure the Rearm type";
              }
              leaf rearm-window {
                xr:xr-xml-map "manageability_perf_thresh_cfg:RearmW"+
                  "indow";
                type Pm-threshold-rearm-window;
                description
                  "Configure the rearm window size (for rearm
                  type Window)";
              }
            }

            container input-messages {
              xr:xr-xml-map "manageability_perf_thresh_cfg:InputMes"+
                "sages";
              presence "enable input-messages";
              description "Number of messages received";
              leaf operator {
                xr:xr-xml-map "manageability_perf_thresh_cfg:Operat"+
                  "or";
                type Pm-threshold-op;
                description "Operator";
              }
              leaf value {
                xr:xr-xml-map "manageability_perf_thresh_cfg:Value";
                type Pm-threshold-val-range-counter32;
                description
                  "Threshold value (or start range value for
                  operator RG)";
              }
              leaf end-range-value {
                xr:xr-xml-map "manageability_perf_thresh_cfg:EndRan"+
                  "geValue";
                type Pm-threshold-val-range-counter32;
                description
                  "Threshold end range value (for operator RG,
                  set to 0 otherwise)";
              }
              leaf percent {
                xr:xr-xml-map "manageability_perf_thresh_cfg:Percen"+
                  "t";
                type boolean;
                description
                  "Set to TRUE if Specified threshold values
                  are in percent";
              }
              leaf rearm-type {
                xr:xr-xml-map "manageability_perf_thresh_cfg:RearmT"+
                  "ype";
                type Pm-threshold-rearm;
                description "Configure the Rearm type";
              }
              leaf rearm-window {
                xr:xr-xml-map "manageability_perf_thresh_cfg:RearmW"+
                  "indow";
                type Pm-threshold-rearm-window;
                description
                  "Configure the rearm window size (for rearm
                  type Window)";
              }
            }
            leaf template-name {
              xr:xr-xml-map "manageability_perf_thresh_cfg:Template"+
                "Name";
              type xr:Cisco-ios-xr-string;
              description "Template Name";
            }
            uses MANAGEABILITY-PERF-THRESH-CFG-SAMPLE-INTERVAL;
          }
        }
      }

      container ospfv2-protocol {
        xr:xr-xml-map "manageability_perf_thresh_cfg:OSPFv2Protocol";
        description "OSPF v2 Protocol threshold configuration";

        container ospfv2-protocol-templates {
          xr:xr-xml-map "manageability_perf_thresh_cfg:OSPFv2Protoc"+
            "olTemplateTable";
          description "OSPF v2 Protocol threshold templates";

          list ospfv2-protocol-template {
            xr:xr-xml-map "manageability_perf_thresh_cfg:OSPFv2Prot"+
              "ocolTemplate";
            key "template-name";
            description
              "OSPF v2 Protocol threshold template instance";

            container checksum-errors {
              xr:xr-xml-map "manageability_perf_thresh_cfg:Checksum"+
                "Errors";
              presence "enable checksum-errors";
              description
                "Number of packets received with checksum
                errors";
              leaf operator {
                xr:xr-xml-map "manageability_perf_thresh_cfg:Operat"+
                  "or";
                type Pm-threshold-op;
                description "Operator";
              }
              leaf value {
                xr:xr-xml-map "manageability_perf_thresh_cfg:Value";
                type Pm-threshold-val-range-counter32;
                description
                  "Threshold value (or start range value for
                  operator RG)";
              }
              leaf end-range-value {
                xr:xr-xml-map "manageability_perf_thresh_cfg:EndRan"+
                  "geValue";
                type Pm-threshold-val-range-counter32;
                description
                  "Threshold end range value (for operator RG,
                  set to 0 otherwise)";
              }
              leaf percent {
                xr:xr-xml-map "manageability_perf_thresh_cfg:Percen"+
                  "t";
                type boolean;
                description
                  "Set to TRUE if Specified threshold values
                  are in percent";
              }
              leaf rearm-type {
                xr:xr-xml-map "manageability_perf_thresh_cfg:RearmT"+
                  "ype";
                type Pm-threshold-rearm;
                description "Configure the Rearm type";
              }
              leaf rearm-window {
                xr:xr-xml-map "manageability_perf_thresh_cfg:RearmW"+
                  "indow";
                type Pm-threshold-rearm-window;
                description
                  "Configure the rearm window size (for rearm
                  type Window)";
              }
            }
            leaf template-name {
              xr:xr-xml-map "manageability_perf_thresh_cfg:Template"+
                "Name";
              type xr:Cisco-ios-xr-string;
              description "Template Name";
            }
            uses INPUT-LSA-ACKS-LSA;
            uses OUTPUT-DB-DS-LSA;
            uses INPUT-DB-DS-LSA;
            uses INPUT-LSA-UPDATES;
            uses OUTPUT-DB-DS;
            uses OUTPUT-LSA-UPDATES-LSA;
            uses INPUT-DB-DS;
            uses INPUT-LSA-UPDATES-LSA;
            uses MANAGEABILITY-PERF-THRESH-CFG-SAMPLE-INTERVAL;
            uses OUTPUT-PACKETS;
            uses INPUT-PACKETS;
            uses OUTPUT-HELLO-PACKETS;
            uses INPUT-HELLO-PACKETS;
            uses OUTPUT-LS-REQUESTS;
            uses OUTPUT-LSA-ACKS-LSA;
            uses OUTPUT-LSA-ACKS;
            uses INPUT-LSA-ACKS;
            uses OUTPUT-LSA-UPDATES;
            uses OUTPUT-LS-REQUESTS-LSA;
            uses INPUT-LS-REQUESTS-LSA;
            uses INPUT-LS-REQUESTS;
          }
        }
      }

      container cpu-node {
        xr:xr-xml-map "manageability_perf_thresh_cfg:CPUNode";
        description "Node CPU threshold configuration";

        container cpu-node-templates {
          xr:xr-xml-map "manageability_perf_thresh_cfg:CPUNodeTempl"+
            "ateTable";
          description "Node CPU threshold configuration templates";

          list cpu-node-template {
            xr:xr-xml-map "manageability_perf_thresh_cfg:CPUNodeTem"+
              "plate";
            key "template-name";
            description
              "Node CPU threshold configuration template
              instances";

            container average-cpu-used {
              xr:xr-xml-map "manageability_perf_thresh_cfg:AverageC"+
                "PUUsed";
              presence "enable average-cpu-used";
              description "Average %CPU utilization";
              leaf operator {
                xr:xr-xml-map "manageability_perf_thresh_cfg:Operat"+
                  "or";
                type Pm-threshold-op;
                description "Operator";
              }
              leaf value {
                xr:xr-xml-map "manageability_perf_thresh_cfg:Value";
                type uint32 {
                  range "0..100";
                }
                description
                  "Threshold value (or start range value for
                  operator RG)";
              }
              leaf end-range-value {
                xr:xr-xml-map "manageability_perf_thresh_cfg:EndRan"+
                  "geValue";
                type uint32 {
                  range "0..100";
                }
                description
                  "Threshold end range value (for operator RG,
                  set to 0 otherwise)";
              }
              leaf percent {
                xr:xr-xml-map "manageability_perf_thresh_cfg:Percen"+
                  "t";
                type boolean;
                description
                  "Set to TRUE if Specified threshold values
                  are in percent";
              }
              leaf rearm-type {
                xr:xr-xml-map "manageability_perf_thresh_cfg:RearmT"+
                  "ype";
                type Pm-threshold-rearm;
                description "Configure the Rearm type";
              }
              leaf rearm-window {
                xr:xr-xml-map "manageability_perf_thresh_cfg:RearmW"+
                  "indow";
                type Pm-threshold-rearm-window;
                description
                  "Configure the rearm window size (for rearm
                  type Window)";
              }
            }

            container no-processes {
              xr:xr-xml-map "manageability_perf_thresh_cfg:NoProces"+
                "ses";
              presence "enable no-processes";
              description "Number of processes";
              leaf operator {
                xr:xr-xml-map "manageability_perf_thresh_cfg:Operat"+
                  "or";
                type Pm-threshold-op;
                description "Operator";
              }
              leaf value {
                xr:xr-xml-map "manageability_perf_thresh_cfg:Value";
                type int32;
                description
                  "Threshold value (or start range value for
                  operator RG)";
              }
              leaf end-range-value {
                xr:xr-xml-map "manageability_perf_thresh_cfg:EndRan"+
                  "geValue";
                type int32;
                description
                  "Threshold end range value (for operator RG,
                  set to 0 otherwise)";
              }
              leaf percent {
                xr:xr-xml-map "manageability_perf_thresh_cfg:Percen"+
                  "t";
                type boolean;
                description
                  "Set to TRUE if Specified threshold values
                  are in percent";
              }
              leaf rearm-type {
                xr:xr-xml-map "manageability_perf_thresh_cfg:RearmT"+
                  "ype";
                type Pm-threshold-rearm;
                description "Configure the Rearm type";
              }
              leaf rearm-window {
                xr:xr-xml-map "manageability_perf_thresh_cfg:RearmW"+
                  "indow";
                type Pm-threshold-rearm-window;
                description
                  "Configure the rearm window size (for rearm
                  type Window)";
              }
            }
            leaf template-name {
              xr:xr-xml-map "manageability_perf_thresh_cfg:Template"+
                "Name";
              type xr:Cisco-ios-xr-string;
              description "Template Name";
            }
            uses SAMPLE-INTERVAL;
          }
        }
      }

      container data-rate-interface {
        xr:xr-xml-map "manageability_perf_thresh_cfg:DataRateInterf"+
          "ace";
        description "Interface Data Rates threshold configuration";

        container data-rate-interface-templates {
          xr:xr-xml-map "manageability_perf_thresh_cfg:DataRateInte"+
            "rfaceTemplateTable";
          description "Interface Data Rates threshold templates";

          list data-rate-interface-template {
            xr:xr-xml-map "manageability_perf_thresh_cfg:DataRateIn"+
              "terfaceTemplate";
            key "template-name";
            description
              "Interface Data Rates threshold template
              instance";

            container input-data-rate {
              xr:xr-xml-map "manageability_perf_thresh_cfg:InputDat"+
                "aRate";
              presence "enable input-data-rate";
              description "Input data rate in kbps";
              leaf operator {
                xr:xr-xml-map "manageability_perf_thresh_cfg:Operat"+
                  "or";
                type Pm-threshold-op;
                description "Operator";
              }
              leaf value {
                xr:xr-xml-map "manageability_perf_thresh_cfg:Value";
                type Pm-threshold-val-range-counter32;
                description
                  "Threshold value (or start range value for
                  operator RG)";
              }
              leaf end-range-value {
                xr:xr-xml-map "manageability_perf_thresh_cfg:EndRan"+
                  "geValue";
                type Pm-threshold-val-range-counter32;
                description
                  "Threshold end range value (for operator RG,
                  set to 0 otherwise)";
              }
              leaf percent {
                xr:xr-xml-map "manageability_perf_thresh_cfg:Percen"+
                  "t";
                type boolean;
                description
                  "Set to TRUE if Specified threshold values
                  are in percent";
              }
              leaf rearm-type {
                xr:xr-xml-map "manageability_perf_thresh_cfg:RearmT"+
                  "ype";
                type Pm-threshold-rearm;
                description "Configure the Rearm type";
              }
              leaf rearm-window {
                xr:xr-xml-map "manageability_perf_thresh_cfg:RearmW"+
                  "indow";
                type Pm-threshold-rearm-window;
                description
                  "Configure the rearm window size (for rearm
                  type Window)";
              }
            }

            container bandwidth {
              xr:xr-xml-map "manageability_perf_thresh_cfg:Bandwidt"+
                "h";
              presence "enable bandwidth";
              description "Bandwidth in kbps";
              leaf operator {
                xr:xr-xml-map "manageability_perf_thresh_cfg:Operat"+
                  "or";
                type Pm-threshold-op;
                description "Operator";
              }
              leaf value {
                xr:xr-xml-map "manageability_perf_thresh_cfg:Value";
                type Pm-threshold-val-range-counter32;
                description
                  "Threshold value (or start range value for
                  operator RG)";
              }
              leaf end-range-value {
                xr:xr-xml-map "manageability_perf_thresh_cfg:EndRan"+
                  "geValue";
                type Pm-threshold-val-range-counter32;
                description
                  "Threshold end range value (for operator RG,
                  set to 0 otherwise)";
              }
              leaf percent {
                xr:xr-xml-map "manageability_perf_thresh_cfg:Percen"+
                  "t";
                type boolean;
                description
                  "Set to TRUE if Specified threshold values
                  are in percent";
              }
              leaf rearm-type {
                xr:xr-xml-map "manageability_perf_thresh_cfg:RearmT"+
                  "ype";
                type Pm-threshold-rearm;
                description "Configure the Rearm type";
              }
              leaf rearm-window {
                xr:xr-xml-map "manageability_perf_thresh_cfg:RearmW"+
                  "indow";
                type Pm-threshold-rearm-window;
                description
                  "Configure the rearm window size (for rearm
                  type Window)";
              }
            }

            container output-packet-rate {
              xr:xr-xml-map "manageability_perf_thresh_cfg:OutputPa"+
                "cketRate";
              presence "enable output-packet-rate";
              description "Number of Output packets per second";
              leaf operator {
                xr:xr-xml-map "manageability_perf_thresh_cfg:Operat"+
                  "or";
                type Pm-threshold-op;
                description "Operator";
              }
              leaf value {
                xr:xr-xml-map "manageability_perf_thresh_cfg:Value";
                type Pm-threshold-val-range-counter32;
                description
                  "Threshold value (or start range value for
                  operator RG)";
              }
              leaf end-range-value {
                xr:xr-xml-map "manageability_perf_thresh_cfg:EndRan"+
                  "geValue";
                type Pm-threshold-val-range-counter32;
                description
                  "Threshold end range value (for operator RG,
                  set to 0 otherwise)";
              }
              leaf percent {
                xr:xr-xml-map "manageability_perf_thresh_cfg:Percen"+
                  "t";
                type boolean;
                description
                  "Set to TRUE if Specified threshold values
                  are in percent";
              }
              leaf rearm-type {
                xr:xr-xml-map "manageability_perf_thresh_cfg:RearmT"+
                  "ype";
                type Pm-threshold-rearm;
                description "Configure the Rearm type";
              }
              leaf rearm-window {
                xr:xr-xml-map "manageability_perf_thresh_cfg:RearmW"+
                  "indow";
                type Pm-threshold-rearm-window;
                description
                  "Configure the rearm window size (for rearm
                  type Window)";
              }
            }

            container input-peak-pkts {
              xr:xr-xml-map "manageability_perf_thresh_cfg:InputPea"+
                "kPkts";
              presence "enable input-peak-pkts";
              description
                "Maximum number of input packets per second";
              leaf operator {
                xr:xr-xml-map "manageability_perf_thresh_cfg:Operat"+
                  "or";
                type Pm-threshold-op;
                description "Operator";
              }
              leaf value {
                xr:xr-xml-map "manageability_perf_thresh_cfg:Value";
                type Pm-threshold-val-range-counter32;
                description
                  "Threshold value (or start range value for
                  operator RG)";
              }
              leaf end-range-value {
                xr:xr-xml-map "manageability_perf_thresh_cfg:EndRan"+
                  "geValue";
                type Pm-threshold-val-range-counter32;
                description
                  "Threshold end range value (for operator RG,
                  set to 0 otherwise)";
              }
              leaf percent {
                xr:xr-xml-map "manageability_perf_thresh_cfg:Percen"+
                  "t";
                type boolean;
                description
                  "Set to TRUE if Specified threshold values
                  are in percent";
              }
              leaf rearm-type {
                xr:xr-xml-map "manageability_perf_thresh_cfg:RearmT"+
                  "ype";
                type Pm-threshold-rearm;
                description "Configure the Rearm type";
              }
              leaf rearm-window {
                xr:xr-xml-map "manageability_perf_thresh_cfg:RearmW"+
                  "indow";
                type Pm-threshold-rearm-window;
                description
                  "Configure the rearm window size (for rearm
                  type Window)";
              }
            }

            container output-peak-rate {
              xr:xr-xml-map "manageability_perf_thresh_cfg:OutputPe"+
                "akRate";
              presence "enable output-peak-rate";
              description "Peak output data rate in kbps";
              leaf operator {
                xr:xr-xml-map "manageability_perf_thresh_cfg:Operat"+
                  "or";
                type Pm-threshold-op;
                description "Operator";
              }
              leaf value {
                xr:xr-xml-map "manageability_perf_thresh_cfg:Value";
                type Pm-threshold-val-range-counter32;
                description
                  "Threshold value (or start range value for
                  operator RG)";
              }
              leaf end-range-value {
                xr:xr-xml-map "manageability_perf_thresh_cfg:EndRan"+
                  "geValue";
                type Pm-threshold-val-range-counter32;
                description
                  "Threshold end range value (for operator RG,
                  set to 0 otherwise)";
              }
              leaf percent {
                xr:xr-xml-map "manageability_perf_thresh_cfg:Percen"+
                  "t";
                type boolean;
                description
                  "Set to TRUE if Specified threshold values
                  are in percent";
              }
              leaf rearm-type {
                xr:xr-xml-map "manageability_perf_thresh_cfg:RearmT"+
                  "ype";
                type Pm-threshold-rearm;
                description "Configure the Rearm type";
              }
              leaf rearm-window {
                xr:xr-xml-map "manageability_perf_thresh_cfg:RearmW"+
                  "indow";
                type Pm-threshold-rearm-window;
                description
                  "Configure the rearm window size (for rearm
                  type Window)";
              }
            }

            container output-data-rate {
              xr:xr-xml-map "manageability_perf_thresh_cfg:OutputDa"+
                "taRate";
              presence "enable output-data-rate";
              description "Output data rate in kbps";
              leaf operator {
                xr:xr-xml-map "manageability_perf_thresh_cfg:Operat"+
                  "or";
                type Pm-threshold-op;
                description "Operator";
              }
              leaf value {
                xr:xr-xml-map "manageability_perf_thresh_cfg:Value";
                type Pm-threshold-val-range-counter32;
                description
                  "Threshold value (or start range value for
                  operator RG)";
              }
              leaf end-range-value {
                xr:xr-xml-map "manageability_perf_thresh_cfg:EndRan"+
                  "geValue";
                type Pm-threshold-val-range-counter32;
                description
                  "Threshold end range value (for operator RG,
                  set to 0 otherwise)";
              }
              leaf percent {
                xr:xr-xml-map "manageability_perf_thresh_cfg:Percen"+
                  "t";
                type boolean;
                description
                  "Set to TRUE if Specified threshold values
                  are in percent";
              }
              leaf rearm-type {
                xr:xr-xml-map "manageability_perf_thresh_cfg:RearmT"+
                  "ype";
                type Pm-threshold-rearm;
                description "Configure the Rearm type";
              }
              leaf rearm-window {
                xr:xr-xml-map "manageability_perf_thresh_cfg:RearmW"+
                  "indow";
                type Pm-threshold-rearm-window;
                description
                  "Configure the rearm window size (for rearm
                  type Window)";
              }
            }

            container input-packet-rate {
              xr:xr-xml-map "manageability_perf_thresh_cfg:InputPac"+
                "ketRate";
              presence "enable input-packet-rate";
              description "Number of input packets per second";
              leaf operator {
                xr:xr-xml-map "manageability_perf_thresh_cfg:Operat"+
                  "or";
                type Pm-threshold-op;
                description "Operator";
              }
              leaf value {
                xr:xr-xml-map "manageability_perf_thresh_cfg:Value";
                type Pm-threshold-val-range-counter32;
                description
                  "Threshold value (or start range value for
                  operator RG)";
              }
              leaf end-range-value {
                xr:xr-xml-map "manageability_perf_thresh_cfg:EndRan"+
                  "geValue";
                type Pm-threshold-val-range-counter32;
                description
                  "Threshold end range value (for operator RG,
                  set to 0 otherwise)";
              }
              leaf percent {
                xr:xr-xml-map "manageability_perf_thresh_cfg:Percen"+
                  "t";
                type boolean;
                description
                  "Set to TRUE if Specified threshold values
                  are in percent";
              }
              leaf rearm-type {
                xr:xr-xml-map "manageability_perf_thresh_cfg:RearmT"+
                  "ype";
                type Pm-threshold-rearm;
                description "Configure the Rearm type";
              }
              leaf rearm-window {
                xr:xr-xml-map "manageability_perf_thresh_cfg:RearmW"+
                  "indow";
                type Pm-threshold-rearm-window;
                description
                  "Configure the rearm window size (for rearm
                  type Window)";
              }
            }

            container output-peak-pkts {
              xr:xr-xml-map "manageability_perf_thresh_cfg:OutputPe"+
                "akPkts";
              presence "enable output-peak-pkts";
              description
                "Maximum number of output packets per second";
              leaf operator {
                xr:xr-xml-map "manageability_perf_thresh_cfg:Operat"+
                  "or";
                type Pm-threshold-op;
                description "Operator";
              }
              leaf value {
                xr:xr-xml-map "manageability_perf_thresh_cfg:Value";
                type Pm-threshold-val-range-counter32;
                description
                  "Threshold value (or start range value for
                  operator RG)";
              }
              leaf end-range-value {
                xr:xr-xml-map "manageability_perf_thresh_cfg:EndRan"+
                  "geValue";
                type Pm-threshold-val-range-counter32;
                description
                  "Threshold end range value (for operator RG,
                  set to 0 otherwise)";
              }
              leaf percent {
                xr:xr-xml-map "manageability_perf_thresh_cfg:Percen"+
                  "t";
                type boolean;
                description
                  "Set to TRUE if Specified threshold values
                  are in percent";
              }
              leaf rearm-type {
                xr:xr-xml-map "manageability_perf_thresh_cfg:RearmT"+
                  "ype";
                type Pm-threshold-rearm;
                description "Configure the Rearm type";
              }
              leaf rearm-window {
                xr:xr-xml-map "manageability_perf_thresh_cfg:RearmW"+
                  "indow";
                type Pm-threshold-rearm-window;
                description
                  "Configure the rearm window size (for rearm
                  type Window)";
              }
            }

            container input-peak-rate {
              xr:xr-xml-map "manageability_perf_thresh_cfg:InputPea"+
                "kRate";
              presence "enable input-peak-rate";
              description "Peak input data rate in kbps";
              leaf operator {
                xr:xr-xml-map "manageability_perf_thresh_cfg:Operat"+
                  "or";
                type Pm-threshold-op;
                description "Operator";
              }
              leaf value {
                xr:xr-xml-map "manageability_perf_thresh_cfg:Value";
                type Pm-threshold-val-range-counter32;
                description
                  "Threshold value (or start range value for
                  operator RG)";
              }
              leaf end-range-value {
                xr:xr-xml-map "manageability_perf_thresh_cfg:EndRan"+
                  "geValue";
                type Pm-threshold-val-range-counter32;
                description
                  "Threshold end range value (for operator RG,
                  set to 0 otherwise)";
              }
              leaf percent {
                xr:xr-xml-map "manageability_perf_thresh_cfg:Percen"+
                  "t";
                type boolean;
                description
                  "Set to TRUE if Specified threshold values
                  are in percent";
              }
              leaf rearm-type {
                xr:xr-xml-map "manageability_perf_thresh_cfg:RearmT"+
                  "ype";
                type Pm-threshold-rearm;
                description "Configure the Rearm type";
              }
              leaf rearm-window {
                xr:xr-xml-map "manageability_perf_thresh_cfg:RearmW"+
                  "indow";
                type Pm-threshold-rearm-window;
                description
                  "Configure the rearm window size (for rearm
                  type Window)";
              }
            }
            leaf template-name {
              xr:xr-xml-map "manageability_perf_thresh_cfg:Template"+
                "Name";
              type xr:Cisco-ios-xr-string;
              description "Template Name";
            }
            uses SAMPLE-INTERVAL;
            uses REG-EXP-GROUP;
            uses VRF-GROUP;
          }
        }
      }

      container process-node {
        xr:xr-xml-map "manageability_perf_thresh_cfg:ProcessNode";
        description "Node Process threshold configuration";

        container process-node-templates {
          xr:xr-xml-map "manageability_perf_thresh_cfg:ProcessNodeT"+
            "emplateTable";
          description "Node Memory threshold templates";

          list process-node-template {
            xr:xr-xml-map "manageability_perf_thresh_cfg:ProcessNod"+
              "eTemplate";
            key "template-name";
            description "Node Memory threshold template instance";

            container average-cpu-used {
              xr:xr-xml-map "manageability_perf_thresh_cfg:AverageC"+
                "puUsed";
              presence "enable average-cpu-used";
              description "Average %CPU utilization";
              leaf operator {
                xr:xr-xml-map "manageability_perf_thresh_cfg:Operat"+
                  "or";
                type Pm-threshold-op;
                description "Operator";
              }
              leaf value {
                xr:xr-xml-map "manageability_perf_thresh_cfg:Value";
                type uint32 {
                  range "0..100";
                }
                description
                  "Threshold value (or start range value for
                  operator RG)";
              }
              leaf end-range-value {
                xr:xr-xml-map "manageability_perf_thresh_cfg:EndRan"+
                  "geValue";
                type uint32 {
                  range "0..100";
                }
                description
                  "Threshold end range value (for operator RG,
                  set to 0 otherwise)";
              }
              leaf percent {
                xr:xr-xml-map "manageability_perf_thresh_cfg:Percen"+
                  "t";
                type boolean;
                description
                  "Set to TRUE if Specified threshold values
                  are in percent";
              }
              leaf rearm-type {
                xr:xr-xml-map "manageability_perf_thresh_cfg:RearmT"+
                  "ype";
                type Pm-threshold-rearm;
                description "Configure the Rearm type";
              }
              leaf rearm-window {
                xr:xr-xml-map "manageability_perf_thresh_cfg:RearmW"+
                  "indow";
                type Pm-threshold-rearm-window;
                description
                  "Configure the rearm window size (for rearm
                  type Window)";
              }
            }

            container peak-memory {
              xr:xr-xml-map "manageability_perf_thresh_cfg:PeakMemo"+
                "ry";
              presence "enable peak-memory";
              description
                "Max memory (KBytes) used since startup time";
              leaf operator {
                xr:xr-xml-map "manageability_perf_thresh_cfg:Operat"+
                  "or";
                type Pm-threshold-op;
                description "Operator";
              }
              leaf value {
                xr:xr-xml-map "manageability_perf_thresh_cfg:Value";
                type int32;
                description
                  "Threshold value (or start range value for
                  operator RG)";
              }
              leaf end-range-value {
                xr:xr-xml-map "manageability_perf_thresh_cfg:EndRan"+
                  "geValue";
                type int32;
                description
                  "Threshold end range value (for operator RG,
                  set to 0 otherwise)";
              }
              leaf percent {
                xr:xr-xml-map "manageability_perf_thresh_cfg:Percen"+
                  "t";
                type boolean;
                description
                  "Set to TRUE if Specified threshold values
                  are in percent";
              }
              leaf rearm-type {
                xr:xr-xml-map "manageability_perf_thresh_cfg:RearmT"+
                  "ype";
                type Pm-threshold-rearm;
                description "Configure the Rearm type";
              }
              leaf rearm-window {
                xr:xr-xml-map "manageability_perf_thresh_cfg:RearmW"+
                  "indow";
                type Pm-threshold-rearm-window;
                description
                  "Configure the rearm window size (for rearm
                  type Window)";
              }
            }

            container no-threads {
              xr:xr-xml-map "manageability_perf_thresh_cfg:NoThread"+
                "s";
              presence "enable no-threads";
              description "Number of threads";
              leaf operator {
                xr:xr-xml-map "manageability_perf_thresh_cfg:Operat"+
                  "or";
                type Pm-threshold-op;
                description "Operator";
              }
              leaf value {
                xr:xr-xml-map "manageability_perf_thresh_cfg:Value";
                type uint32 {
                  range "0..32767";
                }
                description
                  "Threshold value (or start range value for
                  operator RG)";
              }
              leaf end-range-value {
                xr:xr-xml-map "manageability_perf_thresh_cfg:EndRan"+
                  "geValue";
                type uint32 {
                  range "0..32767";
                }
                description
                  "Threshold end range value (for operator RG,
                  set to 0 otherwise)";
              }
              leaf percent {
                xr:xr-xml-map "manageability_perf_thresh_cfg:Percen"+
                  "t";
                type boolean;
                description
                  "Set to TRUE if Specified threshold values
                  are in percent";
              }
              leaf rearm-type {
                xr:xr-xml-map "manageability_perf_thresh_cfg:RearmT"+
                  "ype";
                type Pm-threshold-rearm;
                description "Configure the Rearm type";
              }
              leaf rearm-window {
                xr:xr-xml-map "manageability_perf_thresh_cfg:RearmW"+
                  "indow";
                type Pm-threshold-rearm-window;
                description
                  "Configure the rearm window size (for rearm
                  type Window)";
              }
            }
            leaf template-name {
              xr:xr-xml-map "manageability_perf_thresh_cfg:Template"+
                "Name";
              type xr:Cisco-ios-xr-string;
              description "Template Name";
            }
            uses SAMPLE-INTERVAL;
          }
        }
      }

      container memory-node {
        xr:xr-xml-map "manageability_perf_thresh_cfg:MemoryNode";
        description "Node Memory threshold configuration";

        container memory-node-templates {
          xr:xr-xml-map "manageability_perf_thresh_cfg:MemoryNodeTe"+
            "mplateTable";
          description
            "Node Memory threshold configuration templates";

          list memory-node-template {
            xr:xr-xml-map "manageability_perf_thresh_cfg:MemoryNode"+
              "Template";
            key "template-name";
            description
              "Node Memory threshold configuration template
              instance";

            container peak-memory {
              xr:xr-xml-map "manageability_perf_thresh_cfg:PeakMemo"+
                "ry";
              presence "enable peak-memory";
              description "Maximum memory (KBytes) used";
              leaf operator {
                xr:xr-xml-map "manageability_perf_thresh_cfg:Operat"+
                  "or";
                type Pm-threshold-op;
                description "Operator";
              }
              leaf value {
                xr:xr-xml-map "manageability_perf_thresh_cfg:Value";
                type uint32 {
                  range "0..4194304";
                }
                description
                  "Threshold value (or start range value for
                  operator RG)";
              }
              leaf end-range-value {
                xr:xr-xml-map "manageability_perf_thresh_cfg:EndRan"+
                  "geValue";
                type uint32 {
                  range "0..4194304";
                }
                description
                  "Threshold end range value (for operator RG,
                  set to 0 otherwise)";
              }
              leaf percent {
                xr:xr-xml-map "manageability_perf_thresh_cfg:Percen"+
                  "t";
                type boolean;
                description
                  "Set to TRUE if Specified threshold values
                  are in percent";
              }
              leaf rearm-type {
                xr:xr-xml-map "manageability_perf_thresh_cfg:RearmT"+
                  "ype";
                type Pm-threshold-rearm;
                description "Configure the Rearm type";
              }
              leaf rearm-window {
                xr:xr-xml-map "manageability_perf_thresh_cfg:RearmW"+
                  "indow";
                type Pm-threshold-rearm-window;
                description
                  "Configure the rearm window size (for rearm
                  type Window)";
              }
            }

            container curr-memory {
              xr:xr-xml-map "manageability_perf_thresh_cfg:CurrMemo"+
                "ry";
              presence "enable curr-memory";
              description "Current memory (Bytes) in use";
              leaf operator {
                xr:xr-xml-map "manageability_perf_thresh_cfg:Operat"+
                  "or";
                type Pm-threshold-op;
                description "Operator";
              }
              leaf value {
                xr:xr-xml-map "manageability_perf_thresh_cfg:Value";
                type int32;
                description
                  "Threshold value (or start range value for
                  operator RG)";
              }
              leaf end-range-value {
                xr:xr-xml-map "manageability_perf_thresh_cfg:EndRan"+
                  "geValue";
                type int32;
                description
                  "Threshold end range value (for operator RG,
                  set to 0 otherwise)";
              }
              leaf percent {
                xr:xr-xml-map "manageability_perf_thresh_cfg:Percen"+
                  "t";
                type boolean;
                description
                  "Set to TRUE if Specified threshold values
                  are in percent";
              }
              leaf rearm-type {
                xr:xr-xml-map "manageability_perf_thresh_cfg:RearmT"+
                  "ype";
                type Pm-threshold-rearm;
                description "Configure the Rearm type";
              }
              leaf rearm-window {
                xr:xr-xml-map "manageability_perf_thresh_cfg:RearmW"+
                  "indow";
                type Pm-threshold-rearm-window;
                description
                  "Configure the rearm window size (for rearm
                  type Window)";
              }
            }
            leaf template-name {
              xr:xr-xml-map "manageability_perf_thresh_cfg:Template"+
                "Name";
              type xr:Cisco-ios-xr-string;
              description "Template Name";
            }
            uses SAMPLE-INTERVAL;
          }
        }
      }

      container ospfv3-protocol {
        xr:xr-xml-map "manageability_perf_thresh_cfg:OSPFv3Protocol";
        description "OSPF v2 Protocol threshold configuration";

        container ospfv3-protocol-templates {
          xr:xr-xml-map "manageability_perf_thresh_cfg:OSPFv3Protoc"+
            "olTemplateTable";
          description "OSPF v2 Protocol threshold templates";

          list ospfv3-protocol-template {
            xr:xr-xml-map "manageability_perf_thresh_cfg:OSPFv3Prot"+
              "ocolTemplate";
            key "template-name";
            description
              "OSPF v2 Protocol threshold template instance";
            leaf template-name {
              xr:xr-xml-map "manageability_perf_thresh_cfg:Template"+
                "Name";
              type xr:Cisco-ios-xr-string;
              description "Template Name";
            }
            uses INPUT-LSA-ACKS-LSA;
            uses OUTPUT-DB-DS-LSA;
            uses INPUT-DB-DS-LSA;
            uses INPUT-LSA-UPDATES;
            uses OUTPUT-DB-DS;
            uses OUTPUT-LSA-UPDATES-LSA;
            uses INPUT-DB-DS;
            uses INPUT-LSA-UPDATES-LSA;
            uses MANAGEABILITY-PERF-THRESH-CFG-SAMPLE-INTERVAL;
            uses OUTPUT-PACKETS;
            uses INPUT-PACKETS;
            uses OUTPUT-HELLO-PACKETS;
            uses INPUT-HELLO-PACKETS;
            uses OUTPUT-LS-REQUESTS;
            uses OUTPUT-LSA-ACKS-LSA;
            uses OUTPUT-LSA-ACKS;
            uses INPUT-LSA-ACKS;
            uses OUTPUT-LSA-UPDATES;
            uses OUTPUT-LS-REQUESTS-LSA;
            uses INPUT-LS-REQUESTS-LSA;
            uses INPUT-LS-REQUESTS;
          }
        }
      }
    }
  }
}
