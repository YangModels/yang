submodule Cisco-IOS-XR-crypto-macsec-mka-oper-sub1 {

  belongs-to Cisco-IOS-XR-crypto-macsec-mka-oper {
    prefix Cisco-IOS-XR-crypto-macsec-mka-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR crypto-macsec-mka package operational data.

     Copyright (c) 2013-2016 by Cisco Systems, Inc.
     All rights reserved.";

  revision "2015-11-09" {
    description
      "IOS XR 6.0 revision.";
  }


  grouping PEER-DATA {
    description "PEER DATA";
    leaf mi {
      xr:xr-xml-map "show_mka:MI";
      type string;
      description "Member ID";
    }
    leaf sci {
      xr:xr-xml-map "show_mka:SCI";
      type string;
      description "Rx SCI";
    }
    leaf mn {
      xr:xr-xml-map "show_mka:MN";
      type uint32;
      description "Message Number";
    }
    leaf priority {
      xr:xr-xml-map "show_mka:Priority";
      type uint32;
      description "KS Priority";
    }
    leaf ssci {
      xr:xr-xml-map "show_mka:SSCI";
      type uint32;
      description "Peer SSCI";
    }
  }

  grouping CA-DATA {
    description "CA DATA";
    leaf is-key-server {
      xr:xr-xml-map "show_mka:IsKeyServer";
      type boolean;
      description "Is Key Server";
    }
    leaf status {
      xr:xr-xml-map "show_mka:Status";
      type uint32;
      description "Session Status [Secured/Not Secured]";
    }
    leaf num-live-peers {
      xr:xr-xml-map "show_mka:NumLivePeers";
      type uint32;
      description "Number of Live Peers";
    }
    leaf first-ca {
      xr:xr-xml-map "show_mka:FirstCA";
      type boolean;
      description "Is First CA";
    }
    leaf peer-sci {
      xr:xr-xml-map "show_mka:PeerSCI";
      type string;
      description "Peer SCI(MAC)";
    }
    leaf num-live-peers-responded {
      xr:xr-xml-map "show_mka:NumLivePeersResponded";
      type uint32;
      description "Number of Live Peers responded";
    }
    leaf ckn {
      xr:xr-xml-map "show_mka:CKN";
      type string;
      description "CKN";
    }
    leaf my-mi {
      xr:xr-xml-map "show_mka:MyMI";
      type string;
      description "Member Identifier";
    }
    leaf my-mn {
      xr:xr-xml-map "show_mka:my_MN";
      type uint32;
      description "Message Number";
    }
    leaf authenticator {
      xr:xr-xml-map "show_mka:authenticator";
      type boolean;
      description "authenticator";
    }
    leaf status-description {
      xr:xr-xml-map "show_mka:StatusDescription";
      type string;
      description "Status Description";
    }

    list live-peer {
      description "Live Peer List";
      uses PEER-DATA;
    }

    list potential-peer {
      description "Potential Peer List";
      uses PEER-DATA;
    }

    list dormant-peer {
      description "Dormant Peer List";
      uses PEER-DATA;
    }
  }

  grouping VP-DATA {
    description "VP DATA";
    leaf my-sci {
      xr:xr-xml-map "show_mka:mySCI";
      type string;
      description "Local SCI(MAC)";
    }
    leaf virtual-port-id {
      xr:xr-xml-map "show_mka:VirtualPortID";
      type uint32;
      description "Virtual Port ID";
    }
    leaf latest-rx {
      xr:xr-xml-map "show_mka:LatestRx";
      type boolean;
      description "Latest Rx status";
    }
    leaf latest-tx {
      xr:xr-xml-map "show_mka:LatestTx";
      type boolean;
      description "Latest Tx status";
    }
    leaf latest-an {
      xr:xr-xml-map "show_mka:LatestAN";
      type uint32;
      description "Latest SAK AN";
    }
    leaf latest-ki {
      xr:xr-xml-map "show_mka:LatestKI";
      type string;
      description "Latest SAK KI";
    }
    leaf latest-kn {
      xr:xr-xml-map "show_mka:LatestKN";
      type uint32;
      description "Latest SAK KN";
    }
    leaf old-rx {
      xr:xr-xml-map "show_mka:OldRx";
      type boolean;
      description "Old Rx status";
    }
    leaf old-tx {
      xr:xr-xml-map "show_mka:OldTx";
      type boolean;
      description "Old Tx status";
    }
    leaf old-an {
      xr:xr-xml-map "show_mka:OldAN";
      type uint32;
      description "Old SAK AN";
    }
    leaf old-ki {
      xr:xr-xml-map "show_mka:OldKI";
      type string;
      description "Old SAK KI";
    }
    leaf old-kn {
      xr:xr-xml-map "show_mka:OldKN";
      type uint32;
      description "Old SAK KN";
    }
    leaf wait-time {
      xr:xr-xml-map "show_mka:WaitTime";
      type uint32;
      description "SAK Transmit Wait Time";
    }
    leaf retire-time {
      xr:xr-xml-map "show_mka:RetireTime";
      type uint32;
      description "SAK Retire time";
    }
    leaf cipher-suite {
      xr:xr-xml-map "show_mka:CipherSuite";
      type uint32;
      description "SAK Cipher Suite";
    }
    leaf ssci {
      xr:xr-xml-map "show_mka:SSCI";
      type uint32;
      description "SSCI of the Local TxSC";
    }
  }

  grouping MKA-VLAN-TAG {
    description "MKA VLAN TAG";
    leaf etype {
      xr:xr-xml-map "show_mka:etype";
      type uint16;
      description "etype";
    }
    leaf priority {
      xr:xr-xml-map "show_mka:priority";
      type uint8;
      description "priority";
    }
    leaf cfi {
      xr:xr-xml-map "show_mka:cfi";
      type uint8;
      description "cfi";
    }
    leaf vlan-id {
      xr:xr-xml-map "show_mka:vlan_id";
      type uint16;
      description "vlan id";
    }
  }

  grouping MKA-SESSION-SUMMARY {
    description "MKA SESSION SUMMARY";

    container outer-tag {
      description "VLAN Outer TAG";
      uses MKA-VLAN-TAG;
    }

    container inner-tag {
      description "VLAN Inner TAG";
      uses MKA-VLAN-TAG;
    }
    leaf interface-name {
      xr:xr-xml-map "show_mka:InterfaceName";
      type string;
      description
        "Interface on which macsec is                    
        configured";
    }
    leaf inherited-policy {
      xr:xr-xml-map "show_mka:InheritedPolicy";
      type boolean;
      description "Is Inherited Policy";
    }
    leaf policy {
      xr:xr-xml-map "show_mka:Policy";
      type string;
      description "Policy Name";
    }
    leaf priority {
      xr:xr-xml-map "show_mka:Priority";
      type uint32;
      description "Key Server Priority";
    }
    leaf my-mac {
      xr:xr-xml-map "show_mka:MyMAC";
      type string;
      description "My MAC";
    }
    leaf delay-protect {
      xr:xr-xml-map "show_mka:DelayProtect";
      type boolean;
      description "Delay Protect";
    }
    leaf replay-protect {
      xr:xr-xml-map "show_mka:ReplayProtect";
      type boolean;
      description "Replay Protect";
    }
    leaf window-size {
      xr:xr-xml-map "show_mka:WindowSize";
      type uint32;
      description "Replay Window Size";
    }
    leaf confidentiality-offset {
      xr:xr-xml-map "show_mka:ConfidentialityOffset";
      type uint32;
      description "Confidentiality Offset";
    }
    leaf algo-agility {
      xr:xr-xml-map "show_mka:AlgoAgility";
      type uint32;
      description "Alogorithm Agility";
    }
    leaf capability {
      xr:xr-xml-map "show_mka:Capability";
      type uint32;
      description "MACSec Capability";
    }
    leaf cipher-str {
      xr:xr-xml-map "show_mka:CipherStr";
      type string;
      description "Cipher String";
    }
    leaf mac-sec-desired {
      xr:xr-xml-map "show_mka:MACSecDesired";
      type boolean;
      description "MACSec Desired";
    }
    leaf key-chain {
      xr:xr-xml-map "show_mka:KeyChain";
      type string;
      description "Key Chain name";
    }
  }

  grouping MKA-SESSION {
    description "MKA SESSION";

    container session-summary {
      description "Session summary";
      uses MKA-SESSION-SUMMARY;
    }

    container vp {
      description "Virtual Pointer Info";
      uses VP-DATA;
    }

    list ca {
      description "CA List for a Session";
      uses CA-DATA;
    }
  }
}
