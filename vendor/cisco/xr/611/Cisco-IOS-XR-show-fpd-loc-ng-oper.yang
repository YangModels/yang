module Cisco-IOS-XR-show-fpd-loc-ng-oper {

  /*** NAMESPACE / PREFIX DEFINITION ***/

  namespace "http://cisco.com/ns/yang"+
    "/Cisco-IOS-XR-show-fpd-loc-ng-oper";


  prefix "show-fpd-loc-ng-oper";

  /*** LINKAGE (IMPORTS / INCLUDES) ***/

  import Cisco-IOS-XR-types { prefix "xr"; }

  include Cisco-IOS-XR-show-fpd-loc-ng-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR show-fpd-loc-ng package operational data.

     This module contains definitions
     for the following management objects:
       show-fpd: Show hw-module fpd

     Copyright (c) 2013-2016 by Cisco Systems, Inc.
     All rights reserved.";

  revision "2015-11-09" {
    description
      "IOS XR 6.0 revision.";
  }


  container show-fpd {
    xr:xr-xml-map "show_fpd_loc_ng:Show-Fpd";
    config false;
    description "Show hw-module fpd";

    container locations {
      xr:xr-xml-map "show_fpd_loc_ng:Location-Table";
      description "location table";

      list location {
        xr:xr-xml-map "show_fpd_loc_ng:Location";
        key "location-name";
        description "location";
        leaf location-name {
          xr:xr-xml-map "show_fpd_loc_ng:LocationName";
          type xr:Cisco-ios-xr-string {
            length "0..32";
          }
          description "Fpd location";
        }

        list fpd {
          xr:xr-xml-map "show_fpd_loc_ng:Fpd";
          key "fpd-name";
          description "Display fpds on given locations";
          leaf fpd-name {
            xr:xr-xml-map "show_fpd_loc_ng:FpdName";
            type xr:Cisco-ios-xr-string {
              length "0..32";
            }
            description "Fpd Name";
          }
          uses FPD-INFO-LIST;
        }
      }
    }

    container hw-module-fpd {
      xr:xr-xml-map "show_fpd_loc_ng:hw-module-fpd";
      description
        "Display fpds on all locations -show hw-module
        fpd";
      uses FPD-INFO-LIST;
    }

    container help-locations {
      xr:xr-xml-map "show_fpd_loc_ng:Help-Location-Table";
      description "help location table";

      list help-location {
        xr:xr-xml-map "show_fpd_loc_ng:Help-Location";
        key "location-name";
        description "location";

        container help-fpd {
          xr:xr-xml-map "show_fpd_loc_ng:Help-Fpd";
          description "Display fpds on given locations";
          uses FPD-LOC-INFO-LIST;
        }
        leaf location-name {
          xr:xr-xml-map "show_fpd_loc_ng:LocationName";
          type xr:Cisco-ios-xr-string {
            length "0..32";
          }
          description "Fpd location";
        }
      }
    }

    container hw-module-fpd-help-fpd {
      xr:xr-xml-map "show_fpd_loc_ng:hw-module-fpd-help-fpd";
      description "Display help-fpd -show hw-module fpd help-fpd";
      uses FPD-LOC-INFO-LIST;
    }

    container package {
      xr:xr-xml-map "show_fpd_loc_ng:Package";
      description "gets fpd package info";
      uses FPD-PKG-INFO-LIST;
    }

    container location-help {
      xr:xr-xml-map "show_fpd_loc_ng:Location-Help";
      description "fpd upgradable locations";
      uses FPD-SHOW-LOCATION-NAME-LIST;
    }
  }
}
