module Cisco-IOS-XR-asr9k-asic-errors-oper {

  /*** NAMESPACE / PREFIX DEFINITION ***/

  namespace "http://cisco.com/ns/yang"+
    "/Cisco-IOS-XR-asr9k-asic-errors-oper";


  prefix "asr9k-asic-errors-oper";

  /*** LINKAGE (IMPORTS / INCLUDES) ***/

  import Cisco-IOS-XR-types { prefix "xr"; }

  include Cisco-IOS-XR-asr9k-asic-errors-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR asr9k-asic-errors package operational data.

     This module contains definitions
     for the following management objects:
       asic-error-stats: Asic error stats operational data

     Copyright (c) 2013-2016 by Cisco Systems, Inc.
     All rights reserved.";

  revision "2015-11-09" {
    description
      "IOS XR 6.0 revision.";
  }


  container asic-error-stats {
    xr:xr-xml-map "asic_errors_m2m_oper:AsicErrorStats";
    config false;
    description "Asic error stats operational data";

    container nodes {
      xr:xr-xml-map "asic_errors_m2m_oper:NodeTable";
      description "Table of Nodes";

      list node {
        xr:xr-xml-map "asic_errors_m2m_oper:Node";
        key "node-name";
        description "Information about a particular node";

        container counts {
          xr:xr-xml-map "asic_errors_m2m_oper:AsicTypes";
          description
            "Table of all Asic Types information on a node";

          list count {
            xr:xr-xml-map "asic_errors_m2m_oper:Counts";
            key "type";
            description "Summary Asic error counts for a Asic Type";
            leaf type {
              xr:xr-xml-map "asic_errors_m2m_oper:Type";
              type xr:Cisco-ios-xr-string;
              description "Asic Type";
            }
            uses HFR-ASIC-SUMMARY;
          }
        }
        leaf node-name {
          xr:xr-xml-map "asic_errors_m2m_oper:NodeName";
          type xr:Node-id;
          description "Node name";
        }
      }
    }
  }
}
