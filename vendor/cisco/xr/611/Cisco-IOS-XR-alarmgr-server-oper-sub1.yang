submodule Cisco-IOS-XR-alarmgr-server-oper-sub1 {

  belongs-to Cisco-IOS-XR-alarmgr-server-oper {
    prefix Cisco-IOS-XR-alarmgr-server-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR alarmgr-server package operational data.

     Copyright (c) 2013-2016 by Cisco Systems, Inc.
     All rights reserved.";

  revision "2015-11-09" {
    description
      "IOS XR 6.0 revision.";
  }

  typedef Alarm-client {
    type enumeration {
      enum unknown {
        value 1;
        description "Client type unknown";
      }
      enum producer {
        value 2;
        description "Client type producer";
      }
      enum consumer {
        value 4;
        description "Client type consumer";
      }
      enum subscriber {
        value 8;
        description "Client type subscriber";
      }
      enum client-last {
        value 16;
        description "Client type last";
      }
    }
    description "Alarm client";
  }
  typedef Alarm-client-state {
    type enumeration {
      enum start {
        value 0;
        description "Starting state. Should be 0";
      }
      enum init {
        value 1;
        description "Client initalized";
      }
      enum connecting {
        value 2;
        description "Sent connect request";
      }
      enum connected {
        value 3;
        description "Initial connected";
      }
      enum registered {
        value 4;
        description "Has sent registration message";
      }
      enum disconnected {
        value 5;
        description "Has been disconnected due to request of error";
      }
      enum ready {
        value 6;
        description "The client is ready";
      }
    }
    description "Alarm client state";
  }
  typedef Alarm-event {
    type enumeration {
      enum default {
        value 0;
        description "Default Alarm Event Type";
      }
      enum notification {
        value 1;
        description "Alarm Notifcation Event Type";
      }
      enum last {
        value 2;
        description "Last Event Type";
      }
    }
    description "Alarm event";
  }
  typedef Timing-bucket {
    type enumeration {
      enum not-specified {
        value 0;
        description "Bucket Type not applicable";
      }
      enum fifteen-min {
        value 1;
        description "Fifteen minute time bucket";
      }
      enum one-day {
        value 2;
        description "One day time bucket";
      }
    }
    description "Timing bucket";
  }
  typedef Alarm-notification-src {
    type enumeration {
      enum not-specified {
        value 0;
        description "Notification src not specified";
      }
      enum near-end {
        value 1;
        description "Notification src near end";
      }
      enum far-end {
        value 2;
        description "Notification src far end";
      }
    }
    description "Alarm notification src";
  }
  typedef Alarm-direction {
    type enumeration {
      enum not-specified {
        value 0;
        description "Direction Not Specified";
      }
      enum send {
        value 1;
        description "Direction Send";
      }
      enum receive {
        value 2;
        description "Direction Receive";
      }
      enum send-receive {
        value 3;
        description "Direction Send and Receive";
      }
    }
    description "Alarm direction";
  }
  typedef Alarm-service-affecting {
    type enumeration {
      enum unknown {
        value 0;
        description
          "Unknown whether alarm severity is service
          affecting";
      }
      enum not-service-affecting {
        value 1;
        description "Alarm severity is not service affecting";
      }
      enum service-affecting {
        value 2;
        description "Alarm severity is service affecting";
      }
    }
    description "Alarm service affecting";
  }
  typedef Alarm-groups {
    type enumeration {
      enum unknown {
        value 0;
        description "An unknown alarm group";
      }
      enum environ {
        value 1;
        description "Environomental alarm group";
      }
      enum ethernet {
        value 2;
        description "Ethernet alarm group";
      }
      enum fabric {
        value 3;
        description "Fabric related alarm group";
      }
      enum power {
        value 4;
        description "Power and PEM group of alarms";
      }
      enum software {
        value 5;
        description "Software group of alarms";
      }
      enum slice {
        value 6;
        description "Slice group of alarms";
      }
      enum cpu {
        value 7;
        description "CPU group of alarms";
      }
      enum controller {
        value 8;
        description "Controller group of alarms";
      }
      enum sonet {
        value 9;
        description "Sonet group of alarms";
      }
      enum otn {
        value 10;
        description "OTN group of alarms";
      }
      enum sdh-controller {
        value 11;
        description "SDH group of alarms";
      }
      enum asic {
        value 12;
        description "ASIC group of alarms";
      }
      enum fpd-infra {
        value 13;
        description "FPD group of alarms";
      }
      enum shelf {
        value 14;
        description "Shelf group of alarms";
      }
      enum last {
        value 15;
        description "Last unused group";
      }
    }
    description "Alarm groups";
  }
  typedef Alarm-status {
    type enumeration {
      enum unknown {
        value 0;
        description "Unknown alarm status level";
      }
      enum set {
        value 1;
        description
          "Status of active alarm that is SET by the
          controller";
      }
      enum clear {
        value 2;
        description
          "Status of cleared alarm that is done by the
          controller";
      }
      enum suppress {
        value 3;
        description
          "Status of suppressed alarm that is done by the
          controller";
      }
      enum last {
        value 4;
        description "Last status level";
      }
    }
    description "Alarm status";
  }
  typedef Alarm-severity {
    type enumeration {
      enum unknown {
        value 0;
        description "Unknown severity level";
      }
      enum not-reported {
        value 1;
        description
          "Severity level not reported will not raise an
          alarm";
      }
      enum not-alarmed {
        value 2;
        description
          "Severity level of info to cater to events such
          as Performance TCAS";
      }
      enum minor {
        value 3;
        description
          "Severity level of minor fault not traffic
          affecting";
      }
      enum major {
        value 4;
        description
          "Severity level of major fault leading to
          service disruption";
      }
      enum critical {
        value 5;
        description
          "Severity level of critical leading to drops
          ,route loss, loss of service etc.";
      }
      enum severity-last {
        value 6;
        description "Last severity level";
      }
    }
    description "Alarm severity";
  }

  grouping ALARM-MGR-SHOW-ALARM-BRIEF-SUPPR-DATA {
    description "Alarm mgr show alarm brief suppressed data";
    leaf location {
      xr:xr-xml-map "alarm_mgr_edm:Location";
      type string {
        length "0..128";
      }
      description "Alarm location";
    }
    leaf severity {
      xr:xr-xml-map "alarm_mgr_edm:Severity";
      type Alarm-severity;
      description "Alarm severity";
    }
    leaf group {
      xr:xr-xml-map "alarm_mgr_edm:Group";
      type Alarm-groups;
      description "Alarm group";
    }
    leaf set-time {
      xr:xr-xml-map "alarm_mgr_edm:SetTime";
      type string {
        length "0..64";
      }
      description "Alarm set time";
    }
    leaf set-timestamp {
      xr:xr-xml-map "alarm_mgr_edm:SetTimestamp";
      type uint64;
      description "Alarm set time(timestamp format)";
    }
    leaf suppressed-time {
      xr:xr-xml-map "alarm_mgr_edm:SuppressedTime";
      type string {
        length "0..64";
      }
      description "Alarm suppressed time";
    }
    leaf suppressed-timestamp {
      xr:xr-xml-map "alarm_mgr_edm:SuppressedTimestamp";
      type uint64;
      description "Alarm suppressed time(timestamp format)";
    }
    leaf description {
      xr:xr-xml-map "alarm_mgr_edm:Description";
      type string {
        length "0..256";
      }
      description "Alarm description";
    }
  }

  grouping ALARM-MGR-SHOW-ALARM-BRIEF-SUPPR-INFO {
    description "Alarm mgr show alarm brief suppressed info";

    list suppressed-info {
      description "Suppressed Alarm List";
      uses ALARM-MGR-SHOW-ALARM-BRIEF-SUPPR-DATA;
    }
  }

  grouping ALARM-MGR-SHOW-ALARM-BRIEF-DATA {
    description "Alarm mgr show alarm brief data";
    leaf location {
      xr:xr-xml-map "alarm_mgr_edm:Location";
      type string {
        length "0..128";
      }
      description "Alarm location";
    }
    leaf severity {
      xr:xr-xml-map "alarm_mgr_edm:Severity";
      type Alarm-severity;
      description "Alarm severity";
    }
    leaf group {
      xr:xr-xml-map "alarm_mgr_edm:Group";
      type Alarm-groups;
      description "Alarm group";
    }
    leaf set-time {
      xr:xr-xml-map "alarm_mgr_edm:SetTime";
      type string {
        length "0..64";
      }
      description "Alarm set time";
    }
    leaf set-timestamp {
      xr:xr-xml-map "alarm_mgr_edm:SetTimestamp";
      type uint64;
      description "Alarm set time(timestamp format)";
    }
    leaf clear-time {
      xr:xr-xml-map "alarm_mgr_edm:ClearTime";
      type string {
        length "0..64";
      }
      description "Alarm clear time";
    }
    leaf clear-timestamp {
      xr:xr-xml-map "alarm_mgr_edm:ClearTimestamp";
      type uint64;
      description "Alarm clear time(timestamp format)";
    }
    leaf description {
      xr:xr-xml-map "alarm_mgr_edm:Description";
      type string {
        length "0..256";
      }
      description "Alarm description";
    }
  }

  grouping ALARM-MGR-SHOW-ALARM-BRIEF-INFO {
    description "Alarm mgr show alarm brief info";

    list alarm-info {
      description "Alarm List";
      uses ALARM-MGR-SHOW-ALARM-BRIEF-DATA;
    }
  }

  grouping ALARM-MGR-SHOW-CLIENT-DATA {
    description "Alarm mgr show client data";
    leaf name {
      xr:xr-xml-map "alarm_mgr_edm:Name";
      type string {
        length "0..128";
      }
      description "Alarm client";
    }
    leaf id {
      xr:xr-xml-map "alarm_mgr_edm:Id";
      type uint32;
      description "Alarms agent id of the client";
    }
    leaf location {
      xr:xr-xml-map "alarm_mgr_edm:Location";
      type string {
        length "0..128";
      }
      description "The location of this client";
    }
    leaf handle {
      xr:xr-xml-map "alarm_mgr_edm:Handle";
      type string {
        length "0..128";
      }
      description "The client handle through which interface";
    }
    leaf state {
      xr:xr-xml-map "alarm_mgr_edm:State";
      type Alarm-client-state;
      description "The current state of the client";
    }
    leaf type {
      xr:xr-xml-map "alarm_mgr_edm:Type";
      type Alarm-client;
      description "The type of the client";
    }
    leaf filter-disp {
      xr:xr-xml-map "alarm_mgr_edm:FilterDisp";
      type boolean;
      description "The current subscription status of the client";
    }
    leaf subscriber-id {
      xr:xr-xml-map "alarm_mgr_edm:SubscriberId";
      type uint32;
      description "Alarms agent subscriber id of the client";
    }
    leaf filter-severity {
      xr:xr-xml-map "alarm_mgr_edm:FilterSeverity";
      type Alarm-severity;
      description "The filter used for alarm severity";
    }
    leaf filter-state {
      xr:xr-xml-map "alarm_mgr_edm:FilterState";
      type Alarm-status;
      description "The filter used for alarm bi-state state+";
    }
    leaf filter-group {
      xr:xr-xml-map "alarm_mgr_edm:FilterGroup";
      type Alarm-groups;
      description "The filter used for alarm group";
    }
    leaf connect-count {
      xr:xr-xml-map "alarm_mgr_edm:ConnectCount";
      type uint32;
      description
        "Number of times the agent connected to the alarm
        mgr";
    }
    leaf connect-timestamp {
      xr:xr-xml-map "alarm_mgr_edm:ConnectTimestamp";
      type string {
        length "0..64";
      }
      description "Agent connect timestamp";
    }
    leaf get-count {
      xr:xr-xml-map "alarm_mgr_edm:GetCount";
      type uint32;
      description "Number of times the agent queried for alarms";
    }
    leaf subscribe-count {
      xr:xr-xml-map "alarm_mgr_edm:SubscribeCount";
      type uint32;
      description "Number of times the agent subscribed for alarms";
    }
    leaf report-count {
      xr:xr-xml-map "alarm_mgr_edm:ReportCount";
      type uint32;
      description "Number of times the agent reported alarms";
    }
  }

  grouping ALARM-MGR-SHOW-CLIENT-INFO {
    description "Alarm mgr show alarm info";

    list client-info {
      description "Client List";
      uses ALARM-MGR-SHOW-CLIENT-DATA;
    }
  }

  grouping ALARM-MGR-SHOW-ALARM-STATS {
    description "alarm mgr show alarm stats";
    leaf reported {
      xr:xr-xml-map "alarm_mgr_edm:Reported";
      type uint64;
      description
        "Alarms that were in all reported to this Alarm
        Mgr";
    }
    leaf dropped {
      xr:xr-xml-map "alarm_mgr_edm:Dropped";
      type uint64;
      description
        "Alarms that we couldn't keep track due to some
        error or other";
    }
    leaf active {
      xr:xr-xml-map "alarm_mgr_edm:Active";
      type uint64;
      description "Alarms that are currently in the active state";
    }
    leaf history {
      xr:xr-xml-map "alarm_mgr_edm:History";
      type uint64;
      description
        "Alarms that are cleared. This one is counted
        over a long period of time";
    }
    leaf suppressed {
      xr:xr-xml-map "alarm_mgr_edm:Suppressed";
      type uint64;
      description "Alarms that are in suppressed state";
    }
    leaf sysadmin-active {
      xr:xr-xml-map "alarm_mgr_edm:SysadminActive";
      type uint64;
      description
        "Alarms that are currently in the active
        state(sysadmin plane)";
    }
    leaf sysadmin-history {
      xr:xr-xml-map "alarm_mgr_edm:SysadminHistory";
      type uint64;
      description
        "Alarms that are cleared in sysadmin plane. This
        one is counted over a long period of time";
    }
    leaf sysadmin-suppressed {
      xr:xr-xml-map "alarm_mgr_edm:SysadminSuppressed";
      type uint64;
      description "Alarms that are suppressed in sysadmin plane.";
    }
    leaf dropped-invalid-aid {
      xr:xr-xml-map "alarm_mgr_edm:DroppedInvalidAID";
      type uint32;
      description "Alarms dropped due to invalid aid";
    }
    leaf dropped-insuff-mem {
      xr:xr-xml-map "alarm_mgr_edm:DroppedInsuffMem";
      type uint32;
      description "Alarms dropped due to insufficient memory";
    }
    leaf dropped-db-error {
      xr:xr-xml-map "alarm_mgr_edm:DroppedDbError";
      type uint32;
      description "Alarms dropped due to db error";
    }
    leaf dropped-clear-without-set {
      xr:xr-xml-map "alarm_mgr_edm:DroppedClearWithoutSet";
      type uint32;
      description "Alarms dropped clear without set";
    }
    leaf dropped-duplicate {
      xr:xr-xml-map "alarm_mgr_edm:DroppedDuplicate";
      type uint32;
      description "Alarms dropped which were duplicate";
    }
    leaf cache-hit {
      xr:xr-xml-map "alarm_mgr_edm:CacheHit";
      type uint32;
      description "Total alarms which had the cache hit";
    }
    leaf cache-miss {
      xr:xr-xml-map "alarm_mgr_edm:CacheMiss";
      type uint32;
      description "Total alarms which had the cache miss";
    }
  }

  grouping ALARM-MGR-SHOW-ALARM-SUPPR-DATA {
    description "Alarm mgr show alarm suppressed data";

    container otn {
      description "OTN feature specific alarm attributes";
      uses ALARM-OTN;
    }
    leaf description {
      xr:xr-xml-map "alarm_mgr_edm:Description";
      type string {
        length "0..256";
      }
      description "Alarm description";
    }
    leaf location {
      xr:xr-xml-map "alarm_mgr_edm:Location";
      type string {
        length "0..128";
      }
      description "Alarm location";
    }
    leaf aid {
      xr:xr-xml-map "alarm_mgr_edm:AID";
      type string {
        length "0..128";
      }
      description "Alarm aid";
    }
    leaf tag {
      xr:xr-xml-map "alarm_mgr_edm:Tag";
      type string {
        length "0..128";
      }
      description "Alarm tag description";
    }
    leaf module {
      xr:xr-xml-map "alarm_mgr_edm:Module";
      type string {
        length "0..128";
      }
      description "Alarm module description";
    }
    leaf eid {
      xr:xr-xml-map "alarm_mgr_edm:EID";
      type string {
        length "0..128";
      }
      description "Alarm eid";
    }
    leaf reporting-agent-id {
      xr:xr-xml-map "alarm_mgr_edm:ReportingAgentID";
      type uint32;
      description "Reporting agent id";
    }
    leaf pending-sync {
      xr:xr-xml-map "alarm_mgr_edm:PendingSync";
      type boolean;
      description "Pending async flag";
    }
    leaf severity {
      xr:xr-xml-map "alarm_mgr_edm:Severity";
      type Alarm-severity;
      description "Alarm severity";
    }
    leaf status {
      xr:xr-xml-map "alarm_mgr_edm:Status";
      type Alarm-status;
      description "Alarm status";
    }
    leaf group {
      xr:xr-xml-map "alarm_mgr_edm:Group";
      type Alarm-groups;
      description "Alarm group";
    }
    leaf set-time {
      xr:xr-xml-map "alarm_mgr_edm:SetTime";
      type string {
        length "0..64";
      }
      description "Alarm set time";
    }
    leaf set-timestamp {
      xr:xr-xml-map "alarm_mgr_edm:SetTimestamp";
      type uint64;
      description "Alarm set time(timestamp format)";
    }
    leaf suppressed-time {
      xr:xr-xml-map "alarm_mgr_edm:SuppressedTime";
      type string {
        length "0..64";
      }
      description "Alarm suppressed time";
    }
    leaf suppressed-timestamp {
      xr:xr-xml-map "alarm_mgr_edm:SuppressedTimestamp";
      type uint64;
      description "Alarm suppressed time(timestamp format)";
    }
    leaf service-affecting {
      xr:xr-xml-map "alarm_mgr_edm:ServiceAffecting";
      type Alarm-service-affecting;
      description "Alarm service affecting ";
    }
    leaf interface {
      xr:xr-xml-map "alarm_mgr_edm:Interface";
      type string {
        length "0..128";
      }
      description "Alarm interface name";
    }
    leaf alarm-name {
      xr:xr-xml-map "alarm_mgr_edm:AlarmName";
      type string {
        length "0..128";
      }
      description "Alarm name";
    }
  }

  grouping ALARM-MGR-SHOW-ALARM-INFO-SUPPR-CLI {
    description "alarm mgr show alarm suppressed info for CLI";

    list suppressed-info {
      description "Suppressed Alarm List";
      uses ALARM-MGR-SHOW-ALARM-SUPPR-DATA;
    }
  }

  grouping ALARM-TCA {
    description "Alarm TCA Attributes";
    leaf threshold-value {
      xr:xr-xml-map "alarm_mgr_edm:ThresholdValue";
      type string {
        length "0..20";
      }
      description "Alarm Threshold ";
    }
    leaf current-value {
      xr:xr-xml-map "alarm_mgr_edm:CurrentValue";
      type string {
        length "0..20";
      }
      description "Alarm Threshold";
    }
    leaf bucket-type {
      xr:xr-xml-map "alarm_mgr_edm:BucketType";
      type Timing-bucket;
      description "Timing Bucket";
    }
  }

  grouping ALARM-OTN {
    description "Alarm transport attributes";
    leaf direction {
      xr:xr-xml-map "alarm_mgr_edm:Direction";
      type Alarm-direction;
      description "Alarm direction ";
    }
    leaf notification-source {
      xr:xr-xml-map "alarm_mgr_edm:NotificationSource";
      type Alarm-notification-src;
      description "Source of Alarm";
    }
  }

  grouping ALARM-MGR-SHOW-ALARM-DATA {
    description "Alarm mgr show alarm data";

    container otn {
      description "OTN feature specific alarm attributes";
      uses ALARM-OTN;
    }

    container tca {
      description "TCA feature specific alarm attributes";
      uses ALARM-TCA;
    }
    leaf description {
      xr:xr-xml-map "alarm_mgr_edm:Description";
      type string {
        length "0..256";
      }
      description "Alarm description";
    }
    leaf location {
      xr:xr-xml-map "alarm_mgr_edm:Location";
      type string {
        length "0..128";
      }
      description "Alarm location";
    }
    leaf aid {
      xr:xr-xml-map "alarm_mgr_edm:AID";
      type string {
        length "0..128";
      }
      description "Alarm aid";
    }
    leaf tag {
      xr:xr-xml-map "alarm_mgr_edm:Tag";
      type string {
        length "0..128";
      }
      description "Alarm tag description";
    }
    leaf module {
      xr:xr-xml-map "alarm_mgr_edm:Module";
      type string {
        length "0..128";
      }
      description "Alarm module description";
    }
    leaf eid {
      xr:xr-xml-map "alarm_mgr_edm:EID";
      type string {
        length "0..128";
      }
      description "Alarm eid";
    }
    leaf reporting-agent-id {
      xr:xr-xml-map "alarm_mgr_edm:ReportingAgentID";
      type uint32;
      description "Reporting agent id";
    }
    leaf pending-sync {
      xr:xr-xml-map "alarm_mgr_edm:PendingSync";
      type boolean;
      description "Pending async flag";
    }
    leaf severity {
      xr:xr-xml-map "alarm_mgr_edm:Severity";
      type Alarm-severity;
      description "Alarm severity";
    }
    leaf status {
      xr:xr-xml-map "alarm_mgr_edm:Status";
      type Alarm-status;
      description "Alarm status";
    }
    leaf group {
      xr:xr-xml-map "alarm_mgr_edm:Group";
      type Alarm-groups;
      description "Alarm group";
    }
    leaf set-time {
      xr:xr-xml-map "alarm_mgr_edm:SetTime";
      type string {
        length "0..64";
      }
      description "Alarm set time";
    }
    leaf set-timestamp {
      xr:xr-xml-map "alarm_mgr_edm:SetTimestamp";
      type uint64;
      description "Alarm set time(timestamp format)";
    }
    leaf clear-time {
      xr:xr-xml-map "alarm_mgr_edm:ClearTime";
      type string {
        length "0..64";
      }
      description "Alarm clear time";
    }
    leaf clear-timestamp {
      xr:xr-xml-map "alarm_mgr_edm:ClearTimestamp";
      type uint64;
      description "Alarm clear time(timestamp format)";
    }
    leaf service-affecting {
      xr:xr-xml-map "alarm_mgr_edm:ServiceAffecting";
      type Alarm-service-affecting;
      description "Alarm service affecting";
    }
    leaf type {
      xr:xr-xml-map "alarm_mgr_edm:Type";
      type Alarm-event;
      description "alarm event type";
    }
    leaf interface {
      xr:xr-xml-map "alarm_mgr_edm:Interface";
      type string {
        length "0..128";
      }
      description "Alarm interface name";
    }
    leaf alarm-name {
      xr:xr-xml-map "alarm_mgr_edm:AlarmName";
      type string {
        length "0..128";
      }
      description "Alarm name";
    }
  }

  grouping ALARM-MGR-SHOW-ALARM-INFO-CLI {
    description "alarm mgr show alarm info for CLI";

    list alarm-info {
      description "Alarm List";
      uses ALARM-MGR-SHOW-ALARM-DATA;
    }
  }
}
