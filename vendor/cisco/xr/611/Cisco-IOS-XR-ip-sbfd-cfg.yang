module Cisco-IOS-XR-ip-sbfd-cfg {

  /*** NAMESPACE / PREFIX DEFINITION ***/

  namespace "http://cisco.com/ns/yang/Cisco-IOS-XR-ip-sbfd-cfg";


  prefix "ip-sbfd-cfg";

  /*** LINKAGE (IMPORTS / INCLUDES) ***/

  import ietf-inet-types { prefix "inet"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ip-sbfd package configuration.

     This module contains definitions
     for the following management objects:
       sbfd: SBFD Configuration ,Seamless-BFD is method for detecting
         faultsbetween two different nodes in a network

     Copyright (c) 2013-2016 by Cisco Systems, Inc.
     All rights reserved.";

  revision "2015-11-09" {
    description
      "IOS XR 6.0 revision.";
  }


  grouping REMOTE-DISCRIMINATOR {
    description "Common node of ipv4-address, ipv6-address";

    list remote-discriminator {
      xr:xr-xml-map "ip_sbfd_cfg:RemoteDiscriminator";
      key "remote-discriminator";
      description "Remote Discriminator value";
      leaf remote-discriminator {
        xr:xr-xml-map "ip_sbfd_cfg:RemoteDiscriminator";
        type uint32 {
          range "1..4294967295";
        }
        description "Remote Discriminator Value";
      }
    }
  }

  container sbfd {
    xr:xr-xml-map "ip_sbfd_cfg:SBFD";
    description
      "SBFD Configuration ,Seamless-BFD is method for
      detecting faultsbetween two different nodes in a
      network";

    container remote-target {
      xr:xr-xml-map "ip_sbfd_cfg:RemoteTarget";
      description "configure remote target";

      container ipv4-addresses {
        xr:xr-xml-map "ip_sbfd_cfg:IPv4Table";
        description "ipv4 address as target";

        list ipv4-address {
          xr:xr-xml-map "ip_sbfd_cfg:IPv4Address";
          key "address";
          description
            "IP Address Value for RemoteDiscriminatorTable";
          leaf address {
            xr:xr-xml-map "ip_sbfd_cfg:Address";
            type inet:ipv4-address-no-zone;
            description " IPv4 address";
          }
          uses REMOTE-DISCRIMINATOR;
        }
      }

      container ipv6-addresses {
        xr:xr-xml-map "ip_sbfd_cfg:IPv6Table";
        description "ipv6 address as target";

        list ipv6-address {
          xr:xr-xml-map "ip_sbfd_cfg:IPv6Address";
          key "address";
          description
            "IP Address Value for RemoteDiscriminatorTable";
          leaf address {
            xr:xr-xml-map "ip_sbfd_cfg:Address";
            type inet:ipv6-address-no-zone;
            description " IPv6 adddress";
          }
          uses REMOTE-DISCRIMINATOR;
        }
      }
    }

    container local-discriminator {
      xr:xr-xml-map "ip_sbfd_cfg:LocalDiscriminator";
      description "Configure local discriminator";

      container intf-discriminators {
        xr:xr-xml-map "ip_sbfd_cfg:IntfTable";
        description
          "Configure local discriminator from interface
          address";

        list intf-discriminator {
          xr:xr-xml-map "ip_sbfd_cfg:IntfDiscriminator";
          xr:xr-cli-map "sbfd interface <interface> ";
          key "interface-name";
          description "interface address as discriminator";
          leaf interface-name {
            xr:xr-xml-map "ip_sbfd_cfg:InterfaceName";
            type xr:Interface-name;
            description "Interface Name";
          }
        }
      }

      container dynamic-discriminators {
        xr:xr-xml-map "ip_sbfd_cfg:DynamicTable";
        description "Configure local discriminator dynamically";

        list dynamic-discriminator {
          xr:xr-xml-map "ip_sbfd_cfg:DynamicDiscriminator";
          xr:xr-cli-map "sbfd dynamic ";
          key "discriminator";
          description "Local discriminator value";
          leaf discriminator {
            xr:xr-xml-map "ip_sbfd_cfg:Discriminator";
            type uint32 {
              range "0..1";
            }
            description "Dynamic discriminator value";
          }
        }
      }

      container ipv4-discriminators {
        xr:xr-xml-map "ip_sbfd_cfg:IPv4AddressTable";
        description
          "Configure local discriminator as an ipv4
          address";

        list ipv4-discriminator {
          xr:xr-xml-map "ip_sbfd_cfg:IPv4Discriminator";
          xr:xr-cli-map "sbfd <IPv4 address> ";
          key "address";
          description "ipv4 address as discriminator";
          leaf address {
            xr:xr-xml-map "ip_sbfd_cfg:Address";
            type inet:ip-address-no-zone;
            description " IPv4 address";
          }
        }
      }

      container val32-discriminators {
        xr:xr-xml-map "ip_sbfd_cfg:Val32Table";
        description "Configure local discriminator as an integer";

        list val32-discriminator {
          xr:xr-xml-map "ip_sbfd_cfg:Val32Discriminator";
          xr:xr-cli-map "sbfd <number> ";
          key "discriminator";
          description "Local discriminator value";
          leaf discriminator {
            xr:xr-xml-map "ip_sbfd_cfg:Discriminator";
            type uint32 {
              range "1..4294967295";
            }
            description "Local discriminator value";
          }
        }
      }
    }
  }
}
