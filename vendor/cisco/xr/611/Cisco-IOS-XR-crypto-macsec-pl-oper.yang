module Cisco-IOS-XR-crypto-macsec-pl-oper {

  /*** NAMESPACE / PREFIX DEFINITION ***/

  namespace "http://cisco.com/ns/yang"+
    "/Cisco-IOS-XR-crypto-macsec-pl-oper";


  prefix "crypto-macsec-pl-oper";

  /*** LINKAGE (IMPORTS / INCLUDES) ***/

  import Cisco-IOS-XR-types { prefix "xr"; }

  include Cisco-IOS-XR-crypto-macsec-pl-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR crypto-macsec-pl package operational data.

     This module contains definitions
     for the following management objects:
       macsec: MACSec operational data

     Copyright (c) 2013-2016 by Cisco Systems, Inc.
     All rights reserved.";

  revision "2015-11-09" {
    description
      "IOS XR 6.0 revision.";
  }


  container macsec {
    xr:xr-xml-map "macsec_pl_oper:MACSEC";
    config false;
    description "MACSec operational data";

    container nodes {
      xr:xr-xml-map "macsec_pl_oper:NodeTable";
      description "NodeTable for all the nodes";

      list node {
        xr:xr-xml-map "macsec_pl_oper:Node";
        key "node-name";
        description "Node where macsec interfaces exist";

        container interfaces {
          xr:xr-xml-map "macsec_pl_oper:InterfaceTable";
          description "Table of Interfaces";

          list interface {
            xr:xr-xml-map "macsec_pl_oper:Interface";
            key "name";
            description "Interface Where Macsec is configured";

            container hw-statistics {
              xr:xr-xml-map "macsec_pl_oper:HW_Statistics";
              description "The Hardware Statistics";
              uses PL-MACSEC-STATS;
            }

            container sw-sas {
              xr:xr-xml-map "macsec_pl_oper:SW_SATable";
              description "Table of Software SAs";

              list sw-sa {
                xr:xr-xml-map "macsec_pl_oper:SW_SA";
                key "sa-id";
                description "Software Security Association";
                leaf sa-id {
                  xr:xr-xml-map "macsec_pl_oper:SA_ID";
                  type int32;
                  description "SA ID";
                }
                uses PL-MACSEC-SA;
              }
            }

            container hw-sas {
              xr:xr-xml-map "macsec_pl_oper:HW_SATable";
              description "Table of Hardware SAs";

              list hw-sa {
                xr:xr-xml-map "macsec_pl_oper:HW_SA";
                key "sa-id";
                description "Hardware Security Association";
                leaf sa-id {
                  xr:xr-xml-map "macsec_pl_oper:SA_ID";
                  type int32;
                  description "SA ID";
                }
                uses PL-MACSEC-SA;
              }
            }

            container hw-flow-s {
              xr:xr-xml-map "macsec_pl_oper:HW_FlowTable";
              description "Table of Hardware Flows";

              list hw-flow {
                xr:xr-xml-map "macsec_pl_oper:HW_FLOW";
                key "flow-id";
                description "Hardware Flow";
                leaf flow-id {
                  xr:xr-xml-map "macsec_pl_oper:FLOW_ID";
                  type int32;
                  description "FLOW ID";
                }
                uses PL-MACSEC-FLOW;
              }
            }

            container sw-flow-s {
              xr:xr-xml-map "macsec_pl_oper:SW_FlowTable";
              description "Table of sofware Flows";

              list sw-flow {
                xr:xr-xml-map "macsec_pl_oper:SW_FLOW";
                key "flow-id";
                description "Software Flow";
                leaf flow-id {
                  xr:xr-xml-map "macsec_pl_oper:FLOW_ID";
                  type int32;
                  description "FLOW ID";
                }
                uses PL-MACSEC-FLOW;
              }
            }

            container sw-statistics {
              xr:xr-xml-map "macsec_pl_oper:SW_Statistics";
              description "The Software Statistics";
              uses PL-MACSEC-STATS;
            }
            leaf name {
              xr:xr-xml-map "macsec_pl_oper:Name";
              type xr:Interface-name;
              description "Value";
            }
          }
        }
        leaf node-name {
          xr:xr-xml-map "macsec_pl_oper:NodeName";
          type xr:Node-id;
          description "Node";
        }
      }
    }
  }
}
