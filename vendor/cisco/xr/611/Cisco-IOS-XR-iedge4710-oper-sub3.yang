submodule Cisco-IOS-XR-iedge4710-oper-sub3 {

  belongs-to Cisco-IOS-XR-iedge4710-oper {
    prefix Cisco-IOS-XR-iedge4710-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR iedge4710 package operational data.

     Copyright (c) 2013-2016 by Cisco Systems, Inc.
     All rights reserved.";

  revision "2015-11-09" {
    description
      "IOS XR 6.0 revision.";
  }


  grouping IEDGE-STATS-SRG-DATA {
    description "Geo Redundancy statistics";
    leaf txlist-send-triggered {
      xr:xr-xml-map "iedge_stats_data:TxlistSendTriggered";
      type uint32;
      description "Txlist Send Triggered";
    }
    leaf txlist-send-failed {
      xr:xr-xml-map "iedge_stats_data:TxlistSendFailed";
      type uint32;
      description "Txlist Send Failed";
    }
    leaf txlist-send-failed-notactive {
      xr:xr-xml-map "iedge_stats_data:TxlistSendFailedNotactive";
      type uint32;
      description "Txlist send failed due to not active";
    }
    leaf actual-txlist-sent {
      xr:xr-xml-map "iedge_stats_data:ActualTxlistSent";
      type uint32;
      description "Txlist Send Success";
    }
    leaf alreadyin-txlist {
      xr:xr-xml-map "iedge_stats_data:AlreadyinTxlist";
      type uint32;
      description "Element already in Txlist";
    }
    leaf txlist-encode {
      xr:xr-xml-map "iedge_stats_data:TxlistEncode";
      type uint32;
      description "Txlist Encode";
    }
    leaf txlist-encode-fail {
      xr:xr-xml-map "iedge_stats_data:TxlistEncodeFail";
      type uint32;
      description "Txlist encode Failed";
    }
    leaf create-update-encode {
      xr:xr-xml-map "iedge_stats_data:CreateUpdateEncode";
      type uint32;
      description "Txlist Create Update Encode";
    }
    leaf delete-encode {
      xr:xr-xml-map "iedge_stats_data:DeleteEncode";
      type uint32;
      description "Txlist Delete Encode";
    }
    leaf create-upd-clean-callback {
      xr:xr-xml-map "iedge_stats_data:CreateUpdCleanCallback";
      type uint32;
      description "Txlist Create/update clean callback";
    }
    leaf delete-clean-callback {
      xr:xr-xml-map "iedge_stats_data:DeleteCleanCallback";
      type uint32;
      description "Txlist Delete clean callback";
    }
    leaf slave-recv-entry {
      xr:xr-xml-map "iedge_stats_data:SlaveRecvEntry";
      type uint32;
      description "Slave Recieved Sync";
    }
    leaf slave-decode-fail {
      xr:xr-xml-map "iedge_stats_data:SlaveDecodeFail";
      type uint32;
      description "Decode failed on Slave";
    }
    leaf slave-create-update {
      xr:xr-xml-map "iedge_stats_data:SlaveCreateUpdate";
      type uint32;
      description "Create Update received on slave";
    }
    leaf slave-delete {
      xr:xr-xml-map "iedge_stats_data:SlaveDelete";
      type uint32;
      description "Delete received on slave";
    }
    leaf srg-context-malloc {
      xr:xr-xml-map "iedge_stats_data:SrgContextMalloc";
      type uint32;
      description "SRG context allocated";
    }
    leaf srg-context-free {
      xr:xr-xml-map "iedge_stats_data:SrgContextFree";
      type uint32;
      description "SRG context freed";
    }
    leaf sod-count {
      xr:xr-xml-map "iedge_stats_data:SodCount";
      type uint32;
      description "Number of SODs Received";
    }
    leaf eod-count {
      xr:xr-xml-map "iedge_stats_data:EodCount";
      type uint32;
      description "Number of EODs Received";
    }
    leaf sod-eod-replay-req-count {
      xr:xr-xml-map "iedge_stats_data:SodEodReplayReqCount";
      type uint32;
      description "Number of Replay Requests Within SOD EOD Window";
    }
    leaf sod-eod-dirty-mark-count {
      xr:xr-xml-map "iedge_stats_data:SodEodDirtyMarkCount";
      type uint32;
      description
        "Number of Sessions Marked as Invalid Within SOD
        EOD Window";
    }
    leaf sod-eod-dirty-delete-count {
      xr:xr-xml-map "iedge_stats_data:SodEodDirtyDeleteCount";
      type uint32;
      description
        "Number of Sessions Invalid Deletes Within SOD
        EOD Window";
    }
    leaf ack-to-srg {
      xr:xr-xml-map "iedge_stats_data:AckToSrg";
      type uint32;
      description "Number of ACKs sent to Srg";
    }
    leaf nack-to-srg {
      xr:xr-xml-map "iedge_stats_data:NackToSrg";
      type uint32;
      description "Number of NACKs sent to Srg";
    }
    leaf nack-to-srg-fail-cnt {
      xr:xr-xml-map "iedge_stats_data:NackToSrgFailCnt";
      type uint32;
      description "Number of NACKs Failed to send to Srg";
    }
    leaf txlist-remove-all {
      xr:xr-xml-map "iedge_stats_data:TxlistRemoveAll";
      type uint32;
      description "Number of Txlist remove all calls";
    }
    leaf txlist-del-sync {
      xr:xr-xml-map "iedge_stats_data:TxlistDelSync";
      type uint32;
      description "Number for Txlist delete for sync msg";
    }
    leaf txlist-del-sync-notlinked {
      xr:xr-xml-map "iedge_stats_data:TxlistDelSyncNotlinked";
      type uint32;
      description
        "Number of Txlist delete for sync which are not
        linked";
    }
    leaf txlist-del-app {
      xr:xr-xml-map "iedge_stats_data:TxlistDelApp";
      type uint32;
      description "Number of Txlist delete for App msg";
    }
    leaf txlist-del-app-notlinked {
      xr:xr-xml-map "iedge_stats_data:TxlistDelAppNotlinked";
      type uint32;
      description
        "Number of Txlist delete for App which are not
        linked";
    }
    leaf txlist-clean-invalid-state {
      xr:xr-xml-map "iedge_stats_data:TxlistCleanInvalidState";
      type uint32;
      description
        "Number of Txlist Cleanup called on Invalid
        subscriber srg state";
    }
    leaf txlist-remove-all-internal-error {
      xr:xr-xml-map "iedge_stats_data:TxlistRemoveAllInternalError";
      type uint32;
      description
        "Number of Internal errors upon Master Txlist
        remove all call";
    }
    leaf is-srg-flow-control-enabled {
      xr:xr-xml-map "iedge_stats_data:IsSRGFlowControlEnabled";
      type boolean;
      description "Flag indicating SRG Flow control enabled or not";
    }
    leaf max-inflight-sessoin-count {
      xr:xr-xml-map "iedge_stats_data:MaxInflightSessoinCount";
      type uint32;
      description "Maximum no.of inflight sessions allowed";
    }
    leaf flow-control-resume-threshold {
      xr:xr-xml-map "iedge_stats_data:FlowControlResumeThreshold";
      type uint32;
      description "Threshold Limit to resume the flow control";
    }
    leaf inflight-session-count {
      xr:xr-xml-map "iedge_stats_data:InflightSessionCount";
      type uint32;
      description "No.of Sessions inflight at given time";
    }
    leaf inflight-add-count {
      xr:xr-xml-map "iedge_stats_data:InflightAddCount";
      type uint32;
      description "No.of inflight sessions added";
    }
    leaf inflight-under-run-count {
      xr:xr-xml-map "iedge_stats_data:InflightUnderRunCount";
      type uint32;
      description "Inflight Underrun Counter";
    }
    leaf inflight-alloc-fails {
      xr:xr-xml-map "iedge_stats_data:InflightAllocFails";
      type uint32;
      description "Memory Alloc Failures for Inflight Entry";
    }
    leaf inflight-insert-failures {
      xr:xr-xml-map "iedge_stats_data:InflightInsertFailures";
      type uint32;
      description "Inflight Entry Insert Failures";
    }
    leaf inflight-deletes {
      xr:xr-xml-map "iedge_stats_data:InflightDeletes";
      type uint32;
      description "Inflight Deletes Count";
    }
    leaf inflight-not-found {
      xr:xr-xml-map "iedge_stats_data:InflightNotFound";
      type uint32;
      description "Inflight Entries not found during delete";
    }
    leaf inflight-delete-failures {
      xr:xr-xml-map "iedge_stats_data:InflightDeleteFailures";
      type uint32;
      description "Inflight Entry Delete Failures";
    }
    leaf total-pause-count {
      xr:xr-xml-map "iedge_stats_data:TotalPauseCount";
      type uint32;
      description "Total No.of times Pause is Enabled";
    }
    leaf total-resume-count {
      xr:xr-xml-map "iedge_stats_data:TotalResumeCount";
      type uint32;
      description "Total No.of times Resume is triggered";
    }
    leaf total-dont-send-to-txlist {
      xr:xr-xml-map "iedge_stats_data:TotalDontSendToTxlist";
      type uint32;
      description "Total No of times Dont send to Txlist";
    }
    leaf total-srg-not-master {
      xr:xr-xml-map "iedge_stats_data:TotalSRGNotMaster";
      type uint32;
      description "Total No of times SRG Not Master";
    }
    leaf total-master-eoms-pending {
      xr:xr-xml-map "iedge_stats_data:TotalMasterEOMSPending";
      type uint32;
      description "Total No of times Master EOMS Pending";
    }
    leaf last-pause-period {
      xr:xr-xml-map "iedge_stats_data:LastPausePeriod";
      type uint64;
      description
        "Amount of time paused during last flow control
        window";
    }
    leaf total-pause-time {
      xr:xr-xml-map "iedge_stats_data:TotalPauseTime";
      type uint64;
      description
        "Total Amount of time paused during all flow
        control windows";
    }
    leaf last-pause-time {
      xr:xr-xml-map "iedge_stats_data:LastPauseTime";
      type uint64;
      description "Timestamp of recent Pause Event";
    }
    leaf last-resume-time {
      xr:xr-xml-map "iedge_stats_data:LastResumeTime";
      type uint64;
      description "Timestamp of recent Resume Event";
    }
  }

  grouping IEDGE-STATS-SUMMARY-DATA {
    description "Summary statistics";
    leaf no-subscriber-control-policy-on-interface {
      xr:xr-xml-map "iedge_stats_data:NoSubscriberControlPolicyOnIn"+
        "terface";
      type uint64;
      description
        "Subscriber control policy not applied on
        interface";
    }
    leaf no-class-match-in-start-request {
      xr:xr-xml-map "iedge_stats_data:NoClassMatchInStartRequest";
      type uint64;
      description
        "No control policy class match during subscriber
        start";
    }
    leaf nas-port-attribute-format-warnings {
      xr:xr-xml-map "iedge_stats_data:NASPortAttributeFormatWarning"+
        "s";
      type uint64;
      description "NAS port attribute format warnings";
    }
    leaf nas-port-id-attribute-format-warnings {
      xr:xr-xml-map "iedge_stats_data:NASPortIDAttributeFormatWarni"+
        "ngs";
      type uint64;
      description "NAS port ID attribute format warnings";
    }
    leaf destination-station-id-attribute-format-warnings {
      xr:xr-xml-map "iedge_stats_data:DestinationStationIDAttribute"+
        "FormatWarnings";
      type uint64;
      description
        "Destination station ID attribute format warnings";
    }
    leaf calling-station-id-attribute-format-warnings {
      xr:xr-xml-map "iedge_stats_data:CallingStationIDAttributeForm"+
        "atWarnings";
      type uint64;
      description "Calling station ID attribute format warnings";
    }
    leaf username-attribute-format-warnings {
      xr:xr-xml-map "iedge_stats_data:UsernameAttributeFormatWarnin"+
        "gs";
      type uint64;
      description "Username attribute format warnings";
    }
    leaf install-user-profiles {
      xr:xr-xml-map "iedge_stats_data:InstallUserProfiles";
      type uint64;
      description "User profiles installed";
    }
    leaf user-profile-install-errors {
      xr:xr-xml-map "iedge_stats_data:UserProfileInstallErrors";
      type uint64;
      description "User profile install errors";
    }
    leaf user-profile-removals {
      xr:xr-xml-map "iedge_stats_data:UserProfileRemovals";
      type uint64;
      description "User profile removals";
    }
    leaf user-profile-errors {
      xr:xr-xml-map "iedge_stats_data:UserProfileErrors";
      type uint64;
      description "User profile errors";
    }
    leaf sess-disc-quota-exhausts {
      xr:xr-xml-map "iedge_stats_data:sess_disc_quota_exhausts";
      type uint64;
      description "Session Disconnect Quota Exhausts";
    }
    leaf sess-disc-no-quota {
      xr:xr-xml-map "iedge_stats_data:sess_disc_no_quota";
      type uint64;
      description "Session Disconnect Request Queued, no quota";
    }
    leaf sess-disc-quota-avail {
      xr:xr-xml-map "iedge_stats_data:sess_disc_quota_avail";
      type uint64;
      description
        "Session Disconnect Request Accepted, quota
        available";
    }
    leaf sess-disc-recon-ip {
      xr:xr-xml-map "iedge_stats_data:sess_disc_recon_ip";
      type uint64;
      description
        "Session Disconnect Requests not Dequeued,
        reconciliation in progress";
    }
    leaf sess-disc-none-started {
      xr:xr-xml-map "iedge_stats_data:sess_disc_none_started";
      type uint64;
      description
        "Session Disconnect Requests not Dequeued, no
        quota";
    }
    leaf sess-disc-quota {
      xr:xr-xml-map "iedge_stats_data:sess_disc_quota";
      type uint32;
      description "Session Disconnect Quota";
    }
    leaf sess-disc-quota-remaining {
      xr:xr-xml-map "iedge_stats_data:sess_disc_quota_remaining";
      type uint32;
      description "Session Disconnect Quota Remaining";
    }
    leaf sess-disc-q-count {
      xr:xr-xml-map "iedge_stats_data:sess_disc_q_count";
      type uint32;
      description "Session Disconnect Requests Queued";
    }
  }

  grouping IEDGE-STATS-CH-REQ-STATS {
    description "Change of authorization request statistics";
    leaf received-requests {
      xr:xr-xml-map "iedge_stats_data:ReceivedRequests";
      type uint64;
      description "Received requests";
    }
    leaf acknowledged-requests {
      xr:xr-xml-map "iedge_stats_data:AcknowledgedRequests";
      type uint64;
      description "Acknowledged requests";
    }
    leaf non-acknowledged-requests {
      xr:xr-xml-map "iedge_stats_data:NonAcknowledgedRequests";
      type uint64;
      description "Non acknowledged requests";
    }
  }

  grouping IEDGE-STATS-CH-DATA {
    description "Change of authorization statistics";

    container account-logon {
      description "Account logon request statistics";
      uses IEDGE-STATS-CH-REQ-STATS;
    }

    container account-logoff {
      description "Account logoff request statistics";
      uses IEDGE-STATS-CH-REQ-STATS;
    }

    container account-update {
      description "Account update request statistics";
      uses IEDGE-STATS-CH-REQ-STATS;
    }

    container session-disconnect {
      description "Session disconnect request statistics";
      uses IEDGE-STATS-CH-REQ-STATS;
    }

    container single-service-logon {
      description "Service logon request statistics";
      uses IEDGE-STATS-CH-REQ-STATS;
    }

    container single-service-logoff {
      description "Single Service logoff request statistics";
      uses IEDGE-STATS-CH-REQ-STATS;
    }

    container single-service-modify {
      description "Single Service Modify request statistics";
      uses IEDGE-STATS-CH-REQ-STATS;
    }

    container service-multi {
      description "MA-CoA Service request statistics";
      uses IEDGE-STATS-CH-REQ-STATS;
    }
    leaf unknown-account-cmd-resps {
      xr:xr-xml-map "iedge_stats_data:unknown_account_cmd_resps";
      type uint64;
      description "Responses to unknown account command";
    }
    leaf unknown-service-cmd-resps {
      xr:xr-xml-map "iedge_stats_data:unknown_service_cmd_resps";
      type uint64;
      description "Responses to unknown service command";
    }
    leaf unknown-cmd-resps {
      xr:xr-xml-map "iedge_stats_data:unknown_cmd_resps";
      type uint64;
      description "Responses to unknown command";
    }
    leaf attr-list-retrieve-failure-resps {
      xr:xr-xml-map "iedge_stats_data:attr_list_retrieve_failure_re"+
        "sps";
      type uint64;
      description "Responses to attribute list failure errors";
    }
    leaf resp-send-failure {
      xr:xr-xml-map "iedge_stats_data:resp_send_failure";
      type uint64;
      description "Response send failures";
    }
    leaf internal-err-resps {
      xr:xr-xml-map "iedge_stats_data:internal_err_resps";
      type uint64;
      description "Responses to internal error";
    }
    leaf service-profile-push-failure-resps {
      xr:xr-xml-map "iedge_stats_data:service_profile_push_failure_"+
        "resps";
      type uint64;
      description "Responses to service profile push failures";
    }
    leaf no-cmd-resps {
      xr:xr-xml-map "iedge_stats_data:no_cmd_resps";
      type uint64;
      description "Responses empty (no command) COA request";
    }
    leaf no-session-found-resps {
      xr:xr-xml-map "iedge_stats_data:no_session_found_resps";
      type uint64;
      description
        "Responses to COA with unknown session identifier";
    }
    leaf no-session-peer-resps {
      xr:xr-xml-map "iedge_stats_data:no_session_peer_resps";
      type uint64;
      description "Responses to session peer not found error";
    }
  }

  grouping IEDGE-STATS-MOB-DATA {
    description "Mobility statistics";
    leaf send-request-successes {
      xr:xr-xml-map "iedge_stats_data:SendRequestSuccesses";
      type uint64;
      description "Request send success";
    }
    leaf send-request-failures {
      xr:xr-xml-map "iedge_stats_data:SendRequestFailures";
      type uint64;
      description "Request send failures";
    }
    leaf receive-response-successes {
      xr:xr-xml-map "iedge_stats_data:ReceiveResponseSuccesses";
      type uint64;
      description "Response receive success";
    }
    leaf receive-response-failures {
      xr:xr-xml-map "iedge_stats_data:ReceiveResponseFailures";
      type uint64;
      description "Response receive failures";
    }
  }

  grouping IEDGE-STATS-COORD-AUTH-DATA {
    description "Authorization & authentication statistics";
    leaf sent-requests {
      xr:xr-xml-map "iedge_stats_data:SentRequests";
      type uint64;
      description "Requests sent to radius server";
    }
    leaf accepted-requests {
      xr:xr-xml-map "iedge_stats_data:AcceptedRequests";
      type uint64;
      description "Request accepted by Radius server";
    }
    leaf successful-requests {
      xr:xr-xml-map "iedge_stats_data:SuccessfulRequests";
      type uint64;
      description "Requests which are successful";
    }
    leaf rejected-requests {
      xr:xr-xml-map "iedge_stats_data:RejectedRequests";
      type uint64;
      description "Requests rejected by radius server";
    }
    leaf unreachable-requests {
      xr:xr-xml-map "iedge_stats_data:UnreachableRequests";
      type uint64;
      description "Radius server not available";
    }
    leaf errored-requests {
      xr:xr-xml-map "iedge_stats_data:ErroredRequests";
      type uint64;
      description "Unexpected errors";
    }
    leaf incomplete-requests {
      xr:xr-xml-map "iedge_stats_data:IncompleteRequests";
      type uint64;
      description "Incomplete requests - missing attributes";
    }
    leaf terminated-requests {
      xr:xr-xml-map "iedge_stats_data:TerminatedRequests";
      type uint64;
      description "Requests terminated by disconnect";
    }
  }

  grouping IEDGE-INTERIM-INFLIGHT-COORD-DATA {
    description "Interim inflight information";
    leaf quota-exhausts {
      xr:xr-xml-map "iedge_stats_data:QuotaExhausts";
      type uint32;
      description "Quota exhausts";
    }
    leaf denied-requests {
      xr:xr-xml-map "iedge_stats_data:DeniedRequests";
      type uint32;
      description "Denied requests";
    }
    leaf accepted-requests {
      xr:xr-xml-map "iedge_stats_data:AcceptedRequests";
      type uint32;
      description "Accepted requests";
    }
    leaf total-quota-of-requests {
      xr:xr-xml-map "iedge_stats_data:TotalQuotaOfRequests";
      type uint32;
      description "Total quota of requests";
    }
    leaf remaining-quota-of-requests {
      xr:xr-xml-map "iedge_stats_data:RemainingQuotaOfRequests";
      type uint32;
      description "Remaining quota of requests";
    }
    leaf low-water-mark-quota-of-requests {
      xr:xr-xml-map "iedge_stats_data:LowWaterMarkQuotaOfRequests";
      type uint32;
      description "Low water mark quota of requests";
    }
  }

  grouping IEDGE-STATS-COORD-ACCT-REQ-STATS {
    description "AAA accounting request-response statistics";
    leaf received-requests {
      xr:xr-xml-map "iedge_stats_data:ReceivedRequests";
      type uint64;
      description "Received requests";
    }
    leaf errored-requests {
      xr:xr-xml-map "iedge_stats_data:ErroredRequests";
      type uint64;
      description "Errored requests";
    }
    leaf aaa-errored-requests {
      xr:xr-xml-map "iedge_stats_data:AAAErroredRequests";
      type uint64;
      description "AAA errored requests";
    }
    leaf aaa-sent-requests {
      xr:xr-xml-map "iedge_stats_data:AAASentRequests";
      type uint64;
      description "AAA requests sent";
    }
    leaf aaa-succeeded-responses {
      xr:xr-xml-map "iedge_stats_data:AAASucceededResponses";
      type uint64;
      description "AAA succeeded responses";
    }
    leaf aaa-failed-responses {
      xr:xr-xml-map "iedge_stats_data:AAAFailedResponses";
      type uint64;
      description "AAA failed responses";
    }
  }

  grouping IEDGE-STATS-COORD-ACCT-DATA {
    description "AAA accounting statistics";

    container start {
      description "Start statistics";
      uses IEDGE-STATS-COORD-ACCT-REQ-STATS;
    }

    container stop {
      description "Stop statistics";
      uses IEDGE-STATS-COORD-ACCT-REQ-STATS;
    }

    container interim {
      description "Interim statistics";
      uses IEDGE-STATS-COORD-ACCT-REQ-STATS;
    }

    container pass-through {
      description "Pass-through statistics";
      uses IEDGE-STATS-COORD-ACCT-REQ-STATS;
    }

    container update {
      description "Update statistics";
      uses IEDGE-STATS-COORD-ACCT-REQ-STATS;
    }

    container interim-inflight {
      description "Interim inflight details";
      uses IEDGE-INTERIM-INFLIGHT-COORD-DATA;
    }
    leaf active-sessions {
      xr:xr-xml-map "iedge_stats_data:ActiveSessions";
      type uint32;
      description "Active sessions";
    }
    leaf started-sessions {
      xr:xr-xml-map "iedge_stats_data:StartedSessions";
      type uint64;
      description "Started sessions";
    }
    leaf stopped-sessions {
      xr:xr-xml-map "iedge_stats_data:StoppedSessions";
      type uint64;
      description "Stopped sessions";
    }
    leaf policy-plane-errored-requests {
      xr:xr-xml-map "iedge_stats_data:PolicyPlaneErroredRequests";
      type uint64;
      description "Policy plane errored requests";
    }
    leaf policy-plane-unknown-requests {
      xr:xr-xml-map "iedge_stats_data:PolicyPlaneUnknownRequests";
      type uint64;
      description "Policy plane unknown requests";
    }
  }
}
