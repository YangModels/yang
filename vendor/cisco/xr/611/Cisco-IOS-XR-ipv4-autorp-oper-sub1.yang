submodule Cisco-IOS-XR-ipv4-autorp-oper-sub1 {

  belongs-to Cisco-IOS-XR-ipv4-autorp-oper {
    prefix Cisco-IOS-XR-ipv4-autorp-oper;
  }

  /*** LINKAGE (IMPORTS / INCLUDES) ***/

  import ietf-inet-types { prefix "inet"; }

  import Cisco-IOS-XR-types { prefix "xr"; }

  include Cisco-IOS-XR-ipv4-autorp-oper-sub2 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR ipv4-autorp package operational data.

     Copyright (c) 2013-2016 by Cisco Systems, Inc.
     All rights reserved.";

  revision "2015-11-09" {
    description
      "IOS XR 6.0 revision.";
  }


  grouping AUTORP-MAP-SUMMARY-BAG {
    description "Auto-RP Mapping Agent summary";
    leaf is-maximum-disabled {
      xr:xr-xml-map "autorp_map_agent:IsMaximumDisabled";
      type boolean;
      description "Is maximum enforcement disabled ?";
    }
    leaf cache-limit {
      xr:xr-xml-map "autorp_map_agent:CacheLimit";
      type uint32;
      description "Maximum group to RP mapping entries allowed";
    }
    leaf cache-count {
      xr:xr-xml-map "autorp_map_agent:CacheCount";
      type uint32;
      description
        "Number of group to RP mapping entries in the
        cache";
    }
  }

  grouping AUTORP-MAP-RANGE-BAG {
    description "MRIB multicast-routing entry-interface";
    leaf prefix {
      xr:xr-xml-map "autorp_map_agent:Prefix";
      type inet:ipv4-address;
      description "Prefix of the range";
    }
    leaf prefix-length {
      xr:xr-xml-map "autorp_map_agent:PrefixLength";
      type uint8;
      description "Prefix length of the range";
    }
    leaf protocol-mode {
      xr:xr-xml-map "autorp_map_agent:ProtocolMode";
      type Autorp-protocol-mode;
      description "Protocol Mode";
    }
    leaf is-advertised {
      xr:xr-xml-map "autorp_map_agent:IsAdvertised";
      type boolean;
      description "Is this entry advertised ?";
    }
    leaf create-type {
      xr:xr-xml-map "autorp_map_agent:CreateType";
      type uint8;
      description "Source of the entry";
    }
    leaf check-point-object-id {
      xr:xr-xml-map "autorp_map_agent:CheckPointObjectID";
      type uint32;
      description "Checkpoint object id";
    }
    leaf uptime {
      xr:xr-xml-map "autorp_map_agent:Uptime";
      type uint64;
      units "second";
      description "Uptime in seconds";
    }
  }

  grouping AUTORP-MAP-RP-BAG {
    description "Auto-RP Mapping Agent entry";
    leaf rp-address-xr {
      xr:xr-xml-map "autorp_map_agent:rp-address-xr";
      type inet:ipv4-address;
      description "Candidate-RP address";
    }
    leaf expiry-time {
      xr:xr-xml-map "autorp_map_agent:ExpiryTime";
      type uint64;
      units "second";
      description "Time for expiration in seconds";
    }
    leaf pim-version {
      xr:xr-xml-map "autorp_map_agent:PIMVersion";
      type uint8;
      description "PIM version of the CRP";
    }

    list range {
      description "Array of ranges";
      uses AUTORP-MAP-RANGE-BAG;
    }
  }
}
