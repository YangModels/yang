module Cisco-IOS-XR-infra-rcmd-oper {

  /*** NAMESPACE / PREFIX DEFINITION ***/

  namespace "http://cisco.com/ns/yang/Cisco-IOS-XR-infra-rcmd-oper";


  prefix "infra-rcmd-oper";

  /*** LINKAGE (IMPORTS / INCLUDES) ***/

  import ietf-inet-types { prefix "inet"; }

  import Cisco-IOS-XR-types { prefix "xr"; }

  include Cisco-IOS-XR-infra-rcmd-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR infra-rcmd package operational data.

     This module contains definitions
     for the following management objects:
       rcmd: Show command for Route Convergence Monitoring &
         Diagnostics

     Copyright (c) 2013-2016 by Cisco Systems, Inc.
     All rights reserved.";

  revision "2015-11-09" {
    description
      "IOS XR 6.0 revision.";
  }


  container rcmd {
    xr:xr-xml-map "rcmd_oper:RCMD";
    config false;
    description
      "Show command for Route Convergence Monitoring &
      Diagnostics";

    container ospf {
      xr:xr-xml-map "rcmd_show_ospf:OSPF";
      description "Operational data for OSPF";

      container instances {
        xr:xr-xml-map "rcmd_show_ospf:InstanceTable";
        description "Operational data";

        list instance {
          xr:xr-xml-map "rcmd_show_ospf:Instance";
          key "instance-name";
          description "Operational data for a particular instance";

          container ipfrr-event-summaries {
            xr:xr-xml-map "rcmd_show_ospf:IPFRREventSummaryTable";
            description "OSPF IP-FRR events summary data";

            list ipfrr-event-summary {
              xr:xr-xml-map "rcmd_show_ospf:IPFRREventSummary";
              key "event-id";
              description "IP-FRR Event data";
              leaf event-id {
                xr:xr-xml-map "rcmd_show_ospf:EventID";
                type int32;
                description "Specific IP-FRR Event";
              }
              uses RCMD-SHOW-IPFRR-EVENT-INFO;
            }
          }

          container prefix-event-statistics {
            xr:xr-xml-map "rcmd_show_ospf:PrefixEventStatisticsTabl"+
              "e";
            description "OSPF Prefix events summary data";

            list prefix-event-statistic {
              xr:xr-xml-map "rcmd_show_ospf:PrefixEventStatistics";
              key "prefix-info";
              description "Prefix Event statistics";
              leaf prefix-info {
                xr:xr-xml-map "rcmd_show_ospf:PrefixInfo";
                type inet:ip-prefix;
                description "Events with Prefix";
              }
              uses RCMD-SHOW-PREFIX-INFO;
            }
          }

          container spf-run-summaries {
            xr:xr-xml-map "rcmd_show_ospf:SPFRunSummaryTable";
            description "OSPF SPF run summary data";

            list spf-run-summary {
              xr:xr-xml-map "rcmd_show_ospf:SPFRunSummary";
              key "spf-run-number";
              description "SPF Event data";
              leaf spf-run-number {
                xr:xr-xml-map "rcmd_show_ospf:SPFRunNumber";
                type int32;
                description "Specific SPF run";
              }
              uses RCMD-OSPF-SPF-RUN;
            }
          }

          container ipfrr-event-offlines {
            xr:xr-xml-map "rcmd_show_ospf:IPFRREventOfflineTable";
            description "OSPF IP-FRR Event offline data";

            list ipfrr-event-offline {
              xr:xr-xml-map "rcmd_show_ospf:IPFRREventOffline";
              key "event-id";
              description
                "Offline operational data for particular OSPF
                IP-FRR Event";
              leaf event-id {
                xr:xr-xml-map "rcmd_show_ospf:EventID";
                type int32;
                description "Specific IP-FRR Event";
              }
              uses RCMD-SHOW-IPFRR-EVENT-INFO;
            }
          }

          container spf-run-offlines {
            xr:xr-xml-map "rcmd_show_ospf:SPFRunOfflineTable";
            description "OSPF SPF run offline data";

            list spf-run-offline {
              xr:xr-xml-map "rcmd_show_ospf:SPFRunOffline";
              key "spf-run-number";
              description
                "Offline operational data for particular OSPF
                SPF run";
              leaf spf-run-number {
                xr:xr-xml-map "rcmd_show_ospf:SPFRunNumber";
                type int32;
                description "Specific SPF run";
              }
              uses RCMD-OSPF-SPF-RUN;
            }
          }

          container summary-external-event-summaries {
            xr:xr-xml-map "rcmd_show_ospf:SummaryExternalEventSumma"+
              "ryTable";
            description
              "OSPF Summary-External Prefix events summary
              data";

            list summary-external-event-summary {
              xr:xr-xml-map "rcmd_show_ospf:SummaryExternalEventSum"+
                "mary";
              key "event-id";
              description "OSPF Summary-External Prefix Event data";
              leaf event-id {
                xr:xr-xml-map "rcmd_show_ospf:EventID";
                type int32;
                description "Specific Event ID";
              }
              uses RCMD-SHOW-PREFIX-EVENT;
            }
          }

          container prefix-event-summaries {
            xr:xr-xml-map "rcmd_show_ospf:PrefixEventSummaryTable";
            description "OSPF Prefix events summary data";

            list prefix-event-summary {
              xr:xr-xml-map "rcmd_show_ospf:PrefixEventSummary";
              key "event-id";
              description "OSPF Prefix Event data";
              leaf event-id {
                xr:xr-xml-map "rcmd_show_ospf:EventID";
                type int32;
                description "Specific Event ID";
              }
              uses RCMD-SHOW-PREFIX-EVENT;
            }
          }

          container summary-external-event-offlines {
            xr:xr-xml-map "rcmd_show_ospf:SummaryExternalEventOffli"+
              "neTable";
            description
              "OSPF Summary-External Prefix events offline
              data";

            list summary-external-event-offline {
              xr:xr-xml-map "rcmd_show_ospf:SummaryExternalEventOff"+
                "line";
              key "event-id";
              description
                "Offline operational data for particular OSPF
                Prefix Event";
              leaf event-id {
                xr:xr-xml-map "rcmd_show_ospf:EventID";
                type int32;
                description "Specific Event ID";
              }
              uses RCMD-SHOW-PREFIX-EVENT;
            }
          }

          container prefix-event-offlines {
            xr:xr-xml-map "rcmd_show_ospf:PrefixEventOfflineTable";
            description "OSPF Prefix events offline data";

            list prefix-event-offline {
              xr:xr-xml-map "rcmd_show_ospf:PrefixEventOffline";
              key "event-id";
              description
                "Offline operational data for particular OSPF
                Prefix Event";
              leaf event-id {
                xr:xr-xml-map "rcmd_show_ospf:EventID";
                type int32;
                description "Specific Event ID";
              }
              uses RCMD-SHOW-PREFIX-EVENT;
            }
          }

          container summary-external-event-statistics {
            xr:xr-xml-map "rcmd_show_ospf:SummaryExternalEventStati"+
              "stics";
            description
              "Summary-External prefix monitoring statistics";
            uses RCMD-SHOW-TYPE357-STATS-INFO;
          }
          leaf instance-name {
            xr:xr-xml-map "rcmd_show_ospf:InstanceName";
            type xr:Cisco-ios-xr-string;
            description
              "Operational data for a particular instance";
          }
        }
      }
    }

    container server {
      xr:xr-xml-map "rcmd_show_server:SERVER";
      description "Server Info";

      container normal {
        xr:xr-xml-map "rcmd_show_server:NORMAL";
        description "Server Info";
        uses RCMD-SHOW-SERVER;
      }

      container detail {
        xr:xr-xml-map "rcmd_show_server:DETAIL";
        description "Server Info";
        uses RCMD-SHOW-SERVER;
      }
    }

    container node {
      xr:xr-xml-map "rcmd_show_node:NODE";
      description "Node Info";
      uses RCMD-SHOW-NODE;
    }

    container isis {
      xr:xr-xml-map "rcmd_show_isis:ISIS";
      description "Operational data for ISIS";

      container instances {
        xr:xr-xml-map "rcmd_show_isis:InstanceTable";
        description "Operational data";

        list instance {
          xr:xr-xml-map "rcmd_show_isis:Instance";
          key "instance-name";
          description "Operational data for a particular instance";

          container ipfrr-event-summaries {
            xr:xr-xml-map "rcmd_show_isis:IPFRREventSummaryTable";
            description "ISIS IP-FRR events summary data";

            list ipfrr-event-summary {
              xr:xr-xml-map "rcmd_show_isis:IPFRREventSummary";
              key "event-id";
              description "IP-FRR Event data";
              leaf event-id {
                xr:xr-xml-map "rcmd_show_isis:EventID";
                type int32;
                description "Specific IP-FRR Event";
              }
              uses RCMD-SHOW-IPFRR-EVENT-INFO;
            }
          }

          container prefix-event-statistics {
            xr:xr-xml-map "rcmd_show_isis:PrefixEventStatisticsTabl"+
              "e";
            description "ISIS Prefix events statistics data";

            list prefix-event-statistic {
              xr:xr-xml-map "rcmd_show_isis:PrefixEventStatistics";
              key "prefix-info";
              description "Monitoring Statistics";
              leaf prefix-info {
                xr:xr-xml-map "rcmd_show_isis:PrefixInfo";
                type inet:ip-prefix;
                description "Events with Prefix";
              }
              uses RCMD-SHOW-PREFIX-INFO;
            }
          }

          container spf-run-summaries {
            xr:xr-xml-map "rcmd_show_isis:SPFRunSummaryTable";
            description "ISIS SPF run summary data";

            list spf-run-summary {
              xr:xr-xml-map "rcmd_show_isis:SPFRunSummary";
              key "spf-run-number";
              description "SPF Event data";
              leaf spf-run-number {
                xr:xr-xml-map "rcmd_show_isis:SPFRunNumber";
                type int32;
                description "Specific SPF run";
              }
              uses RCMD-ISIS-SPF-RUN;
            }
          }

          container ipfrr-event-offlines {
            xr:xr-xml-map "rcmd_show_isis:IPFRREventOfflineTable";
            description "ISIS IP-FRR Event offline data";

            list ipfrr-event-offline {
              xr:xr-xml-map "rcmd_show_isis:IPFRREventOffline";
              key "event-id";
              description
                "Offline operational data for particular ISIS
                IP-FRR Event";
              leaf event-id {
                xr:xr-xml-map "rcmd_show_isis:EventID";
                type int32;
                description "Specific IP-FRR Event";
              }
              uses RCMD-SHOW-IPFRR-EVENT-INFO;
            }
          }

          container spf-run-offlines {
            xr:xr-xml-map "rcmd_show_isis:SPFRunOfflineTable";
            description "ISIS SPF run offline data";

            list spf-run-offline {
              xr:xr-xml-map "rcmd_show_isis:SPFRunOffline";
              key "spf-run-number";
              description
                "Offline operational data for particular ISIS
                SPF run";
              leaf spf-run-number {
                xr:xr-xml-map "rcmd_show_isis:SPFRunNumber";
                type int32;
                description "Specific SPF run";
              }
              uses RCMD-ISIS-SPF-RUN;
            }
          }

          container prefix-event-summaries {
            xr:xr-xml-map "rcmd_show_isis:PrefixEventSummaryTable";
            description "ISIS Prefix events summary data";

            list prefix-event-summary {
              xr:xr-xml-map "rcmd_show_isis:PrefixEventSummary";
              key "event-id";
              description "Prefix Event data";
              leaf event-id {
                xr:xr-xml-map "rcmd_show_isis:EventID";
                type int32;
                description "Specific Event ID";
              }
              uses RCMD-SHOW-PREFIX-EVENT;
            }
          }

          container prefix-event-offlines {
            xr:xr-xml-map "rcmd_show_isis:PrefixEventOfflineTable";
            description "ISIS Prefix events offline data";

            list prefix-event-offline {
              xr:xr-xml-map "rcmd_show_isis:PrefixEventOffline";
              key "event-id";
              description
                "Offline operational data for particular ISIS
                Prefix Event";
              leaf event-id {
                xr:xr-xml-map "rcmd_show_isis:EventID";
                type int32;
                description "Specific Event ID";
              }
              uses RCMD-SHOW-PREFIX-EVENT;
            }
          }

          container lsp-regenerateds {
            xr:xr-xml-map "rcmd_show_isis:LSPRegeneratedTable";
            description "Regenerated LSP data";

            list lsp-regenerated {
              xr:xr-xml-map "rcmd_show_isis:LSPRegenerated";
              key "serial-number";
              description "Regenerated LSP data";
              leaf serial-number {
                xr:xr-xml-map "rcmd_show_isis:SerialNumber";
                type int32;
                description "Data for a particular regenerated LSP";
              }
              uses RCMD-REGEN-LSP-INFO;
            }
          }
          leaf instance-name {
            xr:xr-xml-map "rcmd_show_isis:InstanceName";
            type xr:Cisco-ios-xr-string;
            description
              "Operational data for a particular instance";
          }
        }
      }
    }

    container memory {
      xr:xr-xml-map "rcmd_show_memory:MEMORY";
      description "Memory Info";
      uses RCMD-SHOW-MEMORY;
    }

    container ldp {
      xr:xr-xml-map "rcmd_show_ldp:LDP";
      description "LDP data";

      container sessions {
        xr:xr-xml-map "rcmd_show_ldp:SessionTable";
        description "Session Events";

        list session {
          xr:xr-xml-map "rcmd_show_ldp:Session";
          key "event-id";
          description "Session";
          leaf event-id {
            xr:xr-xml-map "rcmd_show_ldp:EventID";
            type int32;
            description "Specific Event ID";
          }
          uses RCMD-SHOW-LDP-SESSION-EVENT;
        }
      }

      container remote-lfa-s {
        xr:xr-xml-map "rcmd_show_ldp:RemoteLFATable";
        description "Remote LFA Coverage Events";

        list remote-lfa {
          xr:xr-xml-map "rcmd_show_ldp:RemoteLFA";
          key "event-id";
          description "RemoteLFA";
          leaf event-id {
            xr:xr-xml-map "rcmd_show_ldp:EventID";
            type int32;
            description "Specific Event ID";
          }
          uses RCMD-SHOW-LDP-RLFA-EVENT;
        }
      }

      container remote-lfa-summaries {
        xr:xr-xml-map "rcmd_show_ldp:RemoteLFASummaryTable";
        description "Remote LFA Coverage Events";

        list remote-lfa-summary {
          xr:xr-xml-map "rcmd_show_ldp:RemoteLFASummary";
          key "event-id";
          description "Summary operational data for Remote LFA";
          leaf event-id {
            xr:xr-xml-map "rcmd_show_ldp:EventID";
            type int32;
            description "Specific Event ID";
          }
          uses RCMD-SHOW-LDP-RLFA-EVENT;
        }
      }
    }

    container intf {
      xr:xr-xml-map "rcmd_show_intf:INTF";
      description "Interface data";

      container events {
        xr:xr-xml-map "rcmd_show_intf:EventTable";
        description "Events";

        list event {
          xr:xr-xml-map "rcmd_show_intf:Event";
          key "event-no";
          description "Events";
          leaf event-no {
            xr:xr-xml-map "rcmd_show_intf:EventNo";
            type int32;
            description "Specific Event No.";
          }
          uses RCMD-SHOW-INTF-EVENT;
        }
      }
    }

    container process {
      xr:xr-xml-map "rcmd_show_process:PROCESS";
      description "Process information";

      container isis {
        xr:xr-xml-map "rcmd_show_process:ISIS";
        description "ISIS Process Information";
        uses RCMD-SHOW-PROCESS;
      }

      container ospf {
        xr:xr-xml-map "rcmd_show_process:OSPF";
        description "OSPF Process Information";
        uses RCMD-SHOW-PROCESS;
      }

      container ldp {
        xr:xr-xml-map "rcmd_show_process:LDP";
        description "LDP Process Information";
        uses RCMD-SHOW-PROCESS;
      }
    }
  }
}
