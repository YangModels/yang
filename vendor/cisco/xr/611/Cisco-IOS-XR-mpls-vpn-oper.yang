module Cisco-IOS-XR-mpls-vpn-oper {

  /*** NAMESPACE / PREFIX DEFINITION ***/

  namespace "http://cisco.com/ns/yang/Cisco-IOS-XR-mpls-vpn-oper";


  prefix "mpls-vpn-oper";

  /*** LINKAGE (IMPORTS / INCLUDES) ***/

  import Cisco-IOS-XR-types { prefix "xr"; }

  include Cisco-IOS-XR-mpls-vpn-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR mpls-vpn package operational data.

     This module contains definitions
     for the following management objects:
       l3vpn: L3VPN operational data

     Copyright (c) 2013-2016 by Cisco Systems, Inc.
     All rights reserved.";

  revision "2015-11-09" {
    description
      "IOS XR 6.0 revision.";
  }


  container l3vpn {
    xr:xr-xml-map "mpls_vpn_oper:L3VPN";
    config false;
    description "L3VPN operational data";

    container invalid-vrfs {
      xr:xr-xml-map "mpls_vpn_oper:InvalidVRFTable";
      description
        "Invalid VRF Table (VRFs that are forward
        referenced)";

      list invalid-vrf {
        xr:xr-xml-map "mpls_vpn_oper:InvalidVRF";
        key "vrf-name";
        description "Invalid VRF (VRF that is forward referenced)";
        leaf vrf-name {
          xr:xr-xml-map "mpls_vpn_oper:VRFName";
          type string;
          description "The Name for an invalid VRF";
        }
        uses MPLS-VPN-VRF;
      }
    }

    container vrfs {
      xr:xr-xml-map "mpls_vpn_oper:VRFTable";
      description "VRF Table";

      list vrf {
        xr:xr-xml-map "mpls_vpn_oper:VRF";
        key "vrf-name";
        description "VRF";
        leaf vrf-name {
          xr:xr-xml-map "mpls_vpn_oper:VRFName";
          type string;
          description "The Name for a VRF";
        }
        uses MPLS-VPN-VRF;
      }
    }
  }
}
