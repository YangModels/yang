module Cisco-IOS-XR-ipv6-new-dhcpv6d-cfg {

  /*** NAMESPACE / PREFIX DEFINITION ***/

  namespace "http://cisco.com/ns/yang"+
    "/Cisco-IOS-XR-ipv6-new-dhcpv6d-cfg";


  prefix "ipv6-new-dhcpv6d-cfg";

  /*** LINKAGE (IMPORTS / INCLUDES) ***/

  import ietf-inet-types { prefix "inet"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ipv6-new-dhcpv6d package configuration.

     This module contains definitions
     for the following management objects:
       dhcpv6: None

     Copyright (c) 2013-2016 by Cisco Systems, Inc.
     All rights reserved.";

  revision "2016-03-08" {
    description
      "Moved augment statement to a separate file";
  }

  revision "2015-11-09" {
    description
      "IOS XR 6.0 revision.";
  }

  typedef Insert {
    type enumeration {
      enum local {
        value 0;
        description
          "Insert locally generated/configured Interface
          ID value";
      }
      enum received {
        value 1;
        description "Insert received Interface ID value";
      }
      enum pppoe {
        value 2;
        description "Insert received Interface ID value from SADB";
      }
    }
    description "Insert";
  }
  typedef Subscriber-id {
    type enumeration {
      enum pppoe {
        value 3;
        description "Insert Received Subscriber-ID Value from SADB";
      }
    }
    description "Subscriber id";
  }
  typedef Link-layer-addr {
    type enumeration {
      enum set {
        value 4;
        description "Insert Received LinkLayerAddr Value from SADB";
      }
    }
    description "Link layer addr";
  }

  container dhcpv6 {
    xr:xr-xml-map "dhcp_ipv6_cfg:DHCPv6";
    presence "Indicates a dhcpv6 node is configured.";
    description "None";

    container database {
      xr:xr-xml-map "dhcp_ipv6_cfg:Database";
      description
        "Enable DHCP binding database storage to file
        system";
      leaf proxy {
        xr:xr-xml-map "dhcp_ipv6_cfg:Proxy";
        type empty;
        description
          "Enable DHCP proxy binding database storage to
          file system";
      }
      leaf server {
        xr:xr-xml-map "dhcp_ipv6_cfg:Server";
        type empty;
        description
          "Enable DHCP server binding database storage to
          file system";
      }
      leaf relay {
        xr:xr-xml-map "dhcp_ipv6_cfg:Relay";
        type empty;
        description
          "Enable DHCP relay binding database storage to
          file system";
      }
      leaf full-write-interval {
        xr:xr-xml-map "dhcp_ipv6_cfg:FullWriteInterval";
        type uint32 {
          range "1..1440";
        }
        default "10";
        description "Full file write interval (default 10 minutes)";
      }
      leaf incremental-write-interval {
        xr:xr-xml-map "dhcp_ipv6_cfg:IncrementalWriteInterval";
        type uint32 {
          range "1..1440";
        }
        default "1";
        description
          "Incremental file write interval (default 1
          minutes)";
      }
    }

    container profiles {
      xr:xr-xml-map "dhcp_ipv6_cfg:ProfileTable";
      description "Table of Profile";

      list profile {
        xr:xr-xml-map "dhcp_ipv6_cfg:Profile";
        key "profile-name";
        description "None";

        container relay {
          xr:xr-xml-map "dhcp_ipv6_cfg:Relay";
          presence "Indicates a relay node is configured.";
          description "None";

          container helper-addresses {
            xr:xr-xml-map "dhcp_ipv6_relay_cfg:HelperAddressTable";
            description "Table of HelperAddress";

            list helper-address {
              xr:xr-xml-map "dhcp_ipv6_relay_cfg:HelperAddress";
              key "vrf-name helper-address";
              description "Specify the server helper address";
              leaf vrf-name {
                xr:xr-xml-map "dhcp_ipv6_relay_cfg:VRFName";
                type xr:Cisco-ios-xr-string {
                  length "0..32";
                }
                description "VRF name";
              }
              leaf helper-address {
                xr:xr-xml-map "dhcp_ipv6_relay_cfg:HelperAddress";
                type inet:ipv6-address-no-zone;
                description "Server Global unicast address";
              }
            }
          }
          leaf enable {
            xr:xr-xml-map "dhcp_ipv6_cfg:Enable";
            type empty;
            mandatory true;
            description
              "Enable None. Deletion of this object also
              causes deletion of all associated objects
              under Relay.";
          }
          leaf iana-route-add {
            xr:xr-xml-map "dhcp_ipv6_relay_cfg:IanaRouteAdd";
            type empty;
            description "Enable route addition for IANA";
          }
        }

        container proxy {
          xr:xr-xml-map "dhcp_ipv6_cfg:Proxy";
          presence "Indicates a proxy node is configured.";
          description "None";

          container interfaces {
            xr:xr-xml-map "dhcp_ipv6_proxy_cfg:InterfaceTable";
            description "Table of Interface";

            list interface {
              xr:xr-xml-map "dhcp_ipv6_proxy_cfg:Interface";
              key "interface-name";
              description "None";
              leaf interface-id {
                xr:xr-xml-map "dhcp_ipv6_proxy_cfg:InterfaceID";
                type string;
                description "Physical interface ID";
              }
              leaf interface-name {
                xr:xr-xml-map "dhcp_ipv6_proxy_cfg:InterfaceName";
                type xr:Interface-name;
                description "Interface to configure";
              }
            }
          }

          container relay {
            xr:xr-xml-map "dhcp_ipv6_proxy_cfg:Relay";
            description "Specify relay configuration";

            container option {
              xr:xr-xml-map "dhcp_ipv6_proxy_cfg:Option";
              description "Specify relay option configuration";

              container interface-id {
                xr:xr-xml-map "dhcp_ipv6_proxy_cfg:InterfaceID";
                description "Interface Id option";
                leaf insert {
                  xr:xr-xml-map "dhcp_ipv6_proxy_cfg:Insert";
                  xr:xr-cli-map "interface-id insert <enum> ";
                  type Insert;
                  description "Configure InterfaceID insert type";
                }
              }
              leaf subscriber-id {
                xr:xr-xml-map "dhcp_ipv6_proxy_cfg:SubscriberID";
                xr:xr-cli-map "subscriber-id <enum> ";
                type Subscriber-id;
                description "Configure Received SubscriberID";
              }
              leaf link-layer-addr {
                xr:xr-xml-map "dhcp_ipv6_proxy_cfg:LinkLayerAddr";
                xr:xr-cli-map "link-layer-addr <enum> ";
                type Link-layer-addr;
                description "Configure Received link-layer-Addr";
              }
              leaf remote-i-dreceived {
                xr:xr-xml-map "dhcp_ipv6_proxy_cfg:RemoteIDreceived";
                xr:xr-cli-map "remote-id pppoe ";
                type int32;
                description "Set remote-id value from SADB";
              }
              leaf remote-id {
                xr:xr-xml-map "dhcp_ipv6_proxy_cfg:RemoteID";
                xr:xr-cli-map "remote-id <string> ";
                type string {
                  length "0..256";
                }
                description "Enter remote-id value";
              }
            }
          }

          container vrfs {
            xr:xr-xml-map "cfg_dhcp_ipv6_proxy_profile_helper:VRFTa"+
              "ble";
            description "VRF related configuration";

            list vrf {
              xr:xr-xml-map "cfg_dhcp_ipv6_proxy_profile_helper:VRF";
              key "vrf-name";
              description "IPv6 DHCP proxy VRF name";

              container helper-addresses {
                xr:xr-xml-map "cfg_dhcp_ipv6_proxy_profile_helper:H"+
                  "elperAddressTable";
                description "Table of HelperAddress";

                list helper-address {
                  xr:xr-xml-map "cfg_dhcp_ipv6_proxy_profile_helper"+
                    ":HelperAddress";
                  key "helper-address";
                  description "DHCPv6 Helper Address";
                  leaf out-interface {
                    xr:xr-xml-map "cfg_dhcp_ipv6_proxy_profile_help"+
                      "er:OutInterface";
                    xr:xr-cli-map "ipv6 profile <string> proxy help"+
                      "er-address [vrf [<string>]] <IPv6 address> <"+
                      "interface> ";
                    type xr:Interface-name;
                    description
                      "DHCPv6 HelperAddress Specific Output
                      Interface";
                  }
                  leaf any-out-interface {
                    xr:xr-xml-map "cfg_dhcp_ipv6_proxy_profile_help"+
                      "er:AnyOutInterface";
                    xr:xr-cli-map "ipv6 profile <string> proxy help"+
                      "er-address [vrf [<string>]] <IPv6 address> ";
                    type empty;
                    description
                      "DHCPv6 HelperAddress Output Interface";
                  }
                  leaf helper-address {
                    xr:xr-xml-map "cfg_dhcp_ipv6_proxy_profile_help"+
                      "er:HelperAddress";
                    type inet:ipv6-address-no-zone;
                    description "DHCPv6 Helper Address";
                  }
                }
              }
              leaf vrf-name {
                xr:xr-xml-map "cfg_dhcp_ipv6_proxy_profile_helper:V"+
                  "RFName";
                type xr:Cisco-ios-xr-string;
                description "VRF name";
              }
            }
          }

          container classes {
            xr:xr-xml-map "dhcp_ipv6_proxy_cfg:ClassTable";
            description "Table of Class";

            list class {
              xr:xr-xml-map "dhcp_ipv6_proxy_cfg:Class";
              key "class-name";
              description "None";

              container helper-addresses {
                xr:xr-xml-map "dhcp_ipv6_proxy_cfg:HelperAddressTab"+
                  "le";
                description "Table of HelperAddress";

                list helper-address {
                  xr:xr-xml-map "dhcp_ipv6_proxy_cfg:HelperAddress";
                  key "vrf-name helper-address";
                  description "Specify the server helper address";
                  leaf vrf-name {
                    xr:xr-xml-map "dhcp_ipv6_proxy_cfg:VRFName";
                    type xr:Cisco-ios-xr-string {
                      length "0..32";
                    }
                    description "VRF name";
                  }
                  leaf helper-address {
                    xr:xr-xml-map "dhcp_ipv6_proxy_cfg:HelperAddres"+
                      "s";
                    type inet:ipv6-address-no-zone;
                    description "Server address";
                  }
                }
              }
              leaf link-address {
                xr:xr-xml-map "dhcp_ipv6_proxy_cfg:LinkAddress";
                type inet:ip-address-no-zone;
                description
                  "IPv6 address to be filled in link-address";
              }
              leaf class-name {
                xr:xr-xml-map "dhcp_ipv6_proxy_cfg:ClassName";
                type xr:Cisco-ios-xr-string {
                  length "0..128";
                }
                description "Class name";
              }
            }
          }

          container sessions {
            xr:xr-xml-map "dhcp_ipv6_proxy_cfg:Sessions";
            description "Change sessions configuration";

            container mac {
              xr:xr-xml-map "dhcp_ipv6_proxy_cfg:Mac";
              description
                "Throttle DHCP sessions based on MAC address";

              container throttle {
                xr:xr-xml-map "dhcp_ipv6_proxy_cfg:Throttle";
                description
                  "Throttle DHCP sessions from any one MAC
                  address";
                leaf limit {
                  xr:xr-xml-map "dhcp_ipv6_proxy_cfg:Limit";
                  type uint32 {
                    range "1..65535";
                  }
                  description
                    "Number of solicits at which to throttle";
                }
                leaf request {
                  xr:xr-xml-map "dhcp_ipv6_proxy_cfg:Request";
                  type uint32 {
                    range "1..100";
                  }
                  units "second";
                  description "Throttle request period (in secs)";
                }
                leaf block {
                  xr:xr-xml-map "dhcp_ipv6_proxy_cfg:Block";
                  type uint32 {
                    range "1..100";
                  }
                  units "second";
                  description "Throttle blocking period (in secs)";
                }
              }
            }
          }
          leaf link-address {
            xr:xr-xml-map "dhcp_ipv6_proxy_cfg:LinkAddress";
            type inet:ip-address-no-zone;
            description "IPv6 address to be filled in link-address";
          }
          leaf src-intf-name {
            xr:xr-xml-map "dhcp_ipv6_proxy_cfg:SrcIntfName";
            type xr:Interface-name;
            description
              "Create or enter proxy profile Source
              Interface Name";
          }
          leaf enable {
            xr:xr-xml-map "dhcp_ipv6_cfg:Enable";
            type empty;
            mandatory true;
            description
              "Enable None. Deletion of this object also
              causes deletion of all associated objects
              under Proxy.";
          }
        }

        container server {
          xr:xr-xml-map "dhcp_ipv6_cfg:Server";
          presence "Indicates a server node is configured.";
          description "None";

          container sessions {
            xr:xr-xml-map "dhcp_ipv6_server_cfg:Sessions";
            description "Change sessions configuration";

            container mac {
              xr:xr-xml-map "dhcp_ipv6_server_cfg:Mac";
              description
                "Throttle DHCP sessions based on MAC address";

              container throttle {
                xr:xr-xml-map "dhcp_ipv6_server_cfg:Throttle";
                description
                  "Throttle DHCP sessions from any one MAC
                  address";
                leaf limit {
                  xr:xr-xml-map "dhcp_ipv6_server_cfg:Limit";
                  type uint32 {
                    range "1..65535";
                  }
                  description
                    "Number of solicits at which to throttle";
                }
                leaf request {
                  xr:xr-xml-map "dhcp_ipv6_server_cfg:Request";
                  type uint32 {
                    range "1..100";
                  }
                  units "second";
                  description "Throttle request period (in secs)";
                }
                leaf block {
                  xr:xr-xml-map "dhcp_ipv6_server_cfg:Block";
                  type uint32 {
                    range "1..100";
                  }
                  units "second";
                  description "Throttle blocking period (in secs)";
                }
              }
            }
          }

          container dns-servers {
            xr:xr-xml-map "dhcp_ipv6_server_cfg:DNSServer";
            description "DNS servers";
            leaf-list dns-server {
              xr:xr-xml-map "dhcp_ipv6_server_cfg:DNSServer";
              type inet:ip-address-no-zone;
              max-elements "8";
              description "Server's IPv6 address";
            }
          }

          container classes {
            xr:xr-xml-map "dhcp_ipv6_server_cfg:ClassTable";
            description "Table of Class";

            list class {
              xr:xr-xml-map "dhcp_ipv6_server_cfg:Class";
              key "class-name";
              description "None";

              container dns-servers {
                xr:xr-xml-map "dhcp_ipv6_server_cfg:DNSServer";
                description "DNS servers";
                leaf-list dns-server {
                  xr:xr-xml-map "dhcp_ipv6_server_cfg:DNSServerAddr"+
                    "ess";
                  type inet:ip-address-no-zone;
                  max-elements "8";
                  description "Server's IPv6 address";
                }
              }
              leaf address-pool {
                xr:xr-xml-map "dhcp_ipv6_server_cfg:AddressPool";
                type string {
                  length "0..64";
                }
                description "Address pool name";
              }
              leaf domain-name {
                xr:xr-xml-map "dhcp_ipv6_server_cfg:DomainName";
                type xr:Cisco-ios-xr-string {
                  length "0..64";
                }
                description "Domain name";
              }
              leaf preference {
                xr:xr-xml-map "dhcp_ipv6_server_cfg:Preference";
                type uint32 {
                  range "1..255";
                }
                description "DHCP Server Preference";
              }
              leaf prefix-pool {
                xr:xr-xml-map "dhcp_ipv6_server_cfg:PrefixPool";
                type string {
                  length "0..64";
                }
                description "Prefix pool name";
              }
              leaf class-name {
                xr:xr-xml-map "dhcp_ipv6_server_cfg:ClassName";
                type xr:Cisco-ios-xr-string {
                  length "0..128";
                }
                description "class name";
              }
            }
          }

          container lease {
            xr:xr-xml-map "dhcp_ipv6_server_cfg:Lease";
            description "lease";
            leaf days {
              xr:xr-xml-map "dhcp_ipv6_server_cfg:Days";
              type uint32 {
                range "0..365";
              }
              units "day";
              description "Days";
            }
            leaf hours {
              xr:xr-xml-map "dhcp_ipv6_server_cfg:Hours";
              type uint32 {
                range "0..23";
              }
              units "hour";
              description "Hours";
            }
            leaf minutes {
              xr:xr-xml-map "dhcp_ipv6_server_cfg:Minutes";
              type uint32 {
                range "1..59";
              }
              units "minute";
              description "Minutes";
            }
            leaf infinite {
              xr:xr-xml-map "dhcp_ipv6_server_cfg:Infinite";
              type string;
              description "Set string";
            }
          }

          container dhcpv6-options {
            xr:xr-xml-map "dhcp_ipv6_server_cfg:DHCPv6Options";
            description "DHCPv6 options";

            container vendor-options {
              xr:xr-xml-map "dhcp_ipv6_server_cfg:VendorOptions";
              description "Vendor options";
              leaf type {
                xr:xr-xml-map "dhcp_ipv6_server_cfg:Type";
                type string;
                description "Set string";
              }
              leaf vendor-options {
                xr:xr-xml-map "dhcp_ipv6_server_cfg:VendorOptions";
                type string {
                  length "0..512";
                }
                description "Vendor options";
              }
            }
          }
          leaf address-pool {
            xr:xr-xml-map "dhcp_ipv6_server_cfg:AddressPool";
            type string {
              length "0..64";
            }
            description "Address pool name";
          }
          leaf aftr-name {
            xr:xr-xml-map "dhcp_ipv6_server_cfg:AFTRName";
            type xr:Cisco-ios-xr-string {
              length "0..64";
            }
            description "AFTR name";
          }
          leaf domain-name {
            xr:xr-xml-map "dhcp_ipv6_server_cfg:DomainName";
            type xr:Cisco-ios-xr-string {
              length "0..64";
            }
            description "Domain name";
          }
          leaf preference {
            xr:xr-xml-map "dhcp_ipv6_server_cfg:Preference";
            type uint32 {
              range "0..255";
            }
            description "DHCP Server Preference";
          }
          leaf rapid-commit {
            xr:xr-xml-map "dhcp_ipv6_server_cfg:RapidCommit";
            type empty;
            description "Allow RAPID Commit";
          }
          leaf enable {
            xr:xr-xml-map "dhcp_ipv6_cfg:Enable";
            type empty;
            mandatory true;
            description
              "Enable None. Deletion of this object also
              causes deletion of all associated objects
              under Server.";
          }
          leaf prefix-pool {
            xr:xr-xml-map "dhcp_ipv6_server_cfg:PrefixPool";
            type string {
              length "0..64";
            }
            description "Prefix pool name";
          }
        }
        leaf profile-name {
          xr:xr-xml-map "dhcp_ipv6_cfg:ProfileName";
          type xr:Cisco-ios-xr-string;
          description "Profile name";
        }
      }
    }

    container interfaces {
      xr:xr-xml-map "dhcp_ipv6_int_cfg:InterfaceTable";
      description "Table of Interface";

      list interface {
        xr:xr-xml-map "dhcp_ipv6_int_cfg:Interface";
        key "interface-name";
        description "None";

        container pppoe {
          xr:xr-xml-map "dhcp_ipv6_int_cfg:PPPOE";
          description "PPPoE subscriber interface";
          leaf profile {
            xr:xr-xml-map "dhcp_ipv6_int_cfg:Profile";
            type xr:Cisco-ios-xr-string {
              length "0..64";
            }
            description "Enter profile name";
          }
        }

        container proxy {
          xr:xr-xml-map "dhcp_ipv6_int_cfg:Proxy";
          description "Assign a proxy profile to interface";
          leaf profile {
            xr:xr-xml-map "dhcp_ipv6_int_cfg:Profile";
            type xr:Cisco-ios-xr-string {
              length "0..64";
            }
            description "Enter profile name";
          }
        }

        container server {
          xr:xr-xml-map "dhcp_ipv6_int_cfg:Server";
          description "Assign a server profile to interface";
          leaf profile {
            xr:xr-xml-map "dhcp_ipv6_int_cfg:Profile";
            xr:xr-cli-map "ipv6 interface <interface> server profil"+
              "e <string> ";
            type xr:Cisco-ios-xr-string {
              length "0..64";
            }
            description "Enter profile name";
          }
        }

        container relay {
          xr:xr-xml-map "dhcp_ipv6_int_cfg:Relay";
          description "Assign a relay profile to interface";
          leaf profile {
            xr:xr-xml-map "dhcp_ipv6_int_cfg:Profile";
            type xr:Cisco-ios-xr-string {
              length "0..64";
            }
            description "Enter profile name";
          }
        }
        leaf interface-name {
          xr:xr-xml-map "dhcp_ipv6_int_cfg:InterfaceName";
          type xr:Interface-name;
          description "Interface to configure";
        }
      }
    }
    leaf enable {
      xr:xr-xml-map "dhcp_ipv6_cfg:Enable";
      type empty;
      mandatory true;
      description
        "Enable None. Deletion of this object also causes
        deletion of all associated objects under DHCPv6.";
    }
    leaf allow-duid-change {
      xr:xr-xml-map "dhcp_ipv6_cfg:allow-duid-change";
      type empty;
      description
        "For BNG session, allow duid change for a client
        MAC";
    }
  }
}
