module Cisco-IOS-XR-mpls-static-cfg {

  /*** NAMESPACE / PREFIX DEFINITION ***/

  namespace "http://cisco.com/ns/yang/Cisco-IOS-XR-mpls-static-cfg";


  prefix "mpls-static-cfg";

  /*** LINKAGE (IMPORTS / INCLUDES) ***/

  import ietf-inet-types { prefix "inet"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR mpls-static package configuration.

     This module contains definitions
     for the following management objects:
       mpls-static: MPLS Static Configuration Data

     Copyright (c) 2013-2016 by Cisco Systems, Inc.
     All rights reserved.";

  revision "2015-11-09" {
    description
      "IOS XR 6.0 revision.";
  }

  typedef Mpls-static-path {
    type enumeration {
      enum pop-and-lookup {
        value 1;
        description "Pop and Lookup";
      }
      enum cross-connect {
        value 2;
        description "Crossconnect";
      }
    }
    description "Mpls static path";
  }
  typedef Mpls-static-address-family {
    type enumeration {
      enum ipv4-unicast {
        value 1;
        description "IPv4 Unicast";
      }
    }
    description "Mpls static address family";
  }
  typedef Mpls-static-label-mode {
    type enumeration {
      enum per-vrf {
        value 1;
        description "Per VRF";
      }
      enum per-prefix {
        value 2;
        description "Per Prefix";
      }
      enum lsp {
        value 3;
        description "Cross connect";
      }
    }
    description "Mpls static label mode";
  }
  typedef Mpls-static-out-label-types {
    type enumeration {
      enum none {
        value 0;
        description "None";
      }
      enum out-label {
        value 1;
        description "OutLabel";
      }
      enum pop {
        value 2;
        description "Pop";
      }
      enum exp-null {
        value 3;
        description "Exp Null";
      }
    }
    description "Mpls static out label types";
  }

  grouping LOCAL-LABEL-TABLE {
    description "Common node of af, top-label-hash";

    container local-labels {
      xr:xr-xml-map "mpls_static_cfg:LocalLabelTable";
      description "Local Label";

      list local-label {
        xr:xr-xml-map "mpls_static_cfg:LocalLabel";
        key "local-label-id";
        description "Specify Local Label";

        container label-type {
          xr:xr-xml-map "mpls_static_cfg:LabelType";
          description "MPLS Static Local Label Value";
          leaf label-mode {
            xr:xr-xml-map "mpls_static_cfg:LabelMode";
            type Mpls-static-label-mode;
            description "Label Mode (PerVRF, PerPrefix or LSP)";
          }
          leaf prefix {
            xr:xr-xml-map "mpls_static_cfg:Prefix";
            type inet:ip-address-no-zone;
            description "Address (IPv4/6 depending on AFI)";
          }
          leaf prefix-length {
            xr:xr-xml-map "mpls_static_cfg:PrefixLength";
            type int32;
            description "Prefix length";
          }
        }
        leaf local-label-id {
          xr:xr-xml-map "mpls_static_cfg:LocalLabelID";
          type uint32 {
            range "16..1048575";
          }
          description "Local Label";
        }
        uses PATH-TABLE;
      }
    }
  }

  grouping LABEL-SWITCHED-PATH-TABLE {
    description "Common node of default-vrf, vrf";

    container label-switched-paths {
      xr:xr-xml-map "mpls_static_cfg:LabelSwitchedPathTable";
      description "Table of the Label Switched Paths";

      list label-switched-path {
        xr:xr-xml-map "mpls_static_cfg:LabelSwitchedPath";
        key "lsp-name";
        description "Label Switched Path";

        container in-label {
          xr:xr-xml-map "mpls_static_cfg:InLabel";
          description "MPLS Static Local Label Value";
          leaf in-label-value {
            xr:xr-xml-map "mpls_static_cfg:InLabelValue";
            type uint32 {
              range "16..1048575";
            }
            description "Local Label";
          }
          leaf label-mode {
            xr:xr-xml-map "mpls_static_cfg:LabelMode";
            type Mpls-static-label-mode;
            description "Label Mode (PerVRF, PerPrefix or LSP)";
          }
          leaf prefix {
            xr:xr-xml-map "mpls_static_cfg:Prefix";
            type inet:ip-address-no-zone;
            description "Address (IPv4/6 depending on AFI)";
          }
          leaf prefix-length {
            xr:xr-xml-map "mpls_static_cfg:PrefixLength";
            type int32;
            description "Prefix length";
          }
        }
        leaf lsp-name {
          xr:xr-xml-map "mpls_static_cfg:LSPName";
          type xr:Cisco-ios-xr-string;
          description "LSP Name";
        }
        uses ENABLE;
        uses PATH-TABLE;
      }
    }
  }

  grouping PATH-TABLE {
    description "Common node of local-label, label-switched-path";

    container paths {
      xr:xr-xml-map "mpls_static_cfg:PathTable";
      description "Forward Path Parameters";

      list path {
        xr:xr-xml-map "mpls_static_cfg:Path";
        key "path-id";
        description "Path Information";
        leaf path-id {
          xr:xr-xml-map "mpls_static_cfg:PathID";
          type uint32;
          description "Number of paths";
        }
        leaf path-type {
          xr:xr-xml-map "mpls_static_cfg:PathType";
          type Mpls-static-path;
          default "cross-connect";
          description "Type of Path (PopAndLookup, CrossConnect)";
        }
        leaf label-type {
          xr:xr-xml-map "mpls_static_cfg:LabelType";
          type Mpls-static-out-label-types;
          default "none";
          description "Type of label (Outlabel, ExpNull or Pop)";
        }
        leaf next-hop-label {
          xr:xr-xml-map "mpls_static_cfg:NextHopLabel";
          type uint32 {
            range "16..1048575";
          }
          default "16";
          description "NH Label";
        }
        leaf next-hop-address {
          xr:xr-xml-map "mpls_static_cfg:NextHopAddress";
          type inet:ip-address-no-zone;
          default "0.0.0.0";
          description "Next Hop IPv4 Address";
        }
        leaf interface-name {
          xr:xr-xml-map "mpls_static_cfg:InterfaceName";
          type xr:Interface-name;
          description
            "Next hop Interface with form
            <Interface>R/S/I/P";
        }
      }
    }
  }

  grouping ENABLE {
    description
      "Common node of mpls-static, af, default-vrf, vrf,
      label-switched-path";
    leaf enable {
      xr:xr-xml-map "mpls_static_cfg:Enable";
      type empty;
      description "MPLS Static Apply Enable";
    }
  }

  grouping AF-TABLE {
    description "Common node of default-vrf, vrf";

    container afs {
      xr:xr-xml-map "mpls_static_cfg:AFTable";
      description "Address Family Table";

      list af {
        xr:xr-xml-map "mpls_static_cfg:AF";
        key "afi";
        description "Address Family";

        container top-label-hash {
          xr:xr-xml-map "mpls_static_cfg:TopLabelHash";
          description "Top Label Hash";
          uses LOCAL-LABEL-TABLE;
        }
        leaf afi {
          xr:xr-xml-map "mpls_static_cfg:AFI";
          type Mpls-static-address-family;
          description "Address Family";
        }
        uses LOCAL-LABEL-TABLE;
        uses ENABLE;
      }
    }
  }

  container mpls-static {
    xr:xr-xml-map "mpls_static_cfg:MPLSStatic";
    description "MPLS Static Configuration Data";

    container vrfs {
      xr:xr-xml-map "mpls_static_cfg:VRFTable";
      description "VRF table";

      list vrf {
        xr:xr-xml-map "mpls_static_cfg:VRF";
        key "vrf-name";
        description "VRF Name";
        leaf vrf-name {
          xr:xr-xml-map "mpls_static_cfg:VRFName";
          type xr:Cisco-ios-xr-string;
          description "VRF Name";
        }
        uses LABEL-SWITCHED-PATH-TABLE;
        uses AF-TABLE;
        uses ENABLE;
      }
    }

    container interfaces {
      xr:xr-xml-map "mpls_static_cfg:InterfaceTable";
      description "MPLS Static Interface Table";

      list interface {
        xr:xr-xml-map "mpls_static_cfg:Interface";
        xr:xr-cli-map "static interface <interface> ";
        key "interface-name";
        description "MPLS Static Interface Enable";
        leaf interface-name {
          xr:xr-xml-map "mpls_static_cfg:InterfaceName";
          type xr:Interface-name;
          description "Name of Interface";
        }
      }
    }

    container default-vrf {
      xr:xr-xml-map "mpls_static_cfg:DefaultVRF";
      description "Default VRF";
      uses LABEL-SWITCHED-PATH-TABLE;
      uses AF-TABLE;
      uses ENABLE;
    }
    uses ENABLE;
  }
}
