module Cisco-IOS-XR-ncs5500-coherent-portmode-oper {

  /*** NAMESPACE / PREFIX DEFINITION ***/

  namespace "http://cisco.com/ns/yang"+
    "/Cisco-IOS-XR-ncs5500-coherent-portmode-oper";


  prefix "ncs5500-coherent-portmode-oper";

  /*** LINKAGE (IMPORTS / INCLUDES) ***/

  import Cisco-IOS-XR-types { prefix "xr"; }

  include Cisco-IOS-XR-ncs5500-coherent-portmode-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ncs5500-coherent-portmode package operational data.

     This module contains definitions
     for the following management objects:
       controller-port-mode: Coherent PortMode  operational data

     Copyright (c) 2013-2016 by Cisco Systems, Inc.
     All rights reserved.";

  revision "2015-11-09" {
    description
      "IOS XR 6.0 revision.";
  }


  container controller-port-mode {
    xr:xr-xml-map "coh_portmode_oper:ControllerPortMode";
    config false;
    description "Coherent PortMode  operational data";

    list optics-name {
      xr:xr-xml-map "coh_portmode_oper:OpticsName";
      key "interface-name";
      description "Name of optics controller";

      container port-mode-info {
        xr:xr-xml-map "coh_portmode_oper:PortModeInfo";
        description "PortMode  operational data";
        uses PORTMODE-INFO;
      }
      leaf interface-name {
        xr:xr-xml-map "coh_portmode_oper:InterfaceName";
        type xr:Interface-name;
        description "Interface Name";
      }
    }
  }
}
