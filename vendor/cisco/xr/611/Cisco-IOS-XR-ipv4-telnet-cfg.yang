module Cisco-IOS-XR-ipv4-telnet-cfg {

  /*** NAMESPACE / PREFIX DEFINITION ***/

  namespace "http://cisco.com/ns/yang/Cisco-IOS-XR-ipv4-telnet-cfg";


  prefix "ipv4-telnet-cfg";

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ipv4-telnet package configuration.

     This module contains definitions
     for the following management objects:
       ipv6-telnet: IPv6 telnet configuration
       ipv4-telnet: ipv4 telnet

     Copyright (c) 2013-2016 by Cisco Systems, Inc.
     All rights reserved.";

  revision "2015-11-09" {
    description
      "IOS XR 6.0 revision.";
  }


  grouping CLIENT {
    description "Common node of ipv4-telnet, ipv6-telnet";

    container client {
      xr:xr-xml-map "telnet_client_cfg:Client";
      description "Telnet client configuration";
      leaf source-interface {
        xr:xr-xml-map "telnet_client_cfg:SourceInterface";
        type xr:Interface-name;
        description "Source interface for telnet sessions";
      }
    }
  }

  container ipv6-telnet {
    xr:xr-xml-map "telnet_client_cfg:IPv6Telnet";
    description "IPv6 telnet configuration";
    uses CLIENT;
  }

  container ipv4-telnet {
    xr:xr-xml-map "telnet_client_cfg:IPv4Telnet";
    description "ipv4 telnet";
    uses CLIENT;
  }
}
