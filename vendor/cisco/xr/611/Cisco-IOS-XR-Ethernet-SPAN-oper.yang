module Cisco-IOS-XR-Ethernet-SPAN-oper {

  /*** NAMESPACE / PREFIX DEFINITION ***/

  namespace "http://cisco.com/ns"+
    "/yang/Cisco-IOS-XR-Ethernet-SPAN-oper";


  prefix "ethernet-span-oper";

  /*** LINKAGE (IMPORTS / INCLUDES) ***/

  import Cisco-IOS-XR-types { prefix "xr"; }

  import Cisco-IOS-XR-Ethernet-SPAN-datatypes { prefix "dt1"; }

  include Cisco-IOS-XR-Ethernet-SPAN-oper-sub3 {
    revision-date 2015-11-09;
  }

  include Cisco-IOS-XR-Ethernet-SPAN-oper-sub2 {
    revision-date 2015-11-09;
  }

  include Cisco-IOS-XR-Ethernet-SPAN-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR Ethernet-SPAN package operational data.

     This module contains definitions
     for the following management objects:
       span-monitor-session: Monitor Session operational data

     Copyright (c) 2013-2016 by Cisco Systems, Inc.
     All rights reserved.";

  revision "2015-11-09" {
    description
      "IOS XR 6.0 revision.";
  }


  container span-monitor-session {
    xr:xr-xml-map "ethernet-span_oper:SpanMonitorSession";
    config false;
    description "Monitor Session operational data";

    container global {
      xr:xr-xml-map "ethernet-span_oper:Global";
      description "Global operational data";

      container statistics {
        xr:xr-xml-map "ethernet-span_oper:StatisticsTable";
        description "Table of statistics for source interfaces";

        list statistic {
          xr:xr-xml-map "ethernet-span_oper:Statistics";
          key "session interface";
          description
            "Statistics for a particular source interface";
          leaf session {
            xr:xr-xml-map "ethernet-span_oper:Session";
            type dt1:Span-session-name;
            description "Session Name";
          }
          leaf interface {
            xr:xr-xml-map "ethernet-span_oper:Interface";
            type xr:Interface-name;
            description "Interface";
          }
          uses SPAN-MA-STATISTICS-BAG;
        }
      }

      container global-sessions {
        xr:xr-xml-map "ethernet-span_oper:GlobalSessionTable";
        description "Global Monitor Sessions table";

        list global-session {
          xr:xr-xml-map "ethernet-span_oper:GlobalSession";
          key "session";
          description
            "Information about a globally-configured
            monitor session";
          leaf session {
            xr:xr-xml-map "ethernet-span_oper:Session";
            type dt1:Span-session-name;
            description "Session Name";
          }
          uses SPAN-MGR-SESSION-BAG;
        }
      }
    }

    container nodes {
      xr:xr-xml-map "ethernet-span_oper:NodeTable";
      description "Node table for node-specific operational data";

      list node {
        xr:xr-xml-map "ethernet-span_oper:Node";
        key "node";
        description "Node-specific data for a particular node";

        container attachments {
          xr:xr-xml-map "ethernet-span_oper:AttachmentTable";
          description
            "Table of source interfaces configured as
            attached to a session";

          list attachment {
            xr:xr-xml-map "ethernet-span_oper:Attachment";
            key "session interface";
            description
              "Information about a particular source
              interface configured as attached to monitor
              session";
            leaf session {
              xr:xr-xml-map "ethernet-span_oper:Session";
              type dt1:Span-session-name;
              description "Session Name";
            }
            leaf interface {
              xr:xr-xml-map "ethernet-span_oper:Interface";
              type xr:Interface-name;
              description "Interface";
            }
            uses SPAN-MA-ATTACHMENT-BAG;
          }
        }

        container hardware-sessions {
          xr:xr-xml-map "ethernet-span_oper:HardwareSessionTable";
          description
            "Table of sessions set up in the hardware. 
            When all sessions are operating correctly the
            entries in this table should match those
            entries in GlobalSessionTable that have a
            destination configured";

          list hardware-session {
            xr:xr-xml-map "ethernet-span_oper:HardwareSession";
            description
              "Information about a particular session that
              is set up in the hardware";
            leaf session-class {
              xr:xr-xml-map "ethernet-span_oper:SessionClass";
              type dt1:Span-session-class;
              description "Sesssion class";
            }
            leaf session-id {
              xr:xr-xml-map "ethernet-span_oper:SessionID";
              type dt1:Span-session-id;
              description "Session ID";
            }
            uses SPAN-EA-SESS-BAG;
          }
        }

        container interfaces {
          xr:xr-xml-map "ethernet-span_oper:InterfaceTable";
          description
            "Table of source interfaces set up in the
            hardware.  The entries in this table should
            match the entries in AttachmentTable when all
            sessions are operating correctly";

          list interface {
            xr:xr-xml-map "ethernet-span_oper:Interface";
            key "interface";
            description
              "Information about a particular interface that
              is set up in the hardware";
            leaf interface {
              xr:xr-xml-map "ethernet-span_oper:Interface";
              type xr:Interface-name;
              description "Interface";
            }
            uses SPAN-EA-INTF-BAG;
          }
        }
        leaf node {
          xr:xr-xml-map "ethernet-span_oper:Node";
          type xr:Node-id;
          description "Node";
        }
      }
    }
  }
}
