module Cisco-IOS-XR-parser-cfg {

  /*** NAMESPACE / PREFIX DEFINITION ***/

  namespace "http://cisco.com/ns/yang/Cisco-IOS-XR-parser-cfg";


  prefix "parser-cfg";

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR parser package configuration.

     This module contains definitions
     for the following management objects:
       parser: Parser configuration

     Copyright (c) 2013-2016 by Cisco Systems, Inc.
     All rights reserved.";

  revision "2015-06-02" {
    description
      "IOS XR 5.3.2 revision.";
  }

  revision "2015-01-07" {
    description
      "IOS XR 5.3.1 revision.";
  }


  container parser {
    xr:xr-xml-map "parser_cfg:Parser";
    description "Parser configuration";

    container indentation {
      xr:xr-xml-map "parser_common:Indentation";
      description "indentation tracking";
      leaf indentation-disable {
        xr:xr-xml-map "parser_common:Indentation_Disable";
        type boolean;
        description "disable the indentation";
      }
    }

    container alias {
      xr:xr-xml-map "parser_common:Alias";
      description "Alias for command mapping";

      container execs {
        xr:xr-xml-map "parser_common:ExecTable";
        description "Exec command alias";

        list exec {
          xr:xr-xml-map "parser_common:Exec";
          key "identifier";
          description "Exec alias name";
          leaf identifier {
            xr:xr-xml-map "parser_common:Identifier";
            type string {
              length "0..30";
            }
            description "Exec Alias name";
          }
          leaf identifier-xr {
            xr:xr-xml-map "parser_common:Identifier";
            type string;
            mandatory true;
            description "Aliased exec command";
          }
        }
      }

      container configurations {
        xr:xr-xml-map "parser_common:ConfigurationTable";
        description "Configuration command alias";

        list configuration {
          xr:xr-xml-map "parser_common:Configuration";
          key "identifier";
          description "Configuration Alias name";
          leaf identifier {
            xr:xr-xml-map "parser_common:Identifier";
            type string {
              length "0..30";
            }
            description "Configuration alias name";
          }
          leaf identifier-xr {
            xr:xr-xml-map "parser_common:Identifier";
            type string;
            mandatory true;
            description "Aliased config command";
          }
        }
      }

      container alls {
        xr:xr-xml-map "parser_common:AliasTable";
        description "Table of all aliases configured";

        list all {
          xr:xr-xml-map "parser_common:All";
          key "identifier";
          description "Alias name to command mapping";
          leaf identifier {
            xr:xr-xml-map "parser_common:Identifier";
            type string {
              length "0..30";
            }
            description "Alias name";
          }
          leaf identifier-xr {
            xr:xr-xml-map "parser_common:Identifier";
            type string;
            mandatory true;
            description "The actual command";
          }
        }
      }
    }

    container history {
      xr:xr-xml-map "parser_common:History";
      description "cli commands history";
      leaf size {
        xr:xr-xml-map "parser_common:size";
        type uint32 {
          range "1000..5000";
        }
        description "maximum number of commands in history";
      }
    }

    container interface-display {
      xr:xr-xml-map "parser_common:InterfaceDisplay";
      description "Configure the Interface display order";
      leaf slot-order {
        xr:xr-xml-map "parser_common:SlotOrder";
        xr:xr-cli-map "display interface slot-order ";
        type boolean;
        description
          "Configure Interface display order as slot order";
      }
    }

    container netmask-format {
      xr:xr-xml-map "parser_common:NetmaskFormat";
      description "Ipv4 netmask-format to be configured";
      leaf bit-count {
        xr:xr-xml-map "parser_common:BitCount";
        xr:xr-cli-map "netmask-format bit-count ";
        type boolean;
        description "Enable ipv4 netmask-format as bit-count";
      }
    }

    container configuration {
      xr:xr-xml-map "parser_common:Configuration";
      description "cli configuration services";

      container disable {
        xr:xr-xml-map "parser_common:Disable";
        description "disable for read-only access users";
        leaf usergroup {
          xr:xr-xml-map "parser_common:Usergroup";
          type string;
          description "Disable config mode for usergroup";
        }
      }
    }

    container submode-exit {
      xr:xr-xml-map "parser_common:SubmodeExit";
      description
        "Exit submode when only '!' seen in interactive
        mode";
      leaf enable {
        xr:xr-xml-map "parser_common:Enable";
        type boolean;
        description "Enable the feature";
      }
    }
  }
}
