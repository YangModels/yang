module Cisco-IOS-XR-lib-mpp-cfg {

  /*** NAMESPACE / PREFIX DEFINITION ***/

  namespace "http://cisco.com/ns/yang/Cisco-IOS-XR-lib-mpp-cfg";


  prefix "lib-mpp-cfg";

  /*** LINKAGE (IMPORTS / INCLUDES) ***/

  import ietf-inet-types { prefix "inet"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR lib-mpp package configuration.

     This module contains definitions
     for the following management objects:
       control-plane: Configure control Plane

     Copyright (c) 2013-2016 by Cisco Systems, Inc.
     All rights reserved.";

  revision "2015-07-30" {
    description
      "Descriptions updated.";
  }

  revision "2015-01-07" {
    description
      "IOS XR 5.3.1 revision.";
  }


  grouping HTTP-PROTOCOL {
    description "Common node of interface, all-interfaces";

    container http-protocol {
      xr:xr-xml-map "lib_mpp_cfg:HTTPProtocol";
      description "Configure HTTP on this interface";
      uses PEER-CLASS;
    }
  }

  grouping SNMP-PROTOCOL {
    description "Common node of interface, all-interfaces";

    container snmp-protocol {
      xr:xr-xml-map "lib_mpp_cfg:SNMPProtocol";
      description "Configure SNMP for this interface";
      uses PEER-CLASS;
    }
  }

  grouping TFTP-PROTOCOL {
    description "Common node of interface, all-interfaces";

    container tftp-protocol {
      xr:xr-xml-map "lib_mpp_cfg:TFTPProtocol";
      description "Configure TFTP on this interface";
      uses PEER-CLASS;
    }
  }

  grouping INTERFACE-SELECTION {
    description "Common node of inband, outband";

    container interface-selection {
      xr:xr-xml-map "lib_mpp_cfg:InterfaceSelection";
      description "Configure interfaces";

      container interfaces {
        xr:xr-xml-map "lib_mpp_cfg:InterfaceTable";
        description "Configure a specific interface";

        list interface {
          xr:xr-xml-map "lib_mpp_cfg:Interface";
          key "interface-name";
          description "Specific interface";
          leaf interface-name {
            xr:xr-xml-map "lib_mpp_cfg:InterfaceName";
            type xr:Interface-name;
            description "Name of the Interface";
          }
          uses HTTP-PROTOCOL;
          uses TFTP-PROTOCOL;
          uses NETCONF-PROTOCOL;
          uses XR-XML;
          uses SSH-PROTOCOL;
          uses SNMP-PROTOCOL;
          uses TELNET-PROTOCOL;
          uses ALL-PROTOCOLS;
        }
      }

      container all-interfaces {
        xr:xr-xml-map "lib_mpp_cfg:AllInterfaces";
        description "Configure all Inband interfaces";
        uses HTTP-PROTOCOL;
        uses TFTP-PROTOCOL;
        uses NETCONF-PROTOCOL;
        uses XR-XML;
        uses SSH-PROTOCOL;
        uses SNMP-PROTOCOL;
        uses TELNET-PROTOCOL;
        uses ALL-PROTOCOLS;
      }
    }
  }

  grouping NETCONF-PROTOCOL {
    description "Common node of interface, all-interfaces";

    container netconf-protocol {
      xr:xr-xml-map "lib_mpp_cfg:NETCONFProtocol";
      description "Configure NETCONF protocol and peer addresses";
      uses PEER-CLASS;
    }
  }

  grouping PEER-PREFIX-CLASS {
    description "Common node of peer-v4, peer-v6";

    container peer-prefixes {
      xr:xr-xml-map "lib_mpp_cfg:PeerPrefixClass";
      description "Configure peer addresses with prefix";

      list peer-prefix {
        xr:xr-xml-map "lib_mpp_cfg:PeerPrefix";
        xr:xr-cli-map "address ipv4 <IPv4 address> ";
        xr:xr-cli-map "address ipv6 <IPv6 address> ";
        key "address-prefix";
        description "Peer address (with prefix)";
        leaf address-prefix {
          xr:xr-xml-map "lib_mpp_cfg:AddressPrefix";
          type inet:ip-prefix;
          description "prefix/length";
        }
      }
    }
  }

  grouping PEER-NO-PREFIX-CLASS {
    description "Common node of peer-v4, peer-v6";

    container peers {
      xr:xr-xml-map "lib_mpp_cfg:PeerNoPrefixClass";
      description "Configure peer addresses";

      list peer {
        xr:xr-xml-map "lib_mpp_cfg:Peer";
        xr:xr-cli-map "address ipv4 <IPv4 address> ";
        xr:xr-cli-map "address ipv6 <IPv6 address> ";
        key "address";
        description "Configure peer on the interface";
        leaf address {
          xr:xr-xml-map "lib_mpp_cfg:Address";
          type inet:ip-address-no-zone;
          description "prefix";
        }
      }
    }
  }

  grouping XR-XML {
    description "Common node of interface, all-interfaces";

    container xr-xml {
      xr:xr-xml-map "lib_mpp_cfg:XML";
      description "Configure XML and peer addresses";
      uses PEER-CLASS;
    }
  }

  grouping PEER-CLASS {
    description
      "Common node of snmp-protocol, http-protocol,
      ssh-protocol, telnet-protocol, tftp-protocol, xml
      , netconf-protocol, all-protocols";

    container peer-class {
      xr:xr-xml-map "lib_mpp_cfg:PeerClass";
      description "Configure peer addresses";

      container peer-v4 {
        xr:xr-xml-map "lib_mpp_cfg:PeerV4";
        description "Configure v4 peer addresses";
        uses PEER-NO-PREFIX-CLASS;
        uses PEER-PREFIX-CLASS;
      }

      container peer-v6 {
        xr:xr-xml-map "lib_mpp_cfg:PeerV6";
        description "Configure v6 peer addresses";
        uses PEER-NO-PREFIX-CLASS;
        uses PEER-PREFIX-CLASS;
      }
      leaf peer-all {
        xr:xr-xml-map "lib_mpp_cfg:PeerAll";
        xr:xr-cli-map "interface <interface> allow HTTP ";
        xr:xr-cli-map "interface <interface> allow TFTP ";
        xr:xr-cli-map "interface <interface> allow NETCONF ";
        xr:xr-cli-map "interface <interface> allow XML ";
        xr:xr-cli-map "interface <interface> allow SSH ";
        xr:xr-cli-map "interface <interface> allow SNMP ";
        xr:xr-cli-map "interface <interface> allow Telnet ";
        xr:xr-cli-map "interface <interface> allow all ";
        xr:xr-cli-map "allow HTTP ";
        xr:xr-cli-map "allow TFTP ";
        xr:xr-cli-map "allow NETCONF ";
        xr:xr-cli-map "allow XML ";
        xr:xr-cli-map "allow SSH ";
        xr:xr-cli-map "allow SNMP ";
        xr:xr-cli-map "allow Telnet ";
        xr:xr-cli-map "allow all ";
        xr:xr-cli-map "control-plane management-plane inband interf"+
          "ace <interface> allow HTTP ";
        xr:xr-cli-map "control-plane management-plane inband interf"+
          "ace <interface> allow TFTP ";
        xr:xr-cli-map "control-plane management-plane inband interf"+
          "ace <interface> allow NETCONF ";
        xr:xr-cli-map "control-plane management-plane inband interf"+
          "ace <interface> allow XML ";
        xr:xr-cli-map "control-plane management-plane inband interf"+
          "ace <interface> allow SSH ";
        xr:xr-cli-map "control-plane management-plane inband interf"+
          "ace <interface> allow SNMP ";
        xr:xr-cli-map "control-plane management-plane inband interf"+
          "ace <interface> allow Telnet ";
        xr:xr-cli-map "control-plane management-plane inband interf"+
          "ace <interface> allow all ";
        type empty;
        description "Only takes 'True'";
      }
    }
  }

  grouping TELNET-PROTOCOL {
    description "Common node of interface, all-interfaces";

    container telnet-protocol {
      xr:xr-xml-map "lib_mpp_cfg:TelnetProtocol";
      description "Configure Telnet for this interface";
      uses PEER-CLASS;
    }
  }

  grouping ALL-PROTOCOLS {
    description "Common node of interface, all-interfaces";

    container all-protocols {
      xr:xr-xml-map "lib_mpp_cfg:AllProtocols";
      description "Configure all protocols on this interface";
      uses PEER-CLASS;
    }
  }

  grouping SSH-PROTOCOL {
    description "Common node of interface, all-interfaces";

    container ssh-protocol {
      xr:xr-xml-map "lib_mpp_cfg:SSHProtocol";
      description "Configure SSH protocol and peer addresses";
      uses PEER-CLASS;
    }
  }

  container control-plane {
    xr:xr-xml-map "lib_mpp_cfg:ControlPlane";
    description "Configure control Plane";

    container management-plane-protection {
      xr:xr-xml-map "lib_mpp_cfg:ManagementPlaneProtection";
      description "Configure management plane protection";

      container outband {
        xr:xr-xml-map "lib_mpp_cfg:Outband";
        description "Outband Configuration";
        leaf outband-vrf {
          xr:xr-xml-map "lib_mpp_cfg:OutbandVRF";
          xr:xr-cli-map "vrf <string> ";
          type string;
          description "Configure outband VRF";
        }
        uses INTERFACE-SELECTION;
      }

      container inband {
        xr:xr-xml-map "lib_mpp_cfg:Inband";
        description "Inband Configuration";
        uses INTERFACE-SELECTION;
      }
    }
  }
}
