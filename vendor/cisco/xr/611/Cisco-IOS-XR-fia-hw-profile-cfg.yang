module Cisco-IOS-XR-fia-hw-profile-cfg {

  /*** NAMESPACE / PREFIX DEFINITION ***/

  namespace "http://cisco.com/ns"+
    "/yang/Cisco-IOS-XR-fia-hw-profile-cfg";


  prefix "fia-hw-profile-cfg";

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR fia-hw-profile package configuration.

     This module contains definitions
     for the following management objects:
       hw-module-profile-config: none

     Copyright (c) 2013-2016 by Cisco Systems, Inc.
     All rights reserved.";

  revision "2016-06-22" {
    description
      "Schema added.";
  }

  revision "2015-11-09" {
    description
      "IOS XR 6.0 revision.";
  }


  container hw-module-profile-config {
    xr:xr-xml-map "fia_cfg_hw_profile:HwModuleProfileConfig";
    description "none";

    container profile {
      xr:xr-xml-map "fia_cfg_hw_profile:Profile";
      description "Configure profile.";

      container tcams {
        xr:xr-xml-map "fia_cfg_hw_profile:TcamTable";
        description "Configure profile for TCAM LC cards";

        list tcam {
          xr:xr-xml-map "fia_cfg_hw_profile:Tcam";
          key "table-type address-type communication-type";
          description
            "In the tcam fib table, denotes the address
            type ipv4 or ipv6 and whether unicast or
            multicast";
          leaf percent {
            xr:xr-xml-map "fia_cfg_hw_profile:Percent";
            type uint32 {
              range "0..100";
            }
            units "percentage";
            description
              "curve out percentage of TCAM table entries";
          }
          leaf table-type {
            xr:xr-xml-map "fia_cfg_hw_profile:TableType";
            type xr:Cisco-ios-xr-string;
            description "none";
          }
          leaf address-type {
            xr:xr-xml-map "fia_cfg_hw_profile:AddressType";
            type xr:Cisco-ios-xr-string;
            description "none";
          }
          leaf communication-type {
            xr:xr-xml-map "fia_cfg_hw_profile:CommunicationType";
            type xr:Cisco-ios-xr-string;
            description "none";
          }
        }
      }
    }
  }
}
