module Cisco-IOS-XR-infra-statsd-cfg {

  /*** NAMESPACE / PREFIX DEFINITION ***/

  namespace "http://cisco.com/ns/yang/Cisco-IOS-XR-infra-statsd-cfg";


  prefix "infra-statsd-cfg";

  /*** LINKAGE (IMPORTS / INCLUDES) ***/

  import Cisco-IOS-XR-types { prefix "xr"; }

  import Cisco-IOS-XR-ifmgr-cfg { prefix "a1"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR infra-statsd package configuration.

     This module contains definitions
     for the following management objects:
       statistics: Global statistics configuration

     This YANG module augments the
       Cisco-IOS-XR-ifmgr-cfg
     module with configuration data.

     Copyright (c) 2013-2016 by Cisco Systems, Inc.
     All rights reserved.";

  revision "2015-11-09" {
    description
      "IOS XR 6.0 revision.";
  }


  container statistics {
    xr:xr-xml-map "infra_statsd_gl_cfg:Statistics";
    description "Global statistics configuration";

    container period {
      xr:xr-xml-map "infra_statsd_gl_cfg:Period";
      description "Collection period for statistics polling";

      container service-accounting {
        xr:xr-xml-map "infra_statsd_gl_cfg:ServiceAccounting";
        must "(polling-period and not(polling-disable)) or"+
          " (not(polling-period) and polling-disable)" {
          description "Describes valid combinations of leafs";
        }
        description
          "Collection polling period for service
          accounting collectors";
        leaf polling-period {
          xr:xr-xml-map "infra_statsd_gl_cfg:PollingPeriod";
          type uint32 {
            range "30..3600";
          }
          default "900";
          description
            "Collection polling period for service
            accounting collectors";
        }
        leaf polling-disable {
          xr:xr-xml-map "infra_statsd_gl_cfg:PollingDisable";
          type empty;
          description
            "Disable periodic statistics polling for
            service accounting collectors";
        }
      }
    }
  }

  augment "/a1:interface-configurations/a1:interface-configuration" {

    container statistics {
      xr:xr-xml-map "infra_statsd_cfg:Statistics";
      description "Per-interface statistics configuration";
      leaf load-interval {
        xr:xr-xml-map "infra_statsd_cfg:LoadInterval";
        type uint32 {
          range "0..600";
        }
        default "300";
        description
          "Specify interval for load calculation for an
          interface";
      }
    }
    description
      "This augment extends the configuration data of
      'Cisco-IOS-XR-ifmgr-cfg'";
  }
}
