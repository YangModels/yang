module Cisco-IOS-XR-ipv4-igmp-dyn-tmpl-cfg {

  /*** NAMESPACE / PREFIX DEFINITION ***/

  namespace "http://cisco.com/ns/yang"+
    "/Cisco-IOS-XR-ipv4-igmp-dyn-tmpl-cfg";


  prefix "ipv4-igmp-dyn-tmpl-cfg";

  /*** LINKAGE (IMPORTS / INCLUDES) ***/

  import Cisco-IOS-XR-types { prefix "xr"; }

  import Cisco-IOS-XR-subscriber-infra-tmplmgr-cfg { prefix "a1"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ipv4-igmp-dyn-tmpl package configuration.

     This YANG module augments the
       Cisco-IOS-XR-subscriber-infra-tmplmgr-cfg
     module with configuration data.

     Copyright (c) 2013-2016 by Cisco Systems, Inc.
     All rights reserved.";

  revision "2015-11-09" {
    description
      "IOS XR 6.0 revision.";
  }


  augment "/a1:dynamic-template/a1:ppps/a1:ppp" {

    container igmp {
      xr:xr-xml-map "ipv4_igmp_dyn_tmpl:IGMP";
      description "IGMPconfiguration";

      container default-vrf {
        xr:xr-xml-map "ipv4_igmp_dyn_tmpl:DefaultVRF";
        description "Default VRF";

        container explicit-tracking {
          xr:xr-xml-map "ipv4_igmp_dyn_tmpl:ExplicitTracking";
          presence "Indicates a explicit-tracking node is"+
            " configured.";
          description "IGMPv3 explicit host tracking";
          leaf enable {
            xr:xr-xml-map "ipv4_igmp_dyn_tmpl:Enable";
            type boolean;
            mandatory true;
            description
              "Enable or disable, when value is TRUE or
              FALSE respectively";
          }
          leaf access-list-name {
            xr:xr-xml-map "ipv4_igmp_dyn_tmpl:AccessListName";
            type string;
            description
              "Access list specifying tracking group range";
          }
        }
        leaf max-groups {
          xr:xr-xml-map "ipv4_igmp_dyn_tmpl:MaxGroups";
          type uint32 {
            range "1..40000";
          }
          default "25000";
          description "IGMP Max Groups";
        }
        leaf access-group {
          xr:xr-xml-map "ipv4_igmp_dyn_tmpl:AccessGroup";
          type string;
          description
            "Access list specifying access-list group range";
        }
        leaf multicast {
          xr:xr-xml-map "ipv4_igmp_dyn_tmpl:Multicast";
          type int32;
          description "Configure Multicast mode variable";
        }
        leaf version {
          xr:xr-xml-map "ipv4_igmp_dyn_tmpl:Version";
          type uint32 {
            range "1..3";
          }
          default "3";
          description "IGMP Version";
        }
        leaf query-interval {
          xr:xr-xml-map "ipv4_igmp_dyn_tmpl:QueryInterval";
          type uint32 {
            range "1..3600";
          }
          default "60";
          description "Query interval in seconds";
        }
        leaf query-max-response-time {
          xr:xr-xml-map "ipv4_igmp_dyn_tmpl:QueryMaxResponseTime";
          type uint32 {
            range "1..12";
          }
          default "10";
          description "Query response value in seconds";
        }
        leaf robustness {
          xr:xr-xml-map "ipv4_igmp_dyn_tmpl:Robustness";
          type uint32 {
            range "2..10";
          }
          default "2";
          description "Configure IGMP Robustness variable";
        }
      }
    }
    description
      "This augment extends the configuration data of
      'Cisco-IOS-XR-subscriber-infra-tmplmgr-cfg'";
  }
}
