submodule Cisco-IOS-XR-mpls-te-oper-sub9 {

  belongs-to Cisco-IOS-XR-mpls-te-oper {
    prefix Cisco-IOS-XR-mpls-te-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR mpls-te package operational data.

     Copyright (c) 2013-2016 by Cisco Systems, Inc.
     All rights reserved.";

  revision "2015-11-09" {
    description
      "IOS XR 6.0 revision.";
  }


  grouping MPLS-TE-MIB-SCALAR-INFO {
    description "MPLS TE MIB Scalar Information";
    leaf mpls-tunnel-configured {
      xr:xr-xml-map "mpls_te_mib:mpls_tunnel_configured";
      type uint32;
      description "mpls tunnel configured";
    }
    leaf mpls-tunnel-active {
      xr:xr-xml-map "mpls_te_mib:mpls_tunnel_active";
      type uint32;
      description "mpls tunnel active";
    }
    leaf mpls-tunnel-te-dist-proto {
      xr:xr-xml-map "mpls_te_mib:mpls_tunnel_te_dist_proto";
      type uint8;
      description "mpls tunnel te dist proto";
    }
    leaf mpls-tunnel-max-hops {
      xr:xr-xml-map "mpls_te_mib:mpls_tunnel_max_hops";
      type uint32;
      description "mpls tunnel max hops";
    }
    leaf mpls-tunnel-notification-max-rate {
      xr:xr-xml-map "mpls_te_mib:mpls_tunnel_notification_max_rate";
      type uint32;
      description "mpls tunnel notification max rate";
    }
  }
}
