submodule Cisco-IOS-XR-ip-bfd-oper-sub1 {

  belongs-to Cisco-IOS-XR-ip-bfd-oper {
    prefix Cisco-IOS-XR-ip-bfd-oper;
  }

  /*** LINKAGE (IMPORTS / INCLUDES) ***/

  import ietf-inet-types { prefix "inet"; }

  import ietf-yang-types { prefix "yang"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR ip-bfd package operational data.

     Copyright (c) 2013-2016 by Cisco Systems, Inc.
     All rights reserved.";

  revision "2015-11-09" {
    description
      "IOS XR 6.0 revision.";
  }

  typedef Bfd-mp-download-state {
    type enumeration {
      enum bfd-mp-download-none {
        value 0;
        description "bfd mp download none";
      }
      enum bfd-mp-download-no-lc {
        value 1;
        description "bfd mp download no lc";
      }
      enum bfd-mp-download-downloaded {
        value 2;
        description "bfd mp download downloaded";
      }
      enum bfd-mp-download-ack {
        value 3;
        description "bfd mp download ack";
      }
      enum bfd-mp-download-nack {
        value 4;
        description "bfd mp download nack";
      }
      enum bfd-mp-download-delete {
        value 5;
        description "bfd mp download delete";
      }
    }
    description "Bfd mp download state";
  }
  typedef Mpls-lib-c {
    type enumeration {
      enum mpls-lib-c-type-null {
        value 0;
        description "NULL Ctype";
      }
      enum mpls-lib-c-type-ipv4 {
        value 1;
        description "IPv4 UDP";
      }
      enum mpls-lib-c-type-ipv4-p2p-tunnel {
        value 7;
        description "IPv4 point-to-point TE tunnel";
      }
      enum mpls-lib-c-type-ipv6-p2p-tunnel {
        value 8;
        description "IPv6 point-to-point TE tunnel";
      }
      enum mpls-lib-c-type-ipv4-uni {
        value 9;
        description "IPv4 unicast";
      }
      enum mpls-lib-c-type-ipv4-p2mp-tunnel {
        value 13;
        description "IPv4 point-to-point TE tunnel";
      }
      enum mpls-lib-c-type-ipv6-p2mp-tunnel {
        value 14;
        description "IPv6 point-to-point TE tunnel";
      }
      enum mpls-lib-c-type-ipv4-tp-tunnel {
        value 15;
        description "IPv4 transport protocol tunnel";
      }
      enum mpls-lib-c-type-ipv6-tp-tunnel {
        value 16;
        description "IPv6 transport protocol tunnel";
      }
      enum mpls-lib-c-type-p2p-binding-label {
        value 17;
        description "P2P transport tunnel binding label";
      }
    }
    description "Mpls lib c";
  }
  typedef Bfd-api-fec {
    type enumeration {
      enum bfd-api-fec-type-none {
        value 0;
        description "bfd api fec type none";
      }
      enum bfd-api-fec-type-p2p-te {
        value 1;
        description "bfd api fec type p2p te";
      }
    }
    description "Bfd api fec";
  }
  typedef Bfd-mgmt-session-diag {
    type enumeration {
      enum bfd-mgmt-session-diag-none {
        value 0;
        description "No diagnostic";
      }
      enum bfd-mgmt-session-diag-control-detect-expired {
        value 1;
        description "Control Detection Time Expired";
      }
      enum bfd-mgmt-session-diag-echo-function-failed {
        value 2;
        description "Echo Function Failed";
      }
      enum bfd-mgmt-session-diag-nb-or-signaled-down {
        value 3;
        description "Neighbor Signaled Session Down";
      }
      enum bfd-mgmt-session-diag-fwding-plane-reset {
        value 4;
        description "Forwarding Plane Reset";
      }
      enum bfd-mgmt-session-diag-path-down {
        value 5;
        description "Path Down";
      }
      enum bfd-mgmt-session-diag-conc-path-down {
        value 6;
        description "Concatenated Path Down";
      }
      enum bfd-mgmt-session-diag-admin-down {
        value 7;
        description "Administratively Down";
      }
      enum bfd-mgmt-session-diag-rev-conc-path-down {
        value 8;
        description "Reverse Concatenated Path Down";
      }
      enum bfd-mgmt-session-diag-num {
        value 10;
        description "Unknown diagnostic state";
      }
    }
    description "BFD session diagnostic";
  }
  typedef Bfd-in6-addr {
    type inet:ipv6-address;
    description "Bfd in6 addr";
  }
  typedef Bfd-in-addr {
    type inet:ipv4-address;
    description "Bfd in addr";
  }
  typedef Bfd-af-id {
    type enumeration {
      enum bfd-af-id-none {
        value 0;
        description "No Address";
      }
      enum bfd-af-id-ipv4 {
        value 2;
        description "IPv4 AFI";
      }
      enum bfd-af-id-ipv6 {
        value 26;
        description "IPv6 AFI";
      }
    }
    description "Bfd af id";
  }
  typedef Bfd-discr {
    type uint32;
    description "Bfd discr";
  }
  typedef Bfd-mgmt-pkt-display {
    type enumeration {
      enum bfd-mgmt-pkt-display-type-none {
        value 0;
        description "None";
      }
      enum bfd-mgmt-pkt-display-type-bob-mbr {
        value 1;
        description "Display Type Bundle RTR Member";
      }
      enum bfd-mgmt-pkt-display-type-max {
        value 2;
        description "Display Type Enum Max Value";
      }
    }
    description "BFD session type";
  }
  typedef Bfd-session {
    type enumeration {
      enum undefined {
        description "Session type is undefined";
      }
      enum bundle-member {
        description "Session type is bundle member";
      }
      enum bundle-interface {
        description "Session type is bundle interface";
      }
      enum state-inheriting {
        description "Session type is state inheriting";
      }
      enum bundle-vlan {
        description "Session type is bundle vlan";
      }
      enum mpls-tp {
        description "Session type is MPLS-TP";
      }
      enum gre {
        description "Session type is GRE tunnel";
      }
      enum pseudowire-headend {
        description "Session type is PW-HE";
      }
      enum ip-single-hop {
        description "Session type is IP single hop";
      }
    }
    description "BFD session type";
  }
  typedef Bfd-mgmt-session-state {
    type enumeration {
      enum bfd-mgmt-session-state-admin-down {
        value 0;
        description "Session in Administratively Shutdown State";
      }
      enum bfd-mgmt-session-state-down {
        value 1;
        description "Session in Down State";
      }
      enum bfd-mgmt-session-state-init {
        value 2;
        description "Session in Initializing State";
      }
      enum bfd-mgmt-session-state-up {
        value 3;
        description "Session in Up State";
      }
      enum bfd-mgmt-session-state-failing {
        value 4;
        description "Session in Failing State";
      }
      enum bfd-mgmt-session-state-unknown {
        value 6;
        description "Session in Unknown State";
      }
    }
    description "BFD session states";
  }

  grouping BFD-MGMT-RELATION-LINK-DETAIL {
    description "Detail Member Link Information";
    leaf state {
      xr:xr-xml-map "ip_bfd_gl_mgmt:State";
      type Bfd-mgmt-session-state;
      description "State";
    }
    leaf interface-name {
      xr:xr-xml-map "ip_bfd_gl_mgmt:InterfaceName";
      type string {
        length "0..64";
      }
      description "Session Interface Name";
    }
    leaf local-discriminator {
      xr:xr-xml-map "ip_bfd_gl_mgmt:LocalDiscriminator";
      type Bfd-discr;
      description "Session's Local discriminator";
    }
  }

  grouping BFD-MGMT-RELATION {
    description "BFD Relation Detail Information";
    leaf state {
      xr:xr-xml-map "ip_bfd_gl_mgmt:State";
      type Bfd-mgmt-session-state;
      description "State";
    }
    leaf local-discriminator {
      xr:xr-xml-map "ip_bfd_gl_mgmt:LocalDiscriminator";
      type Bfd-discr;
      description "Session's Local discriminator";
    }

    list link-information {
      description "Detail Member Link Information";
      uses BFD-MGMT-RELATION-LINK-DETAIL;
    }

    list association-information {
      description "Association session information";
      uses BFD-MGMT-SESSION-ASSOCIATION-INFORMATION;
    }
  }

  grouping BFD-MGMT-RELATION-LINK-BRIEF {
    description "Brief Member Link Information";
    leaf state {
      xr:xr-xml-map "ip_bfd_gl_mgmt:State";
      type Bfd-mgmt-session-state;
      description "State";
    }
    leaf interface-name {
      xr:xr-xml-map "ip_bfd_gl_mgmt:InterfaceName";
      type string {
        length "0..64";
      }
      description "Session Interface Name";
    }
  }

  grouping BFD-MGMT-RELATION-BRIEF {
    description "BFD Relation Brief Information";
    leaf state {
      xr:xr-xml-map "ip_bfd_gl_mgmt:State";
      type Bfd-mgmt-session-state;
      description "State";
    }

    list link-information {
      description "Brief Member Link Information";
      uses BFD-MGMT-RELATION-LINK-BRIEF;
    }
  }

  grouping BFD-MGMT-MIB-DATABASE {
    description "BFD MIB Mapping Database Entry Information";

    container dest-address {
      description "Session Destination address";
      uses IP-ADDR-T-UNION;
    }
    leaf local-discriminator {
      xr:xr-xml-map "ip_bfd_gl_mgmt:LocalDiscriminator";
      type Bfd-discr;
      description "Sessions' Local Discriminator";
    }
    leaf remote-discriminator {
      xr:xr-xml-map "ip_bfd_gl_mgmt:RemoteDiscriminator";
      type Bfd-discr;
      description "Sessions' Remote Discriminator";
    }
    leaf sessionversion {
      xr:xr-xml-map "ip_bfd_gl_mgmt:SessionVersion";
      type uint32;
      description "Session BFD Version";
    }
    leaf session-state {
      xr:xr-xml-map "ip_bfd_gl_mgmt:SessionState";
      type uint32;
      description "Session State";
    }
    leaf trap-bitmap {
      xr:xr-xml-map "ip_bfd_gl_mgmt:TrapBitmap";
      type uint32;
      description "Trap Generator Bitmap";
    }
    leaf pkt-in {
      xr:xr-xml-map "ip_bfd_gl_mgmt:PktIn";
      type uint64;
      description "Packet In Counter";
    }
    leaf pkt-out {
      xr:xr-xml-map "ip_bfd_gl_mgmt:PktOut";
      type uint64;
      description "Packet Out Counter";
    }
    leaf last-up-time-sec {
      xr:xr-xml-map "ip_bfd_gl_mgmt:LastUpTimeSec";
      type uint64;
      units "second";
      description "Last Session Up Time (seconds)";
    }
    leaf last-up-time-nsec {
      xr:xr-xml-map "ip_bfd_gl_mgmt:LastUpTimeNsec";
      type uint32;
      units "nanosecond";
      description "Last Session Up Time (nanoseconds)";
    }
    leaf last-down-time-sec {
      xr:xr-xml-map "ip_bfd_gl_mgmt:LastDownTimeSec";
      type uint64;
      units "second";
      description "Last Session Down Time (seconds)";
    }
    leaf last-down-time-nsec {
      xr:xr-xml-map "ip_bfd_gl_mgmt:LastDownTimeNsec";
      type uint32;
      units "nanosecond";
      description "Last Session Down Time (nanoseconds)";
    }
    leaf last-down-diag {
      xr:xr-xml-map "ip_bfd_gl_mgmt:LastDownDiag";
      type Bfd-mgmt-session-diag;
      description "Last Session Down Diag";
    }
    leaf up-counter {
      xr:xr-xml-map "ip_bfd_gl_mgmt:UpCounter";
      type uint32;
      description "Up Count";
    }
    leaf last-time-cached {
      xr:xr-xml-map "ip_bfd_gl_mgmt:LastTimeCached";
      type uint64;
      description "Last Time Session Info Queried";
    }
    leaf interface-name {
      xr:xr-xml-map "ip_bfd_gl_mgmt:InterfaceName";
      type string {
        length "0..64";
      }
      description "Session Interface Name";
    }
    leaf int-handle {
      xr:xr-xml-map "ip_bfd_gl_mgmt:IntHandle";
      type uint32;
      description "Session Interface Handle";
    }
    leaf detection-multiplier {
      xr:xr-xml-map "ip_bfd_gl_mgmt:DetectionMultiplier";
      type uint32;
      description "Detection Multiplier";
    }
    leaf desired-min-tx-interval {
      xr:xr-xml-map "ip_bfd_gl_mgmt:DesiredMinTxInterval";
      type uint32;
      description "Desired Min TX Interval";
    }
    leaf required-min-rx-interval {
      xr:xr-xml-map "ip_bfd_gl_mgmt:RequiredMinRxInterval";
      type uint32;
      description "Required Min RX Interval";
    }
    leaf required-min-rx-echo-interval {
      xr:xr-xml-map "ip_bfd_gl_mgmt:RequiredMinRxEchoInterval";
      type uint32;
      description "Required Min RX Echo Interval";
    }
  }

  grouping BFD-LOC-MGMT-SESSION-STATE-INFORMATION {
    description "BFD Location Session State Information";
    leaf total-count {
      xr:xr-xml-map "ip_bfd_gl_mgmt:TotalCount";
      type uint32;
      description "Number of sessions in database";
    }
    leaf up-count {
      xr:xr-xml-map "ip_bfd_gl_mgmt:UpCount";
      type uint32;
      description "Number of sessions in up state";
    }
    leaf down-count {
      xr:xr-xml-map "ip_bfd_gl_mgmt:DownCount";
      type uint32;
      description "Number of sessions in down state";
    }
    leaf unknown-count {
      xr:xr-xml-map "ip_bfd_gl_mgmt:UnknownCount";
      type uint32;
      description "Number of sessions in unknown state";
    }
    leaf retry-count {
      xr:xr-xml-map "ip_bfd_gl_mgmt:RetryCount";
      type uint32;
      description "Number of sessions in retry state";
    }
    leaf standby-count {
      xr:xr-xml-map "ip_bfd_gl_mgmt:StandbyCount";
      type uint32;
      description "Number of sessions in standby state";
    }
  }

  grouping BFD-MGMT-BFD-LOC-INFORMATION {
    description "BFD Location Summary Information";

    container session-state {
      description "Statistics of states for sessions";
      uses BFD-LOC-MGMT-SESSION-STATE-INFORMATION;
    }
  }

  grouping BFD-MGMT-SUMMARY {
    description "BFD MGMT SUMMARY";
    leaf node-id {
      xr:xr-xml-map "ip_bfd_gl_mgmt:NodeID";
      type xr:Node-id;
      description "Node ID";
    }
    leaf pps-allocated-value {
      xr:xr-xml-map "ip_bfd_gl_mgmt:PPSAllocatedValue";
      type uint32;
      description "Allocated PPS value";
    }
    leaf ppsmp-allocated-value {
      xr:xr-xml-map "ip_bfd_gl_mgmt:PPSMPAllocatedValue";
      type uint32;
      description "Allocated MP PPS value";
    }
    leaf pps-max-value {
      xr:xr-xml-map "ip_bfd_gl_mgmt:PPSMaxValue";
      type uint32;
      description "Max PPS value";
    }
    leaf ppsmp-max-value {
      xr:xr-xml-map "ip_bfd_gl_mgmt:PPSMPMaxValue";
      type uint32;
      description "Max MP PPS value";
    }
    leaf total-session-number {
      xr:xr-xml-map "ip_bfd_gl_mgmt:TotalSessionNumber";
      type uint32;
      description "Total Session Number";
    }
    leaf mp-session-number {
      xr:xr-xml-map "ip_bfd_gl_mgmt:MPSessionNumber";
      type uint32;
      description "MP Session Number";
    }
    leaf max-session-number {
      xr:xr-xml-map "ip_bfd_gl_mgmt:MaxSessionNumber";
      type uint32;
      description "Max Session Number";
    }
  }

  grouping BFD-MGMT-LSP-PING-INFO {
    description "BFD LSP Ping info";

    container lsp-ping-tx-last-time {
      description "LSP Ping last sent time";
      uses BFD-TIMESPEC;
    }

    container lsp-ping-tx-last-error-time {
      description "LSP Ping last error time";
      uses BFD-TIMESPEC;
    }

    container lsp-ping-rx-last-time {
      description "LSP Ping last received time";
      uses BFD-TIMESPEC;
    }
    leaf lsp-ping-tx-count {
      xr:xr-xml-map "ip_bfd_gl_mgmt:LSPPingTxCount";
      type uint32;
      description "LSP Ping Tx count";
    }
    leaf lsp-ping-tx-error-count {
      xr:xr-xml-map "ip_bfd_gl_mgmt:LSPPingTxErrorCount";
      type uint32;
      description "LSP Ping Tx error count";
    }
    leaf lsp-ping-tx-last-rc {
      xr:xr-xml-map "ip_bfd_gl_mgmt:LSPPingTxLastRc";
      type string;
      description "LSP Ping Tx last result";
    }
    leaf lsp-ping-tx-last-error-rc {
      xr:xr-xml-map "ip_bfd_gl_mgmt:LSPPingTxLastErrorRc";
      type string;
      description "LSP Ping Tx last error";
    }
    leaf lsp-ping-rx-last-discr {
      xr:xr-xml-map "ip_bfd_gl_mgmt:LSPPingRxLastDiscr";
      type Bfd-discr;
      description "LSP Ping Rx last received discriminator";
    }
    leaf lsp-ping-rx-count {
      xr:xr-xml-map "ip_bfd_gl_mgmt:LSPPingRxCount";
      type uint32;
      description "LSP Ping numer of times received";
    }
    leaf lsp-ping-rx-last-code {
      xr:xr-xml-map "ip_bfd_gl_mgmt:LSPPingRxLastCode";
      type uint8;
      description "LSP Ping Rx Last Code";
    }
    leaf lsp-ping-rx-last-subcode {
      xr:xr-xml-map "ip_bfd_gl_mgmt:LSPPingRxLastSubcode";
      type uint8;
      description "LSP Ping Rx Last Subcode";
    }
    leaf lsp-ping-rx-last-output {
      xr:xr-xml-map "ip_bfd_gl_mgmt:LSPPingRxLastOutput";
      type string;
      description "LSP Ping Rx Last Output";
    }
  }

  grouping BFD-TIMESPEC {
    description "BFD TIMESPEC";
    leaf seconds {
      xr:xr-xml-map "ip_bfd_gl_mgmt:Seconds";
      type uint32;
      units "second";
      description "seconds";
    }
    leaf nanoseconds {
      xr:xr-xml-map "ip_bfd_gl_mgmt:Nanoseconds";
      type uint32;
      units "nanosecond";
      description "nanoseconds";
    }
  }

  grouping BFD-MGMT-MP-DOWNLOAD-STATE-INFO {
    description "BFD Download State";

    container change-time {
      description "Change time";
      uses BFD-TIMESPEC;
    }
    leaf mp-download-state {
      xr:xr-xml-map "ip_bfd_gl_mgmt:MPDownloadState";
      type Bfd-mp-download-state;
      description "MP Download State";
    }
  }

  grouping TE-S2L-FEC {
    description "A sub-LSP FEC";
    leaf s2l-fec-subgroup-id {
      xr:xr-xml-map "ip_bfd_gl_mgmt:S2L_FECSubgroupID";
      type uint16;
      description "sub-LSP subgroup ID";
    }
    leaf s2l-fec-lsp-id {
      xr:xr-xml-map "ip_bfd_gl_mgmt:S2L_FEC_LSP_ID";
      type uint16;
      description "LSP ID";
    }
    leaf s2l-fec-tunnel-id {
      xr:xr-xml-map "ip_bfd_gl_mgmt:S2L_FECTunnelID";
      type uint16;
      description "Tunnel ID";
    }
    leaf s2l-fec-extended-tunnel-id {
      xr:xr-xml-map "ip_bfd_gl_mgmt:S2L_FECExtendedTunnelID";
      type inet:ipv4-address;
      description "Extended tunnel ID";
    }
    leaf s2l-fec-source {
      xr:xr-xml-map "ip_bfd_gl_mgmt:S2L_FECSource";
      type inet:ipv4-address;
      description "LSP source address";
    }
    leaf s2l-fec-dest {
      xr:xr-xml-map "ip_bfd_gl_mgmt:S2L_FECDest";
      type inet:ipv4-address;
      description "sub-LSP destination address";
    }
    leaf s2l-fec-p2mp-id {
      xr:xr-xml-map "ip_bfd_gl_mgmt:S2L_FEC_P2MP_ID";
      type uint32;
      description "P2MP ID";
    }
    leaf s2l-fec-subgroup-originator {
      xr:xr-xml-map "ip_bfd_gl_mgmt:S2L_FECSubgroupOriginator";
      type inet:ipv4-address;
      description "Subgroup Originator";
    }
    leaf s2l-fec-ctype {
      xr:xr-xml-map "ip_bfd_gl_mgmt:S2L_FEC_CType";
      type Mpls-lib-c;
      description "Session identifier (ctype)";
    }
    leaf s2l-fec-vrf {
      xr:xr-xml-map "ip_bfd_gl_mgmt:S2L_FEC_VRF";
      type string;
      description "VRF; currently only for GMPLS tunnels";
    }
  }

  grouping BFD-FEC-DUMMY {
    description "BFD FEC DUMMY";
    leaf dummy {
      xr:xr-xml-map "ip_bfd_gl_mgmt:dummy";
      type yang:hex-string;
      description "dummy";
    }
  }

  grouping BFD-FEC-UNION {
    description "BFD FEC UNION";

    container dummy {
      when "../bfdfe-ctype = 'bfd-api-fec-type-none'" {
        description "../BFDFECType = 'BFD_API_FEC_TYPE_NONE'";
      }
      description "dummy";
      uses BFD-FEC-DUMMY;
    }

    container te-s2l-fec {
      when "../bfdfe-ctype = 'bfd-api-fec-type-p2p-te'" {
        description "../BFDFECType = 'BFD_API_FEC_TYPE_P2P_TE'";
      }
      description "te s2l fec";
      uses TE-S2L-FEC;
    }
    leaf bfdfe-ctype {
      xr:xr-xml-map "ip_bfd_gl_mgmt:BFDFECType";
      type Bfd-api-fec;
      description "BFDFECType";
    }
  }

  grouping BFD-MGMT-SESSION-KEY {
    description "BFD Universal Session Key";

    container ip-destination-address {
      description "IPv4/v6 dest address";
      uses IP-ADDR-T-UNION;
    }

    container ip-source-address {
      description "IPv4/v6 source address";
      uses IP-ADDR-T-UNION;
    }

    container bfdfec {
      description "Union of FECs";
      uses BFD-FEC-UNION;
    }

    container target-address {
      description "sbfd target address";
      uses IP-ADDR-T-UNION;
    }
    leaf session-key-type {
      xr:xr-xml-map "ip_bfd_gl_mgmt:SessionKeyType";
      type uint32;
      description "Session Key Type";
    }
    leaf interface-name {
      xr:xr-xml-map "ip_bfd_gl_mgmt:InterfaceName";
      type string {
        length "0..64";
      }
      description "Session Interface Name";
    }
    leaf vrf-name {
      xr:xr-xml-map "ip_bfd_gl_mgmt:VRFName";
      type string {
        length "0..120";
      }
      description "Session VRF Name";
    }
    leaf incoming-label {
      xr:xr-xml-map "ip_bfd_gl_mgmt:IncomingLabel";
      type uint32;
      description "Incoming Label";
    }
    leaf sbfd-enabled {
      xr:xr-xml-map "ip_bfd_gl_mgmt:SBFDEnabled";
      type int32;
      description "SBFD enable flag";
    }
    leaf sbfd-target-type {
      xr:xr-xml-map "ip_bfd_gl_mgmt:SBFDTargetType";
      type uint32;
      description "SBFD target type";
    }
  }

  grouping BFD-MGMT-SESSION-ASSOCIATION-INFORMATION {
    description "BFD Session Association Information";

    container session-key {
      description "Session Key";
      uses BFD-MGMT-SESSION-KEY;
    }
    leaf sessiontype {
      xr:xr-xml-map "ip_bfd_gl_mgmt:Sessiontype";
      type Bfd-session;
      description "Session type";
    }
    leaf local-discriminator {
      xr:xr-xml-map "ip_bfd_gl_mgmt:LocalDiscriminator";
      type Bfd-discr;
      description "Session's Local discriminator";
    }

    list owner-information {
      description "Client applications owning the session";
      uses BFD-MGMT-SESSION-OWNER-INFORMATION;
    }
  }

  grouping BFD-MGMT-SESSION-OWNER-INFORMATION {
    description "BFD Session Owner Information";
    leaf interval {
      xr:xr-xml-map "ip_bfd_gl_mgmt:Interval";
      type uint32;
      units "microsecond";
      description
        "Client specified minimum transmit interval in
        micro-seconds";
    }
    leaf detection-multiplier {
      xr:xr-xml-map "ip_bfd_gl_mgmt:DetectionMultiplier";
      type uint32;
      description
        "Client specified detection multiplier to compute
        detection time";
    }
    leaf adjusted-interval {
      xr:xr-xml-map "ip_bfd_gl_mgmt:AdjustedInterval";
      type uint32;
      units "millisecond";
      description
        "Adjusted minimum transmit interval in
        milli-seconds";
    }
    leaf adjusted-detection-multiplier {
      xr:xr-xml-map "ip_bfd_gl_mgmt:AdjustedDetectionMultiplier";
      type uint32;
      description
        "Adjusted detection multiplier to compute
        detection time";
    }
    leaf name {
      xr:xr-xml-map "ip_bfd_gl_mgmt:Name";
      type string {
        length "0..257";
      }
      description "Client process name";
    }
  }

  grouping BFD-MGMT-INTERVAL-STATISTICS {
    description "BFD Agent Interval between packets Information";
    leaf number {
      xr:xr-xml-map "ip_bfd_gl_mgmt:Number";
      type uint32;
      description
        "Number of Interval Samples between Packets
        sent/received";
    }
    leaf minimum {
      xr:xr-xml-map "ip_bfd_gl_mgmt:Minimum";
      type uint32;
      units "millisecond";
      description
        "Minimum of Transmit/Receive Interval (in
        milli-seconds)";
    }
    leaf maximum {
      xr:xr-xml-map "ip_bfd_gl_mgmt:Maximum";
      type uint32;
      units "millisecond";
      description
        "Maximum of Transmit/Receive Interval (in
        milli-seconds)";
    }
    leaf average {
      xr:xr-xml-map "ip_bfd_gl_mgmt:Average";
      type uint32;
      units "millisecond";
      description
        "Average of Transmit/Receive Interval (in
        milli-seconds)";
    }
    leaf last {
      xr:xr-xml-map "ip_bfd_gl_mgmt:Last";
      type uint32;
      units "millisecond";
      description
        "Time since last Transmit/Receive (in
        milli-seconds)";
    }
  }

  grouping BFD-MGMT-CONTROL-PACKET {
    description "BFD Control Packet";
    leaf version {
      xr:xr-xml-map "ip_bfd_gl_mgmt:Version";
      type uint8;
      description "Version";
    }
    leaf diagnostic {
      xr:xr-xml-map "ip_bfd_gl_mgmt:Diagnostic";
      type Bfd-mgmt-session-diag;
      description "Diagnostic";
    }
    leaf ihear-you {
      xr:xr-xml-map "ip_bfd_gl_mgmt:IHearYou";
      type int32;
      description "I Hear You (v0)";
    }
    leaf state {
      xr:xr-xml-map "ip_bfd_gl_mgmt:State";
      type Bfd-mgmt-session-state;
      description "State (v1)";
    }
    leaf demand {
      xr:xr-xml-map "ip_bfd_gl_mgmt:Demand";
      type int32;
      description "Demand mode";
    }
    leaf poll {
      xr:xr-xml-map "ip_bfd_gl_mgmt:Poll";
      type int32;
      description "Poll bit";
    }
    leaf final {
      xr:xr-xml-map "ip_bfd_gl_mgmt:Final";
      type int32;
      description "Final bit";
    }
    leaf control-plane-independent {
      xr:xr-xml-map "ip_bfd_gl_mgmt:ControlPlaneIndependent";
      type int32;
      description
        "BFD implementation does not share fate with its
        control plane";
    }
    leaf authentication-present {
      xr:xr-xml-map "ip_bfd_gl_mgmt:AuthenticationPresent";
      type int32;
      description "Requesting authentication for the session";
    }
    leaf detection-multiplier {
      xr:xr-xml-map "ip_bfd_gl_mgmt:DetectionMultiplier";
      type uint32;
      description "Detection Multiplier";
    }
    leaf length {
      xr:xr-xml-map "ip_bfd_gl_mgmt:Length";
      type uint32;
      description "Length";
    }
    leaf my-discriminator {
      xr:xr-xml-map "ip_bfd_gl_mgmt:MyDiscriminator";
      type Bfd-discr;
      description "My Discriminator";
    }
    leaf your-discriminator {
      xr:xr-xml-map "ip_bfd_gl_mgmt:YourDiscriminator";
      type Bfd-discr;
      description "Your Discriminator";
    }
    leaf desired-minimum-transmit-interval {
      xr:xr-xml-map "ip_bfd_gl_mgmt:DesiredMinimumTransmitInterval";
      type uint32;
      units "microsecond";
      description
        "Desired minimum transmit interval in
        micro-seconds";
    }
    leaf required-minimum-receive-interval {
      xr:xr-xml-map "ip_bfd_gl_mgmt:RequiredMinimumReceiveInterval";
      type uint32;
      units "microsecond";
      description "Required receive interval in micro-seconds";
    }
    leaf required-minimum-echo-receive-interval {
      xr:xr-xml-map "ip_bfd_gl_mgmt:RequiredMinimumEchoReceiveInter"+
        "val";
      type uint32;
      units "microsecond";
      description "Required echo receive interval in micro-seconds";
    }
  }

  grouping BFD-MGMT-SESSION-STATE-TIME {
    description "BFD Session State Transition Time Information";
    leaf days {
      xr:xr-xml-map "ip_bfd_gl_mgmt:Days";
      type uint32;
      units "day";
      description
        "Number of days since last session state
        transition";
    }
    leaf hours {
      xr:xr-xml-map "ip_bfd_gl_mgmt:Hours";
      type uint8;
      units "hour";
      description
        "Number of hours since last session state
        transition";
    }
    leaf minutes {
      xr:xr-xml-map "ip_bfd_gl_mgmt:Minutes";
      type uint8;
      units "minute";
      description
        "Number of mins since last session state
        transition";
    }
    leaf seconds {
      xr:xr-xml-map "ip_bfd_gl_mgmt:Seconds";
      type uint8;
      units "second";
      description
        "Number of seconds since last session state
        transition";
    }
  }

  grouping IP-ADDR-T-UNION {
    description "IP ADDR T UNION";
    leaf afi {
      xr:xr-xml-map "ip_bfd_gl_mgmt:AFI";
      type Bfd-af-id;
      description "AFI";
    }
    leaf dummy {
      xr:xr-xml-map "ip_bfd_gl_mgmt:Dummy";
      when "../afi = 'bfd-af-id-none'" {
        description "../AFI = 'BFD_AF_ID_NONE'";
      }
      type uint8;
      description "No Address";
    }
    leaf ipv4 {
      xr:xr-xml-map "ip_bfd_gl_mgmt:IPV4";
      when "../afi = 'bfd-af-id-ipv4'" {
        description "../AFI = 'BFD_AF_ID_IPV4'";
      }
      type Bfd-in-addr;
      description "IPv4 address type";
    }
    leaf ipv6 {
      xr:xr-xml-map "ip_bfd_gl_mgmt:IPV6";
      when "../afi = 'bfd-af-id-ipv6'" {
        description "../AFI = 'BFD_AF_ID_IPV6'";
      }
      type Bfd-in6-addr;
      description "IPv6 address type";
    }
  }

  grouping BFD-MGMT-SESSION-STATUS-INFORMATION {
    description "BFD Agent detailed Session Information";

    container source-address {
      description "Source address";
      uses IP-ADDR-T-UNION;
    }

    container last-state-change {
      description "Time since last state change";
      uses BFD-MGMT-SESSION-STATE-TIME;
    }

    container transmit-packet {
      description "Transmit Packet";
      uses BFD-MGMT-CONTROL-PACKET;
    }

    container receive-packet {
      description "Receive Packet";
      uses BFD-MGMT-CONTROL-PACKET;
    }

    container status-brief-information {
      description "Brief Status Information";
      uses BFD-MGMT-SESSION-STATUS-INFORMATION-BRIEF;
    }

    container async-transmit-statistics {
      description
        "Statistics of Interval between Async Packets
        Transmitted (in milli-seconds)";
      uses BFD-MGMT-INTERVAL-STATISTICS;
    }

    container async-receive-statistics {
      description
        "Statistics of Interval between Async Packets
        Received (in milli-seconds)";
      uses BFD-MGMT-INTERVAL-STATISTICS;
    }

    container echo-transmit-statistics {
      description
        "Statistics of Interval between Echo Packets
        Transmitted (in milli-seconds)";
      uses BFD-MGMT-INTERVAL-STATISTICS;
    }

    container echo-received-statistics {
      description
        "Statistics of Interval between Echo Packets
        Received (in milli-seconds)";
      uses BFD-MGMT-INTERVAL-STATISTICS;
    }
    leaf sessiontype {
      xr:xr-xml-map "ip_bfd_gl_mgmt:Sessiontype";
      type Bfd-session;
      description "Session type";
    }
    leaf session-subtype {
      xr:xr-xml-map "ip_bfd_gl_mgmt:SessionSubtype";
      type string;
      description "Session subtype";
    }
    leaf state {
      xr:xr-xml-map "ip_bfd_gl_mgmt:State";
      type Bfd-mgmt-session-state;
      description "State";
    }
    leaf local-discriminator {
      xr:xr-xml-map "ip_bfd_gl_mgmt:LocalDiscriminator";
      type Bfd-discr;
      description "Session's Local discriminator";
    }
    leaf remote-discriminator {
      xr:xr-xml-map "ip_bfd_gl_mgmt:RemoteDiscriminator";
      type Bfd-discr;
      description "Session's Remote discriminator";
    }
    leaf to-up-state-count {
      xr:xr-xml-map "ip_bfd_gl_mgmt:ToUpStateCount";
      type uint32;
      description "Number of times session state went to UP";
    }
    leaf desired-minimum-echo-transmit-interval {
      xr:xr-xml-map "ip_bfd_gl_mgmt:DesiredMinimumEchoTransmitInter"+
        "val";
      type uint32;
      units "millisecond";
      description
        "Desired minimum echo transmit interval in
        milli-seconds";
    }
    leaf remote-negotiated-interval {
      xr:xr-xml-map "ip_bfd_gl_mgmt:RemoteNegotiatedInterval";
      type uint32;
      units "millisecond";
      description "Remote Negotiated Interval in milli-seconds";
    }
    leaf latency-number {
      xr:xr-xml-map "ip_bfd_gl_mgmt:LatencyNumber";
      type uint32;
      description
        "Number of Latency Samples. Time between Transmit
        and Receive";
    }
    leaf latency-minimum {
      xr:xr-xml-map "ip_bfd_gl_mgmt:LatencyMinimum";
      type uint32;
      units "microsecond";
      description "Minimum value of Latency (in micro-seconds)";
    }
    leaf latency-maximum {
      xr:xr-xml-map "ip_bfd_gl_mgmt:LatencyMaximum";
      type uint32;
      units "microsecond";
      description "Maximum value of Latency (in micro-seconds)";
    }
    leaf latency-average {
      xr:xr-xml-map "ip_bfd_gl_mgmt:LatencyAverage";
      type uint32;
      units "microsecond";
      description "Average value of Latency (in micro-seconds)";
    }
    leaf node-id {
      xr:xr-xml-map "ip_bfd_gl_mgmt:NodeID";
      type xr:Node-id;
      description "Location where session is housed";
    }
    leaf internal-label {
      xr:xr-xml-map "ip_bfd_gl_mgmt:InternalLabel";
      type uint32;
      description "Internal Label";
    }
  }

  grouping BFD-MGMT-SESSION-DETAIL {
    description "BFD Detailed Session Information";

    container status-information {
      description "Session status information";
      uses BFD-MGMT-SESSION-STATUS-INFORMATION;
    }

    container mp-download-state {
      description "MP Dowload State";
      uses BFD-MGMT-MP-DOWNLOAD-STATE-INFO;
    }

    container lsp-ping-info {
      description "LSP Ping Info";
      uses BFD-MGMT-LSP-PING-INFO;
    }

    list owner-information {
      description "Client applications owning the session";
      uses BFD-MGMT-SESSION-OWNER-INFORMATION;
    }

    list association-information {
      description "Association session information";
      uses BFD-MGMT-SESSION-ASSOCIATION-INFORMATION;
    }
  }

  grouping BFD-MGMT-MULTIPLE-PATHS {
    description "BFD Multiple paths Info";
    leaf session-subtype {
      xr:xr-xml-map "ip_bfd_gl_mgmt:SessionSubtype";
      type string;
      description "Session subtype";
    }
    leaf state {
      xr:xr-xml-map "ip_bfd_gl_mgmt:State";
      type Bfd-mgmt-session-state;
      description "State";
    }
    leaf local-discriminator {
      xr:xr-xml-map "ip_bfd_gl_mgmt:LocalDiscriminator";
      type Bfd-discr;
      description "Session's Local discriminator";
    }
    leaf node-id {
      xr:xr-xml-map "ip_bfd_gl_mgmt:NodeID";
      type xr:Node-id;
      description "Location where session is housed";
    }
    leaf incoming-label-xr {
      xr:xr-xml-map "ip_bfd_gl_mgmt:incoming-label-xr";
      type uint32;
      description "Incoming Label";
    }
    leaf session-interface-name {
      xr:xr-xml-map "ip_bfd_gl_mgmt:SessionInterfaceName";
      type xr:Interface-name;
      description "Interface name";
    }
  }

  grouping BFD-MGMT-CLIENT-FLAGS {
    description "BFD Client Flags";
    leaf is-zombie-state {
      xr:xr-xml-map "ip_bfd_gl_mgmt:IsZombieState";
      type int32;
      description "Client is in Zombie State";
    }
    leaf is-recreate-state {
      xr:xr-xml-map "ip_bfd_gl_mgmt:IsRecreateState";
      type int32;
      description "Client is in Recreate State";
    }
  }

  grouping BFD-MGMT-CLIENT-BRIEF-INFORMATION {
    description "BFD Brief Client Information";
    leaf name-xr {
      xr:xr-xml-map "ip_bfd_gl_mgmt:name-xr";
      type string {
        length "0..257";
      }
      description "Client process name";
    }
    leaf node-id {
      xr:xr-xml-map "ip_bfd_gl_mgmt:NodeID";
      type xr:Node-id;
      description "Location where client resides";
    }
    leaf session-count {
      xr:xr-xml-map "ip_bfd_gl_mgmt:SessionCount";
      type uint32;
      description "Number of sessions created by this client";
    }
  }

  grouping BFD-MGMT-CLIENT-DETAIL-INFORMATION {
    description "BFD detailed Client Information";

    container brief {
      description "Brief client information";
      uses BFD-MGMT-CLIENT-BRIEF-INFORMATION;
    }

    container flags {
      description "The BFD Client Flags";
      uses BFD-MGMT-CLIENT-FLAGS;
    }
    leaf recreate-time {
      xr:xr-xml-map "ip_bfd_gl_mgmt:RecreateTime";
      type uint32;
      units "second";
      description "Recreate Time in Seconds";
    }
  }

  grouping BFD-MGMT-PACKET-COUNT {
    description "BFD Agent Packet Count Info";
    leaf hello-transmit-count {
      xr:xr-xml-map "ip_bfd_gl_mgmt:HelloTransmitCount";
      type uint32;
      description "Number of Hellos transmitted";
    }
    leaf hello-receive-count {
      xr:xr-xml-map "ip_bfd_gl_mgmt:HelloReceiveCount";
      type uint32;
      description "Number of Hellos received";
    }
    leaf echo-transmit-count {
      xr:xr-xml-map "ip_bfd_gl_mgmt:EchoTransmitCount";
      type uint32;
      description "Number of echo packets transmitted";
    }
    leaf echo-receive-count {
      xr:xr-xml-map "ip_bfd_gl_mgmt:EchoReceiveCount";
      type uint32;
      description "Number of echo packets received";
    }
    leaf display-type {
      xr:xr-xml-map "ip_bfd_gl_mgmt:DisplayType";
      type Bfd-mgmt-pkt-display;
      description "Packet Display Type";
    }
  }

  grouping BFD-MGMT-SESSION-STATE-INFORMATION {
    description "BFD Session State Information";
    leaf total-count {
      xr:xr-xml-map "ip_bfd_gl_mgmt:TotalCount";
      type uint32;
      description "Number of sessions in database";
    }
    leaf down-count {
      xr:xr-xml-map "ip_bfd_gl_mgmt:DownCount";
      type uint32;
      description "Number of sessions in down state";
    }
    leaf up-count {
      xr:xr-xml-map "ip_bfd_gl_mgmt:UpCount";
      type uint32;
      description "Number of sessions in up state";
    }
    leaf unknown-count {
      xr:xr-xml-map "ip_bfd_gl_mgmt:UnknownCount";
      type uint32;
      description "Number of sessions in unknown state";
    }
  }

  grouping BFD-MGMT-BFD-INFORMATION {
    description "BFD Summary Information";

    container session-state {
      description "Statistics of states for sessions";
      uses BFD-MGMT-SESSION-STATE-INFORMATION;
    }
  }

  grouping BFD-MGMT-ECHO-INTERVAL-MULTIPLIER-INFORMATION {
    description
      "BFD Agent Echo Interval and Detection Multiplier
      Information";
    leaf negotiated-transmit-interval {
      xr:xr-xml-map "ip_bfd_gl_mgmt:NegotiatedTransmitInterval";
      type uint32;
      units "microsecond";
      description "Negotiated transmit interval in micro-seconds";
    }
    leaf detection-time {
      xr:xr-xml-map "ip_bfd_gl_mgmt:DetectionTime";
      type uint32;
      units "microsecond";
      description "Detection time in micro-seconds";
    }
    leaf detection-multiplier {
      xr:xr-xml-map "ip_bfd_gl_mgmt:DetectionMultiplier";
      type uint32;
      description "Detection Multiplier";
    }
  }

  grouping BFD-MGMT-ASYNC-INTERVAL-MULTIPLIER-INFORMATION {
    description
      "BFD Agent Async Interval and Detection Multiplier
      Information";
    leaf negotiated-remote-transmit-interval {
      xr:xr-xml-map "ip_bfd_gl_mgmt:NegotiatedRemoteTransmitInterva"+
        "l";
      type uint32;
      units "microsecond";
      description
        "Negotiated remote transmit interval in
        micro-seconds";
    }
    leaf negotiated-local-transmit-interval {
      xr:xr-xml-map "ip_bfd_gl_mgmt:NegotiatedLocalTransmitInterval";
      type uint32;
      units "microsecond";
      description
        "Negotiated local transmit interval in
        micro-seconds";
    }
    leaf detection-time {
      xr:xr-xml-map "ip_bfd_gl_mgmt:DetectionTime";
      type uint32;
      units "microsecond";
      description "Detection time in micro-seconds";
    }
    leaf detection-multiplier {
      xr:xr-xml-map "ip_bfd_gl_mgmt:DetectionMultiplier";
      type uint32;
      description "Detection Multiplier";
    }
  }

  grouping BFD-MGMT-SESSION-STATUS-INFORMATION-BRIEF {
    description "BFD Session Status Brief Information ";

    container async-interval-multiplier {
      description
        "Async Interval and Detect Multiplier Information";
      uses BFD-MGMT-ASYNC-INTERVAL-MULTIPLIER-INFORMATION;
    }

    container echo-interval-multiplier {
      description "Echo Interval and Detect Multiplier Information";
      uses BFD-MGMT-ECHO-INTERVAL-MULTIPLIER-INFORMATION;
    }
  }

  grouping BFD-MGMT-SESSION-BRIEF {
    description "BFD Brief Session Information";

    container status-brief-information {
      description "Brief Status Information";
      uses BFD-MGMT-SESSION-STATUS-INFORMATION-BRIEF;
    }
    leaf node-id {
      xr:xr-xml-map "ip_bfd_gl_mgmt:NodeID";
      type xr:Node-id;
      description "Location where session is housed";
    }
    leaf state {
      xr:xr-xml-map "ip_bfd_gl_mgmt:State";
      type Bfd-mgmt-session-state;
      description "State";
    }
    leaf session-type {
      xr:xr-xml-map "ip_bfd_gl_mgmt:SessionType";
      type Bfd-session;
      description "Session type";
    }
    leaf session-subtype {
      xr:xr-xml-map "ip_bfd_gl_mgmt:SessionSubtype";
      type string;
      description "Session subtype";
    }
    leaf session-flags {
      xr:xr-xml-map "ip_bfd_gl_mgmt:SessionFlags";
      type uint32;
      description "Session Flags";
    }
  }
}
