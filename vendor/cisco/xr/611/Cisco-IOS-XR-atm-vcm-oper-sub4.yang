submodule Cisco-IOS-XR-atm-vcm-oper-sub4 {

  belongs-to Cisco-IOS-XR-atm-vcm-oper {
    prefix Cisco-IOS-XR-atm-vcm-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR atm-vcm package operational data.

     Copyright (c) 2013-2016 by Cisco Systems, Inc.
     All rights reserved.";

  revision "2015-11-09" {
    description
      "IOS XR 6.0 revision.";
  }

  typedef Vc-cell-packing-mode {
    type enumeration {
      enum vp {
        value 1;
        description "VP mode";
      }
      enum vc {
        value 2;
        description "VC mode";
      }
      enum port-mode {
        value 3;
        description "Port mode";
      }
    }
    description "ATM VC cell packing mode";
  }
  typedef Vc-test-mode {
    type enumeration {
      enum test-mode-none {
        value 1;
        description "VC not in test mode";
      }
      enum loop {
        value 2;
        description "VC in test mode Loop";
      }
      enum reserved {
        value 3;
        description "VC in test mode Reserved";
      }
    }
    description "VC Test Mode Type";
  }
  typedef Vc-state {
    type enumeration {
      enum initialized {
        value 0;
        description
          "ATM VC State: only VC data structure
          initialized   ";
      }
      enum modifying {
        value 1;
        description
          "ATM VC State: configuration currently being
          changed";
      }
      enum modified {
        value 2;
        description
          "ATM VC State: configuration changed            ";
      }
      enum activating {
        value 3;
        description
          "ATM VC State: command sent to hardware to
          activate ";
      }
      enum activated {
        value 4;
        description
          "ATM VC State: activated in h/w or protocol     ";
      }
      enum not-verified {
        value 5;
        description
          "ATM VC State: OAM/ILMI - yet to verify         ";
      }
      enum ready {
        value 6;
        description
          "ATM VC State: Ready state                      ";
      }
      enum deactivating {
        value 7;
        description
          "ATM VC State: command sent to h/w to deactivate";
      }
      enum inactive {
        value 8;
        description
          "ATM VC State: inactive/not present in hardware ";
      }
      enum deleting {
        value 9;
        description
          "ATM VC State: VC is being deleted              ";
      }
      enum deleted {
        value 10;
        description
          "ATM VC State: VC is already delete in hardware ";
      }
      enum state-unknown {
        value 11;
        description "ATM VC State: Unknown(invalid)";
      }
    }
    description "VC State";
  }
  typedef Vc-inherit-level {
    type enumeration {
      enum directly-configured-onvc {
        value 0;
        description "ATM vc-class inherit level: Config of VC";
      }
      enum vc-class-configured-onvc {
        value 1;
        description "ATM vc-class inherit level: Class of VC";
      }
      enum vc-class-configured-on-sub-interface {
        value 2;
        description "ATM vc-class inherit level: Class of Sub-if";
      }
      enum vc-class-configured-on-main-interface {
        value 3;
        description "ATM vc-class inherit level: Class of Main-if";
      }
      enum global-default {
        value 4;
        description "ATM vc-class inherit level: Global Default";
      }
      enum unknown {
        value 5;
        description "ATM vc-class inherit level: Unknown (invalid)";
      }
      enum not-supported {
        value 6;
        description
          "ATM vc-class inherit level: Not supported on
          this VC class";
      }
    }
    description "ATM vc-class inheritence level";
  }
  typedef Vc-traf-shaping {
    type enumeration {
      enum cbr {
        value 1;
        description "VC traffic shaping type CBR";
      }
      enum vbr-nrt {
        value 2;
        description "VC traffic shaping type VBR-NR";
      }
      enum vbr-rt {
        value 3;
        description "VC traffic shaping type VBR-RT";
      }
      enum abr {
        value 4;
        description "VC traffic shaping type ABR";
      }
      enum ubr-plus {
        value 5;
        description "VC traffic shaping type UBR+";
      }
      enum ubr {
        value 6;
        description "VC traffic shaping type UBR";
      }
      enum traf-shaping-unknown {
        value 7;
        description "VC traffic shaping type Unknown (invalid)";
      }
    }
    description "VC traffic shaping type";
  }
  typedef Vc-encap {
    type enumeration {
      enum ilmi {
        value 1;
        description "ILMI Encapsulation";
      }
      enum qsaal {
        value 2;
        description "QSAAL Encapsulation";
      }
      enum snap {
        value 3;
        description "SNAP Encapsulation";
      }
      enum mux {
        value 4;
        description "MUX Encapsulation";
      }
      enum nlpid {
        value 5;
        description "NLPID Encapsulation";
      }
      enum f4oam {
        value 6;
        description "F4OAM Encapsulation";
      }
      enum aal0 {
        value 7;
        description "AAL0 Encapsulation";
      }
      enum aal5 {
        value 8;
        description "AAL5 Encapsulation";
      }
      enum encap-unknown {
        value 9;
        description "Uknown (invalid) Encapsulation";
      }
    }
    description "VC Encapsulation Type";
  }
  typedef Vc {
    type enumeration {
      enum layer3-vc {
        value 0;
        description " ATM Layer 3 VC type";
      }
      enum layer2-vc {
        value 1;
        description " ATM Layer 2 VC type";
      }
      enum layer2-vp {
        value 2;
        description " ATM Layer 2 VP type";
      }
      enum vc-type-unknown {
        value 3;
        description " ATM type unknown";
      }
    }
    description " ATM VC type";
  }

  grouping ATM-CELL-PACKING-DATA {
    description "ATM cell packing data";

    container cell-packing {
      description "Cell packing specific data";
      uses ATM-VCM-CELL-PACKING-INFO;
    }
    leaf sub-interface-name {
      xr:xr-xml-map "atm_vcm_vc:SubInterfaceName";
      type xr:Interface-name;
      description "Sub-interface name";
    }
    leaf cell-packing-mode {
      xr:xr-xml-map "atm_vcm_vc:CellPackingMode";
      type Vc-cell-packing-mode;
      description "ATM cell packing mode";
    }
    leaf vpi {
      xr:xr-xml-map "atm_vcm_vc:VPI";
      type uint32;
      description "VPI";
    }
    leaf vci {
      xr:xr-xml-map "atm_vcm_vc:VCI";
      type uint32;
      description "VCI";
    }
    leaf received-average-cells-packets {
      xr:xr-xml-map "atm_vcm_vc:ReceivedAverageCellsPackets";
      type uint64;
      description "Average cells/packets received";
    }
    leaf sent-cells-packets {
      xr:xr-xml-map "atm_vcm_vc:SentCellsPackets";
      type uint64;
      description "Average cells/packets sent";
    }
  }

  grouping ATM-VCM-CELL-PACKING-INFO {
    description "ATM  Layer 2 VC specific information";
    leaf local-max-cells-packed-per-packet {
      xr:xr-xml-map "atm_vcm_vc:LocalMaxCellsPackedPerPacket";
      type uint16;
      description
        "Local configuration of maximum number of cells
        to be packed per packet";
    }
    leaf negotiated-max-cells-packed-per-packet {
      xr:xr-xml-map "atm_vcm_vc:NegotiatedMaxCellsPackedPerPacket";
      type uint16;
      description
        "Negotiated value of maximum number of cells to
        be packed per packed";
    }
    leaf max-cell-packed-timeout {
      xr:xr-xml-map "atm_vcm_vc:MaxCellPackedTimeout";
      type uint16;
      units "microsecond";
      description "Maximum cell packing timeout inmicro seconds";
    }
  }

  grouping ATM-VCM-VC {
    description "ATM VC data";

    container cell-packing-data {
      description "Cell packing specific data";
      uses ATM-VCM-CELL-PACKING-INFO;
    }
    leaf main-interface {
      xr:xr-xml-map "atm_vcm_vc:MainInterface";
      type xr:Interface-name;
      description "Main Interface handle";
    }
    leaf sub-interface {
      xr:xr-xml-map "atm_vcm_vc:SubInterface";
      type xr:Interface-name;
      description "Subinterface handle";
    }
    leaf vc-interface {
      xr:xr-xml-map "atm_vcm_vc:VCInterface";
      type xr:Interface-name;
      description "VC Interfcace handle";
    }
    leaf vpi-xr {
      xr:xr-xml-map "atm_vcm_vc:vpi-xr";
      type uint16;
      description "VC VPI value";
    }
    leaf vci-xr {
      xr:xr-xml-map "atm_vcm_vc:vci-xr";
      type uint16;
      description "VC VCI value";
    }
    leaf type {
      xr:xr-xml-map "atm_vcm_vc:Type";
      type Vc;
      description "VC Type";
    }
    leaf encapsulation {
      xr:xr-xml-map "atm_vcm_vc:Encapsulation";
      type Vc-encap;
      description "Encapsulation type";
    }
    leaf shape {
      xr:xr-xml-map "atm_vcm_vc:Shape";
      type Vc-traf-shaping;
      description "ATM VC traffic shaping type";
    }
    leaf peak-cell-rate {
      xr:xr-xml-map "atm_vcm_vc:PeakCellRate";
      type uint32;
      units "kbit/s";
      description "Peak cell rate in Kbps";
    }
    leaf sustained-cell-rate {
      xr:xr-xml-map "atm_vcm_vc:SustainedCellRate";
      type uint32;
      units "kbit/s";
      description "Sustained cell rate in Kbps";
    }
    leaf burst-rate {
      xr:xr-xml-map "atm_vcm_vc:BurstRate";
      type uint32;
      description "Burst size in cells";
    }
    leaf encaps-inherit-level {
      xr:xr-xml-map "atm_vcm_vc:EncapsInheritLevel";
      type Vc-inherit-level;
      description
        "Encapsulation inherit level - identifies if
        encapsulation is set to default, configured on
        the VC, or inherited from the vcclass.";
    }
    leaf qos-inherit-level {
      xr:xr-xml-map "atm_vcm_vc:QoS_InheritLevel";
      type Vc-inherit-level;
      description
        "Quality of Service inherit level - identifies if
        QoS is set to default, configured on the VC, or
        inherited from the vcclass.";
    }
    leaf transmit-mtu {
      xr:xr-xml-map "atm_vcm_vc:TransmitMTU";
      type uint32;
      description "Transmit MTU";
    }
    leaf receive-mtu {
      xr:xr-xml-map "atm_vcm_vc:ReceiveMTU";
      type uint32;
      description "Receive MTU";
    }
    leaf vc-onvp-tunnel {
      xr:xr-xml-map "atm_vcm_vc:VCOnVPTunnel";
      type boolean;
      description "VC on VP-tunnel flag";
    }
    leaf vc-on-p2p-sub-interface {
      xr:xr-xml-map "atm_vcm_vc:VCOnP2PSubInterface";
      type boolean;
      description "VC on Point-to-point Sub-interface";
    }
    leaf oper-status {
      xr:xr-xml-map "atm_vcm_vc:OperStatus";
      type boolean;
      description
        "TRUE value indicates that the VC is
        operationally UP";
    }
    leaf amin-status {
      xr:xr-xml-map "atm_vcm_vc:AminStatus";
      type boolean;
      description
        "TRUE value indicates that the VC is
        administratively UP";
    }
    leaf internal-state {
      xr:xr-xml-map "atm_vcm_vc:InternalState";
      type Vc-state;
      description "VC Internal state";
    }
    leaf last-state-change-time {
      xr:xr-xml-map "atm_vcm_vc:LastStateChangeTime";
      type uint32;
      description "Time when VC was last changed";
    }
    leaf test-mode {
      xr:xr-xml-map "atm_vcm_vc:TestMode";
      type Vc-test-mode;
      description "VC test mode";
    }
  }
}
