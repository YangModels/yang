submodule Cisco-IOS-XR-infra-statsd-oper-sub1 {

  belongs-to Cisco-IOS-XR-infra-statsd-oper {
    prefix Cisco-IOS-XR-infra-statsd-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR infra-statsd package operational data.

     Copyright (c) 2013-2016 by Cisco Systems, Inc.
     All rights reserved.";

  revision "2015-11-09" {
    description
      "IOS XR 6.0 revision.";
  }


  grouping STATSDBAG-DATARATE {
    description "Datarate information";
    leaf input-data-rate {
      xr:xr-xml-map "statsd:InputDataRate";
      type uint64;
      units "bit/s";
      description "Input data rate in 1000's of bps";
    }
    leaf input-packet-rate {
      xr:xr-xml-map "statsd:InputPacketRate";
      type uint64;
      units "packet/s";
      description "Input packets per second";
    }
    leaf output-data-rate {
      xr:xr-xml-map "statsd:OutputDataRate";
      type uint64;
      units "bit/s";
      description "Output data rate in 1000's of bps";
    }
    leaf output-packet-rate {
      xr:xr-xml-map "statsd:OutputPacketRate";
      type uint64;
      units "packet/s";
      description "Output packets per second";
    }
    leaf peak-input-data-rate {
      xr:xr-xml-map "statsd:PeakInputDataRate";
      type uint64;
      description "Peak input data rate";
    }
    leaf peak-input-packet-rate {
      xr:xr-xml-map "statsd:PeakInputPacketRate";
      type uint64;
      description "Peak input packet rate";
    }
    leaf peak-output-data-rate {
      xr:xr-xml-map "statsd:PeakOutputDataRate";
      type uint64;
      description "Peak output data rate";
    }
    leaf peak-output-packet-rate {
      xr:xr-xml-map "statsd:PeakOutputPacketRate";
      type uint64;
      description "Peak output packet rate";
    }
    leaf bandwidth {
      xr:xr-xml-map "statsd:Bandwidth";
      type uint32;
      units "kbit/s";
      description "Bandwidth (in kbps)";
    }
    leaf load-interval {
      xr:xr-xml-map "statsd:LoadInterval";
      type uint32;
      description "Number of 30-sec intervals less one";
    }
    leaf output-load {
      xr:xr-xml-map "statsd:OutputLoad";
      type uint8;
      description "Output load as fraction of 255";
    }
    leaf input-load {
      xr:xr-xml-map "statsd:InputLoad";
      type uint8;
      description "Input load as fraction of 255";
    }
    leaf reliability {
      xr:xr-xml-map "statsd:Reliability";
      type uint8;
      description "Reliability coefficient";
    }
  }

  grouping IFSTATSBAG-GENERIC {
    description "Generic set of interface counters";
    leaf packets-received {
      xr:xr-xml-map "statsd:PacketsReceived";
      type uint64;
      description "Packets received";
    }
    leaf bytes-received {
      xr:xr-xml-map "statsd:BytesReceived";
      type uint64;
      units "byte";
      description "Bytes received";
    }
    leaf packets-sent {
      xr:xr-xml-map "statsd:PacketsSent";
      type uint64;
      description "Packets sent";
    }
    leaf bytes-sent {
      xr:xr-xml-map "statsd:BytesSent";
      type uint64;
      units "byte";
      description "Bytes sent";
    }
    leaf multicast-packets-received {
      xr:xr-xml-map "statsd:MulticastPacketsReceived";
      type uint64;
      description "Multicast packets received";
    }
    leaf broadcast-packets-received {
      xr:xr-xml-map "statsd:BroadcastPacketsReceived";
      type uint64;
      description "Broadcast packets received";
    }
    leaf multicast-packets-sent {
      xr:xr-xml-map "statsd:MulticastPacketsSent";
      type uint64;
      description "Multicast packets sent";
    }
    leaf broadcast-packets-sent {
      xr:xr-xml-map "statsd:BroadcastPacketsSent";
      type uint64;
      description "Broadcast packets sent";
    }
    leaf output-drops {
      xr:xr-xml-map "statsd:OutputDrops";
      type uint32;
      description "Total output drops";
    }
    leaf output-queue-drops {
      xr:xr-xml-map "statsd:OutputQueueDrops";
      type uint32;
      description "Output queue drops";
    }
    leaf input-drops {
      xr:xr-xml-map "statsd:InputDrops";
      type uint32;
      description "Total input drops";
    }
    leaf input-queue-drops {
      xr:xr-xml-map "statsd:InputQueueDrops";
      type uint32;
      description "Input queue drops";
    }
    leaf runt-packets-received {
      xr:xr-xml-map "statsd:RuntPacketsReceived";
      type uint32;
      description "Received runt packets";
    }
    leaf giant-packets-received {
      xr:xr-xml-map "statsd:GiantPacketsReceived";
      type uint32;
      description "Received giant packets";
    }
    leaf throttled-packets-received {
      xr:xr-xml-map "statsd:ThrottledPacketsReceived";
      type uint32;
      description "Received throttled packets";
    }
    leaf parity-packets-received {
      xr:xr-xml-map "statsd:ParityPacketsReceived";
      type uint32;
      description "Received parity packets";
    }
    leaf unknown-protocol-packets-received {
      xr:xr-xml-map "statsd:UnknownProtocolPacketsReceived";
      type uint32;
      description "Unknown protocol packets received";
    }
    leaf input-errors {
      xr:xr-xml-map "statsd:InputErrors";
      type uint32;
      description "Total input errors";
    }
    leaf crc-errors {
      xr:xr-xml-map "statsd:CRCErrors";
      type uint32;
      description "Input CRC errors";
    }
    leaf input-overruns {
      xr:xr-xml-map "statsd:InputOverruns";
      type uint32;
      description "Input overruns";
    }
    leaf framing-errors-received {
      xr:xr-xml-map "statsd:FramingErrorsReceived";
      type uint32;
      description "Framing-errors received";
    }
    leaf input-ignored-packets {
      xr:xr-xml-map "statsd:InputIgnoredPackets";
      type uint32;
      description "Input ignored packets";
    }
    leaf input-aborts {
      xr:xr-xml-map "statsd:InputAborts";
      type uint32;
      description "Input aborts";
    }
    leaf output-errors {
      xr:xr-xml-map "statsd:OutputErrors";
      type uint32;
      description "Total output errors";
    }
    leaf output-underruns {
      xr:xr-xml-map "statsd:OutputUnderruns";
      type uint32;
      description "Output underruns";
    }
    leaf output-buffer-failures {
      xr:xr-xml-map "statsd:OutputBufferFailures";
      type uint32;
      description "Output buffer failures";
    }
    leaf output-buffers-swapped-out {
      xr:xr-xml-map "statsd:OutputBuffersSwappedOut";
      type uint32;
      description "Output buffers swapped out";
    }
    leaf applique {
      xr:xr-xml-map "statsd:Applique";
      type uint32;
      description "Applique";
    }
    leaf resets {
      xr:xr-xml-map "statsd:Resets";
      type uint32;
      description "Number of board resets";
    }
    leaf carrier-transitions {
      xr:xr-xml-map "statsd:CarrierTransitions";
      type uint32;
      description "Carrier transitions";
    }
    leaf availability-flag {
      xr:xr-xml-map "statsd:AvailabilityFlag";
      type uint32;
      description "Availability bit mask";
    }
    leaf last-data-time {
      xr:xr-xml-map "statsd:LastDataTime";
      type uint32;
      units "second";
      description
        "Time when counters were last written (in
        seconds)";
    }
    leaf seconds-since-last-clear-counters {
      xr:xr-xml-map "statsd:SecondsSinceLastClearCounters";
      type uint32;
      units "second";
      description "Number of seconds since last clear counters";
    }
    leaf last-discontinuity-time {
      xr:xr-xml-map "statsd:LastDiscontinuityTime";
      type uint32;
      units "second";
      description
        "SysUpTime when counters were last reset (in
        seconds)";
    }
    leaf seconds-since-packet-received {
      xr:xr-xml-map "statsd:SecondsSincePacketReceived";
      type uint32;
      units "second";
      description "Seconds since packet received";
    }
    leaf seconds-since-packet-sent {
      xr:xr-xml-map "statsd:SecondsSincePacketSent";
      type uint32;
      units "second";
      description "Seconds since packet sent";
    }
  }

  grouping IFSTATSBAG-PROTO {
    description "Interface counters per protocol";
    leaf bytes-received {
      xr:xr-xml-map "statsd:BytesReceived";
      type uint64;
      units "byte";
      description "Bytes received";
    }
    leaf packets-received {
      xr:xr-xml-map "statsd:PacketsReceived";
      type uint64;
      description "Packets received";
    }
    leaf bytes-sent {
      xr:xr-xml-map "statsd:BytesSent";
      type uint64;
      units "byte";
      description "Bytes sent";
    }
    leaf packets-sent {
      xr:xr-xml-map "statsd:PacketsSent";
      type uint64;
      description "Packets sent";
    }
    leaf protocol {
      xr:xr-xml-map "statsd:Protocol";
      type uint32;
      description "Protocol number";
    }
    leaf last-data-time {
      xr:xr-xml-map "statsd:LastDataTime";
      type uint32;
      units "second";
      description
        "Time when counters were last written (in
        seconds)";
    }
    leaf input-data-rate {
      xr:xr-xml-map "statsd:InputDataRate";
      type uint64;
      units "bit/s";
      description "Input data rate in 1000's of bps";
    }
    leaf input-packet-rate {
      xr:xr-xml-map "statsd:InputPacketRate";
      type uint64;
      units "packet/s";
      description "Input packets per second";
    }
    leaf output-data-rate {
      xr:xr-xml-map "statsd:OutputDataRate";
      type uint64;
      units "bit/s";
      description "Output data rate in 1000's of bps";
    }
    leaf output-packet-rate {
      xr:xr-xml-map "statsd:OutputPacketRate";
      type uint64;
      units "packet/s";
      description "Output packets per second";
    }
  }
}
