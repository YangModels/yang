module Cisco-IOS-XR-controller-optics-cfg {

  /*** NAMESPACE / PREFIX DEFINITION ***/

  namespace "http://cisco.com/ns/yang"+
    "/Cisco-IOS-XR-controller-optics-cfg";


  prefix "controller-optics-cfg";

  /*** LINKAGE (IMPORTS / INCLUDES) ***/

  import Cisco-IOS-XR-types { prefix "xr"; }

  import Cisco-IOS-XR-ifmgr-cfg { prefix "a1"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR controller-optics package configuration.

     This YANG module augments the
       Cisco-IOS-XR-ifmgr-cfg
     module with configuration data.

     Copyright (c) 2013-2016 by Cisco Systems, Inc.
     All rights reserved.";

  revision "2015-11-09" {
    description
      "IOS XR 6.0 revision.";
  }

  typedef Optics-fec {
    type enumeration {
      enum fec-none {
        value 0;
        description "No Fec";
      }
      enum fec-h15 {
        value 1;
        description "Enhanced H15";
      }
      enum fec-h25 {
        value 2;
        description "Enhanced H25";
      }
    }
    description "Optics fec";
  }
  typedef Threshold {
    type enumeration {
      enum low {
        value 1;
        description "Low Threshold";
      }
      enum high {
        value 2;
        description "High Threshold";
      }
    }
    description "Threshold";
  }
  typedef Optics-dwdm-carrier-param {
    type enumeration {
      enum itu-ch {
        value 0;
        description "ITU Wave Channel Number";
      }
      enum wavelength {
        value 1;
        description "Wavelength in nm";
      }
      enum frequency {
        value 2;
        description "Frequency in Hertz";
      }
    }
    description "Optics dwdm carrier param";
  }
  typedef Optics-dwdm-carrier-grid {
    type enumeration {
      enum 50g-hz-grid {
        value 0;
        description "50GHz Grid";
      }
      enum 100mhz-grid {
        value 1;
        description "100MHz Grid";
      }
    }
    description "Optics dwdm carrier grid";
  }
  typedef Optics-loopback {
    type enumeration {
      enum none {
        value 0;
        description "No Loopback";
      }
      enum internal {
        value 1;
        description "Internal Loopback";
      }
      enum line {
        value 2;
        description "Line Loopback";
      }
    }
    description "Optics loopback";
  }

  augment "/a1:interface-configurations/a1:interface-configuration" {

    container optics {
      xr:xr-xml-map "optics_controller_cfg:Optics";
      description "Optics controller configuration";

      container rx-thresholds {
        xr:xr-xml-map "optics_controller_cfg:OpticsRxThreshold";
        description "Configure Rx threshold";

        list rx-threshold {
          xr:xr-xml-map "optics_controller_cfg:RxThreshold";
          key "rx-threshold-type";
          description
            "Optics RX Low or high threshold configuration";
          leaf rx-threshold-type {
            xr:xr-xml-map "optics_controller_cfg:RxThresholdType";
            type Threshold;
            description "Low or high rx threshold";
          }
          leaf rx-threshold {
            xr:xr-xml-map "optics_controller_cfg:RxThreshold";
            type int32 {
              range "-400..300";
            }
            mandatory true;
            description "Select power level (in units of 0.1dBm)";
          }
        }
      }

      container optics-network-srlgs {
        xr:xr-xml-map "optics_controller_cfg:OpticsNetworkSrlgTable";
        description "Configure Network srlgs";

        list optics-network-srlg {
          xr:xr-xml-map "optics_controller_cfg:OpticsNetworkSrlg";
          key "set-id";
          description "Configure network srlg sets";
          leaf set-id {
            xr:xr-xml-map "optics_controller_cfg:SetId";
            type uint32 {
              range "1..17";
            }
            description "Set index";
          }
          leaf srlg1 {
            xr:xr-xml-map "optics_controller_cfg:Srlg1";
            type uint32 {
              range "0..4294967294";
            }
            description "none";
          }
          leaf srlg2 {
            xr:xr-xml-map "optics_controller_cfg:Srlg2";
            type uint32 {
              range "0..4294967294";
            }
            description "none";
          }
          leaf srlg3 {
            xr:xr-xml-map "optics_controller_cfg:Srlg3";
            type uint32 {
              range "0..4294967294";
            }
            description "none";
          }
          leaf srlg4 {
            xr:xr-xml-map "optics_controller_cfg:Srlg4";
            type uint32 {
              range "0..4294967294";
            }
            description "none";
          }
          leaf srlg5 {
            xr:xr-xml-map "optics_controller_cfg:Srlg5";
            type uint32 {
              range "0..4294967294";
            }
            description "none";
          }
          leaf srlg6 {
            xr:xr-xml-map "optics_controller_cfg:Srlg6";
            type uint32 {
              range "0..4294967294";
            }
            description "none";
          }
        }
      }

      container optics-dwdm-carrier {
        xr:xr-xml-map "optics_controller_cfg:OpticsDWDMCarrier";
        presence "Indicates a optics-dwdm-carrier node is"+
          " configured.";
        description "Configure optics DWDM Carrier";
        leaf grid-type {
          xr:xr-xml-map "optics_controller_cfg:GridType";
          type Optics-dwdm-carrier-grid;
          mandatory true;
          description "DWDM Channel Grid Type";
        }
        leaf param-type {
          xr:xr-xml-map "optics_controller_cfg:ParamType";
          type Optics-dwdm-carrier-param;
          mandatory true;
          description
            "DWDM Channel Parameter Type ITU-Channel or
            Frequency or Wavelength";
        }
        leaf param-value {
          xr:xr-xml-map "optics_controller_cfg:ParamValue";
          type uint32 {
            range "1..1961000";
          }
          mandatory true;
          description
            "Type ITU-Channel Range 1-100, Frequency Range
            19115-19610, Wavelength Range 1528773-1568362,
            100MHz Frequency Range 1911500-1961000";
        }
      }

      container tx-thresholds {
        xr:xr-xml-map "optics_controller_cfg:OpticsTxThreshold";
        description "Configure Tx threshold";

        list tx-threshold {
          xr:xr-xml-map "optics_controller_cfg:TxThreshold";
          key "tx-threshold-type";
          description
            "Optics TX Low or high threshold configuration";
          leaf tx-threshold-type {
            xr:xr-xml-map "optics_controller_cfg:TxThresholdType";
            type Threshold;
            description "Low or high tx threshold";
          }
          leaf tx-threshold {
            xr:xr-xml-map "optics_controller_cfg:TxThreshold";
            type int32 {
              range "-400..300";
            }
            mandatory true;
            description "Select power level (in units of 0.1dBm)";
          }
        }
      }
      leaf optics-transmit-power {
        xr:xr-xml-map "optics_controller_cfg:OpticsTransmitPower";
        type int32 {
          range "-190..15";
        }
        description "Select power level (in units of 0.1dBm)";
      }
      leaf optics-loopback {
        xr:xr-xml-map "optics_controller_cfg:OpticsLoopback";
        type Optics-loopback;
        default "none";
        description "Configure optics loopback mode ";
      }
      leaf optics-fec {
        xr:xr-xml-map "optics_controller_cfg:OpticsFEC";
        type Optics-fec;
        default "fec-none";
        description "Configure optics fec ";
      }
      leaf optics-dgd-high-threshold {
        xr:xr-xml-map "optics_controller_cfg:OpticsDGDHighThreshold";
        type int32 {
          range "0..18000";
        }
        description "Select DGD high threshold(in units of 0.1ps)";
      }
      leaf optics-cd-min {
        xr:xr-xml-map "optics_controller_cfg:OpticsCDMin";
        type int32 {
          range "-70000..70000";
        }
        description
          "Select min chromatic dispersion (in units of
          ps/nm)";
      }
      leaf optics-transmit-shutdown {
        xr:xr-xml-map "optics_controller_cfg:OpticsTransmitShutdown";
        type boolean;
        description "Configure optics transmit laser shutdown ";
      }
      leaf optics-description {
        xr:xr-xml-map "optics_controller_cfg:OpticsDescription";
        type string {
          length "0..255";
        }
        description "Configure optics port description ";
      }
      leaf optics-performance-monitoring {
        xr:xr-xml-map "optics_controller_cfg:OpticsPerformanceMonit"+
          "oring";
        type boolean;
        default "true";
        description
          "Select Performance Monitoring as Enable or
          Disable";
      }
      leaf optics-cd-max {
        xr:xr-xml-map "optics_controller_cfg:OpticsCDMax";
        type int32 {
          range "-70000..70000";
        }
        description
          "Select max chromatic dispersion (in units of
          ps/nm)";
      }
      leaf optics-lbc-high-threshold {
        xr:xr-xml-map "optics_controller_cfg:OpticsLbcHighThreshold";
        type int32 {
          range "0..100";
        }
        description "Select power level (in units of percentage)";
      }
      leaf optics-cd-high-threshold {
        xr:xr-xml-map "optics_controller_cfg:OpticsCDHighThreshold";
        type int32 {
          range "-70000..70000";
        }
        description
          "Select chromatic dispersion high threshold(in
          units of ps/nm)";
      }
      leaf optics-osnr-low-threshold {
        xr:xr-xml-map "optics_controller_cfg:OpticsOSNRLowThreshold";
        type int32 {
          range "0..4000";
        }
        description "Select OSNR low threshold(in units of 0.01db)";
      }
      leaf optics-cd-low-threshold {
        xr:xr-xml-map "optics_controller_cfg:OpticsCDLowThreshold";
        type int32 {
          range "-70000..70000";
        }
        description
          "Select chromatic dispersion low threshold(in
          units of ps/nm)";
      }
    }
    description
      "This augment extends the configuration data of
      'Cisco-IOS-XR-ifmgr-cfg'";
  }
}
