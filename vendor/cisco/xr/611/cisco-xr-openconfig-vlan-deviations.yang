//*************  DO-NOT EDIT  **************
//*********** Auto-generated file ********** 

 module cisco-xr-openconfig-vlan-deviations {

  prefix  "vlandevs";

  namespace "http://cisco.com/ns/yang/cisco-xr-openconfig-vlan-deviations";

  import openconfig-vlan { prefix vlan; }
  import openconfig-interfaces { prefix ocif; }
  import openconfig-if-ethernet { prefix eth; }
  import openconfig-if-aggregate { prefix lag; }

  organization "Cisco Systems, Inc.";

  contact
    "Cisco Systems, Inc.
     Customer Service

     Postal: 170 West Tasman Drive
     San Jose, CA 95134

     Tel: +1 800 553-NETS

     E-mail: cs-yang@cisco.com";

  description
    "This module contains a set of deviations for 
 
     openconfig-vlan.yang@2015-10-09 

     on Cisco IOS-XR devices.

     Copyright (c) 2016 by Cisco Systems, Inc.
     All rights reserved.";

  revision "2016-07-08" {
    description
      "Initial revision applicable to IOS-XR 6.1.1";
  }


  deviation /vlan:vlans/vlan:vlan {
    deviate not-supported;
  }

  deviation /ocif:interfaces/ocif:interface/ocif:subinterfaces/ocif:subinterface/vlan:vlan/vlan:config/vlan:global-vlan-id {
    deviate not-supported;
  }

  deviation /ocif:interfaces/ocif:interface/ocif:subinterfaces/ocif:subinterface/vlan:vlan/vlan:state/vlan:global-vlan-id {
    deviate not-supported;
  }

  deviation /ocif:interfaces/ocif:interface/eth:ethernet/vlan:vlan/vlan:config/vlan:interface-mode {
    deviate not-supported;
  }

  deviation /ocif:interfaces/ocif:interface/eth:ethernet/vlan:vlan/vlan:config/vlan:native-vlan {
    deviate not-supported;
  }

  deviation /ocif:interfaces/ocif:interface/eth:ethernet/vlan:vlan/vlan:config/vlan:access-vlan {
    deviate not-supported;
  }

  deviation /ocif:interfaces/ocif:interface/eth:ethernet/vlan:vlan/vlan:config/vlan:trunk-vlans {
    deviate not-supported;
  }

  deviation /ocif:interfaces/ocif:interface/eth:ethernet/vlan:vlan/vlan:state/vlan:interface-mode {
    deviate not-supported;
  }

  deviation /ocif:interfaces/ocif:interface/eth:ethernet/vlan:vlan/vlan:state/vlan:native-vlan {
    deviate not-supported;
  }

  deviation /ocif:interfaces/ocif:interface/eth:ethernet/vlan:vlan/vlan:state/vlan:access-vlan {
    deviate not-supported;
  }

  deviation /ocif:interfaces/ocif:interface/eth:ethernet/vlan:vlan/vlan:state/vlan:trunk-vlans {
    deviate not-supported;
  }

  deviation /ocif:interfaces/ocif:interface/lag:aggregation/vlan:vlan/vlan:config/vlan:interface-mode {
    deviate not-supported;
  }

  deviation /ocif:interfaces/ocif:interface/lag:aggregation/vlan:vlan/vlan:config/vlan:native-vlan {
    deviate not-supported;
  }

  deviation /ocif:interfaces/ocif:interface/lag:aggregation/vlan:vlan/vlan:config/vlan:access-vlan {
    deviate not-supported;
  }

  deviation /ocif:interfaces/ocif:interface/lag:aggregation/vlan:vlan/vlan:config/vlan:trunk-vlans {
    deviate not-supported;
  }

  deviation /ocif:interfaces/ocif:interface/lag:aggregation/vlan:vlan/vlan:state/vlan:interface-mode {
    deviate not-supported;
  }

  deviation /ocif:interfaces/ocif:interface/lag:aggregation/vlan:vlan/vlan:state/vlan:native-vlan {
    deviate not-supported;
  }

  deviation /ocif:interfaces/ocif:interface/lag:aggregation/vlan:vlan/vlan:state/vlan:access-vlan {
    deviate not-supported;
  }

  deviation /ocif:interfaces/ocif:interface/lag:aggregation/vlan:vlan/vlan:state/vlan:trunk-vlans {
    deviate not-supported;
  }

  deviation /ocif:interfaces/ocif:interface/vlan:routed-vlan/vlan:config/vlan:vlan {
    deviate not-supported;
  }

  deviation /ocif:interfaces/ocif:interface/vlan:routed-vlan/vlan:state/vlan:vlan {
    deviate not-supported;
  }


}
//total deviations:21
