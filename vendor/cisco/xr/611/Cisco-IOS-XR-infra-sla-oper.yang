module Cisco-IOS-XR-infra-sla-oper {

  /*** NAMESPACE / PREFIX DEFINITION ***/

  namespace "http://cisco.com/ns/yang/Cisco-IOS-XR-infra-sla-oper";


  prefix "infra-sla-oper";

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR infra-sla package operational data.

     This module contains definitions
     for the following management objects:
       sla: SLA oper commands
       sla-nodes: sla nodes

     Copyright (c) 2013-2016 by Cisco Systems, Inc.
     All rights reserved.";

  revision "2015-11-09" {
    description
      "IOS XR 6.0 revision.";
  }


  container sla {
    xr:xr-xml-map "infra_sla_oper:SLA";
    config false;
    description "SLA oper commands";

    container protocols {
      xr:xr-xml-map "infra_sla_oper:Protocols";
      description "Table of all SLA protocols";
    }
  }

  container sla-nodes {
    xr:xr-xml-map "infra_sla_oper:SLANodeTable";
    config false;
    description "sla nodes";
  }
}
