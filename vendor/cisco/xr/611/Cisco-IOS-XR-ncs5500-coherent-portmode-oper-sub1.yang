submodule Cisco-IOS-XR-ncs5500-coherent-portmode-oper-sub1 {

  belongs-to Cisco-IOS-XR-ncs5500-coherent-portmode-oper {
    prefix Cisco-IOS-XR-ncs5500-coherent-portmode-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR ncs5500-coherent-portmode package operational data.

     Copyright (c) 2013-2016 by Cisco Systems, Inc.
     All rights reserved.";

  revision "2015-11-09" {
    description
      "IOS XR 6.0 revision.";
  }


  grouping PORTMODE-INFO {
    description "portmode entry of optics controller";
    leaf intf-name {
      xr:xr-xml-map "coherent:INTF_NAME";
      type string;
      description "Interface Name";
    }
    leaf speed {
      xr:xr-xml-map "coherent:SPEED";
      type string;
      description "Optics speed";
    }
    leaf fec {
      xr:xr-xml-map "coherent:FEC";
      type string;
      description "Optics fec";
    }
    leaf diff {
      xr:xr-xml-map "coherent:DIFF";
      type string;
      description "Optics diff";
    }
    leaf modulation {
      xr:xr-xml-map "coherent:MODULATION";
      type string;
      description "Optics modulation";
    }
  }
}
