module Cisco-IOS-XR-installmgr-admin-oper {

  /*** NAMESPACE / PREFIX DEFINITION ***/

  namespace "http://cisco.com/ns/yang"+
    "/Cisco-IOS-XR-installmgr-admin-oper";


  prefix "installmgr-admin-oper";

  /*** LINKAGE (IMPORTS / INCLUDES) ***/

  import Cisco-IOS-XR-types { prefix "xr"; }

  include Cisco-IOS-XR-installmgr-admin-oper-sub3 {
    revision-date 2015-11-09;
  }

  include Cisco-IOS-XR-installmgr-admin-oper-sub2 {
    revision-date 2015-11-09;
  }

  include Cisco-IOS-XR-installmgr-admin-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR installmgr package
     admin-plane operational data.

     This module contains definitions
     for the following management objects:
       install: Information of software packages and install
         operations

     Copyright (c) 2013-2016 by Cisco Systems, Inc.
     All rights reserved.";

  revision "2015-11-09" {
    description
      "IOS XR 6.0 revision.";
  }

  typedef Ism-card-type-family {
    type enumeration {
      enum ndsc-active-rp {
        value 1;
        description "Active NDSC RPs";
      }
      enum ndsc-standby-rp {
        value 2;
        description "Standby NDSC RPs";
      }
      enum active-drp {
        value 3;
        description "Active DRP";
      }
      enum standby-drp {
        value 4;
        description "Standby DRP";
      }
      enum dsc-active-rp {
        value 5;
        description "Active dSC";
      }
      enum dsc-standby-rp {
        value 6;
        description "Standby dSC";
      }
      enum active-sc {
        value 7;
        description "Active non-root SC";
      }
      enum standby-sc {
        value 8;
        description "Standby non-root SC";
      }
      enum root-active-sc {
        value 9;
        description "Active root SC";
      }
      enum root-standby-sc {
        value 10;
        description "Standby root SC";
      }
      enum lc {
        value 11;
        description "Line card";
      }
      enum sp {
        value 12;
        description "Non-Fabric SP";
      }
      enum fabric-sp {
        value 13;
        description "Fabric SP";
      }
      enum spa {
        value 14;
        description "SPA";
      }
    }
    description "Ism card type family";
  }

  grouping INVENTORY-TABLE {
    description
      "Common node of active, active, inactive, inactive
      , committed, committed";

    container inventories {
      xr:xr-xml-map "installmgr_common:InventoryTable";
      description "Software inventory";

      list inventory {
        xr:xr-xml-map "installmgr_common:Inventory";
        key "node-name";
        description "Inventory information for specific node";
        leaf node-name {
          xr:xr-xml-map "installmgr_common:NodeName";
          type xr:Node-id;
          description "Node name";
        }
        uses INVENTORY;
      }
    }
  }

  grouping SUMMARY {
    description "Common node of active, inactive, committed";

    container summary {
      xr:xr-xml-map "installmgr_common:Summary";
      description "Summarized inventory information";
      uses INSTALL-INVENTORY-SUMMARY;
    }
  }

  container install {
    xr:xr-xml-map "installmgr_adminoper:Install";
    config false;
    description
      "Information of software packages and install
      operations";

    container configuration-registers {
      xr:xr-xml-map "installmgr_adminoper:ConfigurationRegisterTabl"+
        "e";
      description "Configuration register (confreg) information";

      list configuration-register {
        xr:xr-xml-map "installmgr_adminoper:ConfigurationRegister";
        key "node-name";
        description "Configuration register for specific node";
        leaf node-name {
          xr:xr-xml-map "installmgr_adminoper:NodeName";
          type xr:Node-id;
          description "Node name";
        }
        leaf config-register {
          xr:xr-xml-map "installmgr_adminoper:ConfigRegister";
          type xr:Hex-integer;
          mandatory true;
          description "Configuration register value";
        }
      }
    }

    container request-statuses {
      xr:xr-xml-map "installmgr_adminoper:RequestStatusTable";
      description "Install operation request status";

      list request-status {
        xr:xr-xml-map "installmgr_adminoper:RequestStatus";
        key "request-id";
        description "Request status Information";
        leaf request-id {
          xr:xr-xml-map "installmgr_adminoper:RequestID";
          type int32;
          description "Install operation request ID";
        }
        uses INSTMGR-INSTALL-STATUS;
      }
    }

    container boot-variables {
      xr:xr-xml-map "installmgr_adminoper:BootVariableTable";
      description "Boot variable information";

      list boot-variable {
        xr:xr-xml-map "installmgr_adminoper:BootVariable";
        key "node-name";
        description "Boot variable for specific node";
        leaf node-name {
          xr:xr-xml-map "installmgr_adminoper:NodeName";
          type xr:Node-id;
          description "Node name";
        }
        leaf boot-variable {
          xr:xr-xml-map "installmgr_adminoper:BootVariable";
          type string;
          mandatory true;
          description "Boot variable value";
        }
      }
    }

    container software {
      xr:xr-xml-map "installmgr_adminoper:Software";
      description
        "Software package,component and alias information";

      container alias-devices {
        xr:xr-xml-map "installmgr_adminoper:AliasDeviceTable";
        description "Package alias information";

        list alias-device {
          xr:xr-xml-map "installmgr_adminoper:AliasDevice";
          key "device-name";
          description
            "Package alias information for specific device";

          container aliases {
            xr:xr-xml-map "installmgr_adminoper:AliasTable";
            description "alias information";

            list alias {
              xr:xr-xml-map "installmgr_adminoper:Alias";
              key "package-name";
              description "Aliases for specific package";
              leaf package-name {
                xr:xr-xml-map "installmgr_adminoper:PackageName";
                type string;
                description "Package Name";
              }
              leaf alias-names {
                xr:xr-xml-map "installmgr_adminoper:AliasNames";
                type string;
                mandatory true;
                description "Alias names";
              }
            }
          }
          leaf device-name {
            xr:xr-xml-map "installmgr_adminoper:DeviceName";
            type xr:Cisco-ios-xr-string;
            description "Device Name";
          }
        }
      }

      container package-devices {
        xr:xr-xml-map "installmgr_adminoper:PackageDeviceTable";
        description "Package information";

        list package-device {
          xr:xr-xml-map "installmgr_adminoper:PackageDevice";
          key "device-name";
          description "Package information for specific device";

          container packages {
            xr:xr-xml-map "installmgr_adminoper:PackageTable";
            description "Package information for specific package";

            list package {
              xr:xr-xml-map "installmgr_adminoper:Package";
              key "package-name";
              description "Package information";
              leaf package-name {
                xr:xr-xml-map "installmgr_adminoper:PackageName";
                type string;
                description "Package Name";
              }
              uses INSTMGR-PKG-INFO;
            }
          }
          leaf device-name {
            xr:xr-xml-map "installmgr_adminoper:DeviceName";
            type xr:Cisco-ios-xr-string;
            description "Device Name";
          }
        }
      }

      container component-devices {
        xr:xr-xml-map "installmgr_adminoper:ComponentDeviceTable";
        description "Software component information";

        list component-device {
          xr:xr-xml-map "installmgr_adminoper:ComponentDevice";
          key "device-name";
          description "Component information for specific device";

          container component-packages {
            xr:xr-xml-map "installmgr_adminoper:ComponentPackageTab"+
              "le";
            description "Software package information";

            list component-package {
              xr:xr-xml-map "installmgr_adminoper:ComponentPackage";
              key "package-name";
              description
                "Component information for specific package";
              leaf package-name {
                xr:xr-xml-map "installmgr_adminoper:PackageName";
                type string;
                description "Package Name";
              }

              list component {
                xr:xr-xml-map "installmgr_adminoper:Component";
                key "component-name";
                description "Component information";
                leaf component-name {
                  xr:xr-xml-map "installmgr_adminoper:ComponentName";
                  type string;
                  description "Component Name";
                }
                uses INSTMGR-COMPONENT-INFO;
              }
            }
          }
          leaf device-name {
            xr:xr-xml-map "installmgr_adminoper:DeviceName";
            type xr:Cisco-ios-xr-string;
            description "Device Name";
          }
        }
      }
    }

    container software-inventory {
      xr:xr-xml-map "installmgr_adminoper:SoftwareInventory";
      description "Information of install operations";

      container committed {
        xr:xr-xml-map "installmgr_adminoper:Committed";
        description "Committed inventory information";
        uses SUMMARY;
        uses INVENTORY-TABLE;
      }

      container inactive {
        xr:xr-xml-map "installmgr_adminoper:Inactive";
        description "Inactive inventory information";
        uses SUMMARY;
        uses INVENTORY-TABLE;
      }

      container requests {
        xr:xr-xml-map "installmgr_adminoper:Requests";
        description "Install operation requests";

        container requests {
          xr:xr-xml-map "installmgr_adminoper:RequestTable";
          description "Install operation request history";

          list request {
            xr:xr-xml-map "installmgr_adminoper:Request";
            key "request-id";
            description "Install operation request information";

            container inventories {
              xr:xr-xml-map "installmgr_adminoper:InventoryTable";
              description
                "Inventory information of install operation
                request";

              list inventory {
                xr:xr-xml-map "installmgr_adminoper:Inventory";
                key "node-name";
                description "Inventory information";
                leaf node-name {
                  xr:xr-xml-map "installmgr_adminoper:NodeName";
                  type xr:Node-id;
                  description "Node name";
                }
                uses INVENTORY;
              }
            }
            leaf request-id {
              xr:xr-xml-map "installmgr_adminoper:RequestID";
              type int32;
              description "Install operation request ID";
            }
          }
        }
      }

      container active {
        xr:xr-xml-map "installmgr_adminoper:Active";
        description "Active inventory information";
        uses SUMMARY;
        uses INVENTORY-TABLE;
      }
    }

    container issu {
      xr:xr-xml-map "installmgr_adminoper:ISSU";
      description "Information of install ISSU operations";

      container card-inventories {
        xr:xr-xml-map "installmgr_adminoper:CardInventoryTable";
        description "ISSU manager card inventory table";

        list card-inventory {
          xr:xr-xml-map "installmgr_adminoper:CardInventory";
          key "card-type-id";
          description
            "ISSU manager inventory summary of the same
            card type";
          leaf card-type-id {
            xr:xr-xml-map "installmgr_adminoper:CardTypeID";
            type Ism-card-type-family;
            description "ISSU manager card type ID";
          }
          uses ISM-CARD-INVENTORY-SUMMARY;
        }
      }

      container stage {
        xr:xr-xml-map "installmgr_adminoper:Stage";
        description "Summarized ISSU stage information";
        uses INSTALL-ISSU-STAGE;
      }
    }

    container boot-image {
      xr:xr-xml-map "installmgr_adminoper:BootImage";
      description "System Boot Image";
      uses BOOT-IMG;
    }

    container logs {
      xr:xr-xml-map "installmgr_adminoper:LogTable";
      description "Install operation log";

      list log {
        xr:xr-xml-map "installmgr_adminoper:Log";
        key "request-id";
        description "Log information";
        leaf request-id {
          xr:xr-xml-map "installmgr_adminoper:RequestID";
          type int32;
          description "Install operation request ID";
        }
        uses INSTALL-LOG-ENTRY-4;
      }
    }
    leaf log-size {
      xr:xr-xml-map "installmgr_adminoper:LogSize";
      type int32;
      description "Install operation log history size";
    }
  }
}
