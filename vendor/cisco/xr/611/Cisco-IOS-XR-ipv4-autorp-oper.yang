module Cisco-IOS-XR-ipv4-autorp-oper {

  /*** NAMESPACE / PREFIX DEFINITION ***/

  namespace "http://cisco.com/ns/yang/Cisco-IOS-XR-ipv4-autorp-oper";


  prefix "ipv4-autorp-oper";

  /*** LINKAGE (IMPORTS / INCLUDES) ***/

  import ietf-inet-types { prefix "inet"; }

  import Cisco-IOS-XR-types { prefix "xr"; }

  import Cisco-IOS-XR-ipv4-autorp-datatypes { prefix "dt1"; }

  include Cisco-IOS-XR-ipv4-autorp-oper-sub2 {
    revision-date 2015-11-09;
  }

  include Cisco-IOS-XR-ipv4-autorp-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ipv4-autorp package operational data.

     This module contains definitions
     for the following management objects:
       auto-rp: AutoRP operational data

     Copyright (c) 2013-2016 by Cisco Systems, Inc.
     All rights reserved.";

  revision "2015-11-09" {
    description
      "IOS XR 6.0 revision.";
  }


  grouping MAPPING-AGENT {
    description "Common node of active, standby";

    container mapping-agent {
      xr:xr-xml-map "ipv4_autorp_role_lvl_oper:MappingAgent";
      description "AutoRP Mapping Agent Table";

      container rp-addresses {
        xr:xr-xml-map "ipv4_autorp_common_oper:RPAddressTable";
        description "AutoRP Mapping Agent Table Entries";

        list rp-address {
          xr:xr-xml-map "ipv4_autorp_common_oper:RPAddress";
          key "rp-address";
          description "AutoRP Mapping Agent Entry";
          leaf rp-address {
            xr:xr-xml-map "ipv4_autorp_common_oper:RPAddress";
            type inet:ipv4-address-no-zone;
            description "RP Address";
          }
          uses AUTORP-MAP-RP-BAG;
        }
      }

      container summary {
        xr:xr-xml-map "ipv4_autorp_common_oper:Summary";
        description "AutoRP Mapping Agent Summary Information";
        uses AUTORP-MAP-SUMMARY-BAG;
      }
    }
  }

  grouping CANDIDATE-RP-TABLE {
    description "Common node of active, standby";

    container candidate-rps {
      xr:xr-xml-map "ipv4_autorp_role_lvl_oper:CandidateRPTable";
      description "AutoRP Candidate RP Table";

      list candidate-rp {
        xr:xr-xml-map "ipv4_autorp_common_oper:CandidateRP";
        description "AutoRP Candidate RP Entry";
        leaf interface-name {
          xr:xr-xml-map "ipv4_autorp_common_oper:InterfaceName";
          type xr:Interface-name;
          description "Interface Name";
        }
        leaf protocol-mode {
          xr:xr-xml-map "ipv4_autorp_common_oper:ProtocolMode";
          type dt1:Auto-rp-protocol-mode;
          description "Protocol Mode";
        }
        uses AUTORP-CRP-BAG;
      }
    }
  }

  container auto-rp {
    xr:xr-xml-map "ipv4_multicast_autorp_oper:AutoRP";
    config false;
    description "AutoRP operational data";

    container standby {
      xr:xr-xml-map "ipv4_autorp_role_lvl_oper:Standby";
      description "Standby Process";
      uses CANDIDATE-RP-TABLE;
      uses MAPPING-AGENT;
    }

    container active {
      xr:xr-xml-map "ipv4_autorp_role_lvl_oper:Active";
      description "Active Process";
      uses CANDIDATE-RP-TABLE;
      uses MAPPING-AGENT;
    }
  }
}
