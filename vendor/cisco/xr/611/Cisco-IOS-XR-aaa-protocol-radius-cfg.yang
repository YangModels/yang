module Cisco-IOS-XR-aaa-protocol-radius-cfg {

  /*** NAMESPACE / PREFIX DEFINITION ***/

  namespace "http://cisco.com/ns/yang"+
    "/Cisco-IOS-XR-aaa-protocol-radius-cfg";


  prefix "aaa-protocol-radius-cfg";

  /*** LINKAGE (IMPORTS / INCLUDES) ***/

  import ietf-inet-types { prefix "inet"; }

  import Cisco-IOS-XR-types { prefix "xr"; }

  import Cisco-IOS-XR-aaa-locald-cfg { prefix "a1"; }

  import Cisco-IOS-XR-aaa-lib-cfg { prefix "a2"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR aaa-protocol-radius package configuration.

     This YANG module augments the
       Cisco-IOS-XR-aaa-locald-cfg,
       Cisco-IOS-XR-aaa-lib-cfg
     modules with configuration data.

     Copyright (c) 2013-2016 by Cisco Systems, Inc.
     All rights reserved.";

  revision "2015-11-09" {
    description
      "IOS XR 6.0 revision.";
  }

  typedef Aaa-radius-timeout {
    type uint32 {
      range "1..1000";
    }
    description "Aaa radius timeout";
  }
  typedef Aaa-dscp-value {
    type union {
      type enumeration {
        enum af11 {
          value 10;
          description "Match packets with AF11 DSCP";
        }
        enum af12 {
          value 12;
          description "Match packets with AF12 DSCP";
        }
        enum af13 {
          value 14;
          description "Match packets with AF13 DSCP";
        }
        enum af21 {
          value 18;
          description "Match packets with AF21 DSCP";
        }
        enum af22 {
          value 20;
          description "Match packets with AF22 DSCP";
        }
        enum af23 {
          value 22;
          description "Match packets with AF23 DSCP";
        }
        enum af31 {
          value 26;
          description "Match packets with AF31 DSCP";
        }
        enum af32 {
          value 28;
          description "Match packets with AF32 DSCP";
        }
        enum af33 {
          value 30;
          description "Match packets with AF33 DSCP";
        }
        enum af41 {
          value 34;
          description "Match packets with AF41 DSCP";
        }
        enum af42 {
          value 36;
          description "Match packets with AF42 DSCP";
        }
        enum af43 {
          value 38;
          description "Match packets with AF43 DSCP";
        }
        enum cs1 {
          value 8;
          description "Match packets with CS1 DSCP";
        }
        enum cs2 {
          value 16;
          description "Match packets with CS2 DSCP";
        }
        enum cs3 {
          value 24;
          description "Match packets with CS3 DSCP";
        }
        enum cs4 {
          value 32;
          description "Match packets with CS4 DSCP";
        }
        enum cs5 {
          value 40;
          description "Match packets with CS5 DSCP";
        }
        enum cs6 {
          value 48;
          description "Match packets with CS6 DSCP";
        }
        enum cs7 {
          value 56;
          description "Match packets with CS7 DSCP";
        }
        enum default {
          value 0;
          description "Match packets with 0000 DSCP";
        }
        enum ef {
          value 46;
          description "Match packets with EF DSCP";
        }
      }
      type uint32 {
        range "0..63";
      }
    }
    description "Aaa dscp value";
  }
  typedef Aaa-action {
    type enumeration {
      enum accept {
        value 1;
        description "Accept";
      }
      enum reject {
        value 2;
        description "Reject";
      }
    }
    description "Aaa action";
  }
  typedef Aaa-authentication {
    type enumeration {
      enum all {
        value 101;
        description "All";
      }
      enum any {
        value 102;
        description "Any";
      }
      enum session-key {
        value 103;
        description "Session key";
      }
    }
    description "Aaa authentication";
  }
  typedef Aaa-select-key {
    type enumeration {
      enum server-key {
        value 1;
        description "Server key";
      }
      enum session-key {
        value 2;
        description "Session  key";
      }
    }
    description "Aaa select key";
  }
  typedef Aaa-throttle-access-timeout {
    type uint32 {
      range "1..10";
    }
    description "Aaa throttle access timeout";
  }
  typedef Aaa-radius-dead-detect-tries {
    type uint32 {
      range "1..100";
    }
    description "Aaa radius dead detect tries";
  }
  typedef Aaa-radius-dead-time {
    type uint32 {
      range "1..1440";
    }
    description "Aaa radius dead time";
  }
  typedef Aaa-throttle-accounting {
    type uint32 {
      range "0..65535";
    }
    description "Aaa throttle accounting";
  }
  typedef Aaa-radius-idle-time {
    type uint32 {
      range "1..60";
    }
    description "Aaa radius idle time";
  }
  typedef Aaa-radius-dead-detect-time {
    type uint32 {
      range "1..120";
    }
    description "Aaa radius dead detect time";
  }
  typedef Aaa-radius-retransmit {
    type uint32 {
      range "1..100";
    }
    description "Aaa radius retransmit";
  }
  typedef Aaa-throttle-access {
    type uint32 {
      range "0..65535";
    }
    description "Aaa throttle access";
  }
  typedef Aaa-config {
    type enumeration {
      enum false {
        value 0;
        description "False";
      }
      enum true {
        value 1;
        description "True";
      }
    }
    description "Aaa config";
  }

  grouping IGNORE-ACCOUNTING-PORT {
    description "Common node of radius, host";
    leaf ignore-accounting-port {
      xr:xr-xml-map "aaa_radius_cfg:IgnoreAccountingPort";
      type boolean;
      description "Time to wait for a RADIUS server to reply";
    }
  }

  grouping IDLE-TIME {
    description "Common node of radius, host";
    leaf idle-time {
      xr:xr-xml-map "aaa_radius_cfg:IdleTime";
      type Aaa-radius-timeout;
      default "5";
      description "Idle time for RADIUS server";
    }
  }

  grouping USERNAME {
    description "Common node of radius, host";
    leaf username {
      xr:xr-xml-map "aaa_radius_cfg:Username";
      type string;
      description "Username to be tested for automated testing";
    }
  }

  grouping REPLY {
    description "Common node of authorization, accounting";

    container reply {
      xr:xr-xml-map "aaa_radius_attr_cfg:Reply";
      description "Specify a filter in server group";
      leaf action {
        xr:xr-xml-map "aaa_radius_attr_cfg:Action";
        type Aaa-action;
        description
          "Specify the attribute list type accept or
          reject";
      }
      leaf attribute-list-name {
        xr:xr-xml-map "aaa_radius_attr_cfg:AttributeListName";
        type string;
        description "Name of RADIUS attribute list";
      }
    }
  }

  grouping DSCP {
    description "Common node of ipv4, ipv6";
    leaf dscp {
      xr:xr-xml-map "aaa_radius_attr_cfg:DSCP";
      type Aaa-dscp-value;
      description "Specify the DSCP value";
    }
  }

  grouping SERVER-KEY {
    description "Common node of client, dynamic-authorization";
    leaf server-key {
      xr:xr-xml-map "aaa_radius_dyn_auth_cfg:ServerKey";
      type xr:Proprietary-password;
      description "RADIUS CoA client encryption key";
    }
  }

  grouping IGNORE-AUTH-PORT {
    description "Common node of radius, host";
    leaf ignore-auth-port {
      xr:xr-xml-map "aaa_radius_cfg:IgnoreAuthPort";
      type boolean;
      description "Time to wait for a RADIUS server to reply";
    }
  }

  grouping REQUEST {
    description "Common node of authorization, accounting";

    container request {
      xr:xr-xml-map "aaa_radius_attr_cfg:Request";
      description "Specify a filter in server group";
      leaf action {
        xr:xr-xml-map "aaa_radius_attr_cfg:Action";
        type Aaa-action;
        description
          "Specify the attribute list type accept or
          reject";
      }
      leaf attribute-list-name {
        xr:xr-xml-map "aaa_radius_attr_cfg:AttributeListName";
        type string;
        description "Name of RADIUS attribute list";
      }
    }
  }

  augment "/a2:aaa" {

    container radius {
      xr:xr-xml-map "aaa_radius_cfg:RADIUS";
      description "Remote Access Dial-In User Service";

      container hosts {
        xr:xr-xml-map "aaa_radius_cfg:HostTable";
        description "List of RADIUS servers";

        list host {
          xr:xr-xml-map "aaa_radius_cfg:Host";
          key "ordering-index ip-address auth-port-number"+
            " acct-port-number";
          description "Instance of a RADIUS server";
          leaf host-retransmit {
            xr:xr-xml-map "aaa_radius_cfg:HostRetransmit";
            type Aaa-radius-retransmit;
            default "3";
            description
              "Number of times to retransmit a request to
              the RADIUS server";
          }
          leaf host-timeout {
            xr:xr-xml-map "aaa_radius_cfg:HostTimeout";
            type Aaa-radius-timeout;
            default "5";
            description "Time to wait for a RADIUS server to reply";
          }
          leaf host-key {
            xr:xr-xml-map "aaa_radius_cfg:HostKey";
            type xr:Proprietary-password;
            description "RADIUS encryption key";
          }
          leaf ordering-index {
            xr:xr-xml-map "aaa_radius_cfg:OrderingIndex";
            type int32;
            description
              "This is used to sort the servers in the order
              of precedence";
          }
          leaf ip-address {
            xr:xr-xml-map "aaa_radius_cfg:IPAddress";
            type inet:ip-address-no-zone;
            description "IP address of RADIUS server";
          }
          leaf auth-port-number {
            xr:xr-xml-map "aaa_radius_cfg:AuthPortNumber";
            type inet:port-number;
            description
              "Authentication Port number (standard port
              1645)";
          }
          leaf acct-port-number {
            xr:xr-xml-map "aaa_radius_cfg:AcctPortNumber";
            type inet:port-number;
            description
              "Accounting Port number (standard port 1646)";
          }
          uses IGNORE-ACCOUNTING-PORT;
          uses IDLE-TIME;
          uses USERNAME;
          uses IGNORE-AUTH-PORT;
        }
      }

      container dead-criteria {
        xr:xr-xml-map "aaa_radius_cfg:DeadCriteria";
        description "RADIUS server dead criteria";
        leaf tries {
          xr:xr-xml-map "aaa_radius_cfg:Tries";
          type Aaa-radius-dead-detect-tries;
          description
            "The number of consecutive timeouts the router
            must experience in order to mark the server as
            dead. All transmissions, including the initial
            transmit and all retransmits, will be counted";
        }
        leaf time {
          xr:xr-xml-map "aaa_radius_cfg:Time";
          type Aaa-radius-dead-detect-time;
          description
            "The minimum amount of time which must elapse
            since the router last received a valid RADIUS
            packet from the server prior to marking it
            dead";
        }
      }

      container disallow {
        xr:xr-xml-map "aaa_radius_cfg:Disallow";
        description "disallow null-username";
        leaf null-username {
          xr:xr-xml-map "aaa_radius_cfg:NullUsername";
          type int32;
          description "Disallow null-username";
        }
      }

      container ipv6 {
        xr:xr-xml-map "aaa_radius_attr_cfg:IPv6";
        description "IPv6 configuration";
        uses DSCP;
      }

      container dynamic-authorization {
        xr:xr-xml-map "aaa_radius_dyn_auth_cfg:DynamicAuthorization";
        description "RADIUS dynamic authorization";

        container clients {
          xr:xr-xml-map "aaa_radius_dyn_auth_cfg:ClientTable";

          grouping CLIENT-CONTENT {
            description "CLIENT CONTENT";
            uses SERVER-KEY;
          }

          list client {
            key "ip-address";
            description "Client data";
            leaf ip-address {
              xr:xr-xml-map "aaa_radius_dyn_auth_cfg:IPAddress";
              type inet:ip-address-no-zone;
              description "IP address of COA client";
            }
            uses CLIENT-CONTENT;
          }

          list client-vrf-name {
            key "vrf-name ip-address";
            description "Client data";
            leaf vrf-name {
              xr:xr-xml-map "aaa_radius_dyn_auth_cfg:VRFName";
              type xr:Cisco-ios-xr-string;
              description "VRF name";
            }
            leaf ip-address {
              xr:xr-xml-map "aaa_radius_dyn_auth_cfg:IPAddress";
              type inet:ip-address-no-zone;
              description "IP address of COA client";
            }
            uses CLIENT-CONTENT;
          }
          description "Client data";
        }
        leaf ignore {
          xr:xr-xml-map "aaa_radius_dyn_auth_cfg:Ignore";
          type Aaa-select-key;
          description "Ignore option for server key or session key";
        }
        leaf port {
          xr:xr-xml-map "aaa_radius_dyn_auth_cfg:Port";
          type uint32 {
            range "1000..5000";
          }
          description "Specify the COA server port to listen on";
        }
        leaf authentication-type {
          xr:xr-xml-map "aaa_radius_dyn_auth_cfg:AuthenticationType";
          type Aaa-authentication;
          description "RADIUS  dynamic  authorization  type";
        }
        uses SERVER-KEY;
      }

      container load-balance-options {
        xr:xr-xml-map "aaa_radius_cfg:LoadBalanceOptions";
        description "Radius load-balancing options";

        container load-balance-method {
          xr:xr-xml-map "aaa_radius_cfg:LoadBalanceMethod";
          description
            "Method by which the next host will be picked";

          container batch-size {
            xr:xr-xml-map "aaa_radius_cfg:BatchSize";
            description "Batch size for selection of the server";
            leaf batch-size {
              xr:xr-xml-map "aaa_radius_cfg:BatchSize";
              type uint32 {
                range "1..1500";
              }
              default "25";
              description "Batch size for selection of the server";
            }
            leaf ignore-preferred-server {
              xr:xr-xml-map "aaa_radius_cfg:IgnorePreferredServer";
              type int32;
              default "1";
              description
                "Disable preferred server for this Server
                Group";
            }
          }
        }
      }

      container vrfs {
        xr:xr-xml-map "aaa_radius_cfg:VRFTable";
        description "List of VRFs";

        list vrf {
          xr:xr-xml-map "aaa_radius_cfg:VRF";
          key "vrf-name";
          description "A VRF";
          leaf source-interface {
            xr:xr-xml-map "aaa_radius_cfg:SourceInterface";
            type xr:Interface-name;
            description
              "Specify interface for source address in
              RADIUS packets";
          }
          leaf vrf-name {
            xr:xr-xml-map "aaa_radius_cfg:VRFName";
            type xr:Cisco-ios-xr-string;
            description
              "VRF name. Specify 'default' for defalut VRF";
          }
        }
      }

      container throttle {
        xr:xr-xml-map "aaa_radius_cfg:Throttle";
        description "Radius throttling options";
        leaf access {
          xr:xr-xml-map "aaa_radius_cfg:Access";
          type Aaa-throttle-access;
          default "0";
          description
            "To flow control the number of access requests
            sent to a radius server";
        }
        leaf access-timeout {
          xr:xr-xml-map "aaa_radius_cfg:AccessTimeout";
          type Aaa-throttle-access-timeout;
          default "3";
          description
            "Specify the number of timeouts exceeding which
            a throttled access request is dropped";
        }
        leaf accounting {
          xr:xr-xml-map "aaa_radius_cfg:Accounting";
          type Aaa-throttle-accounting;
          default "0";
          description
            "To flow control the number of accounting
            requests sent to a radius server";
        }
      }

      container vsa {
        xr:xr-xml-map "aaa_radius_cfg:VSA";
        description
          "Unknown VSA (Vendor Specific Attribute) ignore
          configuration for RADIUS server";

        container attribute {
          xr:xr-xml-map "aaa_radius_cfg:Attribute";
          description "Vendor Specific Attribute";

          container ignore {
            xr:xr-xml-map "aaa_radius_cfg:Ignore";
            description "Ignore the VSA";
            leaf unknown {
              xr:xr-xml-map "aaa_radius_cfg:Unknown";
              type empty;
              description
                "Ignore the VSA and no prefix will reject the
                unknown VSA";
            }
          }
        }
      }

      container ipv4 {
        xr:xr-xml-map "aaa_radius_attr_cfg:IPv4";
        description "IPv4 configuration";
        uses DSCP;
      }

      container radius-attribute {
        xr:xr-xml-map "aaa_radius_attr_cfg:RADIUSAttribute";
        description "attribute";

        container acct-multi-session-id {
          xr:xr-xml-map "aaa_radius_attr_cfg:AcctMultiSessionId";
          description "Acct-Session-Id attribute(44)";

          container include-parent-session-id {
            xr:xr-xml-map "aaa_radius_attr_cfg:IncludeParentSession"+
              "Id";
            description
              "Prepend Acct-Session-Id attribute with
              Nas-Port-Id";
            leaf config {
              xr:xr-xml-map "aaa_radius_attr_cfg:Config";
              type Aaa-config;
              description "false/true";
            }
          }
        }

        container acct-session-id {
          xr:xr-xml-map "aaa_radius_attr_cfg:AcctSessionId";
          description "Acct-Session-Id attribute(44)";

          container prepend-nas-port-id {
            xr:xr-xml-map "aaa_radius_attr_cfg:PrependNASPortId";
            description
              "Prepend Acct-Session-Id attribute with
              Nas-Port-Id";
            leaf config {
              xr:xr-xml-map "aaa_radius_attr_cfg:Config";
              type Aaa-config;
              description "false/true";
            }
          }
        }
      }

      container attributes {
        xr:xr-xml-map "aaa_radius_attr_cfg:AttributeListTable";
        description "Table of attribute list";

        list attribute {
          xr:xr-xml-map "aaa_radius_attr_cfg:AttributeList";
          key "attribute-list-name";
          description "Attribute list name";
          leaf attribute {
            xr:xr-xml-map "aaa_radius_attr_cfg:Attribute";
            type string;
            description "Specify RADIUS attribute";
          }
          leaf attribute-list-name {
            xr:xr-xml-map "aaa_radius_attr_cfg:AttributeListName";
            type xr:Cisco-ios-xr-string;
            description "Attribute list name";
          }
        }
      }

      container source-port {
        xr:xr-xml-map "aaa_radius_attr_cfg:SourcePort";
        description "Source port";
        leaf extended {
          xr:xr-xml-map "aaa_radius_attr_cfg:Extended";
          type empty;
          description "Enable source-port extend ";
        }
      }
      leaf retransmit {
        xr:xr-xml-map "aaa_radius_cfg:Retransmit";
        type Aaa-radius-retransmit;
        default "3";
        description
          "Number of times to retransmit a request to the
          RADIUS server";
      }
      leaf dead-time {
        xr:xr-xml-map "aaa_radius_cfg:DeadTime";
        type Aaa-radius-dead-time;
        units "minute";
        description
          "This indicates the length of time (in minutes)
          for which a RADIUS server remains marked as
          dead";
      }
      leaf key {
        xr:xr-xml-map "aaa_radius_cfg:Key";
        type xr:Proprietary-password;
        description "RADIUS encryption key";
      }
      leaf timeout {
        xr:xr-xml-map "aaa_radius_cfg:Timeout";
        type Aaa-radius-timeout;
        default "5";
        description "Time to wait for a RADIUS server to reply";
      }
      uses IGNORE-ACCOUNTING-PORT;
      uses IDLE-TIME;
      uses USERNAME;
      uses IGNORE-AUTH-PORT;
    }
    description
      "This augment extends the configuration data of
      'Cisco-IOS-XR-aaa-lib-cfg'";
  }

  augment "/a2:aaa/a1:server-groups" {

    container radius-server-groups {
      xr:xr-xml-map "aaa_radius_cfg:RADIUSServerGroupTable";
      description "RADIUS server group definition";

      list radius-server-group {
        xr:xr-xml-map "aaa_radius_cfg:RADIUSServerGroup";
        key "server-group-name";
        description "RADIUS server group name";

        container accounting {
          xr:xr-xml-map "aaa_radius_attr_cfg:Accounting";
          description "List of filters in server group";
          uses REQUEST;
          uses REPLY;
        }

        container servers {
          xr:xr-xml-map "aaa_radius_cfg:ServerTable";
          description "List of RADIUS servers present in the group";

          list server {
            xr:xr-xml-map "aaa_radius_cfg:Server";
            key "ordering-index ip-address auth-port-number"+
              " acct-port-number";
            description "A server to include in the server group";
            leaf ordering-index {
              xr:xr-xml-map "aaa_radius_cfg:OrderingIndex";
              type int32;
              description
                "This is used to sort the servers in the
                order of precedence";
            }
            leaf ip-address {
              xr:xr-xml-map "aaa_radius_cfg:IPAddress";
              type inet:ip-address-no-zone;
              description "IP address of RADIUS server";
            }
            leaf auth-port-number {
              xr:xr-xml-map "aaa_radius_cfg:AuthPortNumber";
              type inet:port-number;
              description
                "Authentication Port number (standard port
                1645)";
            }
            leaf acct-port-number {
              xr:xr-xml-map "aaa_radius_cfg:AcctPortNumber";
              type inet:port-number;
              description
                "Accounting Port number (standard port 1646)";
            }
          }
        }

        container private-servers {
          xr:xr-xml-map "aaa_radius_cfg:PrivateServerTable";
          description
            "List of private RADIUS servers present in the
            group";

          list private-server {
            xr:xr-xml-map "aaa_radius_cfg:PrivateServer";
            key "ordering-index ip-address auth-port-number"+
              " acct-port-number";
            description
              "A private server to include in the server
              group";
            leaf private-timeout {
              xr:xr-xml-map "aaa_radius_cfg:PrivateTimeout";
              type Aaa-radius-timeout;
              default "5";
              description
                "Time to wait for a RADIUS server to reply";
            }
            leaf ignore-accounting-port {
              xr:xr-xml-map "aaa_radius_cfg:IgnoreAccountingPort";
              type boolean;
              description "Ignore Accounting port";
            }
            leaf private-retransmit {
              xr:xr-xml-map "aaa_radius_cfg:PrivateRetransmit";
              type Aaa-radius-retransmit;
              default "3";
              description
                "Number of times to retransmit a request to
                the RADIUS server";
            }
            leaf idle-time {
              xr:xr-xml-map "aaa_radius_cfg:IdleTime";
              type Aaa-radius-idle-time;
              default "5";
              description "Idle time for the radius Server";
            }
            leaf private-key {
              xr:xr-xml-map "aaa_radius_cfg:PrivateKey";
              type xr:Proprietary-password;
              description "RADIUS encryption key";
            }
            leaf username {
              xr:xr-xml-map "aaa_radius_cfg:Username";
              type string;
              description
                "Username to be tested for automated testing";
            }
            leaf ignore-auth-port {
              xr:xr-xml-map "aaa_radius_cfg:IgnoreAuthPort";
              type boolean;
              description "Ignore authentication Port";
            }
            leaf ordering-index {
              xr:xr-xml-map "aaa_radius_cfg:OrderingIndex";
              type int32;
              description
                "This is used to sort the servers in the
                order of precedence";
            }
            leaf ip-address {
              xr:xr-xml-map "aaa_radius_cfg:IPAddress";
              type inet:ip-address-no-zone;
              description "IP address of RADIUS server";
            }
            leaf auth-port-number {
              xr:xr-xml-map "aaa_radius_cfg:AuthPortNumber";
              type inet:port-number;
              description
                "Authentication Port number (standard port
                1645)";
            }
            leaf acct-port-number {
              xr:xr-xml-map "aaa_radius_cfg:AcctPortNumber";
              type inet:port-number;
              description
                "Accounting Port number (standard port 1646)";
            }
          }
        }

        container server-group-throttle {
          xr:xr-xml-map "aaa_radius_cfg:ServerGroupThrottle";
          description "Radius throttling options";
          leaf access {
            xr:xr-xml-map "aaa_radius_cfg:Access";
            type Aaa-throttle-access;
            default "0";
            description
              "To flow control the number of access requests
              sent to a radius server";
          }
          leaf access-timeout {
            xr:xr-xml-map "aaa_radius_cfg:AccessTimeout";
            type Aaa-throttle-access-timeout;
            default "3";
            description
              "Specify the number of timeouts exceeding
              which a throttled access request is dropped";
          }
          leaf accounting {
            xr:xr-xml-map "aaa_radius_cfg:Accounting";
            type Aaa-throttle-accounting;
            default "0";
            description
              "To flow control the number of accounting
              requests sent to a radius server";
          }
        }

        container load-balance {
          xr:xr-xml-map "aaa_radius_cfg:LoadBalance";
          description "Radius load-balancing options";

          container method {
            xr:xr-xml-map "aaa_radius_cfg:Method";
            description
              "Method by which the next host will be picked";

            container name {
              xr:xr-xml-map "aaa_radius_cfg:Name";
              description "Batch size for selection of the server";
              leaf least-outstanding {
                xr:xr-xml-map "aaa_radius_cfg:LeastOutstanding";
                type int32;
                default "4";
                description
                  "Pick the server with the least transactions
                  outstanding";
              }
              leaf batch-size {
                xr:xr-xml-map "aaa_radius_cfg:BatchSize";
                type uint32 {
                  range "1..1500";
                }
                default "25";
                description
                  "Batch size for selection of the server";
              }
              leaf ignore-preferred-server {
                xr:xr-xml-map "aaa_radius_cfg:IgnorePreferredServer";
                type int32;
                default "1";
                description
                  "Disable preferred server for this Server
                  Group";
              }
            }
          }
        }

        container authorization {
          xr:xr-xml-map "aaa_radius_attr_cfg:Authorization";
          description "List of filters in server group";
          uses REQUEST;
          uses REPLY;
        }
        leaf dead-time {
          xr:xr-xml-map "aaa_radius_cfg:DeadTime";
          type Aaa-radius-dead-time;
          units "minute";
          description
            "This indicates the length of time (in minutes)
            for which RADIUS servers present in this group
            remain marked as dead";
        }
        leaf source-interface {
          xr:xr-xml-map "aaa_radius_attr_cfg:SourceInterface";
          type xr:Interface-name;
          description
            "Specify interface for source address in RADIUS
            packets";
        }
        leaf vrf {
          xr:xr-xml-map "aaa_radius_cfg:VRF";
          type string;
          description "Specify VRF name of RADIUS group";
        }
        leaf server-group-name {
          xr:xr-xml-map "aaa_radius_cfg:ServerGroupName";
          type xr:Cisco-ios-xr-string;
          description "RADIUS server group name";
        }
      }
    }
    description
      "This augment extends the configuration data of
      'Cisco-IOS-XR-aaa-locald-cfg'";
  }
}
