module Cisco-IOS-XR-ip-ntp-cfg {

  /*** NAMESPACE / PREFIX DEFINITION ***/

  namespace "http://cisco.com/ns/yang/Cisco-IOS-XR-ip-ntp-cfg";


  prefix "ip-ntp-cfg";

  /*** LINKAGE (IMPORTS / INCLUDES) ***/

  import ietf-inet-types { prefix "inet"; }

  import Cisco-IOS-XR-types { prefix "xr"; }

  import Cisco-IOS-XR-snmp-agent-cfg { prefix "a1"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ip-ntp package configuration.

     This module contains definitions
     for the following management objects:
       ntp: NTP configuration

     This YANG module augments the
       Cisco-IOS-XR-snmp-agent-cfg
     module with configuration data.

     Copyright (c) 2013-2016 by Cisco Systems, Inc.
     All rights reserved.";

  revision "2015-11-09" {
    description
      "IOS XR 6.0 revision.";
  }

  typedef Ntp-prefer-peer {
    type empty;
    description "Prefer";
  }
  typedef Ntpdscp {
    type enumeration {
      enum ntp-precedence {
        value 0;
        description "Precedence Value";
      }
      enum ntpdscp {
        value 1;
        description "DSCP Value";
      }
    }
    description "Ntpdscp";
  }
  typedef Ntp-key-number {
    type uint32 {
      range "1..65535";
    }
    description "Ntp key number";
  }
  typedef Ntpttl {
    type uint32 {
      range "1..255";
    }
    description "Ntpttl";
  }
  typedef Ntp-burst {
    type empty;
    description "Burst";
  }
  typedef Ntpi-burst {
    type empty;
    description "IBurst";
  }
  typedef Ntp-version {
    type uint32 {
      range "2..4";
    }
    description "Ntp version";
  }
  typedef Ntp-peer {
    type enumeration {
      enum peer {
        value 0;
        description "Peer";
      }
      enum server {
        value 1;
        description "Server";
      }
    }
    description "Ntp peer";
  }
  typedef Ntp-access-af {
    type enumeration {
      enum ipv4 {
        value 0;
        description "IPv4";
      }
      enum ipv6 {
        value 1;
        description "IPv6";
      }
    }
    description "Ntp access af";
  }
  typedef Ntp-access {
    type enumeration {
      enum peer {
        value 0;
        description "Peer";
      }
      enum serve {
        value 1;
        description "Serve";
      }
      enum serve-only {
        value 2;
        description "Serve Only";
      }
      enum query-only {
        value 3;
        description "Query Only";
      }
    }
    description "Ntp access";
  }

  container ntp {
    xr:xr-xml-map "ip_ntp_cfg:NTP";
    presence "Indicates a ntp node is configured.";
    description "NTP configuration";

    container peer-vrfs {
      xr:xr-xml-map "ip_ntp_cfg:PeerVRFTable";
      description "Configures NTP Peers or Servers";

      list peer-vrf {
        xr:xr-xml-map "ip_ntp_cfg:PeerVRF";
        key "vrf-name";
        description
          "Configures NTP Peers or Servers for a single
          VRF. The 'default' must also be specified for
          default VRF";

        container peer-ipv4s {
          xr:xr-xml-map "ip_ntp_cfg:PeerIPV4Table";
          description "Configures IPv4 NTP Peers or Servers";

          list peer-ipv4 {
            xr:xr-xml-map "ip_ntp_cfg:PeerIPV4";
            key "address-ipv4";
            description "Configure an IPv4 NTP server or peer";
            leaf address-ipv4 {
              xr:xr-xml-map "ip_ntp_cfg:AddressIPV4";
              type inet:ipv4-address-no-zone;
              description "IPv4 Address of a peer";
            }

            list peer-type-ipv4 {
              xr:xr-xml-map "ip_ntp_cfg:PeerTypeIPV4";
              xr:xr-cli-map "ntp <enum> (vrf <string>) (<IP address"+
                " name>)|(ipv4 <IP address name>) [version <number>"+
                "|key <number>|minpoll <number>|maxpoll <number>|pr"+
                "efer|burst|iburst|source <interface>] ";
              key "peer-type";
              description "Configure an IPv4 NTP server or peer";
              leaf peer-type {
                xr:xr-xml-map "ip_ntp_cfg:PeerType";
                type Ntp-peer;
                description "Peer or Server";
              }
              leaf ntp-version {
                xr:xr-xml-map "ip_ntp_cfg:NTPVersion";
                type Ntp-version;
                description "NTP version";
              }
              leaf authentication-key {
                xr:xr-xml-map "ip_ntp_cfg:AuthenticationKey";
                type Ntp-key-number;
                description "Authentication Key";
              }
              leaf min-poll {
                xr:xr-xml-map "ip_ntp_cfg:MinPoll";
                type uint32 {
                  range "4..17";
                }
                description "Minimum poll interval";
              }
              leaf max-poll {
                xr:xr-xml-map "ip_ntp_cfg:MaxPoll";
                type uint32 {
                  range "4..17";
                }
                description "Maxinum poll interval";
              }
              leaf preferred-peer {
                xr:xr-xml-map "ip_ntp_cfg:PreferredPeer";
                type Ntp-prefer-peer;
                description "Preferred peer";
              }
              leaf source-interface {
                xr:xr-xml-map "ip_ntp_cfg:SourceInterface";
                type xr:Interface-name;
                description "Source interface of this peer";
              }
              leaf burst {
                xr:xr-xml-map "ip_ntp_cfg:Burst";
                type Ntp-burst;
                description "Use burst mode";
              }
              leaf iburst {
                xr:xr-xml-map "ip_ntp_cfg:IBurst";
                type Ntpi-burst;
                description "Use iburst mode";
              }
            }
          }
        }

        container peer-ipv6s {
          xr:xr-xml-map "ip_ntp_cfg:PeerIPV6Table";
          description "Configuration NTP Peers or Servers of IPV6";

          list peer-ipv6 {
            xr:xr-xml-map "ip_ntp_cfg:PeerIPV6";
            key "address-ipv6";
            description "Configure a NTP server or peer";
            leaf address-ipv6 {
              xr:xr-xml-map "ip_ntp_cfg:AddressIPV6";
              type xr:Cisco-ios-xr-string;
              description "Address of a peer";
            }

            list peer-type-ipv6 {
              xr:xr-xml-map "ip_ntp_cfg:PeerTypeIPV6";
              xr:xr-cli-map "ntp <enum> (vrf <string>) (ipv6 <IPv6 "+
                "address>)|(<IPv6 address>) [version <number>|key <"+
                "number>|minpoll <number>|maxpoll <number>|prefer|b"+
                "urst|iburst|source <interface>] ";
              key "peer-type";
              description "Configure a NTP server or peer";
              leaf peer-type {
                xr:xr-xml-map "ip_ntp_cfg:PeerType";
                type Ntp-peer;
                description "Peer or Server";
              }
              leaf ntp-version {
                xr:xr-xml-map "ip_ntp_cfg:NTPVersion";
                type Ntp-version;
                description "NTP version";
              }
              leaf authentication-key {
                xr:xr-xml-map "ip_ntp_cfg:AuthenticationKey";
                type Ntp-key-number;
                description "Authentication Key";
              }
              leaf min-poll {
                xr:xr-xml-map "ip_ntp_cfg:MinPoll";
                type uint32 {
                  range "4..17";
                }
                description "Minimum poll interval";
              }
              leaf max-poll {
                xr:xr-xml-map "ip_ntp_cfg:MaxPoll";
                type uint32 {
                  range "4..17";
                }
                description "Maxinum poll interval";
              }
              leaf preferred-peer {
                xr:xr-xml-map "ip_ntp_cfg:PreferredPeer";
                type Ntp-prefer-peer;
                description "Preferred peer";
              }
              leaf source-interface {
                xr:xr-xml-map "ip_ntp_cfg:SourceInterface";
                type xr:Interface-name;
                description "Source interface of this peer";
              }
              leaf burst {
                xr:xr-xml-map "ip_ntp_cfg:Burst";
                type Ntp-burst;
                description "Use burst mode";
              }
              leaf iburst {
                xr:xr-xml-map "ip_ntp_cfg:IBurst";
                type Ntpi-burst;
                description "Use iburst mode";
              }
              leaf address-ipv6 {
                xr:xr-xml-map "ip_ntp_cfg:AddressIPV6";
                type inet:ipv6-address-no-zone;
                mandatory true;
                description "IPv6 address";
              }
            }
          }
        }
        leaf vrf-name {
          xr:xr-xml-map "ip_ntp_cfg:VRFName";
          type xr:Cisco-ios-xr-string;
          description "VRF name";
        }
      }
    }

    container dscp-ipv4 {
      xr:xr-xml-map "ip_ntp_cfg:dscpIPv4";
      presence "Indicates a dscp-ipv4 node is configured.";
      description
        " Set IP DSCP value for outgoing NTP IPV4 packets";
      leaf mode {
        xr:xr-xml-map "ip_ntp_cfg:Mode";
        type Ntpdscp;
        mandatory true;
        description
          "NTPPRECEDENCE (0) to specify Precedence value 
          NTPDSCP (1) to specify DSCP value";
      }
      leaf dscp-or-precedence-value {
        xr:xr-xml-map "ip_ntp_cfg:DscpOrPrecedenceValue";
        type uint32 {
          range "0..63";
        }
        mandatory true;
        description
          "If Mode is set to 'NTPPRECEDENCE(0)' specify
          Precedence value , if Mode is set to
          'NTPDSCP(1)' specify DSCP";
      }
    }

    container dscp-ipv6 {
      xr:xr-xml-map "ip_ntp_cfg:dscpIPv6";
      presence "Indicates a dscp-ipv6 node is configured.";
      description
        " Set IP DSCP value for outgoing NTP IPV6 packets";
      leaf mode {
        xr:xr-xml-map "ip_ntp_cfg:Mode";
        type Ntpdscp;
        mandatory true;
        description
          "NTPPRECEDENCE(0) to specify Precedence value
          NTPDSCP(1) to specify DSCP value";
      }
      leaf dscp-or-precedence-value {
        xr:xr-xml-map "ip_ntp_cfg:DscpOrPrecedenceValue";
        type uint32 {
          range "0..63";
        }
        mandatory true;
        description
          "If Mode is set to 'NTPPRECEDENCE(0)' specify
          Precedence value , if Mode is set to
          'NTPDSCP(1)' specify DSCP";
      }
    }

    container sources {
      xr:xr-xml-map "ip_ntp_cfg:SourceTable";
      description "Configure  NTP source interface";

      list source {
        xr:xr-xml-map "ip_ntp_cfg:Source";
        xr:xr-cli-map "ntp source (vrf <string>) <interface> ";
        key "vrf-name";
        description "Configure  NTP source interface";
        leaf vrf-name {
          xr:xr-xml-map "ip_ntp_cfg:VRFName";
          type xr:Cisco-ios-xr-string;
          description "VRF name";
        }
        leaf source-interface {
          xr:xr-xml-map "ip_ntp_cfg:SourceInterface";
          type xr:Interface-name;
          mandatory true;
          description "Source Interface for NTP";
        }
      }
    }

    container authentication {
      xr:xr-xml-map "ip_ntp_cfg:Authentication";
      description "Configure NTP Authentication keys";

      container keies {
        xr:xr-xml-map "ip_ntp_cfg:KeyTable";
        description "Authentication Key Table";

        list key {
          xr:xr-xml-map "ip_ntp_cfg:Key";
          xr:xr-cli-map "ntp authentication-key <number> md5 ([0] <"+
            "string>)|(clear)|((7)|(encrypted) <string>)|(<string>)"+
            " ";
          key "key-number";
          description "Authentication key for trusted time sources";
          leaf key-number {
            xr:xr-xml-map "ip_ntp_cfg:KeyNumber";
            type Ntp-key-number;
            description "Authentication Key number";
          }
          leaf authentication-key {
            xr:xr-xml-map "ip_ntp_cfg:AuthenticationKey";
            type string;
            mandatory true;
            description
              "Authentication key - maximum 32 characters";
          }
        }
      }

      container trusted-keies {
        xr:xr-xml-map "ip_ntp_cfg:TrustedKeyTable";
        description "Key numbers for trusted time sources";

        list trusted-key {
          xr:xr-xml-map "ip_ntp_cfg:TrustedKey";
          xr:xr-cli-map "ntp trusted-key <number> ";
          key "key-number";
          description "Configure NTP trusted key";
          leaf key-number {
            xr:xr-xml-map "ip_ntp_cfg:KeyNumber";
            type Ntp-key-number;
            description "Key number";
          }
        }
      }
      leaf enable {
        xr:xr-xml-map "ip_ntp_cfg:Enable";
        xr:xr-cli-map "ntp authenticate ";
        type empty;
        description "Enable NTP authentication keys";
      }
    }

    container passive {
      xr:xr-xml-map "ip_ntp_cfg:Passive";
      description "Configure NTP passive associations";
      leaf enable {
        xr:xr-xml-map "ip_ntp_cfg:Enable";
        xr:xr-cli-map "ntp passive ";
        type empty;
        description "Enable NTP Passive associations";
      }
    }

    container interface-tables {
      xr:xr-xml-map "ip_ntp_cfg:InterfaceVRFTable";
      description "NTP per interface configuration";

      list interface-table {
        xr:xr-xml-map "ip_ntp_cfg:InterfaceTable";
        key "vrf-name";
        description "NTP per interface configuration";
        leaf vrf-name {
          xr:xr-xml-map "ip_ntp_cfg:VRFName";
          type xr:Cisco-ios-xr-string;
          description "VRF name";
        }

        list interface {
          xr:xr-xml-map "ip_ntp_cfg:Interface";
          key "interface";
          description "Name of the interface";

          container interface-multicast {
            xr:xr-xml-map "ip_ntp_cfg:InterfaceMulticast";
            description "Configure NTP multicast service";

            container multicast-clients {
              xr:xr-xml-map "ip_ntp_cfg:MulticastClientTable";
              description "Configures multicast client peers";

              list multicast-client {
                xr:xr-xml-map "ip_ntp_cfg:MulticastClient";
                xr:xr-cli-map "ntp interface <interface> (vrf <stri"+
                  "ng>) multicast client (<IPv4/IPv6 address>) ";
                key "ip-address";
                description "Listen to NTP multicasts";
                leaf ip-address {
                  xr:xr-xml-map "ip_ntp_cfg:IPAddress";
                  type inet:ip-address-no-zone;
                  description "IP address of a multicast group";
                }
              }
            }

            container multicast-servers {
              xr:xr-xml-map "ip_ntp_cfg:MulticastServerTable";
              description "Configures multicast server peers";

              list multicast-server {
                xr:xr-xml-map "ip_ntp_cfg:MulticastServer";
                xr:xr-cli-map "ntp interface <interface> (vrf <stri"+
                  "ng>) multicast (destination <IPv4"+
                  "/IPv6 address>) [key <number>|version <number>|t"+
                  "tl <number>] ";
                key "ip-address";
                description
                  "Configure NTP multicast group server peer";
                leaf ip-address {
                  xr:xr-xml-map "ip_ntp_cfg:IPAddress";
                  type inet:ip-address-no-zone;
                  description "IP address of a multicast group";
                }
                leaf authentication-key {
                  xr:xr-xml-map "ip_ntp_cfg:AuthenticationKey";
                  type Ntp-key-number;
                  description "Authentication key";
                }
                leaf version {
                  xr:xr-xml-map "ip_ntp_cfg:Version";
                  type Ntp-version;
                  description "NTP version";
                }
                leaf ttl {
                  xr:xr-xml-map "ip_ntp_cfg:TTL";
                  type Ntpttl;
                  description "TTL";
                }
              }
            }
          }

          container interface-broadcast {
            xr:xr-xml-map "ip_ntp_cfg:InterfaceBroadcast";
            description "Configure NTP broadcast service";

            container broadcast {
              xr:xr-xml-map "ip_ntp_cfg:Broadcast";
              description "Configure NTP broadcast";
              leaf address {
                xr:xr-xml-map "ip_ntp_cfg:Address";
                type inet:ipv4-address-no-zone;
                description "Destination broadcast IPv4 address";
              }
              leaf authentication-key {
                xr:xr-xml-map "ip_ntp_cfg:AuthenticationKey";
                type Ntp-key-number;
                description "Authentication key";
              }
              leaf ntp-version {
                xr:xr-xml-map "ip_ntp_cfg:NTPVersion";
                type Ntp-version;
                description "NTP version";
              }
            }
            leaf broadcast-client {
              xr:xr-xml-map "ip_ntp_cfg:BroadcastClient";
              xr:xr-cli-map "ntp interface <interface> (vrf <string"+
                ">) broadcast client ";
              type empty;
              description "Listen to NTP broadcasts";
            }
          }
          leaf disable {
            xr:xr-xml-map "ip_ntp_cfg:Disable";
            xr:xr-cli-map "ntp interface <interface> (vrf <string>)"+
              " disable ";
            type empty;
            description "Disable NTP";
          }
          leaf interface {
            xr:xr-xml-map "ip_ntp_cfg:Interface";
            type xr:Interface-name;
            description "interface";
          }
        }
      }
    }

    container access-group-tables {
      xr:xr-xml-map "ip_ntp_cfg:AccessGroupVRFTable";
      description "Control NTP access";

      list access-group-table {
        xr:xr-xml-map "ip_ntp_cfg:AccessGroupTable";
        key "vrf-name";
        description "Control NTP access";
        leaf vrf-name {
          xr:xr-xml-map "ip_ntp_cfg:VRFName";
          type xr:Cisco-ios-xr-string;
          description "VRF name";
        }

        list access-group-af-table {
          xr:xr-xml-map "ip_ntp_cfg:AccessGroupAFTable";
          key "af";
          description "Configure NTP access address family";
          leaf af {
            xr:xr-xml-map "ip_ntp_cfg:AF";
            type Ntp-access-af;
            description "Address family";
          }

          list access-group {
            xr:xr-xml-map "ip_ntp_cfg:AccessGroup";
            xr:xr-cli-map "ntp access-group (vrf <string>) (ipv6)|("+
              "ipv4) (peer)|(query-only)|(serve)|(serve-only) <stri"+
              "ng> ";
            key "access-group-type";
            description "Configure NTP access group";
            leaf access-group-type {
              xr:xr-xml-map "ip_ntp_cfg:AccessGroupType";
              type Ntp-access;
              description "Access group type";
            }
            leaf access-list-name {
              xr:xr-xml-map "ip_ntp_cfg:AccessListName";
              type string;
              mandatory true;
              description
                "Access list name - maximum 32 characters";
            }
          }
        }
      }
    }
    leaf max-associations {
      xr:xr-xml-map "ip_ntp_cfg:MaxAssociations";
      xr:xr-cli-map "ntp max-associations <number> ";
      type int32;
      description "Set maximum number of associations";
    }
    leaf master {
      xr:xr-xml-map "ip_ntp_cfg:Master";
      xr:xr-cli-map "ntp master [<number>|primary-reference-clock] ";
      type uint32 {
        range "1..15";
      }
      default "8";
      description "Act as NTP master clock";
    }
    leaf broadcast-delay {
      xr:xr-xml-map "ip_ntp_cfg:BroadcastDelay";
      xr:xr-cli-map "ntp broadcastdelay <number> ";
      type uint32 {
        range "1..999999";
      }
      description "Estimated round-trip delay";
    }
    leaf log-internal-sync {
      xr:xr-xml-map "ip_ntp_cfg:LogInternalSync";
      xr:xr-cli-map "ntp log-internal-sync ";
      type empty;
      description "To enable logging internal sync conflicts";
    }
    leaf update-calendar {
      xr:xr-xml-map "ip_ntp_cfg:UpdateCalendar";
      xr:xr-cli-map "ntp update-calendar ";
      type empty;
      description "To enable calendar update with NTP time";
    }
  }

  augment "/a1:snmp/a1:notification" {

    container ntp {
      xr:xr-xml-map "ciscontpmib_cfg:NTP";
      description "CISCO-NTP-MIB notification configuration";
      leaf enable {
        xr:xr-xml-map "ciscontpmib_cfg:Enable";
        type empty;
        description "Enable ciscoNtpMIB notification configuration";
      }
    }
    description
      "This augment extends the configuration data of
      'Cisco-IOS-XR-snmp-agent-cfg'";
  }
}
