submodule Cisco-IOS-XR-ip-rsvp-oper-sub2 {

  belongs-to Cisco-IOS-XR-ip-rsvp-oper {
    prefix Cisco-IOS-XR-ip-rsvp-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR ip-rsvp package operational data.

     Copyright (c) 2013-2016 by Cisco Systems, Inc.
     All rights reserved.";

  revision "2015-11-09" {
    description
      "IOS XR 6.0 revision.";
  }


  grouping MPLS-RSVP-INTERFACE-COUNTERS {
    description "MPLS RSVP interface counters";
    leaf interface-name-xr {
      xr:xr-xml-map "oc_mpls_rsvp:interface-name-xr";
      type string;
      description "Interface name";
    }
    leaf in-path-messages {
      xr:xr-xml-map "oc_mpls_rsvp:InPathMessages";
      type uint64;
      description "Per interface count of path messages received";
    }
    leaf in-path-error-messages {
      xr:xr-xml-map "oc_mpls_rsvp:InPathErrorMessages";
      type uint64;
      description
        "Per interface count of path error messages
        received";
    }
    leaf in-path-tear-messages {
      xr:xr-xml-map "oc_mpls_rsvp:InPathTearMessages";
      type uint64;
      description
        "Per interface count of path tear messages
        received";
    }
    leaf in-reservation-messages {
      xr:xr-xml-map "oc_mpls_rsvp:InReservationMessages";
      type uint64;
      description
        "Per interface count of reservation messages
        received";
    }
    leaf in-reservation-error-messages {
      xr:xr-xml-map "oc_mpls_rsvp:InReservationErrorMessages";
      type uint64;
      description
        "Per interface count of reservation error
        messages received";
    }
    leaf in-reservation-tear-messages {
      xr:xr-xml-map "oc_mpls_rsvp:InReservationTearMessages";
      type uint64;
      description
        "Per interface count of reservation tear messages
        received";
    }
    leaf in-hello-messages {
      xr:xr-xml-map "oc_mpls_rsvp:InHelloMessages";
      type uint64;
      description "Per interface count of hello messages received";
    }
    leaf in-srefresh-messages {
      xr:xr-xml-map "oc_mpls_rsvp:InSrefreshMessages";
      type uint64;
      description
        "Per interface count of srefresh messages
        received";
    }
    leaf in-ack-messages {
      xr:xr-xml-map "oc_mpls_rsvp:InAckMessages";
      type uint64;
      description "Per interface count of ack messages received";
    }
    leaf out-path-messages {
      xr:xr-xml-map "oc_mpls_rsvp:OutPathMessages";
      type uint64;
      description "Per interface count of path messages send";
    }
    leaf out-path-error-messages {
      xr:xr-xml-map "oc_mpls_rsvp:OutPathErrorMessages";
      type uint64;
      description "Per interface count of path error messages send";
    }
    leaf out-path-tear-messages {
      xr:xr-xml-map "oc_mpls_rsvp:OutPathTearMessages";
      type uint64;
      description "Per interface count of path tear messages send";
    }
    leaf out-reservation-messages {
      xr:xr-xml-map "oc_mpls_rsvp:OutReservationMessages";
      type uint64;
      description
        "Per interface count of reservation messages send";
    }
    leaf out-reservation-error-messages {
      xr:xr-xml-map "oc_mpls_rsvp:OutReservationErrorMessages";
      type uint64;
      description
        "Per interface count of reservation error
        messages send";
    }
    leaf out-reservation-tear-messages {
      xr:xr-xml-map "oc_mpls_rsvp:OutReservationTearMessages";
      type uint64;
      description
        "Per interface count of reservation tear messages
        send";
    }
    leaf out-hello-messages {
      xr:xr-xml-map "oc_mpls_rsvp:OutHelloMessages";
      type uint64;
      description "Per interface count of hello messages send";
    }
    leaf out-srefresh-messages {
      xr:xr-xml-map "oc_mpls_rsvp:OutSrefreshMessages";
      type uint64;
      description "Per interface count of srefresh messages send";
    }
    leaf out-ack-messages {
      xr:xr-xml-map "oc_mpls_rsvp:OutAckMessages";
      type uint64;
      description "Per interface count of ack messages send";
    }
  }

  grouping MPLS-RSVP-GLOBAL-COUNTERS {
    description "MPLS RSVP global counters";
    leaf path-timeouts {
      xr:xr-xml-map "oc_mpls_rsvp:PathTimeouts";
      type uint64;
      description "Global count of Path Timeouts";
    }
    leaf reservation-timeouts {
      xr:xr-xml-map "oc_mpls_rsvp:ReservationTimeouts";
      type uint64;
      description "Global count of reservation timeouts";
    }
    leaf rate-limited-messages {
      xr:xr-xml-map "oc_mpls_rsvp:RateLimitedMessages";
      type uint64;
      description "Global count of rate limited messages";
    }
    leaf in-path-messages {
      xr:xr-xml-map "oc_mpls_rsvp:InPathMessages";
      type uint64;
      description "Global count of path messages received";
    }
    leaf in-path-error-messages {
      xr:xr-xml-map "oc_mpls_rsvp:InPathErrorMessages";
      type uint64;
      description "Global count of path error messages received";
    }
    leaf in-path-tear-messages {
      xr:xr-xml-map "oc_mpls_rsvp:InPathTearMessages";
      type uint64;
      description "Global count of path tear messages received";
    }
    leaf in-reservation-messages {
      xr:xr-xml-map "oc_mpls_rsvp:InReservationMessages";
      type uint64;
      description "Global count of reservation messages received";
    }
    leaf in-reservation-error-messages {
      xr:xr-xml-map "oc_mpls_rsvp:InReservationErrorMessages";
      type uint64;
      description
        "Global count of reservation error messages
        received";
    }
    leaf in-reservation-tear-messages {
      xr:xr-xml-map "oc_mpls_rsvp:InReservationTearMessages";
      type uint64;
      description
        "Global count of reservation tear messages
        received";
    }
    leaf in-hello-messages {
      xr:xr-xml-map "oc_mpls_rsvp:InHelloMessages";
      type uint64;
      description "Global count of hello messages received";
    }
    leaf in-srefresh-messages {
      xr:xr-xml-map "oc_mpls_rsvp:InSrefreshMessages";
      type uint64;
      description "Global count of srefresh messages received";
    }
    leaf in-ack-messages {
      xr:xr-xml-map "oc_mpls_rsvp:InAckMessages";
      type uint64;
      description "Global count of ack messages received";
    }
    leaf out-path-messages {
      xr:xr-xml-map "oc_mpls_rsvp:OutPathMessages";
      type uint64;
      description "Global count of path messages send";
    }
    leaf out-path-error-messages {
      xr:xr-xml-map "oc_mpls_rsvp:OutPathErrorMessages";
      type uint64;
      description "Global count of path error messages send";
    }
    leaf out-path-tear-messages {
      xr:xr-xml-map "oc_mpls_rsvp:OutPathTearMessages";
      type uint64;
      description "Global count of path tear messages send";
    }
    leaf out-reservation-messages {
      xr:xr-xml-map "oc_mpls_rsvp:OutReservationMessages";
      type uint64;
      description "Global count of reservation messages send";
    }
    leaf out-reservation-error-messages {
      xr:xr-xml-map "oc_mpls_rsvp:OutReservationErrorMessages";
      type uint64;
      description "Global count of reservation error messages send";
    }
    leaf out-reservation-tear-messages {
      xr:xr-xml-map "oc_mpls_rsvp:OutReservationTearMessages";
      type uint64;
      description "Global count of reservation tear messages send";
    }
    leaf out-hello-messages {
      xr:xr-xml-map "oc_mpls_rsvp:OutHelloMessages";
      type uint64;
      description "Global count of hello messages send";
    }
    leaf out-srefresh-messages {
      xr:xr-xml-map "oc_mpls_rsvp:OutSrefreshMessages";
      type uint64;
      description "Global count of srefresh messages send";
    }
    leaf out-ack-messages {
      xr:xr-xml-map "oc_mpls_rsvp:OutAckMessages";
      type uint64;
      description "Global count of ack messages send";
    }
  }
}
