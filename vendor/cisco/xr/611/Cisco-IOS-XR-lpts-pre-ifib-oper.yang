module Cisco-IOS-XR-lpts-pre-ifib-oper {

  /*** NAMESPACE / PREFIX DEFINITION ***/

  namespace "http://cisco.com/ns"+
    "/yang/Cisco-IOS-XR-lpts-pre-ifib-oper";


  prefix "lpts-pre-ifib-oper";

  /*** LINKAGE (IMPORTS / INCLUDES) ***/

  import Cisco-IOS-XR-types { prefix "xr"; }

  include Cisco-IOS-XR-lpts-pre-ifib-oper-sub1 {
    revision-date 2016-02-22;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR lpts-pre-ifib package operational data.

     This module contains definitions
     for the following management objects:
       lpts-pifib: lpts pre-ifib data

     Copyright (c) 2013-2016 by Cisco Systems, Inc.
     All rights reserved.";

  revision "2016-02-22" {
    description
      "Initial revision for pre-ifib oper yang.";
  }

  revision "2015-11-09" {
    description
      "IOS XR 6.0 revision.";
  }

  typedef Lpts-pifib {
    type enumeration {
      enum isis {
        value 0;
        description "ISIS packets";
      }
      enum ipv4-frag {
        value 1;
        description "IPv4 fragmented packets";
      }
      enum ipv4-echo {
        value 2;
        description "IPv4 ICMP Echo packets";
      }
      enum ipv4-any {
        value 3;
        description "All IPv4 packets";
      }
      enum ipv6-frag {
        value 4;
        description "IPv6 fragmented packets";
      }
      enum ipv6-echo {
        value 5;
        description "IPv6 ICMP Echo packets";
      }
      enum ipv6-nd {
        value 6;
        description "IPv6 ND packets";
      }
      enum ipv6-any {
        value 7;
        description "All IPv6 packets";
      }
      enum bfd-any {
        value 8;
        description "BFD packets";
      }
      enum all {
        value 9;
        description "All packets";
      }
    }
    description "Lpts pifib";
  }

  container lpts-pifib {
    xr:xr-xml-map "pifib_oper:LptsPifib";
    config false;
    description "lpts pre-ifib data";

    container nodes {
      xr:xr-xml-map "pifib_oper:NodeTable";
      description "List of Pre-ifib Nodes";

      list node {
        xr:xr-xml-map "pifib_oper:Node";
        key "node-name";
        description "Pre-ifib data for particular node";

        container type-values {
          xr:xr-xml-map "pifib_oper:Type";
          description "Type specific";

          list type-value {
            xr:xr-xml-map "pifib_oper:TypeValue";
            key "pifib-type";
            description "pifib types";
            leaf pifib-type {
              xr:xr-xml-map "pifib_oper:pifibType";
              type Lpts-pifib;
              description "Type value";
            }

            list entry {
              xr:xr-xml-map "pifib_oper:Entry";
              key "entry";
              description "Data for single pre-ifib entry";
              leaf entry {
                xr:xr-xml-map "pifib_oper:entry";
                type xr:Cisco-ios-xr-string;
                description "Single Pre-ifib entry";
              }
              uses PIFIB-SHOW-ENTRY;
            }
          }
        }
        leaf node-name {
          xr:xr-xml-map "pifib_oper:NodeName";
          type xr:Node-id;
          description "The node name";
        }
      }
    }
  }
}
