submodule Cisco-IOS-XR-mpls-te-oper-sub2 {

  belongs-to Cisco-IOS-XR-mpls-te-oper {
    prefix Cisco-IOS-XR-mpls-te-oper;
  }

  /*** LINKAGE (IMPORTS / INCLUDES) ***/

  import ietf-inet-types { prefix "inet"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR mpls-te package operational data.

     Copyright (c) 2013-2016 by Cisco Systems, Inc.
     All rights reserved.";

  revision "2015-11-09" {
    description
      "IOS XR 6.0 revision.";
  }

  typedef Tp-mid-lsp-status {
    type enumeration {
      enum up {
        description "TP LSP Up";
      }
      enum down {
        description "TP LSP Down";
      }
    }
    description "Transport profile mid-point LSP states";
  }

  grouping MPLS-TP-MID-SUMMARY-INFO {
    description
      "Transport profile mid-point LSP summary
      information";
    leaf mid-points {
      xr:xr-xml-map "mpls_te_slsp:MidPoints";
      type uint32;
      description "Total number of mid points";
    }
    leaf up-forward-ls-ps {
      xr:xr-xml-map "mpls_te_slsp:UpForwardLSPs";
      type uint32;
      description "Total number of forward LSPs that are Up";
    }
    leaf down-forward-ls-ps {
      xr:xr-xml-map "mpls_te_slsp:DownForwardLSPs";
      type uint32;
      description "Total number of forward LSPs that are Down";
    }
    leaf up-reverse-ls-ps {
      xr:xr-xml-map "mpls_te_slsp:UpReverseLSPs";
      type uint32;
      description "Total number of reverse LSPs that are Up";
    }
    leaf down-reverse-ls-ps {
      xr:xr-xml-map "mpls_te_slsp:DownReverseLSPs";
      type uint32;
      description "Total number of reverse LSPs that are Down";
    }
  }

  grouping MPLS-TP-MID-LSP-INFO {
    description
      "Transport profile mid-point LSP detailed
      information";
    leaf out-label {
      xr:xr-xml-map "mpls_te_slsp:OutLabel";
      type uint32;
      description "Outgoing label";
    }
    leaf out-link {
      xr:xr-xml-map "mpls_te_slsp:OutLink";
      type uint32;
      description "Outgoing TP link ID";
    }
    leaf oam-refresh-interval {
      xr:xr-xml-map "mpls_te_slsp:OAMRefreshInterval";
      type uint32;
      units "second";
      description "OAM Refresh time in seconds";
    }
    leaf outgoing-interface {
      xr:xr-xml-map "mpls_te_slsp:OutgoingInterface";
      type string;
      description "Outgoing interface";
    }
    leaf next-hop-address {
      xr:xr-xml-map "mpls_te_slsp:NextHopAddress";
      type inet:ipv4-address;
      description "Outgoing next-hop in IPv4 address format";
    }
    leaf in-label {
      xr:xr-xml-map "mpls_te_slsp:InLabel";
      type uint32;
      description "Incoming label";
    }
    leaf bandwidth {
      xr:xr-xml-map "mpls_te_slsp:Bandwidth";
      type uint32;
      units "kbit/s";
      description "Configured bandwidth in Kbps";
    }
  }

  grouping MPLS-TP-MID-INFO {
    description "Transport profile mid-point LSP information";
    leaf midpoint-name {
      xr:xr-xml-map "mpls_te_slsp:MidpointName";
      type string;
      description "Mid Point Name";
    }
    leaf tunnel-name {
      xr:xr-xml-map "mpls_te_slsp:TunnelName";
      type string;
      description "Tunnel Name";
    }
    leaf source-node-id {
      xr:xr-xml-map "mpls_te_slsp:SourceNodeID";
      type inet:ipv4-address;
      description "Source Node ID";
    }
    leaf source-global-id {
      xr:xr-xml-map "mpls_te_slsp:SourceGlobalID";
      type uint32;
      description "Source Global ID";
    }
    leaf source-tunnel-id {
      xr:xr-xml-map "mpls_te_slsp:SourceTunnelID";
      type uint32;
      description "Source Tunnel ID";
    }
    leaf lsp-id {
      xr:xr-xml-map "mpls_te_slsp:LSP_ID";
      type uint32;
      description "LSP ID";
    }
    leaf destination-node-id {
      xr:xr-xml-map "mpls_te_slsp:DestinationNodeID";
      type inet:ipv4-address;
      description "Destination Node ID";
    }
    leaf destination-global-id {
      xr:xr-xml-map "mpls_te_slsp:DestinationGlobalID";
      type uint32;
      description "Destination Global ID";
    }
    leaf destination-tunnel-id {
      xr:xr-xml-map "mpls_te_slsp:DestinationTunnelID";
      type uint32;
      description "Destination Tunnel ID";
    }
    leaf forward-lsp-state {
      xr:xr-xml-map "mpls_te_slsp:ForwardLSPState";
      type Tp-mid-lsp-status;
      description "Forward LSP State";
    }
    leaf reverse-lsp-state {
      xr:xr-xml-map "mpls_te_slsp:ReverseLSPState";
      type Tp-mid-lsp-status;
      description "Reverse LSP State";
    }
  }

  grouping MPLS-TP-DETAIL-MID-INFO {
    description
      "Transport profile mid-point LSP detail
      information";

    container brief-lsp-information {
      description "Brief LSP information";
      uses MPLS-TP-MID-INFO;
    }

    container forward-lsp {
      description "Forward LSP information";
      uses MPLS-TP-MID-LSP-INFO;
    }

    container reverse-lsp {
      description "Reverse LSP information";
      uses MPLS-TP-MID-LSP-INFO;
    }
    leaf forward-lsp-reserved-bandwidth {
      xr:xr-xml-map "mpls_te_slsp:ForwardLSPReservedBandwidth";
      type uint32;
      units "kbit/s";
      description "Forward LSP reserved bandwidth in Kbps";
    }
    leaf reverse-lsp-reserved-bandwidth {
      xr:xr-xml-map "mpls_te_slsp:ReverseLSPReservedBandwidth";
      type uint32;
      units "kbit/s";
      description "Reverse LSP reserved bandwidth in Kbps";
    }
  }
}
