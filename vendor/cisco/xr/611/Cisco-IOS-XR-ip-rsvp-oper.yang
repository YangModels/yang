module Cisco-IOS-XR-ip-rsvp-oper {

  /*** NAMESPACE / PREFIX DEFINITION ***/

  namespace "http://cisco.com/ns/yang/Cisco-IOS-XR-ip-rsvp-oper";


  prefix "ip-rsvp-oper";

  /*** LINKAGE (IMPORTS / INCLUDES) ***/

  import ietf-inet-types { prefix "inet"; }

  import Cisco-IOS-XR-types { prefix "xr"; }

  include Cisco-IOS-XR-ip-rsvp-oper-sub2 {
    revision-date 2015-11-09;
  }

  include Cisco-IOS-XR-ip-rsvp-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ip-rsvp package operational data.

     This module contains definitions
     for the following management objects:
       rsvp-standby: RSVP operational data for standby role
       rsvp: rsvp

     Copyright (c) 2013-2016 by Cisco Systems, Inc.
     All rights reserved.";

  revision "2015-11-09" {
    description
      "IOS XR 6.0 revision.";
  }

  typedef Rsvp-mode {
    type enumeration {
      enum send {
        value 0;
        description "Send";
      }
      enum receive {
        value 1;
        description "Receive";
      }
    }
    description "Rsvp mode";
  }
  typedef Rsvp-session {
    type enumeration {
      enum ipv4 {
        value 1;
        description "Show IPv4 sessions only";
      }
      enum p2p-lsp-ipv4 {
        value 7;
        description "Show IPv4 P2P LSP sessions only";
      }
      enum ouni-ipv4 {
        value 9;
        description "Show IPv4 OUNI sessions only";
      }
      enum p2mp-lsp-ipv4 {
        value 13;
        description "Show IPv4 P2MP LSP sessions only";
      }
    }
    description "Rsvp session";
  }

  grouping INTERFACE-NEIGHBOR-DETAIL-TABLE {
    description "Common node of rsvp, rsvp-standby";

    container interface-neighbor-details {
      xr:xr-xml-map "ip_rsvp_oper:InterfaceNeighborDetailTable";
      description "Table of detailed info about I/F neighbors";

      list interface-neighbor-detail {
        xr:xr-xml-map "ip_rsvp_oper:InterfaceNeighborDetail";
        key "neighbor-address";
        description "Detailed info for a single interface neighbor";
        leaf neighbor-address {
          xr:xr-xml-map "ip_rsvp_oper:NeighborAddress";
          type inet:ipv4-address-no-zone;
          description "Address of global neighbor";
        }
        uses RSVP-MGMT-NBR-DETAIL;
      }
    }
  }

  grouping COUNTERS {
    description "Common node of rsvp, rsvp-standby";

    container counters {
      xr:xr-xml-map "ip_rsvp_oper:Counters";
      description "Counters";

      container interface-messages {
        xr:xr-xml-map "ip_rsvp_oper:InterfaceMessagesTable";
        description "Table of message counters";

        list interface-message {
          xr:xr-xml-map "ip_rsvp_oper:InterfaceMessages";
          key "interface-name";
          description "Interface message counters";
          leaf interface-name {
            xr:xr-xml-map "ip_rsvp_oper:InterfaceName";
            type xr:Interface-name;
            description
              "Interface Name. 'None' is used internally
              where the true interface is unknown (e.g. for
              routed packets)";
          }
          uses RSVP-MGMT-COUNT-MESSAGE;
        }
      }

      container message-summary {
        xr:xr-xml-map "ip_rsvp_oper:MessageSummary";
        description
          "Summary information for all RSVP message
          counters";
        uses RSVP-MGMT-COUNT-MESSAGE;
      }

      container prefix-filtering {
        xr:xr-xml-map "ip_rsvp_prefix_filtering_oper:PrefixFilterin"+
          "g";
        description "Prefix filtering counters";

        container accesses {
          xr:xr-xml-map "ip_rsvp_prefix_filtering_oper:AccessListTa"+
            "ble";
          description
            "AccessList specific prefix filtering counters";

          list access {
            xr:xr-xml-map "ip_rsvp_prefix_filtering_oper:AccessList";
            key "access-list-name";
            description
              "Prefix filtering counters for a specific
              AccessList";
            leaf access-list-name {
              xr:xr-xml-map "ip_rsvp_prefix_filtering_oper:AccessLi"+
                "stName";
              type xr:Cisco-ios-xr-string {
                length "0..65";
              }
              description "AccessList Name";
            }
            uses RSVP-MGMT-COUNT-PREFIX-ACL-INFO;
          }
        }

        container interfaces {
          xr:xr-xml-map "ip_rsvp_prefix_filtering_oper:Interfaces";
          description
            "Interface specific prefix filtering counters";

          container summary {
            xr:xr-xml-map "ip_rsvp_prefix_filtering_oper:Summary";
            description
              "Summary of prefix filtering counts for all
              interfaces";
            uses RSVP-MGMT-COUNT-PREFIX-INTERFACE-INFO;
          }

          container interfaces {
            xr:xr-xml-map "ip_rsvp_prefix_filtering_oper:InterfaceT"+
              "able";
            description
              "Table of interface specific prefix filtering
              counters";

            list interface {
              xr:xr-xml-map "ip_rsvp_prefix_filtering_oper:Interfac"+
                "e";
              key "interface-name";
              description
                "Prefix filtering counters for a specific
                interface";
              leaf interface-name {
                xr:xr-xml-map "ip_rsvp_prefix_filtering_oper:Interf"+
                  "aceName";
                type xr:Cisco-ios-xr-string;
                description
                  "Interface Name. 'None' is used internally
                  where the true interface is unknown (e.g.
                  for routed packets)";
              }
              uses RSVP-MGMT-COUNT-PREFIX-INTERFACE-INFO;
            }
          }
        }
      }

      container out-of-resource {
        xr:xr-xml-map "ip_rsvp_oor_oper:OutOfResource";
        description "Out of resource counters";

        container interfaces {
          xr:xr-xml-map "ip_rsvp_oor_oper:Interfaces";
          description "Interface specific out of resource counters";

          container summary {
            xr:xr-xml-map "ip_rsvp_oor_oper:Summary";
            description
              "Summary of out of resource counts for all
              interfaces";
            uses RSVP-MGMT-COUNTERS-OOR;
          }

          container interfaces {
            xr:xr-xml-map "ip_rsvp_oor_oper:InterfaceTable";
            description
              "Table of interface specific out of resource
              counters";

            list interface {
              xr:xr-xml-map "ip_rsvp_oor_oper:Interface";
              key "interface-name";
              description
                "Out of resource counters for a specific
                interface";
              leaf interface-name {
                xr:xr-xml-map "ip_rsvp_oor_oper:InterfaceName";
                type xr:Cisco-ios-xr-string;
                description
                  "Interface Name. 'None' is used internally
                  where the true interface is unknown (e.g.
                  for routed packets)";
              }
              uses RSVP-MGMT-COUNTERS-OOR;
            }
          }
        }
      }

      container interface-events {
        xr:xr-xml-map "ip_rsvp_oper:InterfaceEventsTable";
        description "Event counters";

        list interface-event {
          xr:xr-xml-map "ip_rsvp_oper:InterfaceEvents";
          key "interface-name";
          description "Event counters for an interface";
          leaf interface-name {
            xr:xr-xml-map "ip_rsvp_oper:InterfaceName";
            type xr:Interface-name;
            description
              "Interface Name. 'None' is used internally
              where the true interface is unknown (e.g. for
              routed packets)";
          }
          uses RSVP-MGMT-EVENT-COUNT-INFO;
        }
      }

      container nsr {
        xr:xr-xml-map "ip_rsvp_oper:NSR";
        description "Summary information for all RSVP NSR counters";
        uses RSVP-SYNC-COUNT-INFO;
      }

      container issu {
        xr:xr-xml-map "ip_rsvp_oper:ISSU";
        description
          "Summary information for all RSVP ISSU counters";
        uses RSVP-SYNC-COUNT-INFO;
      }

      container database {
        xr:xr-xml-map "ip_rsvp_oper:Database";
        description
          "Summary information for all RSVP database
          counters";
        uses RSVP-MGMT-ALL-DB-COUNTERS;
      }

      container event-syncs {
        xr:xr-xml-map "ip_rsvp_oper:EventSyncTable";
        description "Table containing event sync counters";

        list event-sync {
          xr:xr-xml-map "ip_rsvp_oper:EventSync";
          key "interface-name";
          description "Event sync counters";
          leaf interface-name {
            xr:xr-xml-map "ip_rsvp_oper:InterfaceName";
            type xr:Interface-name;
            description "Interface Name";
          }
          uses RSVP-MGMT-EVENT-COUNT-INFO;
        }
      }
    }
  }

  grouping HELLO-INTERFACE-INSTANCE-DETAIL-TABLE {
    description "Common node of rsvp, rsvp-standby";

    container hello-interface-instance-details {
      xr:xr-xml-map "ip_rsvp_oper:HelloInterfaceInstanceDetailTable";
      description
        "Table of detailed info about i/f-based hello
        instances";

      list hello-interface-instance-detail {
        xr:xr-xml-map "ip_rsvp_oper:HelloInterfaceInstanceDetail";
        key "source-address destination-address";
        description
          "Detailed info for a single interface-based
          hello instance";
        leaf source-address {
          xr:xr-xml-map "ip_rsvp_oper:SourceAddress";
          type inet:ipv4-address-no-zone;
          description "Source Address";
        }
        leaf destination-address {
          xr:xr-xml-map "ip_rsvp_oper:DestinationAddress";
          type inet:ipv4-address-no-zone;
          description "Destination Address";
        }
        uses RSVP-MGMT-HELLO-IF-INSTANCE-DETAIL;
      }
    }
  }

  grouping AUTHENTICATION-BRIEF-TABLE {
    description "Common node of rsvp, rsvp-standby";

    container authentication-briefs {
      xr:xr-xml-map "ip_rsvp_oper:AuthenticationBriefTable";
      description "Table for Authentication related information";

      list authentication-brief {
        xr:xr-xml-map "ip_rsvp_oper:AuthenticationBrief";
        key "source-address destination-address mode-id"+
          " interface-name";
        description "Brief Authentication information";
        leaf source-address {
          xr:xr-xml-map "ip_rsvp_oper:SourceAddress";
          type inet:ipv4-address-no-zone;
          description "Source Address";
        }
        leaf destination-address {
          xr:xr-xml-map "ip_rsvp_oper:DestinationAddress";
          type inet:ipv4-address-no-zone;
          description "Destination Address";
        }
        leaf mode-id {
          xr:xr-xml-map "ip_rsvp_oper:ModeID";
          type Rsvp-mode;
          description "Mode (Tx or Rx)";
        }
        leaf interface-name {
          xr:xr-xml-map "ip_rsvp_oper:InterfaceName";
          type xr:Interface-name;
          description "InterfaceName";
        }
        uses RSVP-MGMT-AUTHENTICATION-COMPACT;
      }
    }
  }

  grouping REQUEST-DETAIL-TABLE {
    description "Common node of rsvp, rsvp-standby";

    container request-details {
      xr:xr-xml-map "ip_rsvp_oper:RequestDetailTable";
      description "Table of detail info about requests";

      list request-detail {
        xr:xr-xml-map "ip_rsvp_oper:RequestDetail";
        description "Detail info for a request";
        leaf destination-address {
          xr:xr-xml-map "ip_rsvp_oper:DestinationAddress";
          type inet:ipv4-address-no-zone;
          description "Destination Address";
        }
        leaf destination-port {
          xr:xr-xml-map "ip_rsvp_oper:DestinationPort";
          type int32;
          description "Destination Port";
        }
        leaf protocol {
          xr:xr-xml-map "ip_rsvp_oper:Protocol";
          type int32;
          description "Protocol";
        }
        leaf extended-tunnel-id {
          xr:xr-xml-map "ip_rsvp_oper:ExtendedTunnelID";
          type inet:ipv4-address-no-zone;
          description "Extended Tunnel ID";
        }
        leaf session-type {
          xr:xr-xml-map "ip_rsvp_oper:SessionType";
          type Rsvp-session;
          description "Session Type";
        }
        leaf p2mp-id {
          xr:xr-xml-map "ip_rsvp_oper:P2MP_ID";
          type int32;
          description "P2MP ID";
        }
        leaf source-address {
          xr:xr-xml-map "ip_rsvp_oper:SourceAddress";
          type inet:ipv4-address-no-zone;
          description "Source Address";
        }
        leaf source-port {
          xr:xr-xml-map "ip_rsvp_oper:SourcePort";
          type int32;
          description "Source Port";
        }
        leaf sub-group-origin {
          xr:xr-xml-map "ip_rsvp_oper:SubGroupOrigin";
          type inet:ipv4-address-no-zone;
          description "Subgroup Origin";
        }
        leaf sub-group-id {
          xr:xr-xml-map "ip_rsvp_oper:SubGroupID";
          type int32;
          description "Subgroup ID";
        }
        leaf vrf-name {
          xr:xr-xml-map "ip_rsvp_oper:VRFName";
          type xr:Cisco-ios-xr-string;
          description "VRF Name";
        }
        uses RSVP-MGMT-REQUEST-DETAIL;
      }
    }
  }

  grouping RSB-BRIEF-TABLE {
    description "Common node of rsvp, rsvp-standby";

    container rsb-briefs {
      xr:xr-xml-map "ip_rsvp_oper:RSBBriefTable";
      description
        "Table of brief info about reservation state
        blocks";

      list rsb-brief {
        xr:xr-xml-map "ip_rsvp_oper:RSBBrief";
        description
          "Brief info for a single reservation state block";
        leaf destination-address {
          xr:xr-xml-map "ip_rsvp_oper:DestinationAddress";
          type inet:ipv4-address-no-zone;
          description "Destination Address";
        }
        leaf destination-port {
          xr:xr-xml-map "ip_rsvp_oper:DestinationPort";
          type int32;
          description "Destination Port";
        }
        leaf protocol {
          xr:xr-xml-map "ip_rsvp_oper:Protocol";
          type int32;
          description "Protocol";
        }
        leaf extended-tunnel-id {
          xr:xr-xml-map "ip_rsvp_oper:ExtendedTunnelID";
          type inet:ipv4-address-no-zone;
          description "Extended Tunnel ID";
        }
        leaf session-type {
          xr:xr-xml-map "ip_rsvp_oper:SessionType";
          type Rsvp-session;
          description "Session Type";
        }
        leaf p2mp-id {
          xr:xr-xml-map "ip_rsvp_oper:P2MP_ID";
          type int32;
          description "P2MP ID";
        }
        leaf source-address {
          xr:xr-xml-map "ip_rsvp_oper:SourceAddress";
          type inet:ipv4-address-no-zone;
          description "Source Address";
        }
        leaf source-port {
          xr:xr-xml-map "ip_rsvp_oper:SourcePort";
          type int32;
          description "Source Port ";
        }
        leaf sub-group-origin {
          xr:xr-xml-map "ip_rsvp_oper:SubGroupOrigin";
          type inet:ipv4-address-no-zone;
          description "Subgroup Origin";
        }
        leaf sub-group-id {
          xr:xr-xml-map "ip_rsvp_oper:SubGroupID";
          type int32;
          description "Subgroup ID";
        }
        leaf vrf-name {
          xr:xr-xml-map "ip_rsvp_oper:VRFName";
          type xr:Cisco-ios-xr-string;
          description "VRF Name";
        }
        uses RSVP-MGMT-RESERVATION-COMPACT;
      }
    }
  }

  grouping OPEN-CONFIG {
    description "Common node of rsvp, rsvp-standby";

    container open-config {
      xr:xr-xml-map "oc_mpls_rsvp_oper:OpenConfig";
      description "OpenConfig info";

      container global-counters {
        xr:xr-xml-map "oc_mpls_rsvp_oper:GlobalCounters";
        description "Platform wide RSVP statistics and counters";
        uses MPLS-RSVP-GLOBAL-COUNTERS;
      }

      container interface-counters {
        xr:xr-xml-map "oc_mpls_rsvp_oper:InterfaceCountersTable";
        description
          "Table of info about RSVP-enabled interface
          counters for OpenConfig";

        list interface-counter {
          xr:xr-xml-map "oc_mpls_rsvp_oper:InterfaceCounters";
          key "interface-name";
          description
            "Info about an RSVP-enabled interface counters";
          leaf interface-name {
            xr:xr-xml-map "oc_mpls_rsvp_oper:InterfaceName";
            type xr:Interface-name;
            description "Interface name";
          }
          uses MPLS-RSVP-INTERFACE-COUNTERS;
        }
      }
    }
  }

  grouping REQUEST-BRIEF-TABLE {
    description "Common node of rsvp, rsvp-standby";

    container request-briefs {
      xr:xr-xml-map "ip_rsvp_oper:RequestBriefTable";
      description "Table of brief info about requests";

      list request-brief {
        xr:xr-xml-map "ip_rsvp_oper:RequestBrief";
        description "Brief info for a request";
        leaf destination-address {
          xr:xr-xml-map "ip_rsvp_oper:DestinationAddress";
          type inet:ipv4-address-no-zone;
          description "Destination Address";
        }
        leaf destination-port {
          xr:xr-xml-map "ip_rsvp_oper:DestinationPort";
          type int32;
          description "Destination Port";
        }
        leaf protocol {
          xr:xr-xml-map "ip_rsvp_oper:Protocol";
          type int32;
          description "Protocol";
        }
        leaf extended-tunnel-id {
          xr:xr-xml-map "ip_rsvp_oper:ExtendedTunnelID";
          type inet:ipv4-address-no-zone;
          description "Extended Tunnel ID";
        }
        leaf session-type {
          xr:xr-xml-map "ip_rsvp_oper:SessionType";
          type Rsvp-session;
          description "Session Type";
        }
        leaf p2mp-id {
          xr:xr-xml-map "ip_rsvp_oper:P2MP_ID";
          type int32;
          description "P2MP ID";
        }
        leaf source-address {
          xr:xr-xml-map "ip_rsvp_oper:SourceAddress";
          type inet:ipv4-address-no-zone;
          description "Source Address";
        }
        leaf source-port {
          xr:xr-xml-map "ip_rsvp_oper:SourcePort";
          type int32;
          description "Source Port";
        }
        leaf sub-group-origin {
          xr:xr-xml-map "ip_rsvp_oper:SubGroupOrigin";
          type inet:ipv4-address-no-zone;
          description "Subgroup Origin";
        }
        leaf sub-group-id {
          xr:xr-xml-map "ip_rsvp_oper:SubGroupID";
          type int32;
          description "Subgroup ID";
        }
        leaf vrf-name {
          xr:xr-xml-map "ip_rsvp_oper:VRFName";
          type xr:Cisco-ios-xr-string;
          description "VRF Name";
        }
        uses RSVP-MGMT-REQUEST-COMPACT;
      }
    }
  }

  grouping HELLO-INTERFACE-INSTANCE-BRIEF-TABLE {
    description "Common node of rsvp, rsvp-standby";

    container hello-interface-instance-briefs {
      xr:xr-xml-map "ip_rsvp_oper:HelloInterfaceInstanceBriefTable";
      description
        "Table of brief info about i/f-based hello
        instances";

      list hello-interface-instance-brief {
        xr:xr-xml-map "ip_rsvp_oper:HelloInterfaceInstanceBrief";
        key "source-address destination-address";
        description
          "Brief info for a single interface-based hello
          instance";
        leaf source-address {
          xr:xr-xml-map "ip_rsvp_oper:SourceAddress";
          type inet:ipv4-address-no-zone;
          description "Source Address";
        }
        leaf destination-address {
          xr:xr-xml-map "ip_rsvp_oper:DestinationAddress";
          type inet:ipv4-address-no-zone;
          description "Destination Address";
        }
        uses RSVP-MGMT-HELLO-IF-INSTANCE-COMPACT;
      }
    }
  }

  grouping INTERFACE-NEIGHBOR-BRIEF-TABLE {
    description "Common node of rsvp, rsvp-standby";

    container interface-neighbor-briefs {
      xr:xr-xml-map "ip_rsvp_oper:InterfaceNeighborBriefTable";
      description "Table of brief info about I/F neighbors";

      list interface-neighbor-brief {
        xr:xr-xml-map "ip_rsvp_oper:InterfaceNeighborBrief";
        key "neighbor-address";
        description "Brief info for a single interface neighbor";
        leaf neighbor-address {
          xr:xr-xml-map "ip_rsvp_oper:NeighborAddress";
          type inet:ipv4-address-no-zone;
          description "Address of global neighbor";
        }
        uses RSVP-MGMT-NBR-COMPACT;
      }
    }
  }

  grouping PSB-BRIEF-TABLE {
    description "Common node of rsvp, rsvp-standby";

    container psb-briefs {
      xr:xr-xml-map "ip_rsvp_oper:PSBBriefTable";
      description "Table of brief info about path state blocks";

      list psb-brief {
        xr:xr-xml-map "ip_rsvp_oper:PSBBrief";
        description "Brief info for a single path state block";
        leaf destination-address {
          xr:xr-xml-map "ip_rsvp_oper:DestinationAddress";
          type inet:ipv4-address-no-zone;
          description "Destination Address";
        }
        leaf destination-port {
          xr:xr-xml-map "ip_rsvp_oper:DestinationPort";
          type int32;
          description "Destination Port";
        }
        leaf protocol {
          xr:xr-xml-map "ip_rsvp_oper:Protocol";
          type int32;
          description "Protocol";
        }
        leaf extended-tunnel-id {
          xr:xr-xml-map "ip_rsvp_oper:ExtendedTunnelID";
          type inet:ipv4-address-no-zone;
          description "Extended Tunnel ID";
        }
        leaf session-type {
          xr:xr-xml-map "ip_rsvp_oper:SessionType";
          type Rsvp-session;
          description "Session Type";
        }
        leaf p2mp-id {
          xr:xr-xml-map "ip_rsvp_oper:P2MP_ID";
          type int32;
          description "P2MP ID";
        }
        leaf source-address {
          xr:xr-xml-map "ip_rsvp_oper:SourceAddress";
          type inet:ipv4-address-no-zone;
          description "Source Address";
        }
        leaf source-port {
          xr:xr-xml-map "ip_rsvp_oper:SourcePort";
          type int32;
          description "Source Port ";
        }
        leaf sub-group-origin {
          xr:xr-xml-map "ip_rsvp_oper:SubGroupOrigin";
          type inet:ipv4-address-no-zone;
          description "Subgroup Origin";
        }
        leaf sub-group-id {
          xr:xr-xml-map "ip_rsvp_oper:SubGroupID";
          type int32;
          description "Subgroup ID";
        }
        leaf vrf-name {
          xr:xr-xml-map "ip_rsvp_oper:VRFName";
          type xr:Cisco-ios-xr-string;
          description "VRF Name";
        }
        uses RSVP-MGMT-PATH-COMPACT;
      }
    }
  }

  grouping GLOBAL-NEIGHBOR-BRIEF-TABLE {
    description "Common node of rsvp, rsvp-standby";

    container global-neighbor-briefs {
      xr:xr-xml-map "ip_rsvp_oper:GlobalNeighborBriefTable";
      description "Table of brief info about global neighbors";

      list global-neighbor-brief {
        xr:xr-xml-map "ip_rsvp_oper:GlobalNeighborBrief";
        key "neighbor-address";
        description "Brief info for a single global neighbor";
        leaf neighbor-address {
          xr:xr-xml-map "ip_rsvp_oper:NeighborAddress";
          type inet:ipv4-address-no-zone;
          description "Address of global neighbor";
        }
        uses RSVP-MGMT-GLBL-NBR-COMPACT;
      }
    }
  }

  grouping SESSION-DETAILED-TABLE {
    description "Common node of rsvp, rsvp-standby";

    container session-detaileds {
      xr:xr-xml-map "ip_rsvp_oper:SessionDetailedTable";
      description "Table of detailed info about sessions";

      list session-detailed {
        xr:xr-xml-map "ip_rsvp_oper:SessionDetailed";
        description "Detailed info about session";
        leaf destination-address {
          xr:xr-xml-map "ip_rsvp_oper:DestinationAddress";
          type inet:ipv4-address-no-zone;
          description "Destination Address";
        }
        leaf destination-port {
          xr:xr-xml-map "ip_rsvp_oper:DestinationPort";
          type int32;
          description "Destination Port";
        }
        leaf protocol {
          xr:xr-xml-map "ip_rsvp_oper:Protocol";
          type int32;
          description "Protocol";
        }
        leaf extended-tunnel-id {
          xr:xr-xml-map "ip_rsvp_oper:ExtendedTunnelID";
          type inet:ipv4-address-no-zone;
          description "Extended Tunnel ID";
        }
        leaf session-type {
          xr:xr-xml-map "ip_rsvp_oper:SessionType";
          type Rsvp-session;
          description "Session Type";
        }
        leaf p2mp-id {
          xr:xr-xml-map "ip_rsvp_oper:P2MP_ID";
          type int32;
          description "P2MP ID";
        }
        leaf vrf-name {
          xr:xr-xml-map "ip_rsvp_oper:VRFName";
          type xr:Cisco-ios-xr-string;
          description "VRF Name";
        }
        uses RSVP-MGMT-SESSION-DETAIL;
      }
    }
  }

  grouping AUTHENTICATION-DETAIL-TABLE {
    description "Common node of rsvp, rsvp-standby";

    container authentication-details {
      xr:xr-xml-map "ip_rsvp_oper:AuthenticationDetailTable";
      description
        "Table for detailed authentication related
        information";

      list authentication-detail {
        xr:xr-xml-map "ip_rsvp_oper:AuthenticationDetail";
        key "source-address destination-address mode-id"+
          " interface-name";
        description "Brief Authentication information";
        leaf source-address {
          xr:xr-xml-map "ip_rsvp_oper:SourceAddress";
          type inet:ipv4-address-no-zone;
          description "Source Address";
        }
        leaf destination-address {
          xr:xr-xml-map "ip_rsvp_oper:DestinationAddress";
          type inet:ipv4-address-no-zone;
          description "Destination Address";
        }
        leaf mode-id {
          xr:xr-xml-map "ip_rsvp_oper:ModeID";
          type Rsvp-mode;
          description "Mode (Tx or Rx)";
        }
        leaf interface-name {
          xr:xr-xml-map "ip_rsvp_oper:InterfaceName";
          type xr:Interface-name;
          description "InterfaceName";
        }
        uses RSVP-MGMT-AUTHENTICATION-DETAIL;
      }
    }
  }

  grouping GLOBAL-NEIGHBOR-DETAIL-TABLE {
    description "Common node of rsvp, rsvp-standby";

    container global-neighbor-details {
      xr:xr-xml-map "ip_rsvp_oper:GlobalNeighborDetailTable";
      description "Table of detailed info about global neighbors";

      list global-neighbor-detail {
        xr:xr-xml-map "ip_rsvp_oper:GlobalNeighborDetail";
        key "neighbor-address";
        description "Detail info for a single global neighbor";
        leaf neighbor-address {
          xr:xr-xml-map "ip_rsvp_oper:NeighborAddress";
          type inet:ipv4-address-no-zone;
          description "Address of global neighbor";
        }
        uses RSVP-MGMT-GLBL-NBR-DETAIL;
      }
    }
  }

  grouping INTERFACE-SUMMARY-TABLE {
    description "Common node of rsvp, rsvp-standby";

    container interface-summaries {
      xr:xr-xml-map "ip_rsvp_oper:InterfaceSummaryTable";
      description
        "Table of summary info about RSVP-enabled
        interfaces";

      list interface-summary {
        xr:xr-xml-map "ip_rsvp_oper:InterfaceSummary";
        key "interface-name";
        description "Summary info about an RSVP-enabled interface";
        leaf interface-name {
          xr:xr-xml-map "ip_rsvp_oper:InterfaceName";
          type xr:Interface-name;
          description "Interface Name";
        }
        uses RSVP-MGMT-INTERFACE-SUMMARY;
      }
    }
  }

  grouping INTERFACE-BRIEF-TABLE {
    description "Common node of rsvp, rsvp-standby";

    container interface-briefs {
      xr:xr-xml-map "ip_rsvp_oper:InterfaceBriefTable";
      description
        "Table of brief info about RSVP-enabled
        interfaces";

      list interface-brief {
        xr:xr-xml-map "ip_rsvp_oper:InterfaceBrief";
        key "interface-name";
        description "Brief info about an RSVP-enabled interface";
        leaf interface-name {
          xr:xr-xml-map "ip_rsvp_oper:InterfaceName";
          type xr:Interface-name;
          description "Interface Name";
        }
        uses RSVP-MGMT-INTERFACE-COMPACT;
      }
    }
  }

  grouping HELLO-INSTANCE-DETAIL-TABLE {
    description "Common node of rsvp, rsvp-standby";

    container hello-instance-details {
      xr:xr-xml-map "ip_rsvp_oper:HelloInstanceDetailTable";
      description "Table of detailed info about hello instances";

      list hello-instance-detail {
        xr:xr-xml-map "ip_rsvp_oper:HelloInstanceDetail";
        key "source-address destination-address";
        description "Detailed info for a single hello instance";
        leaf source-address {
          xr:xr-xml-map "ip_rsvp_oper:SourceAddress";
          type inet:ipv4-address-no-zone;
          description "Source Address";
        }
        leaf destination-address {
          xr:xr-xml-map "ip_rsvp_oper:DestinationAddress";
          type inet:ipv4-address-no-zone;
          description "Destination Address";
        }
        uses RSVP-MGMT-HELLO-INSTANCE-DETAIL;
      }
    }
  }

  grouping SUMMARY {
    description "Common node of rsvp, rsvp-standby";

    container summary {
      xr:xr-xml-map "ip_rsvp_oper:Summary";
      description "RSVP summary information";
      uses RSVP-GLOBAL-INFO;
    }
  }

  grouping PSB-DETAILED-TABLE {
    description "Common node of rsvp, rsvp-standby";

    container psb-detaileds {
      xr:xr-xml-map "ip_rsvp_oper:PSBDetailedTable";
      description "Table of detailed info about path state blocks";

      list psb-detailed {
        xr:xr-xml-map "ip_rsvp_oper:PSBDetailed";
        description "Detailed info for a single path state block";
        leaf destination-address {
          xr:xr-xml-map "ip_rsvp_oper:DestinationAddress";
          type inet:ipv4-address-no-zone;
          description "Destination Address";
        }
        leaf destination-port {
          xr:xr-xml-map "ip_rsvp_oper:DestinationPort";
          type int32;
          description "Destination Port";
        }
        leaf protocol {
          xr:xr-xml-map "ip_rsvp_oper:Protocol";
          type int32;
          description "Protocol";
        }
        leaf extended-tunnel-id {
          xr:xr-xml-map "ip_rsvp_oper:ExtendedTunnelID";
          type inet:ipv4-address-no-zone;
          description "Extended Tunnel ID";
        }
        leaf session-type {
          xr:xr-xml-map "ip_rsvp_oper:SessionType";
          type Rsvp-session;
          description "Session Type";
        }
        leaf p2mp-id {
          xr:xr-xml-map "ip_rsvp_oper:P2MP_ID";
          type int32;
          description "P2MP ID";
        }
        leaf source-address {
          xr:xr-xml-map "ip_rsvp_oper:SourceAddress";
          type inet:ipv4-address-no-zone;
          description "Source Address";
        }
        leaf source-port {
          xr:xr-xml-map "ip_rsvp_oper:SourcePort";
          type int32;
          description "Source Port ";
        }
        leaf sub-group-origin {
          xr:xr-xml-map "ip_rsvp_oper:SubGroupOrigin";
          type inet:ipv4-address-no-zone;
          description "Subgroup Origin";
        }
        leaf sub-group-id {
          xr:xr-xml-map "ip_rsvp_oper:SubGroupID";
          type int32;
          description "Subgroup ID";
        }
        leaf vrf-name {
          xr:xr-xml-map "ip_rsvp_oper:VRFName";
          type xr:Cisco-ios-xr-string;
          description "VRF Name";
        }
        uses RSVP-MGMT-PATH-DETAIL;
      }
    }
  }

  grouping NSR {
    description "Common node of rsvp, rsvp-standby";

    container nsr {
      xr:xr-xml-map "ip_rsvp_oper:NSR";
      description "RSVP NSR information";

      container status {
        xr:xr-xml-map "ip_rsvp_oper:Status";
        description "RSVP NSR status information";
        uses RSVP-NSR-ISSU-STATUS-INFO;
      }
    }
  }

  grouping GRACEFUL-RESTART {
    description "Common node of rsvp, rsvp-standby";

    container graceful-restart {
      xr:xr-xml-map "ip_rsvp_oper:GracefulRestart";
      description "Info about graceful-restart";
      uses RSVP-MGMT-GRACEFUL-RESTART;
    }
  }

  grouping FRR-SUMMARY {
    description "Common node of rsvp, rsvp-standby";

    container frr-summary {
      xr:xr-xml-map "ip_rsvp_oper:FRRSummary";
      description "Fast Re-Route Summary State Information";
      uses RSVP-MGMT-FRR-STATES-COMPACT;
    }
  }

  grouping RSB-DETAILED-TABLE {
    description "Common node of rsvp, rsvp-standby";

    container rsb-detaileds {
      xr:xr-xml-map "ip_rsvp_oper:RSBDetailedTable";
      description
        "Table of detailed info about reservation state
        blocks";

      list rsb-detailed {
        xr:xr-xml-map "ip_rsvp_oper:RSBDetailed";
        description
          "Detailed info for a single reservation state
          block";
        leaf destination-address {
          xr:xr-xml-map "ip_rsvp_oper:DestinationAddress";
          type inet:ipv4-address-no-zone;
          description "Destination Address";
        }
        leaf destination-port {
          xr:xr-xml-map "ip_rsvp_oper:DestinationPort";
          type int32;
          description "Destination Port";
        }
        leaf protocol {
          xr:xr-xml-map "ip_rsvp_oper:Protocol";
          type int32;
          description "Protocol";
        }
        leaf extended-tunnel-id {
          xr:xr-xml-map "ip_rsvp_oper:ExtendedTunnelID";
          type inet:ipv4-address-no-zone;
          description "Extended Tunnel ID";
        }
        leaf session-type {
          xr:xr-xml-map "ip_rsvp_oper:SessionType";
          type Rsvp-session;
          description "Session Type";
        }
        leaf p2mp-id {
          xr:xr-xml-map "ip_rsvp_oper:P2MP_ID";
          type int32;
          description "P2MP ID";
        }
        leaf source-address {
          xr:xr-xml-map "ip_rsvp_oper:SourceAddress";
          type inet:ipv4-address-no-zone;
          description "Source Address";
        }
        leaf source-port {
          xr:xr-xml-map "ip_rsvp_oper:SourcePort";
          type int32;
          description "Source Port ";
        }
        leaf sub-group-origin {
          xr:xr-xml-map "ip_rsvp_oper:SubGroupOrigin";
          type inet:ipv4-address-no-zone;
          description "Subgroup Origin";
        }
        leaf sub-group-id {
          xr:xr-xml-map "ip_rsvp_oper:SubGroupID";
          type int32;
          description "Subgroup ID";
        }
        leaf vrf-name {
          xr:xr-xml-map "ip_rsvp_oper:VRFName";
          type xr:Cisco-ios-xr-string;
          description "VRF Name";
        }
        uses RSVP-MGMT-RESERVATION-DETAIL;
      }
    }
  }

  grouping HELLO-INSTANCE-BRIEF-TABLE {
    description "Common node of rsvp, rsvp-standby";

    container hello-instance-briefs {
      xr:xr-xml-map "ip_rsvp_oper:HelloInstanceBriefTable";
      description "Table of brief info about hello instances";

      list hello-instance-brief {
        xr:xr-xml-map "ip_rsvp_oper:HelloInstanceBrief";
        key "source-address destination-address";
        description "Brief info for a single hello instance";
        leaf source-address {
          xr:xr-xml-map "ip_rsvp_oper:SourceAddress";
          type inet:ipv4-address-no-zone;
          description "Source Address";
        }
        leaf destination-address {
          xr:xr-xml-map "ip_rsvp_oper:DestinationAddress";
          type inet:ipv4-address-no-zone;
          description "Destination Address";
        }
        uses RSVP-MGMT-HELLO-INSTANCE-COMPACT;
      }
    }
  }

  grouping FRR-TABLE {
    description "Common node of rsvp, rsvp-standby";

    container frrs {
      xr:xr-xml-map "ip_rsvp_oper:FRRTable";
      description
        "Table of detailed info about Fast Re-route
        states";

      list frr {
        xr:xr-xml-map "ip_rsvp_oper:FRR";
        description
          "Detailed info for a single Fast Re-route state";
        leaf destination-address {
          xr:xr-xml-map "ip_rsvp_oper:DestinationAddress";
          type inet:ipv4-address-no-zone;
          description "Destination Address";
        }
        leaf destination-port {
          xr:xr-xml-map "ip_rsvp_oper:DestinationPort";
          type int32;
          description "Destination Port";
        }
        leaf protocol {
          xr:xr-xml-map "ip_rsvp_oper:Protocol";
          type int32;
          description "Protocol";
        }
        leaf extended-tunnel-id {
          xr:xr-xml-map "ip_rsvp_oper:ExtendedTunnelID";
          type inet:ipv4-address-no-zone;
          description "Extended Tunnel ID";
        }
        leaf session-type {
          xr:xr-xml-map "ip_rsvp_oper:SessionType";
          type Rsvp-session;
          description "Session Type";
        }
        leaf p2mp-id {
          xr:xr-xml-map "ip_rsvp_oper:P2MP_ID";
          type int32;
          description "P2MP ID";
        }
        leaf source-address {
          xr:xr-xml-map "ip_rsvp_oper:SourceAddress";
          type inet:ipv4-address-no-zone;
          description "Source Address";
        }
        leaf source-port {
          xr:xr-xml-map "ip_rsvp_oper:SourcePort";
          type int32;
          description "Source Port";
        }
        leaf sub-group-origin {
          xr:xr-xml-map "ip_rsvp_oper:SubGroupOrigin";
          type inet:ipv4-address-no-zone;
          description "Subgroup Origin";
        }
        leaf sub-group-id {
          xr:xr-xml-map "ip_rsvp_oper:SubGroupID";
          type int32;
          description "Subgroup ID";
        }
        leaf vrf-name {
          xr:xr-xml-map "ip_rsvp_oper:VRFName";
          type xr:Cisco-ios-xr-string;
          description "VRF Name";
        }
        uses RSVP-MGMT-FRR-STATES-DETAIL;
      }
    }
  }

  grouping SESSION-BRIEF-TABLE {
    description "Common node of rsvp, rsvp-standby";

    container session-briefs {
      xr:xr-xml-map "ip_rsvp_oper:SessionBriefTable";
      description "Table of brief info about sessions";

      list session-brief {
        xr:xr-xml-map "ip_rsvp_oper:SessionBrief";
        description "Brief info about session";
        leaf destination-address {
          xr:xr-xml-map "ip_rsvp_oper:DestinationAddress";
          type inet:ipv4-address-no-zone;
          description "Destination Address";
        }
        leaf destination-port {
          xr:xr-xml-map "ip_rsvp_oper:DestinationPort";
          type int32;
          description "Destination Port";
        }
        leaf protocol {
          xr:xr-xml-map "ip_rsvp_oper:Protocol";
          type int32;
          description "Protocol";
        }
        leaf extended-tunnel-id {
          xr:xr-xml-map "ip_rsvp_oper:ExtendedTunnelID";
          type inet:ipv4-address-no-zone;
          description "Extended Tunnel ID";
        }
        leaf session-type {
          xr:xr-xml-map "ip_rsvp_oper:SessionType";
          type Rsvp-session;
          description "Session Type";
        }
        leaf p2mp-id {
          xr:xr-xml-map "ip_rsvp_oper:P2MP_ID";
          type int32;
          description "P2MP ID";
        }
        leaf vrf-name {
          xr:xr-xml-map "ip_rsvp_oper:VRFName";
          type xr:Cisco-ios-xr-string;
          description "VRF Name";
        }
        uses RSVP-MGMT-SESSION-COMPACT;
      }
    }
  }

  grouping INTERFACE-DETAILED-TABLE {
    description "Common node of rsvp, rsvp-standby";

    container interface-detaileds {
      xr:xr-xml-map "ip_rsvp_oper:InterfaceDetailedTable";
      description
        "Table of detailed info about RSVP-enabled
        interfaces";

      list interface-detailed {
        xr:xr-xml-map "ip_rsvp_oper:InterfaceDetailed";
        key "interface-name";
        description "Detailed info about an RSVP-enabled interface";
        leaf interface-name {
          xr:xr-xml-map "ip_rsvp_oper:InterfaceName";
          type xr:Interface-name;
          description "Interface Name";
        }
        uses RSVP-MGMT-INTERFACE-DETAIL;
      }
    }
  }

  container rsvp-standby {
    xr:xr-xml-map "ip_rsvp_oper:RSVPStandby";
    config false;
    description "RSVP operational data for standby role";
    uses INTERFACE-NEIGHBOR-BRIEF-TABLE;
    uses AUTHENTICATION-BRIEF-TABLE;
    uses SESSION-BRIEF-TABLE;
    uses PSB-DETAILED-TABLE;
    uses FRR-SUMMARY;
    uses RSB-DETAILED-TABLE;
    uses INTERFACE-SUMMARY-TABLE;
    uses HELLO-INSTANCE-BRIEF-TABLE;
    uses AUTHENTICATION-DETAIL-TABLE;
    uses RSB-BRIEF-TABLE;
    uses OPEN-CONFIG;
    uses COUNTERS;
    uses INTERFACE-DETAILED-TABLE;
    uses GRACEFUL-RESTART;
    uses HELLO-INTERFACE-INSTANCE-BRIEF-TABLE;
    uses HELLO-INTERFACE-INSTANCE-DETAIL-TABLE;
    uses INTERFACE-NEIGHBOR-DETAIL-TABLE;
    uses NSR;
    uses SUMMARY;
    uses FRR-TABLE;
    uses REQUEST-BRIEF-TABLE;
    uses REQUEST-DETAIL-TABLE;
    uses INTERFACE-BRIEF-TABLE;
    uses SESSION-DETAILED-TABLE;
    uses HELLO-INSTANCE-DETAIL-TABLE;
    uses GLOBAL-NEIGHBOR-DETAIL-TABLE;
    uses PSB-BRIEF-TABLE;
    uses GLOBAL-NEIGHBOR-BRIEF-TABLE;
  }

  container rsvp {
    xr:xr-xml-map "ip_rsvp_oper:RSVP";
    config false;
    description "rsvp";

    container controller-summaries {
      xr:xr-xml-map "ip_rsvp_oper:ControllerSummaryTable";
      description
        "Table of summary info about RSVP-enabled
        controllers";

      list controller-summary {
        xr:xr-xml-map "ip_rsvp_oper:ControllerSummary";
        key "controller-name";
        description "Summary info about an RSVP-enabled controller";
        leaf controller-name {
          xr:xr-xml-map "ip_rsvp_oper:ControllerName";
          type xr:Interface-name;
          description "Controller Name";
        }
        uses RSVP-MGMT-INTERFACE-SUMMARY;
      }
    }

    container issu {
      xr:xr-xml-map "ip_rsvp_oper:ISSU";
      description "RSVP ISSU information";

      container status {
        xr:xr-xml-map "ip_rsvp_oper:Status";
        description "RSVP ISSU status information";
        uses RSVP-NSR-ISSU-STATUS-INFO;
      }
    }

    container controller-detaileds {
      xr:xr-xml-map "ip_rsvp_oper:ControllerDetailedTable";
      description
        "Table of detailed info about RSVP-enabled
        controllers";

      list controller-detailed {
        xr:xr-xml-map "ip_rsvp_oper:ControllerDetailed";
        key "controller-name";
        description
          "Detailed info about an RSVP-enabled controller";
        leaf controller-name {
          xr:xr-xml-map "ip_rsvp_oper:ControllerName";
          type xr:Interface-name;
          description "Controller Name";
        }
        uses RSVP-MGMT-INTERFACE-DETAIL;
      }
    }

    container bw-pool-info {
      xr:xr-xml-map "ip_rsvp_oper:BWPoolInfo";
      description "All B/W Pool info";
      uses RSVP-MGMT-GLBL-BW-POOL-INFO;
    }

    container controller-briefs {
      xr:xr-xml-map "ip_rsvp_oper:ControllerBriefTable";
      description
        "Table of brief info about RSVP-enabled
        controller";

      list controller-brief {
        xr:xr-xml-map "ip_rsvp_oper:ControllerBrief";
        key "controller-name";
        description "Brief info about an RSVP-enabled controller";
        leaf controller-name {
          xr:xr-xml-map "ip_rsvp_oper:ControllerName";
          type xr:Interface-name;
          description "Controller Name";
        }
        uses RSVP-MGMT-INTERFACE-COMPACT;
      }
    }

    container pxsb-details {
      xr:xr-xml-map "ip_rsvp_oper:PXSBDetailTable";
      description "Table of detailed PXSB info";

      list pxsb-detail {
        xr:xr-xml-map "ip_rsvp_oper:PXSBDetail";
        description "Detailed PXSB info";
        leaf destination-address {
          xr:xr-xml-map "ip_rsvp_oper:DestinationAddress";
          type inet:ipv4-address-no-zone;
          description "Destination Address";
        }
        leaf destination-port {
          xr:xr-xml-map "ip_rsvp_oper:DestinationPort";
          type int32;
          description "Destination Port";
        }
        leaf protocol {
          xr:xr-xml-map "ip_rsvp_oper:Protocol";
          type int32;
          description "Protocol";
        }
        leaf extended-tunnel-id {
          xr:xr-xml-map "ip_rsvp_oper:ExtendedTunnelID";
          type inet:ipv4-address-no-zone;
          description "Extended Tunnel ID";
        }
        leaf session-type {
          xr:xr-xml-map "ip_rsvp_oper:SessionType";
          type Rsvp-session;
          description "Session Type";
        }
        leaf p2mp-id {
          xr:xr-xml-map "ip_rsvp_oper:P2MP_ID";
          type int32;
          description "P2MP ID";
        }
        leaf source-address {
          xr:xr-xml-map "ip_rsvp_oper:SourceAddress";
          type inet:ipv4-address-no-zone;
          description "Source Address";
        }
        leaf source-port {
          xr:xr-xml-map "ip_rsvp_oper:SourcePort";
          type int32;
          description "Source Port";
        }
        leaf sub-group-origin {
          xr:xr-xml-map "ip_rsvp_oper:SubGroupOrigin";
          type inet:ipv4-address-no-zone;
          description "Subgroup Origin";
        }
        leaf sub-group-id {
          xr:xr-xml-map "ip_rsvp_oper:SubGroupID";
          type int32;
          description "Subgroup ID";
        }
        leaf vrf-name {
          xr:xr-xml-map "ip_rsvp_oper:VRFName";
          type xr:Cisco-ios-xr-string;
          description "VRF Name";
        }
        uses RSVP-MGMT-PXSB-DETAIL;
      }
    }

    container rxsb-details {
      xr:xr-xml-map "ip_rsvp_oper:RXSBDetailTable";
      description "Table of detailed RXSB info";

      list rxsb-detail {
        xr:xr-xml-map "ip_rsvp_oper:RXSBDetail";
        description "Detailed RXSB info";
        leaf destination-address {
          xr:xr-xml-map "ip_rsvp_oper:DestinationAddress";
          type inet:ipv4-address-no-zone;
          description "Destination Address";
        }
        leaf destination-port {
          xr:xr-xml-map "ip_rsvp_oper:DestinationPort";
          type int32;
          description "Destination Port";
        }
        leaf protocol {
          xr:xr-xml-map "ip_rsvp_oper:Protocol";
          type int32;
          description "Protocol";
        }
        leaf extended-tunnel-id {
          xr:xr-xml-map "ip_rsvp_oper:ExtendedTunnelID";
          type inet:ipv4-address-no-zone;
          description "Extended Tunnel ID";
        }
        leaf session-type {
          xr:xr-xml-map "ip_rsvp_oper:SessionType";
          type Rsvp-session;
          description "Session Type";
        }
        leaf p2mp-id {
          xr:xr-xml-map "ip_rsvp_oper:P2MP_ID";
          type int32;
          description "P2MP ID";
        }
        leaf source-address {
          xr:xr-xml-map "ip_rsvp_oper:SourceAddress";
          type inet:ipv4-address-no-zone;
          description "Source Address";
        }
        leaf source-port {
          xr:xr-xml-map "ip_rsvp_oper:SourcePort";
          type int32;
          description "Source Port";
        }
        leaf sub-group-origin {
          xr:xr-xml-map "ip_rsvp_oper:SubGroupOrigin";
          type inet:ipv4-address-no-zone;
          description "Subgroup Origin";
        }
        leaf sub-group-id {
          xr:xr-xml-map "ip_rsvp_oper:SubGroupID";
          type int32;
          description "Subgroup ID";
        }
        leaf vrf-name {
          xr:xr-xml-map "ip_rsvp_oper:VRFName";
          type xr:Cisco-ios-xr-string;
          description "VRF Name";
        }
        uses RSVP-MGMT-RXSB-DETAIL;
      }
    }
    uses INTERFACE-NEIGHBOR-BRIEF-TABLE;
    uses AUTHENTICATION-BRIEF-TABLE;
    uses SESSION-BRIEF-TABLE;
    uses PSB-DETAILED-TABLE;
    uses FRR-SUMMARY;
    uses RSB-DETAILED-TABLE;
    uses INTERFACE-SUMMARY-TABLE;
    uses HELLO-INSTANCE-BRIEF-TABLE;
    uses AUTHENTICATION-DETAIL-TABLE;
    uses RSB-BRIEF-TABLE;
    uses OPEN-CONFIG;
    uses COUNTERS;
    uses INTERFACE-DETAILED-TABLE;
    uses GRACEFUL-RESTART;
    uses HELLO-INTERFACE-INSTANCE-BRIEF-TABLE;
    uses HELLO-INTERFACE-INSTANCE-DETAIL-TABLE;
    uses INTERFACE-NEIGHBOR-DETAIL-TABLE;
    uses NSR;
    uses SUMMARY;
    uses FRR-TABLE;
    uses REQUEST-BRIEF-TABLE;
    uses REQUEST-DETAIL-TABLE;
    uses INTERFACE-BRIEF-TABLE;
    uses SESSION-DETAILED-TABLE;
    uses HELLO-INSTANCE-DETAIL-TABLE;
    uses GLOBAL-NEIGHBOR-DETAIL-TABLE;
    uses PSB-BRIEF-TABLE;
    uses GLOBAL-NEIGHBOR-BRIEF-TABLE;
  }
}
