module Cisco-IOS-XR-ipv6-new-dhcpv6d-oper {

  /*** NAMESPACE / PREFIX DEFINITION ***/

  namespace "http://cisco.com/ns/yang"+
    "/Cisco-IOS-XR-ipv6-new-dhcpv6d-oper";


  prefix "ipv6-new-dhcpv6d-oper";

  /*** LINKAGE (IMPORTS / INCLUDES) ***/

  import Cisco-IOS-XR-types { prefix "xr"; }

  include Cisco-IOS-XR-ipv6-new-dhcpv6d-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ipv6-new-dhcpv6d package operational data.

     This module contains definitions
     for the following management objects:
       dhcpv6: IPV6 DHCPD operational data

     Copyright (c) 2013-2016 by Cisco Systems, Inc.
     All rights reserved.";

  revision "2015-11-09" {
    description
      "IOS XR 6.0 revision.";
  }


  container dhcpv6 {
    xr:xr-xml-map "ipv6_dhcpd_oper:DHCPv6";
    config false;
    description "IPV6 DHCPD operational data";

    container database {
      xr:xr-xml-map "ipv6_dhcpd_oper:Database";
      description "DHCP database";
      uses IPV6-DHCPD-DATABASE;
    }

    container nodes {
      xr:xr-xml-map "ipv6_dhcpd_oper:NodeTable";
      description "IPv6 DHCP list of nodes";

      list node {
        xr:xr-xml-map "ipv6_dhcpd_oper:Node";
        key "node-name";
        description "IPv6 DHCP particular node name";

        container proxy {
          xr:xr-xml-map "dhcp_ipv6_proxy_oper:Proxy";
          description "IPv6 DHCP proxy operational data";

          container vrfs {
            xr:xr-xml-map "dhcp_ipv6_proxy_oper:VRFTable";
            description "DHCPV6 proxy list of VRF names";

            list vrf {
              xr:xr-xml-map "dhcp_ipv6_proxy_oper:VRF";
              key "vrf-name";
              description "IPv6 DHCP proxy VRF name";

              container statistics {
                xr:xr-xml-map "dhcp_ipv6_proxy_oper:Statistics";
                description "IPv6 DHCP proxy statistics";
                uses IPV6-DHCPV6D-TYPE;
              }
              leaf vrf-name {
                xr:xr-xml-map "dhcp_ipv6_proxy_oper:VRFName";
                type xr:Cisco-ios-xr-string;
                description "VRF name";
              }
            }
          }

          container profiles {
            xr:xr-xml-map "dhcp_ipv6_proxy_oper:ProfileTable";
            description "IPv6 DHCP proxy profile";

            list profile {
              xr:xr-xml-map "dhcp_ipv6_proxy_oper:Profile";
              key "profile-name";
              description "IPv6 DHCP proxy profile";

              container throttle-infos {
                xr:xr-xml-map "dhcp_ipv6_proxy_oper:ThrottleTable";
                description "DHCPV6 throttle table";

                list throttle-info {
                  xr:xr-xml-map "dhcp_ipv6_proxy_oper:ThrottleInfo";
                  key "mac-address";
                  description
                    "IPv6 DHCP proxy profile Throttle Info";
                  leaf mac-address {
                    xr:xr-xml-map "dhcp_ipv6_proxy_oper:MACAddress";
                    type xr:Cisco-ios-xr-string;
                    description "MAC address";
                  }
                  uses IPV6-DHCPV6D-MAC-THROTTLE;
                }
              }

              container info {
                xr:xr-xml-map "dhcp_ipv6_proxy_oper:Info";
                description "IPv6 DHCP proxy profile Info";
                uses IPV6-DHCPV6D-PROXY-PROFILE;
              }
              leaf profile-name {
                xr:xr-xml-map "dhcp_ipv6_proxy_oper:ProfileName";
                type xr:Cisco-ios-xr-string;
                description "Profile name";
              }
            }
          }

          container statistics {
            xr:xr-xml-map "dhcp_ipv6_proxy_oper:Statistics";
            description "DHCPv6 proxy statistics";
            uses IPV6-DHCPV6D-PROXY-STATS;
          }

          container binding {
            xr:xr-xml-map "dhcp_ipv6_proxy_oper:Binding";
            description "DHCPV6 proxy bindings";

            container clients {
              xr:xr-xml-map "dhcp_ipv6_proxy_oper:ClientTable";
              description "DHCPV6 proxy client bindings";

              list client {
                xr:xr-xml-map "dhcp_ipv6_proxy_oper:Client";
                key "client-id";
                description "Single DHCPV6 proxy binding";
                leaf client-id {
                  xr:xr-xml-map "dhcp_ipv6_proxy_oper:ClientID";
                  type xr:Cisco-ios-xr-string;
                  description "Client ID";
                }
                uses IPV6-DHCPV6D-PROXY-BINDING;
              }
            }

            container summary {
              xr:xr-xml-map "dhcp_ipv6_proxy_oper:Summary";
              description "DHCPV6 proxy binding summary";
              uses IPV6-DHCPV6D-PROXY-BINDINGS-SUMMARY;
            }
          }
        }

        container server {
          xr:xr-xml-map "dhcp_ipv6_server_oper:Server";
          description "IPv6 DHCP server operational data";

          container binding {
            xr:xr-xml-map "dhcp_ipv6_server_oper:Binding";
            description "DHCPV6 server bindings";

            container summary {
              xr:xr-xml-map "dhcp_ipv6_server_oper:Summary";
              description "DHCPV6 server binding summary";
              uses IPV6-DHCPV6D-SERVER-BINDINGS-SUMMARY;
            }

            container clients {
              xr:xr-xml-map "dhcp_ipv6_server_oper:ClientTable";
              description "DHCPV6 server client bindings";

              list client {
                xr:xr-xml-map "dhcp_ipv6_server_oper:Client";
                key "client-id";
                description "Single DHCPV6 server binding";
                leaf client-id {
                  xr:xr-xml-map "dhcp_ipv6_server_oper:ClientID";
                  type xr:Cisco-ios-xr-string;
                  description "Client ID";
                }
                uses IPV6-DHCPV6D-SERVER-BINDING;
              }
            }
          }

          container vrfs {
            xr:xr-xml-map "dhcp_ipv6_server_oper:VRFTable";
            description "DHCPV6 server list of VRF names";

            list vrf {
              xr:xr-xml-map "dhcp_ipv6_server_oper:VRF";
              key "vrf-name";
              description "IPv6 DHCP server VRF name";

              container statistics {
                xr:xr-xml-map "dhcp_ipv6_server_oper:Statistics";
                description "IPv6 DHCP server statistics";
                uses IPV6-DHCPV6D-TYPE;
              }
              leaf vrf-name {
                xr:xr-xml-map "dhcp_ipv6_server_oper:VRFName";
                type xr:Cisco-ios-xr-string;
                description "VRF name";
              }
            }
          }

          container profiles {
            xr:xr-xml-map "dhcp_ipv6_server_oper:ProfileTable";
            description "IPv6 DHCP server profile";

            list profile {
              xr:xr-xml-map "dhcp_ipv6_server_oper:Profile";
              key "profile-name";
              description "IPv6 DHCP server profile";

              container info {
                xr:xr-xml-map "dhcp_ipv6_server_oper:Info";
                description "IPv6 DHCP server profile Info";
                uses IPV6-DHCPV6D-SERVER-PROFILE;
              }

              container throttle-infos {
                xr:xr-xml-map "dhcp_ipv6_server_oper:ThrottleTable";
                description "DHCPV6 throttle table";

                list throttle-info {
                  xr:xr-xml-map "dhcp_ipv6_server_oper:ThrottleInfo";
                  key "mac-address";
                  description
                    "IPv6 DHCP server profile Throttle Info";
                  leaf mac-address {
                    xr:xr-xml-map "dhcp_ipv6_server_oper:MACAddress";
                    type xr:Cisco-ios-xr-string;
                    description "MAC address";
                  }
                  uses IPV6-DHCPV6D-MAC-THROTTLE;
                }
              }
              leaf profile-name {
                xr:xr-xml-map "dhcp_ipv6_server_oper:ProfileName";
                type xr:Cisco-ios-xr-string;
                description "Profile name";
              }
            }
          }

          container statistics {
            xr:xr-xml-map "dhcp_ipv6_server_oper:Statistics";
            description "DHCPv6 server statistics";
            uses IPV6-DHCPV6D-SERVER-STATS;
          }

          container binding-options {
            xr:xr-xml-map "dhcp_ipv6_server_oper:BindingOptions";
            description "DHCPv6 server binding with options";

            container mac-bind-options {
              xr:xr-xml-map "dhcp_ipv6_server_oper:MacFilter";
              description "DHCPv6 server binding from MAC address";

              list mac-bind-option {
                xr:xr-xml-map "dhcp_ipv6_server_oper:MacBindOptions";
                key "mac-address";
                description "DHCPv6 server binding with options";
                leaf mac-address {
                  xr:xr-xml-map "dhcp_ipv6_server_oper:MACAddress";
                  type xr:Cisco-ios-xr-string;
                  description "MAC address";
                }
                uses IPV6-DHCPV6D-SERVER-BINDING-OPTIONS;
              }
            }

            container duid-bind-options {
              xr:xr-xml-map "dhcp_ipv6_server_oper:DuidFilter";
              description "DHCPv6 server binding from DUID";

              list duid-bind-option {
                xr:xr-xml-map "dhcp_ipv6_server_oper:DuidBindOption"+
                  "s";
                key "duid";
                description "DHCPv6 server binding with options";
                leaf duid {
                  xr:xr-xml-map "dhcp_ipv6_server_oper:DUID";
                  type xr:Cisco-ios-xr-string;
                  description "DUID of Binding";
                }
                uses IPV6-DHCPV6D-SERVER-BINDING-OPTIONS;
              }
            }
          }
        }

        container relay {
          xr:xr-xml-map "dhcp_ipv6_relay_oper:Relay";
          description "IPv6 DHCP relay operational data";

          container statistics {
            xr:xr-xml-map "dhcp_ipv6_relay_oper:Statistics";
            description "DHCPv6 relay statistics";
            uses IPV6-DHCPV6D-RELAY-STATS;
          }

          container binding {
            xr:xr-xml-map "dhcp_ipv6_relay_oper:Binding";
            description "DHCPV6 relay bindings";

            container summary {
              xr:xr-xml-map "dhcp_ipv6_relay_oper:Summary";
              description "DHCPV6 relay binding summary";
              uses IPV6-DHCPV6D-RELAY-BINDINGS-SUMMARY;
            }

            container clients {
              xr:xr-xml-map "dhcp_ipv6_relay_oper:ClientTable";
              description "DHCPV6 relay client bindings";

              list client {
                xr:xr-xml-map "dhcp_ipv6_relay_oper:Client";
                key "client-id";
                description "Single DHCPV6 relay binding";
                leaf client-id {
                  xr:xr-xml-map "dhcp_ipv6_relay_oper:ClientID";
                  type xr:Cisco-ios-xr-string;
                  description "Client ID";
                }
                uses IPV6-DHCPV6D-RELAY-ROUTE-BINDING;
              }
            }
          }

          container vrfs {
            xr:xr-xml-map "dhcp_ipv6_relay_oper:VRFTable";
            description "DHCPV6 relay list of VRF names";

            list vrf {
              xr:xr-xml-map "dhcp_ipv6_relay_oper:VRF";
              key "vrf-name";
              description "IPv6 DHCP relay VRF name";

              container statistics {
                xr:xr-xml-map "dhcp_ipv6_relay_oper:Statistics";
                description "IPv6 DHCP relay statistics";
                uses IPV6-DHCPV6D-TYPE;
              }
              leaf vrf-name {
                xr:xr-xml-map "dhcp_ipv6_relay_oper:VRFName";
                type xr:Cisco-ios-xr-string;
                description "VRF name";
              }
            }
          }
        }
        leaf node-name {
          xr:xr-xml-map "ipv6_dhcpd_oper:NodeName";
          type xr:Node-id;
          description "Node name";
        }
      }
    }
  }
}
