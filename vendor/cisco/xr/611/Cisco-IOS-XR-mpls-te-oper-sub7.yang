submodule Cisco-IOS-XR-mpls-te-oper-sub7 {

  belongs-to Cisco-IOS-XR-mpls-te-oper {
    prefix Cisco-IOS-XR-mpls-te-oper;
  }

  /*** LINKAGE (IMPORTS / INCLUDES) ***/

  import ietf-inet-types { prefix "inet"; }

  import Cisco-IOS-XR-types { prefix "xr"; }

  include Cisco-IOS-XR-mpls-te-oper-sub5 {
    revision-date 2015-11-09;
  }

  include Cisco-IOS-XR-mpls-te-oper-sub6 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR mpls-te package operational data.

     Copyright (c) 2013-2016 by Cisco Systems, Inc.
     All rights reserved.";

  revision "2015-11-09" {
    description
      "IOS XR 6.0 revision.";
  }

  typedef Te-stats-sig-filter {
    type enumeration {
      enum te-stat-sig-filter-vif {
        description "te stat sig filter vif";
      }
      enum te-stat-sig-filter-lsp {
        description "te stat sig filter lsp";
      }
    }
    description "TE Signaling Filter types";
  }

  grouping MPLS-TE-BFD-SESSION-COUNTERS {
    description "TE BFDoLM counters";
    leaf session-create-events {
      xr:xr-xml-map "te_stats:SessionCreateEvents";
      type uint32;
      description "The number of BFDOverLM session create events";
    }
    leaf session-up-events {
      xr:xr-xml-map "te_stats:SessionUpEvents";
      type uint32;
      description "The number of BFDOverLM session up events";
    }
    leaf session-creation-failed-events {
      xr:xr-xml-map "te_stats:SessionCreationFailedEvents";
      type uint32;
      description
        "The number of BFDOverLM session creation failed
        events";
    }
    leaf session-down-events {
      xr:xr-xml-map "te_stats:SessionDownEvents";
      type uint32;
      description "The number of BFDOverLM session down events";
    }
    leaf session-admin-down-events {
      xr:xr-xml-map "te_stats:SessionAdminDownEvents";
      type uint32;
      description
        "The number of BFDOverLM session admin down
        events";
    }
    leaf session-gracefully-delete-events {
      xr:xr-xml-map "te_stats:SessionGracefullyDeleteEvents";
      type uint32;
      description
        "The number of BFDOverLM session gracefully
        delete events";
    }
    leaf session-non-gracefully-delete-events {
      xr:xr-xml-map "te_stats:SessionNonGracefullyDeleteEvents";
      type uint32;
      description
        "The number of BFDOverLM session non gracefully
        delete events";
    }
    leaf session-replay-events {
      xr:xr-xml-map "te_stats:SessionReplayEvents";
      type uint32;
      description "The number of BFDOverLSP session replay events";
    }
  }

  grouping MPLS-TE-BFD-COUNTERS {
    description "TE BFD Counters";

    container bfd-over-lsp-head-counters {
      description "BFD over Head-end LSPs Cumulative Counters";
      uses MPLS-TE-BFD-LSP-COUNTERS;
    }

    container sbfd-over-lsp-head-counters {
      description "SBFD over Head-end LSPs Cumulative Counters";
      uses MPLS-TE-BFD-LSP-COUNTERS;
    }

    container bfd-over-lsp-tail-counters {
      description "BFD over Tail-end LSPs Cumulative Counters";
      uses MPLS-TE-BFD-SESSION-COUNTERS;
    }

    container bf-do-lm-counters {
      description "BFD over Links Cumulative Counters";
      uses MPLS-TE-BFD-SESSION-COUNTERS;
    }
    leaf last-cleared-timestamp {
      xr:xr-xml-map "te_stats:LastClearedTimestamp";
      type uint32;
      description
        "The timestamp when these stats are cleared
        relative to Jan 1, 1970";
    }
  }

  grouping TE-STATS-SIG-FILTER-DATA-U {
    description "Union of TE Signalling Filter data";

    container te-signalling-filter-vif {
      when "../statistics-filter = 'te-stat-sig-filter-vif'" {
        description
          "../StatisticsFilter = 'TE_STAT_SIG_FILTER_VIF'";
      }
      description "VIF data";
      uses TE-STATS-BAG-VIF;
    }

    container te-signalling-filter-lsp {
      when "../statistics-filter = 'te-stat-sig-filter-lsp'" {
        description
          "../StatisticsFilter = 'TE_STAT_SIG_FILTER_LSP'";
      }
      description "LSP data";
      uses TE-STATS-BAG-LSP;
    }
    leaf statistics-filter {
      xr:xr-xml-map "te_stats:StatisticsFilter";
      type Te-stats-sig-filter;
      description "StatisticsFilter";
    }
  }

  grouping TE-STATS-SIG-FILTER {
    description "TE Signaling Filter Data";

    container te-signalling-filter-data {
      description "TE Signaling Filter data";
      uses TE-STATS-SIG-FILTER-DATA-U;
    }
  }

  grouping TE-STATS-BAG-LSP {
    description "MPLS TE LSP Statistics";

    container statistics {
      description "LSP statistics";
      uses TE-STATS-SIG;
    }
    leaf tunnel-name {
      xr:xr-xml-map "te_stats:TunnelName";
      type string;
      description "Tunnel Name";
    }

    list s2l-statistic {
      description "List of S2L Statistics";
      uses TE-STATS-BAG-S2L;
    }
  }

  grouping TE-STATS-BAG-S2L {
    description "MPLS TE S2L Statistics";

    container statistics {
      description "S2L stats";
      uses TE-STATS-SIG;
    }
    leaf sub-group-originator {
      xr:xr-xml-map "te_stats:SubGroupOriginator";
      type inet:ipv4-address;
      description "Subgroup Originator";
    }
    leaf sub-group-id {
      xr:xr-xml-map "te_stats:SubGroupID";
      type uint16;
      description "subgroup ID";
    }
    leaf destination-address {
      xr:xr-xml-map "te_stats:DestinationAddress";
      type inet:ipv4-address;
      description "Destination address";
    }
  }

  grouping TE-STATS-BAG-DEST {
    description "MPLS TE Destination Statistics";

    container statistics {
      description "Destination stats";
      uses TE-STATS-SIG;
    }
    leaf destination-address {
      xr:xr-xml-map "te_stats:DestinationAddress";
      type inet:ipv4-address;
      description "Destination address";
    }

    list s2l-statistic {
      description "List of S2L Stats";
      uses TE-STATS-BAG-S2L;
    }
  }

  grouping TE-STATS-SIG {
    description "Send-Recv count for TE Signaling";
    leaf tx-event-unknown {
      xr:xr-xml-map "te_stats:TXEventUnknown";
      type uint32;
      description "Unknown TX events";
    }
    leaf tx-path-create-event {
      xr:xr-xml-map "te_stats:TXPathCreateEvent";
      type uint32;
      description "TX Path Create event";
    }
    leaf tx-path-change-event {
      xr:xr-xml-map "te_stats:TXPathChangeEvent";
      type uint32;
      description "TX Path Change event";
    }
    leaf tx-path-delete-event {
      xr:xr-xml-map "te_stats:TXPathDeleteEvent";
      type uint32;
      description "TX Path Delete event";
    }
    leaf tx-path-error-event {
      xr:xr-xml-map "te_stats:TXPathErrorEvent";
      type uint32;
      description "TX Path Error event";
    }
    leaf tx-resv-create-event {
      xr:xr-xml-map "te_stats:TXResvCreateEvent";
      type uint32;
      description "TX Resv Create event";
    }
    leaf tx-resv-change-event {
      xr:xr-xml-map "te_stats:TXResvChangeEvent";
      type uint32;
      description "TX Resv Change event";
    }
    leaf tx-resv-delete-event {
      xr:xr-xml-map "te_stats:TXResvDeleteEvent";
      type uint32;
      description "TX Resv Delete event";
    }
    leaf tx-resv-error-event {
      xr:xr-xml-map "te_stats:TXResvErrorEvent";
      type uint32;
      description "TX Resv Error event";
    }
    leaf tx-path-reeval-query-event {
      xr:xr-xml-map "te_stats:TXPathReevalQueryEvent";
      type uint32;
      description "TX Path Reeval Query event";
    }
    leaf rx-event-unknown {
      xr:xr-xml-map "te_stats:RXEventUnknown";
      type uint32;
      description "RX Unknown events";
    }
    leaf rx-path-create-event {
      xr:xr-xml-map "te_stats:RXPathCreateEvent";
      type uint32;
      description "RX Path Create event";
    }
    leaf rx-path-change-event {
      xr:xr-xml-map "te_stats:RXPathChangeEvent";
      type uint32;
      description "RX Path Change event";
    }
    leaf rx-path-delete-event {
      xr:xr-xml-map "te_stats:RXPathDeleteEvent";
      type uint32;
      description "RX Path Delete event";
    }
    leaf rx-path-error-event {
      xr:xr-xml-map "te_stats:RXPathErrorEvent";
      type uint32;
      description "RX Path Error event";
    }
    leaf rx-resv-create-event {
      xr:xr-xml-map "te_stats:RXResvCreateEvent";
      type uint32;
      description "RX Resv Create event";
    }
    leaf rx-resv-change-event {
      xr:xr-xml-map "te_stats:RXResvChangeEvent";
      type uint32;
      description "RX Resv Change event";
    }
    leaf rx-resv-delete-event {
      xr:xr-xml-map "te_stats:RXResvDeleteEvent";
      type uint32;
      description "RX Resv Delete event";
    }
    leaf rx-resv-error-event {
      xr:xr-xml-map "te_stats:RXResvErrorEvent";
      type uint32;
      description "RX Resv Error event";
    }
    leaf rx-path-reeval-query-event {
      xr:xr-xml-map "te_stats:RXPathReevalQueryEvent";
      type uint32;
      description "RX Path Reeval Query event";
    }
    leaf tx-backup-assign-event {
      xr:xr-xml-map "te_stats:TXBackupAssignEvent";
      type uint32;
      description "Backup Assign event";
    }
    leaf rx-backup-assign-err-event {
      xr:xr-xml-map "te_stats:RXBackupAssignErrEvent";
      type uint32;
      description "Error on Backup Assign event";
    }
    leaf events-total-count {
      xr:xr-xml-map "te_stats:EventsTotalCount";
      type uint32;
      description "Total TE Signalling event count";
    }
    leaf events-count {
      xr:xr-xml-map "te_stats:EventsCount";
      type uint32;
      description "TE Signaling event count";
    }
  }

  grouping TE-STATS-BAG-VIF {
    description "MPLS TE VIF Statistics";

    container statistics {
      description "VIF stats";
      uses TE-STATS-SIG;
    }
    leaf tunnel-name {
      xr:xr-xml-map "te_stats:TunnelName";
      type string;
      description "Tunnel Name";
    }
    leaf tunnel-sig-name {
      xr:xr-xml-map "te_stats:TunnelSigName";
      type string;
      description "Tunnel Signalled-Name";
    }
    leaf lsp-id {
      xr:xr-xml-map "te_stats:LSP_ID";
      type uint16;
      description "LSP ID";
    }

    list destination-statistic {
      description "List of Destination Stats";
      uses TE-STATS-BAG-DEST;
    }
  }

  grouping MPLS-TE-SYNC-COUNT-INFO {
    description "MPLS TE NSR and ISSU counters";
    leaf last-cleared-timestamp {
      xr:xr-xml-map "te_stats:LastClearedTimestamp";
      type uint32;
      units "second";
      description
        "The timestamp, in seconds, when these statistics
        are cleared              since 00:00:00 UTC,
        January 1, 1970";
    }
    leaf role {
      xr:xr-xml-map "te_stats:Role";
      type Te-proc-role;
      description "Process role";
    }
    leaf last-idt-states {
      xr:xr-xml-map "te_stats:LastIDTStates";
      type uint32;
      description "Last IDT States";
    }
    leaf total-states {
      xr:xr-xml-map "te_stats:TotalStates";
      type uint32;
      description "Total states";
    }
    leaf total-deletions {
      xr:xr-xml-map "te_stats:TotalDeletions";
      type uint32;
      description "Total deletions";
    }
    leaf total-nac-ks {
      xr:xr-xml-map "te_stats:TotalNACKs";
      type uint64;
      description "Total NACKs";
    }
    leaf total-id-ts {
      xr:xr-xml-map "te_stats:TotalIDTs";
      type uint32;
      description "Total IDTs";
    }
  }

  grouping MPLS-TE-SOFT-PREEMPTION-STATS {
    description "Soft preemption stats ";
    leaf last-cleared-timestamp {
      xr:xr-xml-map "te_stats:LastClearedTimestamp";
      type uint32;
      description
        "The timestamp when these stats are cleared
        relative to Jan 1, 1970";
    }
    leaf soft-preemption-events {
      xr:xr-xml-map "te_stats:SoftPreemptionEvents";
      type uint32;
      description "The number of soft preemption events triggered";
    }
    leaf soft-preempted-ls-ps {
      xr:xr-xml-map "te_stats:SoftPreemptedLSPs";
      type uint32;
      description
        "The number of LSPs that have been soft preempted
        at this node";
    }
    leaf timed-out-soft-preempted-lsp-ss {
      xr:xr-xml-map "te_stats:TimedOutSoftPreemptedLSPSs";
      type uint32;
      description
        "The number of LSPs that have been soft preempted
        and timed out at this node";
    }
    leaf torn-down-soft-preempted-ls-ps {
      xr:xr-xml-map "te_stats:TornDownSoftPreemptedLSPs";
      type uint32;
      description
        "The number of LSPs that have been soft preempted
        at this node and torn down before timing out";
    }
    leaf frr-triggered-soft-preempted-lsp-ss {
      xr:xr-xml-map "te_stats:FRRTriggeredSoftPreemptedLSPSs";
      type uint32;
      description
        "The number of LSPs that have been soft preempted
        and then fast rerouted at this node";
    }
    leaf minimum-time-in-soft-preempted-state {
      xr:xr-xml-map "te_stats:MinimumTimeInSoftPreemptedState";
      type uint16;
      units "second";
      description
        "The minimum number of seconds an LSP remained in
        the soft preempted state";
    }
    leaf time-in-soft-preempted-state-max {
      xr:xr-xml-map "te_stats:TimeInSoftPreemptedStateMax";
      type uint16;
      units "second";
      description
        "The maximum number of seconds an LSP remained in
        the soft preempted state without being hard
        preempted";
    }
    leaf time-in-soft-preempted-state-avg {
      xr:xr-xml-map "te_stats:TimeInSoftPreemptedStateAvg";
      type uint16;
      units "second";
      description
        "The average number of seconds an LSP remained in
        the soft preempted state. This excludes the
        timed out LSPs";
    }
    leaf soft-preempted-head-ls-ps {
      xr:xr-xml-map "te_stats:SoftPreemptedHeadLSPs";
      type uint32;
      description
        "Number of soft preempted LSPs at the headend.
        This is relevant to the headend";
    }
    leaf reoptimized-soft-preempted-ls-ps {
      xr:xr-xml-map "te_stats:ReoptimizedSoftPreemptedLSPs";
      type uint32;
      description
        "Number of soft preemption LSPs that are
        reoptimized. This is relevant to the headend";
    }
    leaf torndown-soft-preempted-ls-ps {
      xr:xr-xml-map "te_stats:TorndownSoftPreemptedLSPs";
      type uint32;
      description
        "Number of soft preemption LSPs that are torn
        down instead of being reoptimized. This is
        relevant to the headend.";
    }
    leaf path-protected-switchover-soft-preempted-ls-ps {
      xr:xr-xml-map "te_stats:PathProtectedSwitchoverSoftPreemptedL"+
        "SPs";
      type uint32;
      description
        "Number of soft preemption LSPs that are replaced
        with the path protection LSP. This is relevant
        to the headend";
    }
  }

  grouping TE-STATS-AUTOBACKUP-COUNTERS {
    description "TE Auto Backup Counter Types";
    leaf total-tunnels {
      xr:xr-xml-map "te_stats:TotalTunnels";
      type uint32;
      description "Total auto backup tunnels";
    }
    leaf next-hop-tunnels {
      xr:xr-xml-map "te_stats:NextHopTunnels";
      type uint32;
      description "Next hop auto backup tunnels only";
    }
    leaf next-next-hop-tunnels {
      xr:xr-xml-map "te_stats:NextNextHopTunnels";
      type uint32;
      description "Next next hop auto backup tunnels only";
    }
  }

  grouping TE-STATS-AUTOBACKUP {
    description "Counters for TE Autobackup";

    container created {
      description "Number of connected auto backup tunnels";
      uses TE-STATS-AUTOBACKUP-COUNTERS;
    }

    container connected {
      description "Number of connected auto backup tunnels";
      uses TE-STATS-AUTOBACKUP-COUNTERS;
    }

    container removed-down {
      description
        "Number of NNHOP auto backup tunnels removed
        while down";
      uses TE-STATS-AUTOBACKUP-COUNTERS;
    }

    container removed-unused {
      description
        "Number of auto backup tunnels removed while
        unused";
      uses TE-STATS-AUTOBACKUP-COUNTERS;
    }

    container removed-in-use {
      description
        "Number of auto backup tunnels removed while up
        and in use";
      uses TE-STATS-AUTOBACKUP-COUNTERS;
    }

    container removed-range-exceeded {
      description
        "Number of auto backup tunnel attempts rejected
        because the total number exceeds the range";
      uses TE-STATS-AUTOBACKUP-COUNTERS;
    }
    leaf last-cleared-time {
      xr:xr-xml-map "te_stats:LastClearedTime";
      type uint32;
      description "Timestamp when the stat has been cleared";
    }
  }

  grouping TE-STATS-AUTOMESH {
    description "Counters for TE Automesh";
    leaf created {
      xr:xr-xml-map "te_stats:Created";
      type uint32;
      description "Number of connected automesh tunnels";
    }
    leaf connected {
      xr:xr-xml-map "te_stats:Connected";
      type uint32;
      description "Number of connected automesh tunnels";
    }
    leaf removed-unused {
      xr:xr-xml-map "te_stats:RemovedUnused";
      type uint32;
      description "Number of automesh tunnels removed while unused";
    }
    leaf removed-in-use {
      xr:xr-xml-map "te_stats:RemovedInUse";
      type uint32;
      description
        "Number of automesh tunnels removed while up and
        in use";
    }
    leaf removed-range-exceeded {
      xr:xr-xml-map "te_stats:RemovedRangeExceeded";
      type uint32;
      description
        "Number of automesh tunnel attempts rejected
        because the total number exceeds the range";
    }
    leaf last-cleared-time {
      xr:xr-xml-map "te_stats:LastClearedTime";
      type uint32;
      units "second";
      description
        "Time at which these were last cleared in seconds
        since (in seconds since 1st Jan 1970 00:00:00)'";
    }
  }
}
