module Cisco-IOS-XR-manageability-perfmgmt-oper {

  /*** NAMESPACE / PREFIX DEFINITION ***/

  namespace "http://cisco.com/ns/yang"+
    "/Cisco-IOS-XR-manageability-perfmgmt-oper";


  prefix "manageability-perfmgmt-oper";

  /*** LINKAGE (IMPORTS / INCLUDES) ***/

  import ietf-inet-types { prefix "inet"; }

  import Cisco-IOS-XR-types { prefix "xr"; }

  include Cisco-IOS-XR-manageability-perfmgmt-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR manageability-perfmgmt package operational data.

     This module contains definitions
     for the following management objects:
       perf-mgmt: Performance Management agent operational data

     Copyright (c) 2013-2016 by Cisco Systems, Inc.
     All rights reserved.";

  revision "2015-11-09" {
    description
      "IOS XR 6.0 revision.";
  }

  typedef Pm-process-id {
    type int32;
    description "Pm process id";
  }
  typedef Pm-sample-id {
    type int32;
    description "Pm sample id";
  }

  grouping MPLS {
    description "Common node of periodic, monitor";

    container mpls {
      xr:xr-xml-map "manageability_perf_oper:MPLS";
      description "Collected MPLS data";

      container ldp-neighbors {
        xr:xr-xml-map "manageability_perf_oper:LDPNeighborTable";
        description
          "LDP neighbors for which statistics are
          collected";

        list ldp-neighbor {
          xr:xr-xml-map "manageability_perf_oper:LDPNeighbor";
          key "nbr";
          description "Samples for a particular LDP neighbor";

          container samples {
            xr:xr-xml-map "manageability_perf_oper:LDPNeighborSampl"+
              "eTable";
            description "Samples for a particular LDP neighbor";

            list sample {
              xr:xr-xml-map "manageability_perf_oper:Sample";
              key "sample-id";
              description "LDP neighbor statistics sample";
              leaf sample-id {
                xr:xr-xml-map "manageability_perf_oper:SampleID";
                type Pm-sample-id;
                description "Sample ID";
              }
              uses PM-MPLS-LDP-BAG;
            }
          }
          leaf nbr {
            xr:xr-xml-map "manageability_perf_oper:Nbr";
            type inet:ipv4-address-no-zone;
            description "Neighbor Address";
          }
        }
      }
    }
  }

  grouping INTERFACE {
    description "Common node of periodic, monitor";

    container interface {
      xr:xr-xml-map "manageability_perf_oper:Interface";
      description "Collected Interface data";

      container generic-counter-interfaces {
        xr:xr-xml-map "manageability_perf_oper:GenericCounterInterf"+
          "aceTable";
        description
          "Interfaces for which Generic Counters are
          collected";

        list generic-counter-interface {
          xr:xr-xml-map "manageability_perf_oper:GenericCounterInte"+
            "rface";
          key "interface-name";
          description "Samples for a particular interface";

          container samples {
            xr:xr-xml-map "manageability_perf_oper:GenericCounterSa"+
              "mpleTable";
            description "Generic Counter samples for an interface";

            list sample {
              xr:xr-xml-map "manageability_perf_oper:Sample";
              key "sample-id";
              description "Generic Counters sample";
              leaf sample-id {
                xr:xr-xml-map "manageability_perf_oper:SampleID";
                type Pm-sample-id;
                description "Sample ID";
              }
              uses PM-INTERFACE-GENERIC-BAG;
            }
          }
          leaf interface-name {
            xr:xr-xml-map "manageability_perf_oper:InterfaceName";
            type xr:Interface-name;
            description "Interface Name";
          }
        }
      }

      container basic-counter-interfaces {
        xr:xr-xml-map "manageability_perf_oper:BasicCounterInterfac"+
          "eTable";
        description
          "Interfaces for which Basic Counters are
          collected";

        list basic-counter-interface {
          xr:xr-xml-map "manageability_perf_oper:BasicCounterInterf"+
            "ace";
          key "interface-name";
          description "Samples for a particular interface";

          container samples {
            xr:xr-xml-map "manageability_perf_oper:BasicCounterSamp"+
              "leTable";
            description "Basic Counter samples for an interface";

            list sample {
              xr:xr-xml-map "manageability_perf_oper:Sample";
              key "sample-id";
              description "Basic Counters sample";
              leaf sample-id {
                xr:xr-xml-map "manageability_perf_oper:SampleID";
                type Pm-sample-id;
                description "Sample ID";
              }
              uses PM-INTERFACE-BASIC-STATS;
            }
          }
          leaf interface-name {
            xr:xr-xml-map "manageability_perf_oper:InterfaceName";
            type xr:Interface-name;
            description "Interface Name";
          }
        }
      }

      container data-rate-interfaces {
        xr:xr-xml-map "manageability_perf_oper:DataRateInterfaceTab"+
          "le";
        description "Interfaces for which Data Rates are collected";

        list data-rate-interface {
          xr:xr-xml-map "manageability_perf_oper:DataRateInterface";
          key "interface-name";
          description "Samples for a particular interface";

          container samples {
            xr:xr-xml-map "manageability_perf_oper:DataRateSampleTa"+
              "ble";
            description "Data Rate samples for an interface";

            list sample {
              xr:xr-xml-map "manageability_perf_oper:Sample";
              key "sample-id";
              description "Data Rates sample";
              leaf sample-id {
                xr:xr-xml-map "manageability_perf_oper:SampleID";
                type Pm-sample-id;
                description "Sample ID";
              }
              uses PM-INTERFACE-DATARATE-BAG;
            }
          }
          leaf interface-name {
            xr:xr-xml-map "manageability_perf_oper:InterfaceName";
            type xr:Interface-name;
            description "Interface Name";
          }
        }
      }
    }
  }

  grouping NODE-TABLE {
    description "Common node of periodic, monitor";

    container nodes {
      xr:xr-xml-map "manageability_perf_oper:NodeTable";
      description "Nodes for which data is collected";

      list node {
        xr:xr-xml-map "manageability_perf_oper:Node";
        key "node-id";
        description "Node Instance";

        container sample-xr {
          xr:xr-xml-map "manageability_perf_oper:CPUSampleTable";
          description "Node CPU data";

          list sample {
            xr:xr-xml-map "manageability_perf_oper:Sample";
            key "sample-id";
            description "Node CPU data sample";
            leaf sample-id {
              xr:xr-xml-map "manageability_perf_oper:SampleID";
              type Pm-sample-id;
              description "Sample ID";
            }
            uses PM-NODE-CPU-BAG;
          }
        }

        container processes {
          xr:xr-xml-map "manageability_perf_oper:ProcessTable";
          description "Processes data";

          list process {
            xr:xr-xml-map "manageability_perf_oper:Process";
            key "process-id";
            description "Process data";

            container samples {
              xr:xr-xml-map "manageability_perf_oper:ProcessSampleT"+
                "able";
              description "Process data";

              list sample {
                xr:xr-xml-map "manageability_perf_oper:Sample";
                key "sample-id";
                description "Process data sample";
                leaf sample-id {
                  xr:xr-xml-map "manageability_perf_oper:SampleID";
                  type Pm-sample-id;
                  description "Sample ID";
                }
                uses PM-NODE-PROCESS-BAG;
              }
            }
            leaf process-id {
              xr:xr-xml-map "manageability_perf_oper:ProcessID";
              type Pm-process-id;
              description "Process ID";
            }
          }
        }

        container samples {
          xr:xr-xml-map "manageability_perf_oper:MemorySampleTable";
          description "Node Memory data";

          list sample {
            xr:xr-xml-map "manageability_perf_oper:Sample";
            key "sample-id";
            description "Node Memory data sample";
            leaf sample-id {
              xr:xr-xml-map "manageability_perf_oper:SampleID";
              type Pm-sample-id;
              description "Sample ID";
            }
            uses PM-NODE-MEM-BAG;
          }
        }
        leaf node-id {
          xr:xr-xml-map "manageability_perf_oper:NodeID";
          type xr:Node-id;
          description "Node ID";
        }
      }
    }
  }

  grouping OSPF {
    description "Common node of periodic, monitor";

    container ospf {
      xr:xr-xml-map "manageability_perf_oper:OSPF";
      description "Collected OSPF data";

      container ospfv2-protocol-instances {
        xr:xr-xml-map "manageability_perf_oper:OSPFv2ProtocolInstan"+
          "ceTable";
        description
          "OSPF v2 instances for which protocol statistics
          are collected";

        list ospfv2-protocol-instance {
          xr:xr-xml-map "manageability_perf_oper:OSPFv2ProtocolInst"+
            "ance";
          key "instance-name";
          description
            "Protocol samples for a particular OSPF v2
            instance";

          container samples {
            xr:xr-xml-map "manageability_perf_oper:OSPFv2ProtocolSa"+
              "mpleTable";
            description "Sample Table for an OSPV v2 instance";

            list sample {
              xr:xr-xml-map "manageability_perf_oper:Sample";
              key "sample-id";
              description "Generic Counters sample";
              leaf sample-id {
                xr:xr-xml-map "manageability_perf_oper:SampleID";
                type Pm-sample-id;
                description "Sample ID";
              }
              uses PM-OSPF-V2PROTO-BAG;
            }
          }
          leaf instance-name {
            xr:xr-xml-map "manageability_perf_oper:InstanceName";
            type xr:Cisco-ios-xr-string;
            description "OSPF Instance Name";
          }
        }
      }

      container ospfv3-protocol-instances {
        xr:xr-xml-map "manageability_perf_oper:OSPFv3ProtocolInstan"+
          "ceTable";
        description
          "OSPF v3 instances for which protocol statistics
          are collected";

        list ospfv3-protocol-instance {
          xr:xr-xml-map "manageability_perf_oper:OSPFv3ProtocolInst"+
            "ance";
          key "instance-name";
          description
            "Protocol samples for a particular OSPF v3
            instance";

          container samples {
            xr:xr-xml-map "manageability_perf_oper:OSPFv3ProtocolSa"+
              "mpleTable";
            description "Sample Table for an OSPV v3 instance";

            list sample {
              xr:xr-xml-map "manageability_perf_oper:Sample";
              key "sample-id";
              description "Generic Counters sample";
              leaf sample-id {
                xr:xr-xml-map "manageability_perf_oper:SampleID";
                type Pm-sample-id;
                description "Sample ID";
              }
              uses PM-OSPF-V3PROTO-BAG;
            }
          }
          leaf instance-name {
            xr:xr-xml-map "manageability_perf_oper:InstanceName";
            type xr:Cisco-ios-xr-string;
            description "OSPF Instance Name";
          }
        }
      }
    }
  }

  grouping BGP {
    description "Common node of periodic, monitor";

    container bgp {
      xr:xr-xml-map "manageability_perf_oper:BGP";
      description "Collected BGP data";

      container bgp-neighbors {
        xr:xr-xml-map "manageability_perf_oper:BGPNeighborTable";
        description "Neighbors for which statistics are collected";

        list bgp-neighbor {
          xr:xr-xml-map "manageability_perf_oper:BGPNeighbor";
          key "ip-address";
          description "Samples for particular neighbor";

          container samples {
            xr:xr-xml-map "manageability_perf_oper:BGPNeighborSampl"+
              "eTable";
            description "Sample Table for a BGP neighbor";

            list sample {
              xr:xr-xml-map "manageability_perf_oper:Sample";
              key "sample-id";
              description "Neighbor statistics sample";
              leaf sample-id {
                xr:xr-xml-map "manageability_perf_oper:SampleID";
                type Pm-sample-id;
                description "Sample ID";
              }
              uses PM-BGP-NBR-BAG;
            }
          }
          leaf ip-address {
            xr:xr-xml-map "manageability_perf_oper:IPAddress";
            type inet:ipv4-address-no-zone;
            description "BGP Neighbor Identifier";
          }
        }
      }
    }
  }

  container perf-mgmt {
    xr:xr-xml-map "manageability_perf_oper:PerfMgmt";
    config false;
    description "Performance Management agent operational data";

    container periodic {
      xr:xr-xml-map "manageability_perf_oper:Periodic";
      description "Data from periodic requests";
      uses OSPF;
      uses MPLS;
      uses NODE-TABLE;
      uses BGP;
      uses INTERFACE;
    }

    container monitor {
      xr:xr-xml-map "manageability_perf_oper:Monitor";
      description "Data from monitor (one history period) requests";
      uses OSPF;
      uses MPLS;
      uses NODE-TABLE;
      uses BGP;
      uses INTERFACE;
    }
  }
}
