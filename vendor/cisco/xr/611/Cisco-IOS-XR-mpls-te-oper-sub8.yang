submodule Cisco-IOS-XR-mpls-te-oper-sub8 {

  belongs-to Cisco-IOS-XR-mpls-te-oper {
    prefix Cisco-IOS-XR-mpls-te-oper;
  }

  /*** LINKAGE (IMPORTS / INCLUDES) ***/

  import ietf-inet-types { prefix "inet"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR mpls-te package operational data.

     Copyright (c) 2013-2016 by Cisco Systems, Inc.
     All rights reserved.";

  revision "2015-11-09" {
    description
      "IOS XR 6.0 revision.";
  }

  typedef Mpls-te-lsp-role {
    type enumeration {
      enum mpls-te-lsp-role-unknown {
        description "MPLS TE lsp role unknown";
      }
      enum mpls-te-lsp-role-head {
        description "MPLS TE lsp role head";
      }
      enum mpls-te-lsp-role-transit {
        description "MPLS TE lsp role transit";
      }
      enum mpls-te-lsp-role-tail {
        description "MPLS TE lsp role tail";
      }
    }
    description "MPLS TE LSP Role";
  }
  typedef Mpls-protection {
    type enumeration {
      enum mpls-protection-type-unprotected {
        description "MPLS no protection is desired";
      }
      enum mpls-protection-type-link {
        description "MPLS link protection is desired";
      }
      enum mpls-protection-type-link-node {
        description
          "MPLS node and link protection are both desired";
      }
    }
    description "MPLS Protection Type";
  }
  typedef Oc-mpls-te-metric {
    type enumeration {
      enum oc-mpls-te-metric-type-igp {
        description "MPLS TE metric type IGP";
      }
      enum oc-mpls-te-metric-type-te {
        description "MPLS TE metric type TE";
      }
    }
    description "OC MPLS TE Metric Type";
  }
  typedef Lsp-oper-status {
    type enumeration {
      enum mpls-te-lsp-oper-up {
        description "MPLS TE lsp operational up";
      }
      enum mpls-te-lsp-oper-down {
        description "MPLS TE lsp operational down";
      }
    }
    description "LSP Admin Status";
  }
  typedef Lsp-admin-status {
    type enumeration {
      enum mpls-te-lsp-admin-up {
        description "MPLS TE lsp admin up";
      }
      enum mpls-te-lsp-admin-shutdown {
        description "MPLS TE lsp admin shutdown";
      }
    }
    description "LSP Admin Status";
  }
  typedef Mpls-te-protocol {
    type enumeration {
      enum mpls-te-signaling-type-unknown {
        description "MPLS TE signaling type unknown";
      }
      enum mpls-te-signaling-type-rsvp {
        description "MPLS TE signaling type RSVP";
      }
    }
    description "MPLS TE Protocol Type";
  }
  typedef Oc-mpls-te-lsp {
    type enumeration {
      enum oc-mpls-te-lsp-type-not-set {
        description "MPLS TE lsp type not set";
      }
      enum oc-mpls-te-lsp-type-p2p {
        description "MPLS TE lsp type point to point";
      }
      enum oc-mpls-te-lsp-type-p2mp {
        description "MPLS TE lsp type point to multi-point";
      }
    }
    description "OC MPLS TE LSP Type";
  }

  grouping OC-MPLS-TE-LSP-COUNTERS {
    description "OC MPLS TE LSP counters";
    leaf name {
      xr:xr-xml-map "oc_mpls_te:Name";
      type string;
      description "LSP Name";
    }
    leaf type {
      xr:xr-xml-map "oc_mpls_te:Type";
      type Oc-mpls-te-lsp;
      description "LSP Type";
    }
    leaf bytes {
      xr:xr-xml-map "oc_mpls_te:Bytes";
      type uint64;
      units "byte";
      description "Number of bytes forwarded over the lsp";
    }
    leaf packets {
      xr:xr-xml-map "oc_mpls_te:Packets";
      type uint64;
      description "Number of packets forwarded over the lsp";
    }
    leaf path-changes {
      xr:xr-xml-map "oc_mpls_te:PathChanges";
      type uint64;
      description "Number of path changes for the lsp";
    }
    leaf state-changes {
      xr:xr-xml-map "oc_mpls_te:StateChanges";
      type uint64;
      description "Number of state changes for the lsp";
    }
    leaf online-time {
      xr:xr-xml-map "oc_mpls_te:OnlineTime";
      type string;
      description "Timestamp of LSP oper state up";
    }
    leaf current-path-time {
      xr:xr-xml-map "oc_mpls_te:CurrentPathTime";
      type string;
      description "Timestamp of LSP switched onto current path";
    }
    leaf next-reoptimization-time {
      xr:xr-xml-map "oc_mpls_te:NextReoptimizationTime";
      type string;
      description "Timestamp of next scheduled reoptmiziation";
    }
  }

  grouping OC-MPLS-TE-LSP-STATE {
    description "OC MPLS TE LSP State";
    leaf name {
      xr:xr-xml-map "oc_mpls_te:Name";
      type string;
      description "LSP Name";
    }
    leaf type {
      xr:xr-xml-map "oc_mpls_te:Type";
      type Oc-mpls-te-lsp;
      description "LSP Type";
    }
    leaf signaling-protocol {
      xr:xr-xml-map "oc_mpls_te:SignalingProtocol";
      type Mpls-te-protocol;
      description "Signaling Protocol";
    }
    leaf local-id {
      xr:xr-xml-map "oc_mpls_te:LocalID";
      type uint32;
      description "Local ID - TBD";
    }
    leaf source {
      xr:xr-xml-map "oc_mpls_te:Source";
      type inet:ipv4-address;
      description "Source Address";
    }
    leaf description {
      xr:xr-xml-map "oc_mpls_te:Description";
      type string;
      description "Description";
    }
    leaf admin-status {
      xr:xr-xml-map "oc_mpls_te:AdminStatus";
      type Lsp-admin-status;
      description "Admin Status";
    }
    leaf oper-status {
      xr:xr-xml-map "oc_mpls_te:OperStatus";
      type Lsp-oper-status;
      description "Operational Status";
    }
    leaf metric {
      xr:xr-xml-map "oc_mpls_te:Metric";
      type Oc-mpls-te-metric;
      description "Metric type";
    }
    leaf protection-style-requested {
      xr:xr-xml-map "oc_mpls_te:ProtectionStyleRequested";
      type Mpls-protection;
      description "Protection Style Requested";
    }
    leaf reoptimize-timer {
      xr:xr-xml-map "oc_mpls_te:ReoptimizeTimer";
      type uint16;
      description "frequency of reoptimization";
    }
    leaf role {
      xr:xr-xml-map "oc_mpls_te:Role";
      type Mpls-te-lsp-role;
      description "Role";
    }
    leaf setup-priority {
      xr:xr-xml-map "oc_mpls_te:SetupPriority";
      type uint8;
      description "Setup priority";
    }
    leaf hold-priority {
      xr:xr-xml-map "oc_mpls_te:HoldPriority";
      type uint8;
      description "Hold priority";
    }
    leaf soft-preemption {
      xr:xr-xml-map "oc_mpls_te:SoftPreemption";
      type boolean;
      description "Soft Preemption";
    }
  }
}
