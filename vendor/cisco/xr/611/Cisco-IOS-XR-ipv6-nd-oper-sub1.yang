submodule Cisco-IOS-XR-ipv6-nd-oper-sub1 {

  belongs-to Cisco-IOS-XR-ipv6-nd-oper {
    prefix Cisco-IOS-XR-ipv6-nd-oper;
  }

  /*** LINKAGE (IMPORTS / INCLUDES) ***/

  import ietf-inet-types { prefix "inet"; }

  import ietf-yang-types { prefix "yang"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR ipv6-nd package operational data.

     Copyright (c) 2013-2016 by Cisco Systems, Inc.
     All rights reserved.";

  revision "2015-11-09" {
    description
      "IOS XR 6.0 revision.";
  }

  typedef Ipv6-nd-sh-vr-flags {
    type enumeration {
      enum no-flags {
        description "None";
      }
      enum final-ra {
        description "Final RA";
      }
    }
    description "IPv6 ND VR Entry Flags Type ";
  }
  typedef Ipv6-nd-sh-vr-state {
    type enumeration {
      enum deleted {
        description "Delete";
      }
      enum standby {
        description "Standby";
      }
      enum active {
        description "Active";
      }
    }
    description "IPv6 ND VR Entry State Type ";
  }
  typedef Ipv6-nd-bndl-state {
    type enumeration {
      enum run {
        description "Running state";
      }
      enum error {
        description "Error state";
      }
      enum wait {
        description "Wait state";
      }
    }
    description "IPv6 ND Bundle State";
  }
  typedef Ipv6-nd-neighbor-origin {
    type enumeration {
      enum other {
        description "Other Address";
      }
      enum static {
        description "Static Address";
      }
      enum dynamic {
        description "Dynamic Address";
      }
    }
    description "IPv6 ND Neighbor Origin Type";
  }
  typedef Ipv6-nd-media-encap {
    type enumeration {
      enum none {
        description "No encapsulation";
      }
      enum arpa {
        description "ARPA encapsulation";
      }
      enum snap {
        description "SNAP encapsulation";
      }
      enum ieee802-1q {
        description "802_1Q encapsulation";
      }
      enum srp {
        description "SRP encapsulation";
      }
      enum srpa {
        description "SRPA encapsulation";
      }
      enum srpb {
        description "SRPB encapsulation";
      }
      enum ppp {
        description "PPP encapsulation";
      }
      enum hdlc {
        description "HDLC encapsulation";
      }
      enum chdlc {
        description "CHDLC encapsulation";
      }
      enum dot1q {
        description "DOT1Q encapsulation";
      }
      enum fr {
        description "FR encapsulation";
      }
      enum gre {
        description "GRE encapsulation";
      }
    }
    description "IPv6 ND Media Encapsulation Type";
  }
  typedef Ipv6-nd-sh-state {
    type enumeration {
      enum incomplete {
        description "Incomplete";
      }
      enum reachable {
        description "Reachable";
      }
      enum stale {
        description "Stale";
      }
      enum glean {
        description "Glean";
      }
      enum delay {
        description "Delay";
      }
      enum probe {
        description "Probe";
      }
      enum delete {
        description "Delete";
      }
    }
    description "IPv6 ND Neighbor Reachability State";
  }

  grouping IPV6-ND-VR-ENTRY {
    description "Detailed Info of ND IPv6 Virtual Router entry";

    container local-address {
      description "Link local address";
      uses IPV6-ND-ADDR;
    }
    leaf link-layer-address {
      xr:xr-xml-map "ipv6_nd:LinkLayerAddress";
      type yang:mac-address;
      description "Link-Layer Address";
    }
    leaf context {
      xr:xr-xml-map "ipv6_nd:Context";
      type uint32;
      description "Virtual Router ID";
    }
    leaf state {
      xr:xr-xml-map "ipv6_nd:State";
      type Ipv6-nd-sh-vr-state;
      description "VR state";
    }
    leaf flags {
      xr:xr-xml-map "ipv6_nd:Flags";
      type Ipv6-nd-sh-vr-flags;
      description "VR Flags";
    }
    leaf vr-gl-addr-ct {
      xr:xr-xml-map "ipv6_nd:VrGlAddrCt";
      type uint32;
      description "Virtual Global Address Count";
    }

    list vr-global-address {
      description "List of ND global addresses";
      uses IPV6-ND-ADDR;
    }
  }

  grouping IPV6-ND-GSPNODE {
    description "GSP node info ";
    leaf node-name {
      xr:xr-xml-map "ipv6_nd:NodeName";
      type xr:Node-id;
      description "Node Name";
    }
    leaf total-links {
      xr:xr-xml-map "ipv6_nd:TotalLinks";
      type uint32;
      description "Number of links on the node";
    }
  }

  grouping IPV6-ND-ADDR {
    description "List of IPv6 ND Addresses ";
    leaf ipv6-address {
      xr:xr-xml-map "ipv6_nd:IPv6Address";
      type inet:ipv6-address;
      description "IPv6 address";
    }
  }

  grouping IPV6-ND-IF-PARAMS {
    description "Detailed Info of ND IPv6 Interface";
    leaf is-dad-enabled {
      xr:xr-xml-map "ipv6_nd:IsDADEnabled";
      type boolean;
      description
        "If true, DAD (D.. A.. D..) is enabled otherwise
        it is disabled";
    }
    leaf dad-attempts {
      xr:xr-xml-map "ipv6_nd:DADAttempts";
      type uint32;
      description "DAD attempt count";
    }
    leaf is-icm-pv6-redirect {
      xr:xr-xml-map "ipv6_nd:IsICMPv6Redirect";
      type boolean;
      description "ICMP redirect flag";
    }
    leaf is-dhcp-managed {
      xr:xr-xml-map "ipv6_nd:IsDHCPManaged";
      type boolean;
      description "Flag used for utilising DHCP";
    }
    leaf is-route-address-managed {
      xr:xr-xml-map "ipv6_nd:IsRouteAddressManaged";
      type boolean;
      description "Flag used to manage routable address";
    }
    leaf is-suppressed {
      xr:xr-xml-map "ipv6_nd:IsSuppressed";
      type boolean;
      description "Suppress flag";
    }
    leaf nd-retransmit-interval {
      xr:xr-xml-map "ipv6_nd:NDRetransmitInterval";
      type uint32;
      description "ND retransmit interval in msec";
    }
    leaf nd-min-transmit-interval {
      xr:xr-xml-map "ipv6_nd:NDMinTransmitInterval";
      type uint32;
      description
        "ND router advertisement minimum transmit
        interval in sec";
    }
    leaf nd-max-transmit-interval {
      xr:xr-xml-map "ipv6_nd:NDMaxTransmitInterval";
      type uint32;
      description
        "ND router advertisement maximum transmit
        interval in sec";
    }
    leaf nd-advertisement-lifetime {
      xr:xr-xml-map "ipv6_nd:NDAdvertisementLifetime";
      type uint32;
      description "ND router advertisement life time in sec";
    }
    leaf nd-reachable-time {
      xr:xr-xml-map "ipv6_nd:NDReachableTime";
      type uint32;
      description "Time to reach ND in msec";
    }
    leaf nd-cache-limit {
      xr:xr-xml-map "ipv6_nd:NDCacheLimit";
      type uint32;
      description "Completed adjacency limit per interface";
    }
    leaf complete-protocol-count {
      xr:xr-xml-map "ipv6_nd:CompleteProtocolCount";
      type uint32;
      description "Completed PROTO entry Count";
    }
    leaf complete-glean-count {
      xr:xr-xml-map "ipv6_nd:CompleteGleanCount";
      type uint32;
      description "Completed GLEAN entry count";
    }
    leaf incomplete-protocol-count {
      xr:xr-xml-map "ipv6_nd:IncompleteProtocolCount";
      type uint32;
      description "Incomplete PROTO entry count";
    }
    leaf incomplete-glean-count {
      xr:xr-xml-map "ipv6_nd:IncompleteGleanCount";
      type uint32;
      description "Incomplete GLEAN entry count";
    }
    leaf dropped-protocol-req-count {
      xr:xr-xml-map "ipv6_nd:DroppedProtocolReqCount";
      type uint32;
      description "Dropped PROTO entry request count";
    }
    leaf dropped-glean-req-count {
      xr:xr-xml-map "ipv6_nd:DroppedGleanReqCount";
      type uint32;
      description "Dropped GLEAN entry lequest count";
    }
  }

  grouping IPV6-ND-IF-ENTRY {
    description "Detailed Info of ND IPv6 Interface entry";

    container nd-parameters {
      description "ND interface parameters";
      uses IPV6-ND-IF-PARAMS;
    }

    container local-address {
      description "Link local address";
      uses IPV6-ND-ADDR;
    }
    leaf parent-interface-name {
      xr:xr-xml-map "ipv6_nd:ParentInterfaceName";
      type xr:Interface-name;
      description "Parent interface name";
    }
    leaf iftype {
      xr:xr-xml-map "ipv6_nd:Iftype";
      type uint32;
      description "Interface type";
    }
    leaf mtu {
      xr:xr-xml-map "ipv6_nd:Mtu";
      type uint32;
      description "MTU";
    }
    leaf etype {
      xr:xr-xml-map "ipv6_nd:Etype";
      type uint32;
      description "etype";
    }
    leaf vlan-tag {
      xr:xr-xml-map "ipv6_nd:vlanTag";
      type uint16;
      description "vlan tag/id/ucv";
    }
    leaf mac-addr-size {
      xr:xr-xml-map "ipv6_nd:macAddrSize";
      type uint32;
      description "mac address size";
    }
    leaf mac-addr {
      xr:xr-xml-map "ipv6_nd:macAddr";
      type yang:mac-address;
      description "mac address";
    }
    leaf is-interface-enabled {
      xr:xr-xml-map "ipv6_nd:IsInterfaceEnabled";
      type boolean;
      description "If true, interface is enabled";
    }
    leaf is-ipv6-enabled {
      xr:xr-xml-map "ipv6_nd:IsIPv6Enabled";
      type boolean;
      description "If true, IPv6 is enabled";
    }
    leaf is-mpls-enabled {
      xr:xr-xml-map "ipv6_nd:IsMplsEnabled";
      type boolean;
      description "If true, MPLS is enabled";
    }
    leaf-list member-link {
      xr:xr-xml-map "ipv6_nd:MemberLinkList";
      type uint32;
      description "List of member links";
    }

    list global-address {
      description "List of ND global addresses";
      uses IPV6-ND-ADDR;
    }

    list member-node {
      description "List of member nodes";
      uses IPV6-ND-GSPNODE;
    }
  }

  grouping IPV6-ND-BL-NODE-ENTRY {
    description "IPv6 node discovery bundle node information";

    container age {
      description "Uptime of node (secs)";
      uses BAG-TIMESPEC;
    }
    leaf group-id {
      xr:xr-xml-map "ipv6_nd:GroupID";
      type uint32;
      description "Group ID";
    }
    leaf process-name {
      xr:xr-xml-map "ipv6_nd:ProcessName";
      type string;
      description "Process Name";
    }
    leaf sent-sequence-number {
      xr:xr-xml-map "ipv6_nd:SentSequenceNumber";
      type uint32;
      description "Sent sequence num";
    }
    leaf received-sequence-number {
      xr:xr-xml-map "ipv6_nd:ReceivedSequenceNumber";
      type uint32;
      description "Received sequence num";
    }
    leaf state {
      xr:xr-xml-map "ipv6_nd:State";
      type Ipv6-nd-bndl-state;
      description "State";
    }
    leaf state-changes {
      xr:xr-xml-map "ipv6_nd:StateChanges";
      type uint32;
      description "State changes";
    }
    leaf sent-packets {
      xr:xr-xml-map "ipv6_nd:SentPackets";
      type uint32;
      description "Total packet sends";
    }
    leaf received-packets {
      xr:xr-xml-map "ipv6_nd:ReceivedPackets";
      type uint32;
      description "Total packet receives";
    }
  }

  grouping BAG-NBR-ENTRY-SUM {
    description "IPv6 ND summary information";
    leaf incomplete-entries {
      xr:xr-xml-map "ipv6_nd:IncompleteEntries";
      type uint32;
      description "Total incomplete entries";
    }
    leaf reachable-entries {
      xr:xr-xml-map "ipv6_nd:ReachableEntries";
      type uint32;
      description "Total reachable entries";
    }
    leaf stale-entries {
      xr:xr-xml-map "ipv6_nd:StaleEntries";
      type uint32;
      description "Total stale entries";
    }
    leaf delayed-entries {
      xr:xr-xml-map "ipv6_nd:DelayedEntries";
      type uint32;
      description "Total delayed entries";
    }
    leaf probe-entries {
      xr:xr-xml-map "ipv6_nd:ProbeEntries";
      type uint32;
      description "Total probe entries";
    }
    leaf deleted-entries {
      xr:xr-xml-map "ipv6_nd:DeletedEntries";
      type uint32;
      description "Total deleted entries";
    }
    leaf subtotal-neighbor-entries {
      xr:xr-xml-map "ipv6_nd:SubtotalNeighborEntries";
      type uint32;
      description "Total number of entries";
    }
  }

  grouping IPV6-ND-NEIGHBOR-ENTRY-SUMMARY {
    description "IPv6 ND neighbor entry summary";

    container multicast {
      description "Multicast neighbor summary";
      uses BAG-NBR-ENTRY-SUM;
    }

    container static {
      description "Static neighbor summary";
      uses BAG-NBR-ENTRY-SUM;
    }

    container dynamic {
      description "Dynamic neighbor summary";
      uses BAG-NBR-ENTRY-SUM;
    }
    leaf total-neighbor-entries {
      xr:xr-xml-map "ipv6_nd:TotalNeighborEntries";
      type uint32;
      description "Total number of entries";
    }
  }

  grouping BAG-TIMESPEC {
    description
      "Timespec specifying the number of seconds since
      the base time of 00:00:00 GMT, 1 January 1970.";
    leaf seconds {
      xr:xr-xml-map "ipv6_nd:Seconds";
      type uint32;
      units "second";
      description "Number of seconds";
    }
  }

  grouping IPV6-ND-NEIGHBOR-ENTRY {
    description "IPv6 ND neighbor entry";

    container last-reached-time {
      description "Last time of reachability";
      uses BAG-TIMESPEC;
    }
    leaf reachability-state {
      xr:xr-xml-map "ipv6_nd:ReachabilityState";
      type Ipv6-nd-sh-state;
      description "Current state";
    }
    leaf link-layer-address {
      xr:xr-xml-map "ipv6_nd:LinkLayerAddress";
      type yang:mac-address;
      description "Link-Layer Address";
    }
    leaf encapsulation {
      xr:xr-xml-map "ipv6_nd:Encapsulation";
      type Ipv6-nd-media-encap;
      description "Preferred media encap type";
    }
    leaf selected-encapsulation {
      xr:xr-xml-map "ipv6_nd:SelectedEncapsulation";
      type Ipv6-nd-media-encap;
      description "Selected media encap";
    }
    leaf origin-encapsulation {
      xr:xr-xml-map "ipv6_nd:OriginEncapsulation";
      type Ipv6-nd-neighbor-origin;
      description "Neighbor origin";
    }
    leaf interface-name {
      xr:xr-xml-map "ipv6_nd:InterfaceName";
      type string;
      description "Interface name";
    }
    leaf location {
      xr:xr-xml-map "ipv6_nd:Location";
      type xr:Node-id;
      description "Location where the neighbor entry exists";
    }
    leaf is-router {
      xr:xr-xml-map "ipv6_nd:IsRouter";
      type boolean;
      description "IsRouter";
    }
  }
}
