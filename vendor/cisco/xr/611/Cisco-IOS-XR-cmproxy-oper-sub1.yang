submodule Cisco-IOS-XR-cmproxy-oper-sub1 {

  belongs-to Cisco-IOS-XR-cmproxy-oper {
    prefix Cisco-IOS-XR-cmproxy-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR cmproxy package operational data.

     Copyright (c) 2013-2016 by Cisco Systems, Inc.
     All rights reserved.";

  revision "2015-11-09" {
    description
      "IOS XR 6.0 revision.";
  }


  grouping CMP-INV-ST {
    description "cmp inv info";
    leaf valid {
      xr:xr-xml-map "cmp:valid";
      type uint32;
      description "valid flag";
    }
    leaf card-type {
      xr:xr-xml-map "cmp:card_type";
      type uint32;
      description "card type";
    }
    leaf card-type-string {
      xr:xr-xml-map "cmp:card_type_string";
      type string {
        length "0..32";
      }
      description "card type string";
    }
    leaf nodeid {
      xr:xr-xml-map "cmp:nodeid";
      type int32;
      description "node ID";
    }
    leaf node-name {
      xr:xr-xml-map "cmp:node_name";
      type string {
        length "0..32";
      }
      description "node name string";
    }
    leaf partner-id {
      xr:xr-xml-map "cmp:partner_id";
      type int32;
      description "partner node id";
    }
    leaf partner-name {
      xr:xr-xml-map "cmp:partner_name";
      type string {
        length "0..32";
      }
      description "partner name string";
    }
    leaf red-state {
      xr:xr-xml-map "cmp:red_state";
      type uint32;
      description "redundancy state";
    }
    leaf red-state-string {
      xr:xr-xml-map "cmp:red_state_string";
      type string {
        length "0..32";
      }
      description "redundancy state string";
    }
    leaf node-sw-state {
      xr:xr-xml-map "cmp:node_sw_state";
      type uint32;
      description "current software state";
    }
    leaf node-sw-state-string {
      xr:xr-xml-map "cmp:node_sw_state_string";
      type string {
        length "0..32";
      }
      description "current software state string";
    }
    leaf prev-sw-state {
      xr:xr-xml-map "cmp:prev_sw_state";
      type uint32;
      description "previous software state";
    }
    leaf prev-sw-state-string {
      xr:xr-xml-map "cmp:prev_sw_state_string";
      type string {
        length "0..32";
      }
      description "previous software state string";
    }
    leaf node-ip {
      xr:xr-xml-map "cmp:node_ip";
      type uint32;
      description "node IP address";
    }
    leaf node-ipv4-string {
      xr:xr-xml-map "cmp:node_ipv4_string";
      type string {
        length "0..16";
      }
      description "node IPv4 address string";
    }
  }
}
