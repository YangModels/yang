module Cisco-IOS-XR-ip-bfd-oper {

  /*** NAMESPACE / PREFIX DEFINITION ***/

  namespace "http://cisco.com/ns/yang/Cisco-IOS-XR-ip-bfd-oper";


  prefix "ip-bfd-oper";

  /*** LINKAGE (IMPORTS / INCLUDES) ***/

  import ietf-inet-types { prefix "inet"; }

  import Cisco-IOS-XR-types { prefix "xr"; }

  include Cisco-IOS-XR-ip-bfd-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ip-bfd package operational data.

     This module contains definitions
     for the following management objects:
       bfd: Bidirectional Forwarding Detection(BFD) operational data

     Copyright (c) 2013-2016 by Cisco Systems, Inc.
     All rights reserved.";

  revision "2015-11-09" {
    description
      "IOS XR 6.0 revision.";
  }


  container bfd {
    xr:xr-xml-map "ip_bfd_oper:BFD";
    config false;
    description
      "Bidirectional Forwarding Detection(BFD)
      operational data";

    container label-session-briefs {
      xr:xr-xml-map "ip_bfd_oper:LabelSessionBriefTable";
      description
        "Table of brief information about all Label BFD
        sessions in the System";

      list label-session-brief {
        xr:xr-xml-map "ip_bfd_oper:LabelSessionBrief";
        description
          "Brief information for a single Label BFD
          session";
        leaf interface-name {
          xr:xr-xml-map "ip_bfd_oper:InterfaceName";
          type xr:Interface-name;
          description "Interface Name";
        }
        leaf incoming-label {
          xr:xr-xml-map "ip_bfd_oper:IncomingLabel";
          type int32;
          description "Incoming Label";
        }
        leaf location {
          xr:xr-xml-map "ip_bfd_oper:Location";
          type xr:Node-id;
          description "Location";
        }
        uses BFD-MGMT-SESSION-BRIEF;
      }
    }

    container ipv4bf-do-mplste-tail-summary {
      xr:xr-xml-map "ip_bfd_oper:IPv4BFDoMPLSTETailSummary";
      description
        "Summary information of IPv4 BFD over MPLS-TE
        Tail";
      uses BFD-MGMT-BFD-INFORMATION;
    }

    container ipv6-single-hop-counters {
      xr:xr-xml-map "ip_bfd_oper:IPv6SingleHopCounters";
      description "IPv6 single hop Counters";

      container ipv6-single-hop-packet-counters {
        xr:xr-xml-map "ip_bfd_oper:IPv6SingleHopPacketCountersTable";
        description "Table of IPv6 single hop Packet counters";

        list ipv6-single-hop-packet-counter {
          xr:xr-xml-map "ip_bfd_oper:IPv6SingleHopPacketCounters";
          key "interface-name";
          description "Interface IPv6 single hop Packet counters";
          leaf interface-name {
            xr:xr-xml-map "ip_bfd_oper:InterfaceName";
            type xr:Interface-name;
            description "Interface Name";
          }
          uses BFD-MGMT-PACKET-COUNT;
        }
      }
    }

    container counters {
      xr:xr-xml-map "ip_bfd_oper:Counters";
      description "Counters";

      container packet-counters {
        xr:xr-xml-map "ip_bfd_oper:PacketCountersTable";
        description "Table of Packet counters";

        list packet-counter {
          xr:xr-xml-map "ip_bfd_oper:PacketCounters";
          key "interface-name";
          description "Interface Packet counters";
          leaf interface-name {
            xr:xr-xml-map "ip_bfd_oper:InterfaceName";
            type xr:Interface-name;
            description "Interface Name";
          }
          uses BFD-MGMT-PACKET-COUNT;
        }
      }
    }

    container client-details {
      xr:xr-xml-map "ip_bfd_oper:ClientDetailTable";
      description "Table of detailed information about BFD clients";

      list client-detail {
        xr:xr-xml-map "ip_bfd_oper:ClientDetail";
        key "client-name";
        description "Detailed information of client";
        leaf client-name {
          xr:xr-xml-map "ip_bfd_oper:ClientName";
          type xr:Cisco-ios-xr-string;
          description "Client Name";
        }
        uses BFD-MGMT-CLIENT-DETAIL-INFORMATION;
      }
    }

    container ipv4-single-hop-summary {
      xr:xr-xml-map "ip_bfd_oper:IPv4SingleHopSummary";
      description
        "Summary information of BFD IPv4 singlehop
        sessions";
      uses BFD-MGMT-BFD-INFORMATION;
    }

    container ipv6-single-hop-summary {
      xr:xr-xml-map "ip_bfd_oper:IPv6SingleHopSummary";
      description
        "Summary information of BFD IPv6 singlehop
        sessions";
      uses BFD-MGMT-BFD-INFORMATION;
    }

    container label-multi-paths {
      xr:xr-xml-map "ip_bfd_oper:LabelMultiPathTable";
      description "Label multipath";

      list label-multi-path {
        xr:xr-xml-map "ip_bfd_oper:LabelMultiPath";
        description "Label multipath table";
        leaf interface-name {
          xr:xr-xml-map "ip_bfd_oper:InterfaceName";
          type xr:Interface-name;
          description "Interface Name";
        }
        leaf incoming-label {
          xr:xr-xml-map "ip_bfd_oper:IncomingLabel";
          type int32;
          description "Incoming Label";
        }
        leaf location {
          xr:xr-xml-map "ip_bfd_oper:Location";
          type xr:Node-id;
          description "Location";
        }
        uses BFD-MGMT-MULTIPLE-PATHS;
      }
    }

    container ipv4-multi-hop-session-details {
      xr:xr-xml-map "ip_bfd_oper:IPv4MultiHopSessionDetailTable";
      description
        "Table of detailed information about all IPv4
        multihop BFD sessions in the System ";

      list ipv4-multi-hop-session-detail {
        xr:xr-xml-map "ip_bfd_oper:IPv4MultiHopSessionDetail";
        description
          "Detailed information for a single IPv4 multihop
          BFD session";
        leaf source-address {
          xr:xr-xml-map "ip_bfd_oper:SourceAddress";
          type inet:ip-address-no-zone;
          description "Source Address";
        }
        leaf destination-address {
          xr:xr-xml-map "ip_bfd_oper:DestinationAddress";
          type inet:ip-address-no-zone;
          description "Destination Address";
        }
        leaf location {
          xr:xr-xml-map "ip_bfd_oper:Location";
          type xr:Node-id;
          description "Location";
        }
        leaf vrf-name {
          xr:xr-xml-map "ip_bfd_oper:VRFName";
          type xr:Cisco-ios-xr-string;
          description "VRF name";
        }
        uses BFD-MGMT-SESSION-DETAIL;
      }
    }

    container ipv4-single-hop-session-details {
      xr:xr-xml-map "ip_bfd_oper:IPv4SingleHopSessionDetailTable";
      description
        "Table of detailed information about all IPv4
        singlehop BFD sessions in the System ";

      list ipv4-single-hop-session-detail {
        xr:xr-xml-map "ip_bfd_oper:IPv4SingleHopSessionDetail";
        description
          "Detailed information for a single IPv4
          singlehop BFD session";
        leaf interface-name {
          xr:xr-xml-map "ip_bfd_oper:InterfaceName";
          type xr:Interface-name;
          description "Interface Name";
        }
        leaf destination-address {
          xr:xr-xml-map "ip_bfd_oper:DestinationAddress";
          type inet:ipv4-address-no-zone;
          description "Destination Address";
        }
        leaf location {
          xr:xr-xml-map "ip_bfd_oper:Location";
          type xr:Node-id;
          description "Location";
        }
        uses BFD-MGMT-SESSION-DETAIL;
      }
    }

    container ipv4-multi-hop-session-briefs {
      xr:xr-xml-map "ip_bfd_oper:IPv4MultiHopSessionBriefTable";
      description
        "Table of brief information about all IPv4
        multihop BFD sessions in the System";

      list ipv4-multi-hop-session-brief {
        xr:xr-xml-map "ip_bfd_oper:IPv4MultiHopSessionBrief";
        description
          "Brief information for a single IPv4 multihop
          BFD session";
        leaf source-address {
          xr:xr-xml-map "ip_bfd_oper:SourceAddress";
          type inet:ipv4-address-no-zone;
          description "Source Address";
        }
        leaf destination-address {
          xr:xr-xml-map "ip_bfd_oper:DestinationAddress";
          type inet:ipv4-address-no-zone;
          description "Destination Address";
        }
        leaf location {
          xr:xr-xml-map "ip_bfd_oper:Location";
          type xr:Node-id;
          description "Location";
        }
        leaf vrf-name {
          xr:xr-xml-map "ip_bfd_oper:VRFName";
          type xr:Cisco-ios-xr-string;
          description "VRF name";
        }
        uses BFD-MGMT-SESSION-BRIEF;
      }
    }

    container generic-summaries {
      xr:xr-xml-map "ip_bfd_oper:GenericSummaryTable";
      description "Generic summary information about BFD location";

      list generic-summary {
        xr:xr-xml-map "ip_bfd_oper:GenericSummary";
        key "location";
        description
          "Generic summary information for bfd location
          table";
        leaf location {
          xr:xr-xml-map "ip_bfd_oper:Location";
          type xr:Node-id;
          description "Location";
        }
        uses BFD-MGMT-SUMMARY;
      }
    }

    container ipv6-single-hop-multi-paths {
      xr:xr-xml-map "ip_bfd_oper:IPv6SingleHopMultiPathTable";
      description "IPv6 single hop multipath";

      list ipv6-single-hop-multi-path {
        xr:xr-xml-map "ip_bfd_oper:IPv6SingleHopMultiPath";
        description "IPv6 single hop multipath table";
        leaf interface-name {
          xr:xr-xml-map "ip_bfd_oper:InterfaceName";
          type xr:Interface-name;
          description "Interface name";
        }
        leaf destination-address {
          xr:xr-xml-map "ip_bfd_oper:DestinationAddress";
          type inet:ip-address-no-zone;
          description "Destination address";
        }
        leaf location {
          xr:xr-xml-map "ip_bfd_oper:Location";
          type xr:Node-id;
          description "Location";
        }
        uses BFD-MGMT-MULTIPLE-PATHS;
      }
    }

    container ipv4-single-hop-node-location-summaries {
      xr:xr-xml-map "ip_bfd_oper:IPv4SingleHopNodeLocationSummaryTa"+
        "ble";
      description
        "Table of summary information about BFD IPv4
        singlehop sessions per location";

      list ipv4-single-hop-node-location-summary {
        xr:xr-xml-map "ip_bfd_oper:IPv4SingleHopNodeLocationSummary";
        key "location";
        description
          "Summary information for BFD IPv4 singlehop
          sessions for location";
        leaf location {
          xr:xr-xml-map "ip_bfd_oper:Location";
          type xr:Node-id;
          description "Location";
        }
        uses BFD-MGMT-BFD-LOC-INFORMATION;
      }
    }

    container label-summary {
      xr:xr-xml-map "ip_bfd_oper:LabelSummary";
      description "Summary information of Label BFD";
      uses BFD-MGMT-BFD-INFORMATION;
    }

    container ipv4bf-do-mplste-head-session-briefs {
      xr:xr-xml-map "ip_bfd_oper:IPv4BFDoMPLSTEHeadSessionBriefTabl"+
        "e";
      description
        "Table of brief information about all IPv4 BFD
        over MPLS-TE Head sessions in the System";

      list ipv4bf-do-mplste-head-session-brief {
        xr:xr-xml-map "ip_bfd_oper:IPv4BFDoMPLSTEHeadSessionBrief";
        description
          "Brief information for a single IPv4 BFD over
          MPLS-TE Head session";
        leaf interface-name {
          xr:xr-xml-map "ip_bfd_oper:InterfaceName";
          type xr:Interface-name;
          description "Interface Name";
        }
        leaf vrf-name {
          xr:xr-xml-map "ip_bfd_oper:VRFName";
          type xr:Cisco-ios-xr-string;
          description "VRF name";
        }
        leaf incoming-label {
          xr:xr-xml-map "ip_bfd_oper:IncomingLabel";
          type int32;
          description "Incoming Label";
        }
        leaf fe-ctype {
          xr:xr-xml-map "ip_bfd_oper:FECType";
          type int32;
          description "FEC Type";
        }
        leaf fec-subgroup-id {
          xr:xr-xml-map "ip_bfd_oper:FECSubgroupID";
          type int32;
          description "FEC Subgroup ID";
        }
        leaf feclspid {
          xr:xr-xml-map "ip_bfd_oper:FECLSPID";
          type int32;
          description "FEC LSP ID";
        }
        leaf fec-tunnel-id {
          xr:xr-xml-map "ip_bfd_oper:FECTunnelID";
          type int32;
          description "FEC Tunnel ID";
        }
        leaf fec-extended-tunnel-id {
          xr:xr-xml-map "ip_bfd_oper:FECExtendedTunnelID";
          type inet:ipv4-address-no-zone;
          description "FEC Extended Tunnel ID";
        }
        leaf fec-source {
          xr:xr-xml-map "ip_bfd_oper:FECSource";
          type inet:ipv4-address-no-zone;
          description "FEC Source";
        }
        leaf fec-destination {
          xr:xr-xml-map "ip_bfd_oper:FECDestination";
          type inet:ipv4-address-no-zone;
          description "FEC Destination";
        }
        leaf fecp2mpid {
          xr:xr-xml-map "ip_bfd_oper:FECP2MPID";
          type int32;
          description "FEC P2MP ID";
        }
        leaf fec-subgroup-originator {
          xr:xr-xml-map "ip_bfd_oper:FECSubgroupOriginator";
          type inet:ipv4-address-no-zone;
          description "FEC Subgroup originator";
        }
        leaf fec-ctype {
          xr:xr-xml-map "ip_bfd_oper:FECCType";
          type int32;
          description "FEC C Type";
        }
        leaf location {
          xr:xr-xml-map "ip_bfd_oper:Location";
          type xr:Node-id;
          description "Location";
        }
        uses BFD-MGMT-SESSION-BRIEF;
      }
    }

    container ipv4bf-do-mplste-tail-session-details {
      xr:xr-xml-map "ip_bfd_oper:IPv4BFDoMPLSTETailSessionDetailTab"+
        "le";
      description
        "Table of detailed information about all IPv4 BFD
        over MPLS-TE Tail sessions in the System";

      list ipv4bf-do-mplste-tail-session-detail {
        xr:xr-xml-map "ip_bfd_oper:IPv4BFDoMPLSTETailSessionDetail";
        description
          "Detailed information for a single IPv4 BFD over
          MPLS-TE Tail session";
        leaf vrf-name {
          xr:xr-xml-map "ip_bfd_oper:VRFName";
          type xr:Cisco-ios-xr-string;
          description "VRF name";
        }
        leaf incoming-label {
          xr:xr-xml-map "ip_bfd_oper:IncomingLabel";
          type int32;
          description "Incoming Label";
        }
        leaf fe-ctype {
          xr:xr-xml-map "ip_bfd_oper:FECType";
          type int32;
          description "FEC Type";
        }
        leaf fec-subgroup-id {
          xr:xr-xml-map "ip_bfd_oper:FECSubgroupID";
          type int32;
          description "FEC Subgroup ID";
        }
        leaf feclspid {
          xr:xr-xml-map "ip_bfd_oper:FECLSPID";
          type int32;
          description "FEC LSP ID";
        }
        leaf fec-tunnel-id {
          xr:xr-xml-map "ip_bfd_oper:FECTunnelID";
          type int32;
          description "FEC Tunnel ID";
        }
        leaf fec-extended-tunnel-id {
          xr:xr-xml-map "ip_bfd_oper:FECExtendedTunnelID";
          type inet:ipv4-address-no-zone;
          description "FEC Extended Tunnel ID";
        }
        leaf fec-source {
          xr:xr-xml-map "ip_bfd_oper:FECSource";
          type inet:ipv4-address-no-zone;
          description "FEC Source";
        }
        leaf fec-destination {
          xr:xr-xml-map "ip_bfd_oper:FECDestination";
          type inet:ipv4-address-no-zone;
          description "FEC Destination";
        }
        leaf fecp2mpid {
          xr:xr-xml-map "ip_bfd_oper:FECP2MPID";
          type int32;
          description "FEC P2MP ID";
        }
        leaf fec-subgroup-originator {
          xr:xr-xml-map "ip_bfd_oper:FECSubgroupOriginator";
          type inet:ipv4-address-no-zone;
          description "FEC Subgroup originator";
        }
        leaf fec-ctype {
          xr:xr-xml-map "ip_bfd_oper:FECCType";
          type int32;
          description "FEC C Type";
        }
        leaf location {
          xr:xr-xml-map "ip_bfd_oper:Location";
          type xr:Node-id;
          description "Location";
        }
        uses BFD-MGMT-SESSION-DETAIL;
      }
    }

    container ipv4-multi-hop-node-location-summaries {
      xr:xr-xml-map "ip_bfd_oper:IPv4MultiHopNodeLocationSummaryTab"+
        "le";
      description
        "Table of summary information about BFD IPv4
        multihop sessions per location";

      list ipv4-multi-hop-node-location-summary {
        xr:xr-xml-map "ip_bfd_oper:IPv4MultiHopNodeLocationSummary";
        key "location";
        description
          "Summary information for BFD IPv4 multihop
          sessions for location";
        leaf location {
          xr:xr-xml-map "ip_bfd_oper:Location";
          type xr:Node-id;
          description "Location";
        }
        uses BFD-MGMT-BFD-LOC-INFORMATION;
      }
    }

    container ipv4bf-do-mplste-tail-session-briefs {
      xr:xr-xml-map "ip_bfd_oper:IPv4BFDoMPLSTETailSessionBriefTabl"+
        "e";
      description
        "Table of brief information about all IPv4 BFD
        over MPLS-TE Tail sessions in the System";

      list ipv4bf-do-mplste-tail-session-brief {
        xr:xr-xml-map "ip_bfd_oper:IPv4BFDoMPLSTETailSessionBrief";
        description
          "Brief information for a single IPv4 BFD over
          MPLS-TE session";
        leaf vrf-name {
          xr:xr-xml-map "ip_bfd_oper:VRFName";
          type xr:Cisco-ios-xr-string;
          description "VRF name";
        }
        leaf incoming-label {
          xr:xr-xml-map "ip_bfd_oper:IncomingLabel";
          type int32;
          description "Incoming Label";
        }
        leaf fe-ctype {
          xr:xr-xml-map "ip_bfd_oper:FECType";
          type int32;
          description "FEC Type";
        }
        leaf fec-subgroup-id {
          xr:xr-xml-map "ip_bfd_oper:FECSubgroupID";
          type int32;
          description "FEC Subgroup ID";
        }
        leaf feclspid {
          xr:xr-xml-map "ip_bfd_oper:FECLSPID";
          type int32;
          description "FEC LSP ID";
        }
        leaf fec-tunnel-id {
          xr:xr-xml-map "ip_bfd_oper:FECTunnelID";
          type int32;
          description "FEC Tunnel ID";
        }
        leaf fec-extended-tunnel-id {
          xr:xr-xml-map "ip_bfd_oper:FECExtendedTunnelID";
          type inet:ipv4-address-no-zone;
          description "FEC Extended Tunnel ID";
        }
        leaf fec-source {
          xr:xr-xml-map "ip_bfd_oper:FECSource";
          type inet:ipv4-address-no-zone;
          description "FEC Source";
        }
        leaf fec-destination {
          xr:xr-xml-map "ip_bfd_oper:FECDestination";
          type inet:ipv4-address-no-zone;
          description "FEC Destination";
        }
        leaf fecp2mpid {
          xr:xr-xml-map "ip_bfd_oper:FECP2MPID";
          type int32;
          description "FEC P2MP ID";
        }
        leaf fec-subgroup-originator {
          xr:xr-xml-map "ip_bfd_oper:FECSubgroupOriginator";
          type inet:ipv4-address-no-zone;
          description "FEC Subgroup originator";
        }
        leaf fec-ctype {
          xr:xr-xml-map "ip_bfd_oper:FECCType";
          type int32;
          description "FEC C Type";
        }
        leaf location {
          xr:xr-xml-map "ip_bfd_oper:Location";
          type xr:Node-id;
          description "Location";
        }
        uses BFD-MGMT-SESSION-BRIEF;
      }
    }

    container ipv6-multi-hop-node-location-summaries {
      xr:xr-xml-map "ip_bfd_oper:IPv6MultiHopNodeLocationSummaryTab"+
        "le";
      description
        "Table of summary information about BFD IPv6
        multihop sessions per location";

      list ipv6-multi-hop-node-location-summary {
        xr:xr-xml-map "ip_bfd_oper:IPv6MultiHopNodeLocationSummary";
        key "location";
        description
          "Summary information for BFD IPv6 multihop
          sessions for location";
        leaf location {
          xr:xr-xml-map "ip_bfd_oper:Location";
          type xr:Node-id;
          description "Location";
        }
        uses BFD-MGMT-BFD-LOC-INFORMATION;
      }
    }

    container ipv4-multi-hop-summary {
      xr:xr-xml-map "ip_bfd_oper:IPv4MultiHopSummary";
      description
        "Summary information of BFD IPv4 multihop
        sessions";
      uses BFD-MGMT-BFD-INFORMATION;
    }

    container ipv4-single-hop-counters {
      xr:xr-xml-map "ip_bfd_oper:IPv4SingleHopCounters";
      description "IPv4 single hop Counters";

      container ipv4-single-hop-packet-counters {
        xr:xr-xml-map "ip_bfd_oper:IPv4SingleHopPacketCountersTable";
        description "Table of IPv4 single hop Packet counters";

        list ipv4-single-hop-packet-counter {
          xr:xr-xml-map "ip_bfd_oper:IPv4SingleHopPacketCounters";
          key "interface-name";
          description "Interface IPv4 single hop Packet counters";
          leaf interface-name {
            xr:xr-xml-map "ip_bfd_oper:InterfaceName";
            type xr:Interface-name;
            description "Interface Name";
          }
          uses BFD-MGMT-PACKET-COUNT;
        }
      }
    }

    container ipv6-multi-hop-session-details {
      xr:xr-xml-map "ip_bfd_oper:IPv6MultiHopSessionDetailTable";
      description
        "Table of detailed information about all IPv6
        multihop BFD sessions in the System ";

      list ipv6-multi-hop-session-detail {
        xr:xr-xml-map "ip_bfd_oper:IPv6MultiHopSessionDetail";
        description
          "Detailed information for a single IPv6 multihop
          BFD session";
        leaf source-address {
          xr:xr-xml-map "ip_bfd_oper:SourceAddress";
          type inet:ip-address-no-zone;
          description "Source Address";
        }
        leaf destination-address {
          xr:xr-xml-map "ip_bfd_oper:DestinationAddress";
          type inet:ip-address-no-zone;
          description "Destination Address";
        }
        leaf location {
          xr:xr-xml-map "ip_bfd_oper:Location";
          type xr:Node-id;
          description "Location";
        }
        leaf vrf-name {
          xr:xr-xml-map "ip_bfd_oper:VRFName";
          type xr:Cisco-ios-xr-string;
          description "VRF name";
        }
        uses BFD-MGMT-SESSION-DETAIL;
      }
    }

    container ipv6-multi-hop-multi-paths {
      xr:xr-xml-map "ip_bfd_oper:IPv6MultiHopMultiPathTable";
      description "IPv6 multi hop multipath";

      list ipv6-multi-hop-multi-path {
        xr:xr-xml-map "ip_bfd_oper:IPv6MultiHopMultiPath";
        description "IPv6 multihop multipath table";
        leaf source-address {
          xr:xr-xml-map "ip_bfd_oper:SourceAddress";
          type inet:ip-address-no-zone;
          description "Source address";
        }
        leaf destination-address {
          xr:xr-xml-map "ip_bfd_oper:DestinationAddress";
          type inet:ip-address-no-zone;
          description "Destination address";
        }
        leaf location {
          xr:xr-xml-map "ip_bfd_oper:Location";
          type xr:Node-id;
          description "Location";
        }
        leaf vrf-name {
          xr:xr-xml-map "ip_bfd_oper:VRFName";
          type xr:Cisco-ios-xr-string;
          description "VRF name";
        }
        uses BFD-MGMT-MULTIPLE-PATHS;
      }
    }

    container ipv4bf-do-mplste-head-counters {
      xr:xr-xml-map "ip_bfd_oper:IPv4BFDoMPLSTEHeadCounters";
      description "IPv4 BFD over MPLS-TE Counters";

      container ipv4bf-do-mplste-head-packet-counters {
        xr:xr-xml-map "ip_bfd_oper:IPv4BFDoMPLSTEHeadPacketCounters"+
          "Table";
        description
          "Table of IPv4 BFD over MPLS-TE Packet counters";

        list ipv4bf-do-mplste-head-packet-counter {
          xr:xr-xml-map "ip_bfd_oper:IPv4BFDoMPLSTEHeadPacketCounte"+
            "rs";
          description
            "Interface  IPv4 BFD over MPLS-TE Packet
            counters";
          leaf interface-name {
            xr:xr-xml-map "ip_bfd_oper:InterfaceName";
            type xr:Interface-name;
            description "Interface Name";
          }
          leaf location {
            xr:xr-xml-map "ip_bfd_oper:Location";
            type xr:Node-id;
            description "Location";
          }
          uses BFD-MGMT-PACKET-COUNT;
        }
      }
    }

    container session-mibs {
      xr:xr-xml-map "ip_bfd_oper:SessionMIBTable";
      description "BFD session MIB database";

      list session-mib {
        xr:xr-xml-map "ip_bfd_oper:SessionMIB";
        key "discriminator";
        description "Brief information for BFD session MIB";
        leaf discriminator {
          xr:xr-xml-map "ip_bfd_oper:Discriminator";
          type int32;
          description "Sesison Discr ";
        }
        uses BFD-MGMT-MIB-DATABASE;
      }
    }

    container ipv6-multi-hop-summary {
      xr:xr-xml-map "ip_bfd_oper:IPv6MultiHopSummary";
      description
        "Summary information of BFD IPv6 multihop
        sessions";
      uses BFD-MGMT-BFD-INFORMATION;
    }

    container label-summary-nodes {
      xr:xr-xml-map "ip_bfd_oper:LabelSummaryNodeTable";
      description
        "Table of summary about Label BFD sessions for
        location";

      list label-summary-node {
        xr:xr-xml-map "ip_bfd_oper:LabelSummaryNode";
        key "location-name";
        description "Summary of Label BFD ";
        leaf location-name {
          xr:xr-xml-map "ip_bfd_oper:LocationName";
          type xr:Cisco-ios-xr-string;
          description "Location name";
        }
        uses BFD-MGMT-BFD-LOC-INFORMATION;
      }
    }

    container ipv6-multi-hop-session-briefs {
      xr:xr-xml-map "ip_bfd_oper:IPv6MultiHopSessionBriefTable";
      description
        "Table of brief information about all IPv6
        multihop BFD sessions in the System";

      list ipv6-multi-hop-session-brief {
        xr:xr-xml-map "ip_bfd_oper:IPv6MultiHopSessionBrief";
        description
          "Brief information for a single IPv6 multihop
          BFD session";
        leaf source-address {
          xr:xr-xml-map "ip_bfd_oper:SourceAddress";
          type inet:ip-address-no-zone;
          description "Source Address";
        }
        leaf destination-address {
          xr:xr-xml-map "ip_bfd_oper:DestinationAddress";
          type inet:ip-address-no-zone;
          description "Destination Address";
        }
        leaf location {
          xr:xr-xml-map "ip_bfd_oper:Location";
          type xr:Node-id;
          description "Location";
        }
        leaf vrf-name {
          xr:xr-xml-map "ip_bfd_oper:VRFName";
          type xr:Cisco-ios-xr-string;
          description "VRF name";
        }
        uses BFD-MGMT-SESSION-BRIEF;
      }
    }

    container session-briefs {
      xr:xr-xml-map "ip_bfd_oper:SessionBriefTable";
      description
        "Table of brief information about singlehop IPv4
        BFD sessions in the System";

      list session-brief {
        xr:xr-xml-map "ip_bfd_oper:SessionBrief";
        description
          "Brief information for a single IPv4 singlehop
          BFD session";
        leaf interface-name {
          xr:xr-xml-map "ip_bfd_oper:InterfaceName";
          type xr:Interface-name;
          description "Interface Name";
        }
        leaf destination-address {
          xr:xr-xml-map "ip_bfd_oper:DestinationAddress";
          type inet:ipv4-address-no-zone;
          description "Destination Address";
        }
        leaf location {
          xr:xr-xml-map "ip_bfd_oper:Location";
          type xr:Node-id;
          description "Location";
        }
        uses BFD-MGMT-SESSION-BRIEF;
      }
    }

    container ipv6-single-hop-node-location-summaries {
      xr:xr-xml-map "ip_bfd_oper:IPv6SingleHopNodeLocationSummaryTa"+
        "ble";
      description
        "Table of summary information about BFD IPv6
        singlehop sessions per location";

      list ipv6-single-hop-node-location-summary {
        xr:xr-xml-map "ip_bfd_oper:IPv6SingleHopNodeLocationSummary";
        key "location";
        description
          "Summary information for BFD IPv6 singlehop
          sessions for location";
        leaf location {
          xr:xr-xml-map "ip_bfd_oper:Location";
          type xr:Node-id;
          description "Location";
        }
        uses BFD-MGMT-BFD-LOC-INFORMATION;
      }
    }

    container summary {
      xr:xr-xml-map "ip_bfd_oper:Summary";
      description
        "Summary information of BFD IPv4 singlehop
        sessions";
      uses BFD-MGMT-BFD-INFORMATION;
    }

    container ipv4bfd-mplste-tail-node-summaries {
      xr:xr-xml-map "ip_bfd_oper:IPv4BFD_MPLSTETailSummaryNodeTable";
      description
        "Table of summary about IPv4 TE tail BFD sessions
        for location";

      list ipv4bfd-mplste-tail-node-summary {
        xr:xr-xml-map "ip_bfd_oper:IPv4BFD_MPLSTETailNodeSummary";
        key "location-name";
        description "Summary of IPv4 BFD over MPLS-TE tail";
        leaf location-name {
          xr:xr-xml-map "ip_bfd_oper:LocationName";
          type xr:Cisco-ios-xr-string;
          description "Location name";
        }
        uses BFD-MGMT-BFD-LOC-INFORMATION;
      }
    }

    container ipv4-single-hop-location-summaries {
      xr:xr-xml-map "ip_bfd_oper:IPv4SingleHopLocationSummaryTable";
      description
        "Table of summary information about IPv4
        singlehop BFD sessions for location";

      list ipv4-single-hop-location-summary {
        xr:xr-xml-map "ip_bfd_oper:IPv4SingleHopLocationSummary";
        key "location-name";
        description
          "Summary information for BFD IPv4 singlehop
          sessions for location";
        leaf location-name {
          xr:xr-xml-map "ip_bfd_oper:LocationName";
          type xr:Cisco-ios-xr-string;
          description "Location Name";
        }
        uses BFD-MGMT-BFD-LOC-INFORMATION;
      }
    }

    container ipv4bfd-mplste-head-summary-nodes {
      xr:xr-xml-map "ip_bfd_oper:IPv4BFD_MPLSTEHeadSummaryNodeTable";
      description
        "Table of summary about IPv4 TE head BFD sessions
        for location";

      list ipv4bfd-mplste-head-summary-node {
        xr:xr-xml-map "ip_bfd_oper:IPv4BFD_MPLSTEHeadSummaryNode";
        key "location-name";
        description "Summary of IPv4 BFD over MPLS-TE head";
        leaf location-name {
          xr:xr-xml-map "ip_bfd_oper:LocationName";
          type xr:Cisco-ios-xr-string;
          description "Location name";
        }
        uses BFD-MGMT-BFD-LOC-INFORMATION;
      }
    }

    container label-session-details {
      xr:xr-xml-map "ip_bfd_oper:LabelSessionDetailTable";
      description
        "Table of detailed information about all Label
        BFD sessions in the System ";

      list label-session-detail {
        xr:xr-xml-map "ip_bfd_oper:LabelSessionDetail";
        description "Detailed information for a single BFD session";
        leaf interface-name {
          xr:xr-xml-map "ip_bfd_oper:InterfaceName";
          type xr:Interface-name;
          description "Interface Name";
        }
        leaf incoming-label {
          xr:xr-xml-map "ip_bfd_oper:IncomingLabel";
          type int32;
          description "Incoming Label";
        }
        leaf location {
          xr:xr-xml-map "ip_bfd_oper:Location";
          type xr:Node-id;
          description "Location";
        }
        uses BFD-MGMT-SESSION-DETAIL;
      }
    }

    container ipv6-single-hop-session-details {
      xr:xr-xml-map "ip_bfd_oper:IPv6SingleHopSessionDetailTable";
      description
        "Table of detailed information about all IPv6
        singlehop BFD sessions in the System ";

      list ipv6-single-hop-session-detail {
        xr:xr-xml-map "ip_bfd_oper:IPv6SingleHopSessionDetail";
        description
          "Detailed information for a single IPv6
          singlehop BFD session";
        leaf interface-name {
          xr:xr-xml-map "ip_bfd_oper:InterfaceName";
          type xr:Interface-name;
          description "Interface Name";
        }
        leaf destination-address {
          xr:xr-xml-map "ip_bfd_oper:DestinationAddress";
          type inet:ip-address-no-zone;
          description "Destination Address";
        }
        leaf location {
          xr:xr-xml-map "ip_bfd_oper:Location";
          type xr:Node-id;
          description "Location";
        }
        uses BFD-MGMT-SESSION-DETAIL;
      }
    }

    container ipv4-multi-hop-counters {
      xr:xr-xml-map "ip_bfd_oper:IPv4MultiHopCounters";
      description "IPv4 multiple hop Counters";

      container ipv4-multi-hop-packet-counters {
        xr:xr-xml-map "ip_bfd_oper:IPv4MultiHopPacketCountersTable";
        description "Table of IPv4 multiple hop Packet counters";

        list ipv4-multi-hop-packet-counter {
          xr:xr-xml-map "ip_bfd_oper:IPv4MultiHopPacketCounters";
          description "IPv4 multiple hop Packet counters";
          leaf source-address {
            xr:xr-xml-map "ip_bfd_oper:SourceAddress";
            type inet:ip-address-no-zone;
            description "Source Address";
          }
          leaf destination-address {
            xr:xr-xml-map "ip_bfd_oper:DestinationAddress";
            type inet:ip-address-no-zone;
            description "Destination Address";
          }
          leaf location {
            xr:xr-xml-map "ip_bfd_oper:Location";
            type xr:Node-id;
            description "Location";
          }
          leaf vrf-name {
            xr:xr-xml-map "ip_bfd_oper:VRFName";
            type xr:Cisco-ios-xr-string;
            description "VRF name";
          }
          uses BFD-MGMT-PACKET-COUNT;
        }
      }
    }

    container session-details {
      xr:xr-xml-map "ip_bfd_oper:SessionDetailTable";
      description
        "Table of detailed information about IPv4
        singlehop BFD sessions in the System ";

      list session-detail {
        xr:xr-xml-map "ip_bfd_oper:SessionDetail";
        description
          "Detailed information for a single IPv4
          singlehop BFD session";
        leaf interface-name {
          xr:xr-xml-map "ip_bfd_oper:InterfaceName";
          type xr:Interface-name;
          description "Interface Name";
        }
        leaf destination-address {
          xr:xr-xml-map "ip_bfd_oper:DestinationAddress";
          type inet:ipv4-address-no-zone;
          description "Destination Address";
        }
        leaf location {
          xr:xr-xml-map "ip_bfd_oper:Location";
          type xr:Node-id;
          description "Location";
        }
        uses BFD-MGMT-SESSION-DETAIL;
      }
    }

    container ipv4-single-hop-multi-paths {
      xr:xr-xml-map "ip_bfd_oper:IPv4SingleHopMultiPathTable";
      description "IPv4 single hop multipath";

      list ipv4-single-hop-multi-path {
        xr:xr-xml-map "ip_bfd_oper:IPv4SingleHopMultiPath";
        description "IPv4 single hop multipath table";
        leaf interface-name {
          xr:xr-xml-map "ip_bfd_oper:InterfaceName";
          type xr:Interface-name;
          description "Interface Name";
        }
        leaf destination-address {
          xr:xr-xml-map "ip_bfd_oper:DestinationAddress";
          type inet:ipv4-address-no-zone;
          description "Destination Address";
        }
        leaf location {
          xr:xr-xml-map "ip_bfd_oper:Location";
          type xr:Node-id;
          description "Location";
        }
        uses BFD-MGMT-MULTIPLE-PATHS;
      }
    }

    container ipv4-single-hop-session-briefs {
      xr:xr-xml-map "ip_bfd_oper:IPv4SingleHopSessionBriefTable";
      description
        "Table of brief information about all IPv4
        singlehop BFD sessions in the System";

      list ipv4-single-hop-session-brief {
        xr:xr-xml-map "ip_bfd_oper:IPv4SingleHopSessionBrief";
        description
          "Brief information for a single IPv4 singlehop
          BFD session";
        leaf interface-name {
          xr:xr-xml-map "ip_bfd_oper:InterfaceName";
          type xr:Interface-name;
          description "Interface Name";
        }
        leaf destination-address {
          xr:xr-xml-map "ip_bfd_oper:DestinationAddress";
          type inet:ipv4-address-no-zone;
          description "Destination Address";
        }
        leaf location {
          xr:xr-xml-map "ip_bfd_oper:Location";
          type xr:Node-id;
          description "Location";
        }
        uses BFD-MGMT-SESSION-BRIEF;
      }
    }

    container ipv6-multi-hop-counters {
      xr:xr-xml-map "ip_bfd_oper:IPv6MultiHopCounters";
      description "IPv6 multiple hop Counters";

      container ipv6-multi-hop-packet-counters {
        xr:xr-xml-map "ip_bfd_oper:IPv6MultiHopPacketCountersTable";
        description "Table of IPv6 multiple hop Packet counters";

        list ipv6-multi-hop-packet-counter {
          xr:xr-xml-map "ip_bfd_oper:IPv6MultiHopPacketCounters";
          description "IPv4 multiple hop Packet counters";
          leaf source-address {
            xr:xr-xml-map "ip_bfd_oper:SourceAddress";
            type inet:ip-address-no-zone;
            description "Source Address";
          }
          leaf destination-address {
            xr:xr-xml-map "ip_bfd_oper:DestinationAddress";
            type inet:ip-address-no-zone;
            description "Destination Address";
          }
          leaf location {
            xr:xr-xml-map "ip_bfd_oper:Location";
            type xr:Node-id;
            description "Location";
          }
          leaf vrf-name {
            xr:xr-xml-map "ip_bfd_oper:VRFName";
            type xr:Cisco-ios-xr-string;
            description "VRF name";
          }
          uses BFD-MGMT-PACKET-COUNT;
        }
      }
    }

    container ipv6-single-hop-location-summaries {
      xr:xr-xml-map "ip_bfd_oper:IPv6SingleHopLocationSummaryTable";
      description
        "Table of summary information about BFD IPv6
        singlehop sessions per location";

      list ipv6-single-hop-location-summary {
        xr:xr-xml-map "ip_bfd_oper:IPv6SingleHopLocationSummary";
        key "location-name";
        description
          "Summary information for BFD IPv6 singlehop
          sessions for location";
        leaf location-name {
          xr:xr-xml-map "ip_bfd_oper:LocationName";
          type xr:Cisco-ios-xr-string;
          description "Location Name";
        }
        uses BFD-MGMT-BFD-LOC-INFORMATION;
      }
    }

    container label-counters {
      xr:xr-xml-map "ip_bfd_oper:LabelCounters";
      description "Label Counters";

      container label-packet-counters {
        xr:xr-xml-map "ip_bfd_oper:LabelPacketCountersTable";
        description "Table of Label Packet counters";

        list label-packet-counter {
          xr:xr-xml-map "ip_bfd_oper:LabelPacketCounters";
          description "Interface Label Packet counters";
          leaf interface-name {
            xr:xr-xml-map "ip_bfd_oper:InterfaceName";
            type xr:Interface-name;
            description "Interface Name";
          }
          leaf location {
            xr:xr-xml-map "ip_bfd_oper:Location";
            type xr:Node-id;
            description "Location";
          }
          uses BFD-MGMT-PACKET-COUNT;
        }
      }
    }

    container ipv4bf-do-mplste-head-session-details {
      xr:xr-xml-map "ip_bfd_oper:IPv4BFDoMPLSTEHeadSessionDetailTab"+
        "le";
      description
        "Table of detailed information about all IPv4 BFD
        over MPLS-TE Head sessions in the System";

      list ipv4bf-do-mplste-head-session-detail {
        xr:xr-xml-map "ip_bfd_oper:IPv4BFDoMPLSTEHeadSessionDetail";
        description
          "Detailed information for a single IPv4 BFD over
          MPLS-TE head session";
        leaf interface-name {
          xr:xr-xml-map "ip_bfd_oper:InterfaceName";
          type xr:Interface-name;
          description "Interface Name";
        }
        leaf vrf-name {
          xr:xr-xml-map "ip_bfd_oper:VRFName";
          type xr:Cisco-ios-xr-string;
          description "VRF name";
        }
        leaf incoming-label {
          xr:xr-xml-map "ip_bfd_oper:IncomingLabel";
          type int32;
          description "Incoming Label";
        }
        leaf fe-ctype {
          xr:xr-xml-map "ip_bfd_oper:FECType";
          type int32;
          description "FEC Type";
        }
        leaf fec-subgroup-id {
          xr:xr-xml-map "ip_bfd_oper:FECSubgroupID";
          type int32;
          description "FEC Subgroup ID";
        }
        leaf feclspid {
          xr:xr-xml-map "ip_bfd_oper:FECLSPID";
          type int32;
          description "FEC LSP ID";
        }
        leaf fec-tunnel-id {
          xr:xr-xml-map "ip_bfd_oper:FECTunnelID";
          type int32;
          description "FEC Tunnel ID";
        }
        leaf fec-extended-tunnel-id {
          xr:xr-xml-map "ip_bfd_oper:FECExtendedTunnelID";
          type inet:ipv4-address-no-zone;
          description "FEC Extended Tunnel ID";
        }
        leaf fec-source {
          xr:xr-xml-map "ip_bfd_oper:FECSource";
          type inet:ipv4-address-no-zone;
          description "FEC Source";
        }
        leaf fec-destination {
          xr:xr-xml-map "ip_bfd_oper:FECDestination";
          type inet:ipv4-address-no-zone;
          description "FEC Destination";
        }
        leaf fecp2mpid {
          xr:xr-xml-map "ip_bfd_oper:FECP2MPID";
          type int32;
          description "FEC P2MP ID";
        }
        leaf fec-subgroup-originator {
          xr:xr-xml-map "ip_bfd_oper:FECSubgroupOriginator";
          type inet:ipv4-address-no-zone;
          description "FEC Subgroup originator";
        }
        leaf fec-ctype {
          xr:xr-xml-map "ip_bfd_oper:FECCType";
          type int32;
          description "FEC C Type";
        }
        leaf location {
          xr:xr-xml-map "ip_bfd_oper:Location";
          type xr:Node-id;
          description "Location";
        }
        uses BFD-MGMT-SESSION-DETAIL;
      }
    }

    container relation-briefs {
      xr:xr-xml-map "ip_bfd_oper:RelationBriefTable";
      description
        "Table of brief information about all BFD
        relations in the System";

      list relation-brief {
        xr:xr-xml-map "ip_bfd_oper:RelationBrief";
        description
          "Brief information for relation of a single BFD
          session";
        leaf interface-name {
          xr:xr-xml-map "ip_bfd_oper:InterfaceName";
          type xr:Interface-name;
          description "Interface Name";
        }
        leaf destination-address {
          xr:xr-xml-map "ip_bfd_oper:DestinationAddress";
          type inet:ip-address-no-zone;
          description "Destination Address";
        }
        uses BFD-MGMT-RELATION-BRIEF;
      }
    }

    container client-briefs {
      xr:xr-xml-map "ip_bfd_oper:ClientBriefTable";
      description "Table of Brief information about BFD clients";

      list client-brief {
        xr:xr-xml-map "ip_bfd_oper:ClientBrief";
        key "name";
        description "Brief information of client";
        leaf name {
          xr:xr-xml-map "ip_bfd_oper:Name";
          type xr:Cisco-ios-xr-string;
          description "Client Name";
        }
        uses BFD-MGMT-CLIENT-BRIEF-INFORMATION;
      }
    }

    container ipv4bf-do-mplste-head-multi-paths {
      xr:xr-xml-map "ip_bfd_oper:IPv4BFDoMPLSTEHeadMultiPathTable";
      description "IPv4 BFD over MPLS-TE Head multipath";

      list ipv4bf-do-mplste-head-multi-path {
        xr:xr-xml-map "ip_bfd_oper:IPv4BFDoMPLSTEHeadMultiPath";
        description "Label multipath table";
        leaf interface-name {
          xr:xr-xml-map "ip_bfd_oper:InterfaceName";
          type xr:Interface-name;
          description "Interface Name";
        }
        leaf vrf-name {
          xr:xr-xml-map "ip_bfd_oper:VRFName";
          type xr:Cisco-ios-xr-string;
          description "VRF name";
        }
        leaf incoming-label {
          xr:xr-xml-map "ip_bfd_oper:IncomingLabel";
          type int32;
          description "Incoming Label";
        }
        leaf fe-ctype {
          xr:xr-xml-map "ip_bfd_oper:FECType";
          type int32;
          description "FEC Type";
        }
        leaf fec-subgroup-id {
          xr:xr-xml-map "ip_bfd_oper:FECSubgroupID";
          type int32;
          description "FEC Subgroup ID";
        }
        leaf feclspid {
          xr:xr-xml-map "ip_bfd_oper:FECLSPID";
          type int32;
          description "FEC LSP ID";
        }
        leaf fec-tunnel-id {
          xr:xr-xml-map "ip_bfd_oper:FECTunnelID";
          type int32;
          description "FEC Tunnel ID";
        }
        leaf fec-extended-tunnel-id {
          xr:xr-xml-map "ip_bfd_oper:FECExtendedTunnelID";
          type inet:ipv4-address-no-zone;
          description "FEC Extended Tunnel ID";
        }
        leaf fec-source {
          xr:xr-xml-map "ip_bfd_oper:FECSource";
          type inet:ipv4-address-no-zone;
          description "FEC Source";
        }
        leaf fec-destination {
          xr:xr-xml-map "ip_bfd_oper:FECDestination";
          type inet:ipv4-address-no-zone;
          description "FEC Destination";
        }
        leaf fecp2mpid {
          xr:xr-xml-map "ip_bfd_oper:FECP2MPID";
          type int32;
          description "FEC P2MP ID";
        }
        leaf fec-subgroup-originator {
          xr:xr-xml-map "ip_bfd_oper:FECSubgroupOriginator";
          type inet:ipv4-address-no-zone;
          description "FEC Subgroup originator";
        }
        leaf fec-ctype {
          xr:xr-xml-map "ip_bfd_oper:FECCType";
          type int32;
          description "FEC C Type";
        }
        leaf location {
          xr:xr-xml-map "ip_bfd_oper:Location";
          type xr:Node-id;
          description "Location";
        }
        uses BFD-MGMT-MULTIPLE-PATHS;
      }
    }

    container relation-details {
      xr:xr-xml-map "ip_bfd_oper:RelationDetailTable";
      description
        "Table of detail information about all BFD
        relations in the System";

      list relation-detail {
        xr:xr-xml-map "ip_bfd_oper:RelationDetail";
        description
          "Detail information for relation of a single BFD
          session";
        leaf interface-name {
          xr:xr-xml-map "ip_bfd_oper:InterfaceName";
          type xr:Interface-name;
          description "Interface Name";
        }
        leaf destination-address {
          xr:xr-xml-map "ip_bfd_oper:DestinationAddress";
          type inet:ip-address-no-zone;
          description "Destination Address";
        }
        uses BFD-MGMT-RELATION;
      }
    }

    container ipv4bf-do-mplste-tail-counters {
      xr:xr-xml-map "ip_bfd_oper:IPv4BFDoMPLSTETailCounters";
      description "IPv4 BFD over MPLS-TE Counters";

      container ipv4bf-do-mplste-tail-packet-counters {
        xr:xr-xml-map "ip_bfd_oper:IPv4BFDoMPLSTETailPacketCounters"+
          "Table";
        description
          "Table of IPv4 BFD over MPLS-TE Packet counters";

        list ipv4bf-do-mplste-tail-packet-counter {
          xr:xr-xml-map "ip_bfd_oper:IPv4BFDoMPLSTETailPacketCounte"+
            "rs";
          description
            "Interface  IPv4 BFD over MPLS-TE Packet
            counters";
          leaf vrf-name {
            xr:xr-xml-map "ip_bfd_oper:VRFName";
            type xr:Cisco-ios-xr-string;
            description "VRF name";
          }
          leaf incoming-label {
            xr:xr-xml-map "ip_bfd_oper:IncomingLabel";
            type int32;
            description "Incoming Label";
          }
          leaf fe-ctype {
            xr:xr-xml-map "ip_bfd_oper:FECType";
            type int32;
            description "FEC Type";
          }
          leaf fec-subgroup-id {
            xr:xr-xml-map "ip_bfd_oper:FECSubgroupID";
            type int32;
            description "FEC Subgroup ID";
          }
          leaf feclspid {
            xr:xr-xml-map "ip_bfd_oper:FECLSPID";
            type int32;
            description "FEC LSP ID";
          }
          leaf fec-tunnel-id {
            xr:xr-xml-map "ip_bfd_oper:FECTunnelID";
            type int32;
            description "FEC Tunnel ID";
          }
          leaf fec-extended-tunnel-id {
            xr:xr-xml-map "ip_bfd_oper:FECExtendedTunnelID";
            type inet:ipv4-address-no-zone;
            description "FEC Extended Tunnel ID";
          }
          leaf fec-source {
            xr:xr-xml-map "ip_bfd_oper:FECSource";
            type inet:ipv4-address-no-zone;
            description "FEC Source";
          }
          leaf fec-destination {
            xr:xr-xml-map "ip_bfd_oper:FECDestination";
            type inet:ipv4-address-no-zone;
            description "FEC Destination";
          }
          leaf fecp2mpid {
            xr:xr-xml-map "ip_bfd_oper:FECP2MPID";
            type int32;
            description "FEC P2MP ID";
          }
          leaf fec-subgroup-originator {
            xr:xr-xml-map "ip_bfd_oper:FECSubgroupOriginator";
            type inet:ipv4-address-no-zone;
            description "FEC Subgroup originator";
          }
          leaf fec-ctype {
            xr:xr-xml-map "ip_bfd_oper:FECCType";
            type int32;
            description "FEC C Type";
          }
          leaf location {
            xr:xr-xml-map "ip_bfd_oper:Location";
            type xr:Node-id;
            description "Location";
          }
          uses BFD-MGMT-PACKET-COUNT;
        }
      }
    }

    container ipv6-single-hop-session-briefs {
      xr:xr-xml-map "ip_bfd_oper:IPv6SingleHopSessionBriefTable";
      description
        "Table of brief information about all IPv6
        singlehop BFD sessions in the System";

      list ipv6-single-hop-session-brief {
        xr:xr-xml-map "ip_bfd_oper:IPv6SingleHopSessionBrief";
        description
          "Brief information for a single IPv6 singlehop
          BFD session";
        leaf interface-name {
          xr:xr-xml-map "ip_bfd_oper:InterfaceName";
          type xr:Interface-name;
          description "Interface Name";
        }
        leaf destination-address {
          xr:xr-xml-map "ip_bfd_oper:DestinationAddress";
          type inet:ip-address-no-zone;
          description "Destination Address";
        }
        leaf location {
          xr:xr-xml-map "ip_bfd_oper:Location";
          type xr:Node-id;
          description "Location";
        }
        uses BFD-MGMT-SESSION-BRIEF;
      }
    }

    container ipv4bf-do-mplste-tail-multi-paths {
      xr:xr-xml-map "ip_bfd_oper:IPv4BFDoMPLSTETailMultiPathTable";
      description "IPv4 BFD over MPLS-TE Tail multipath";

      list ipv4bf-do-mplste-tail-multi-path {
        xr:xr-xml-map "ip_bfd_oper:IPv4BFDoMPLSTETailMultiPath";
        description "Label multipath table";
        leaf vrf-name {
          xr:xr-xml-map "ip_bfd_oper:VRFName";
          type xr:Cisco-ios-xr-string;
          description "VRF name";
        }
        leaf incoming-label {
          xr:xr-xml-map "ip_bfd_oper:IncomingLabel";
          type int32;
          description "Incoming Label";
        }
        leaf fe-ctype {
          xr:xr-xml-map "ip_bfd_oper:FECType";
          type int32;
          description "FEC Type";
        }
        leaf fec-subgroup-id {
          xr:xr-xml-map "ip_bfd_oper:FECSubgroupID";
          type int32;
          description "FEC Subgroup ID";
        }
        leaf feclspid {
          xr:xr-xml-map "ip_bfd_oper:FECLSPID";
          type int32;
          description "FEC LSP ID";
        }
        leaf fec-tunnel-id {
          xr:xr-xml-map "ip_bfd_oper:FECTunnelID";
          type int32;
          description "FEC Tunnel ID";
        }
        leaf fec-extended-tunnel-id {
          xr:xr-xml-map "ip_bfd_oper:FECExtendedTunnelID";
          type inet:ipv4-address-no-zone;
          description "FEC Extended Tunnel ID";
        }
        leaf fec-source {
          xr:xr-xml-map "ip_bfd_oper:FECSource";
          type inet:ipv4-address-no-zone;
          description "FEC Source";
        }
        leaf fec-destination {
          xr:xr-xml-map "ip_bfd_oper:FECDestination";
          type inet:ipv4-address-no-zone;
          description "FEC Destination";
        }
        leaf fecp2mpid {
          xr:xr-xml-map "ip_bfd_oper:FECP2MPID";
          type int32;
          description "FEC P2MP ID";
        }
        leaf fec-subgroup-originator {
          xr:xr-xml-map "ip_bfd_oper:FECSubgroupOriginator";
          type inet:ipv4-address-no-zone;
          description "FEC Subgroup originator";
        }
        leaf fec-ctype {
          xr:xr-xml-map "ip_bfd_oper:FECCType";
          type int32;
          description "FEC C Type";
        }
        leaf location {
          xr:xr-xml-map "ip_bfd_oper:Location";
          type xr:Node-id;
          description "Location";
        }
        uses BFD-MGMT-MULTIPLE-PATHS;
      }
    }

    container ipv4-multi-hop-multi-paths {
      xr:xr-xml-map "ip_bfd_oper:IPv4MultiHopMultiPathTable";
      description "IPv4 multi-hop multipath";

      list ipv4-multi-hop-multi-path {
        xr:xr-xml-map "ip_bfd_oper:IPv4MultiHopMultiPath";
        description "IPv4 multi hop multipath table";
        leaf source-address {
          xr:xr-xml-map "ip_bfd_oper:SourceAddress";
          type inet:ip-address-no-zone;
          description "Source Address";
        }
        leaf destination-address {
          xr:xr-xml-map "ip_bfd_oper:DestinationAddress";
          type inet:ip-address-no-zone;
          description "Destination Address";
        }
        leaf location {
          xr:xr-xml-map "ip_bfd_oper:Location";
          type xr:Node-id;
          description "Location";
        }
        leaf vrf-name {
          xr:xr-xml-map "ip_bfd_oper:VRFName";
          type xr:Cisco-ios-xr-string;
          description "VRF name";
        }
        uses BFD-MGMT-MULTIPLE-PATHS;
      }
    }

    container ipv4bf-do-mplste-head-summary {
      xr:xr-xml-map "ip_bfd_oper:IPv4BFDoMPLSTEHeadSummary";
      description
        "Summary information of IPv4 BFD over MPLS-TE
        Head";
      uses BFD-MGMT-BFD-INFORMATION;
    }
  }
}
