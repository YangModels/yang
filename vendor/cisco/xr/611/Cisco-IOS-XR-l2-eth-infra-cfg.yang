module Cisco-IOS-XR-l2-eth-infra-cfg {

  /*** NAMESPACE / PREFIX DEFINITION ***/

  namespace "http://cisco.com/ns/yang/Cisco-IOS-XR-l2-eth-infra-cfg";


  prefix "l2-eth-infra-cfg";

  /*** LINKAGE (IMPORTS / INCLUDES) ***/

  import ietf-yang-types { prefix "yang"; }

  import Cisco-IOS-XR-types { prefix "xr"; }

  import Cisco-IOS-XR-l2-eth-infra-datatypes { prefix "dt1"; }

  import Cisco-IOS-XR-ifmgr-cfg { prefix "a1"; }

  import Cisco-IOS-XR-l2vpn-cfg { prefix "a2"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR l2-eth-infra package configuration.

     This module contains definitions
     for the following management objects:
       ethernet-features: Ethernet Features Configuration

     This YANG module augments the
       Cisco-IOS-XR-ifmgr-cfg,
       Cisco-IOS-XR-l2vpn-cfg
     modules with configuration data.

     Copyright (c) 2013-2016 by Cisco Systems, Inc.
     All rights reserved.";

  revision "2015-11-09" {
    description
      "IOS XR 6.0 revision.";
  }

  typedef L2-protocol-name {
    type enumeration {
      enum cdp {
        value 0;
        description "CDP";
      }
      enum stp {
        value 1;
        description "STP";
      }
      enum vtp {
        value 2;
        description "VTP";
      }
      enum pvst {
        value 3;
        description "PVST+";
      }
      enum cpsv {
        value 4;
        description "CDP, PVST+, STP, and VTP";
      }
    }
    description "L2 protocol name";
  }
  typedef L2-protocol-mode {
    type enumeration {
      enum forward {
        value 0;
        description "Forward packets transparently";
      }
      enum drop {
        value 1;
        description "Drop the protocol's packets";
      }
      enum tunnel {
        value 2;
        description "Tunnel ingress frames, untunnel egress frames";
      }
      enum reverse-tunnel {
        value 3;
        description "Tunnel egress frames, untunnel ingress frames";
      }
    }
    description "L2 protocol mode";
  }
  typedef Egress-filtering {
    type enumeration {
      enum egress-filtering-type-strict {
        value 1;
        description "Strict Egress Filtering";
      }
      enum egress-filtering-type-disable {
        value 2;
        description "Egress Filtering Disabled";
      }
      enum egress-filtering-type-default {
        value 3;
        description "Default Egress Filtering Behavior";
      }
    }
    description "Egress filtering";
  }
  typedef Filtering {
    type enumeration {
      enum filtering-type-dot1q {
        value 0;
        description
          "C-Vlan ingress frame filtering (Table 8-1 of
          802.1ad standard)";
      }
      enum filtering-type-dot1ad {
        value 1;
        description
          "S-Vlan ingress frame filtering (Table 8-2 of
          802.1ad standard)";
      }
      enum filtering-type-mac-relay {
        value 2;
        description
          "2-Port Mac Relay ingress frame filtering (802
          .1aj standard)";
      }
    }
    description "Filtering";
  }
  typedef L2-protocol-mpls-exp-bits-value {
    type uint32 {
      range "0..7";
    }
    description "L2 protocol mpls exp bits value";
  }

  container ethernet-features {
    xr:xr-xml-map "ether_gl_feature_cfg:EthernetFeatures";
    description "Ethernet Features Configuration";

    container egress-filtering {
      xr:xr-xml-map "ether_gl_cfg:EgressFiltering";
      description "Egress Filtering Configuration";
      leaf egress-filtering-default-on {
        xr:xr-xml-map "ether_gl_cfg:EgressFilteringDefaultOn";
        type empty;
        description "Whether Egress Filtering is on by default";
      }
    }
  }

  augment "/a1:interface-configurations/a1:interface-configuration" {

    container vlan-sub-configuration {
      xr:xr-xml-map "vlan_interface_cfg:VLANSubConfiguration";
      description "IEEE 802.1Q VLAN subinterface configuration";

      container vlan-identifier {
        xr:xr-xml-map "vlan_interface_cfg:VLANIdentifier";
        presence "Indicates a vlan-identifier node is configured.";
        description
          "The VLAN tag stack associated with this
          sub-interface.";
        leaf vlan-type {
          xr:xr-xml-map "vlan_interface_cfg:VlanType";
          type dt1:Vlan;
          mandatory true;
          description
            "Whether this sub-interface is dot1ad or dot1Q";
        }
        leaf first-tag {
          xr:xr-xml-map "vlan_interface_cfg:FirstTag";
          type dt1:Vlan-tag;
          mandatory true;
          description "First (outermost) VLAN tag value";
        }
        leaf second-tag {
          xr:xr-xml-map "vlan_interface_cfg:SecondTag";
          type dt1:Vlan-tag-or-null;
          description
            "Second VLAN tag value. The any value may only
            be used for Layer 2 subinterfaces";
        }
      }
    }
    description
      "This augment extends the configuration data of
      'Cisco-IOS-XR-ifmgr-cfg'";
  }

  augment "/a1:interface-configurations/a1:interface-configuration" {

    container ethernet-service {
      xr:xr-xml-map "vlan_interface_cfg:EthernetService";
      description "Ethernet service configuration";

      container local-traffic-default-encapsulation {
        xr:xr-xml-map "vlan_interface_cfg:LocalTrafficDefaultEncaps"+
          "ulation";
        presence "Indicates a local-traffic-default-encapsulation"+
          " node is configured.";
        description
          "The default encapsulation to be used for
          locally-sourced packets";
        leaf outer-tag-type {
          xr:xr-xml-map "vlan_interface_cfg:OuterTagType";
          type dt1:Vlan;
          mandatory true;
          description "Type of outer tag";
        }
        leaf outer-vlan-id {
          xr:xr-xml-map "vlan_interface_cfg:OuterVLANId";
          type dt1:Vlan-tag;
          mandatory true;
          description "VLAN id for outer tag";
        }
        leaf inner-vlan-id {
          xr:xr-xml-map "vlan_interface_cfg:InnerVLANId";
          type dt1:Vlan-tag;
          description "Optional VLAN Id for inner Dot1Q tag";
        }
      }

      container encapsulation {
        xr:xr-xml-map "vlan_interface_cfg:Encapsulation";
        presence "Indicates a encapsulation node is configured.";
        description "The encapsulation of this Ethernet service";
        leaf outer-tag-type {
          xr:xr-xml-map "vlan_interface_cfg:OuterTagType";
          type dt1:Match;
          mandatory true;
          description
            "Whether to match all unmatched packets,
            untagged packets or tagged packets, and if
            matching tagged packets, the outer tag type to
            match";
        }
        leaf outer-range1-low {
          xr:xr-xml-map "vlan_interface_cfg:OuterRange1Low";
          type dt1:Vlan-tag-or-any;
          description
            "Low value of first range for outer tag match";
        }
        leaf outer-range1-high {
          xr:xr-xml-map "vlan_interface_cfg:OuterRange1High";
          type dt1:Vlan-tag-or-native;
          description
            "High value of first range for outer tag match";
        }
        leaf inner-tag-type {
          xr:xr-xml-map "vlan_interface_cfg:InnerTagType";
          type dt1:Match;
          description "Type of tag for inner match (if present)";
        }
        leaf inner-range1-low {
          xr:xr-xml-map "vlan_interface_cfg:InnerRange1Low";
          type dt1:Vlan-tag-or-any;
          description
            "Low value of first range for inner tag match";
        }
        leaf inner-range1-high {
          xr:xr-xml-map "vlan_interface_cfg:InnerRange1High";
          type dt1:Vlan-tag;
          description
            "High value of first range for inner tag match";
        }
        leaf additional-range1-low {
          xr:xr-xml-map "vlan_interface_cfg:AdditionalRange1Low";
          type dt1:Vlan-tag-or-cvp;
          description
            "Low value of first additional range for tag
            match";
        }
        leaf additional-range1-high {
          xr:xr-xml-map "vlan_interface_cfg:AdditionalRange1High";
          type dt1:Vlan-tag;
          description
            "High value of first additional range for tag
            match";
        }
        leaf additional-range2-low {
          xr:xr-xml-map "vlan_interface_cfg:AdditionalRange2Low";
          type dt1:Vlan-tag-or-cvp;
          description
            "Low value of second additional range for tag
            match";
        }
        leaf additional-range2-high {
          xr:xr-xml-map "vlan_interface_cfg:AdditionalRange2High";
          type dt1:Vlan-tag;
          description
            "High value of second additional range for tag
            match";
        }
        leaf additional-range3-low {
          xr:xr-xml-map "vlan_interface_cfg:AdditionalRange3Low";
          type dt1:Vlan-tag-or-cvp;
          description
            "Low value of third additional range for tag
            match";
        }
        leaf additional-range3-high {
          xr:xr-xml-map "vlan_interface_cfg:AdditionalRange3High";
          type dt1:Vlan-tag;
          description
            "High value of third additional range for tag
            match";
        }
        leaf additional-range4-low {
          xr:xr-xml-map "vlan_interface_cfg:AdditionalRange4Low";
          type dt1:Vlan-tag-or-cvp;
          description
            "Low value of forth additional range for tag
            match";
        }
        leaf additional-range4-high {
          xr:xr-xml-map "vlan_interface_cfg:AdditionalRange4High";
          type dt1:Vlan-tag;
          description
            "High value of forth additional range for tag
            match";
        }
        leaf additional-range5-low {
          xr:xr-xml-map "vlan_interface_cfg:AdditionalRange5Low";
          type dt1:Vlan-tag-or-cvp;
          description
            "Low value of fifth additional range for tag
            match";
        }
        leaf additional-range5-high {
          xr:xr-xml-map "vlan_interface_cfg:AdditionalRange5High";
          type dt1:Vlan-tag;
          description
            "High value of fifth additional range for tag
            match";
        }
        leaf additional-range6-low {
          xr:xr-xml-map "vlan_interface_cfg:AdditionalRange6Low";
          type dt1:Vlan-tag-or-cvp;
          description
            "Low value of sixth additional range for tag
            match";
        }
        leaf additional-range6-high {
          xr:xr-xml-map "vlan_interface_cfg:AdditionalRange6High";
          type dt1:Vlan-tag;
          description
            "High value of sixth additional range for tag
            match";
        }
        leaf additional-range7-low {
          xr:xr-xml-map "vlan_interface_cfg:AdditionalRange7Low";
          type dt1:Vlan-tag-or-cvp;
          description
            "Low value of seventh additional range for tag
            match";
        }
        leaf additional-range7-high {
          xr:xr-xml-map "vlan_interface_cfg:AdditionalRange7High";
          type dt1:Vlan-tag;
          description
            "High value of seventh additional range for tag
            match";
        }
        leaf additional-range8-low {
          xr:xr-xml-map "vlan_interface_cfg:AdditionalRange8Low";
          type dt1:Vlan-tag-or-cvp;
          description
            "Low value of eighth additional range for tag
            match";
        }
        leaf additional-range8-high {
          xr:xr-xml-map "vlan_interface_cfg:AdditionalRange8High";
          type dt1:Vlan-tag;
          description
            "High value of eighth additional range for tag
            match";
        }
        leaf outer-class-of-service {
          xr:xr-xml-map "vlan_interface_cfg:OuterClassOfService";
          type dt1:Class-of-service;
          description
            "Value to match against Class Of Service bits
            for outer tag";
        }
        leaf inner-class-of-service {
          xr:xr-xml-map "vlan_interface_cfg:InnerClassOfService";
          type dt1:Class-of-service;
          description
            "Value to match against Class Of Service bits
            for inner tag";
        }
        leaf payload-ethertype-match {
          xr:xr-xml-map "vlan_interface_cfg:PayloadEthertypeMatch";
          type dt1:Ethertype-match;
          description "Which payload ethertype values to match";
        }
        leaf ingress-source-mac {
          xr:xr-xml-map "vlan_interface_cfg:IngressSourceMAC";
          type yang:mac-address;
          description "Source MAC address to match on ingress";
        }
        leaf ingress-destination-mac {
          xr:xr-xml-map "vlan_interface_cfg:IngressDestinationMAC";
          type yang:mac-address;
          description "Destination MAC address to match on egress";
        }
        leaf exact {
          xr:xr-xml-map "vlan_interface_cfg:Exact";
          type empty;
          description
            "Only match packets with no more tags than
            explicitly matched";
        }
      }

      container rewrite {
        xr:xr-xml-map "vlan_interface_cfg:Rewrite";
        presence "Indicates a rewrite node is configured.";
        description
          "The rewrite operation for the Ethernet service";
        leaf rewrite-type {
          xr:xr-xml-map "vlan_interface_cfg:RewriteType";
          type dt1:Rewrite;
          mandatory true;
          description "The type of rewrite to perform";
        }
        leaf outer-tag-type {
          xr:xr-xml-map "vlan_interface_cfg:OuterTagType";
          type dt1:Match;
          description "Type of outermost tag to be pushed";
        }
        leaf outer-tag-value {
          xr:xr-xml-map "vlan_interface_cfg:OuterTagValue";
          type dt1:Vlan-tag;
          description "VLAN Id of outermost tag to be pushed";
        }
        leaf inner-tag-type {
          xr:xr-xml-map "vlan_interface_cfg:InnerTagType";
          type dt1:Match;
          description "Type of innermost tag to be pushed";
        }
        leaf inner-tag-value {
          xr:xr-xml-map "vlan_interface_cfg:InnerTagValue";
          type dt1:Vlan-tag;
          description "VLAN Id of innermost tag to be pushed";
        }
      }
    }
    description
      "This augment extends the configuration data of
      'Cisco-IOS-XR-ifmgr-cfg'";
  }

  augment "/a1:interface-configurations/a1:interface-configuration" {

    container ethernet-bng {
      xr:xr-xml-map "eth_infra_bng_intf_cfg:EthernetBNG";
      description "Ethernet Infra BNG specific configuration";

      container ambiguous-encapsulation {
        xr:xr-xml-map "eth_infra_bng_intf_cfg:AmbiguousEncapsulatio"+
          "n";
        presence "Indicates a ambiguous-encapsulation node is"+
          " configured.";
        description "L3 Ambiguous encapsulation";
        leaf outer-tag-type {
          xr:xr-xml-map "eth_infra_bng_intf_cfg:OuterTagType";
          type dt1:Match;
          mandatory true;
          description
            "Whether to match all unmatched packets,
            untagged packets or tagged packets, and if
            matching tagged packets, the outer tag type to
            match";
        }
        leaf outer-range1-low {
          xr:xr-xml-map "eth_infra_bng_intf_cfg:OuterRange1Low";
          type dt1:Vlan-tag-or-any;
          description
            "Low value of first range for outer tag match";
        }
        leaf outer-range1-high {
          xr:xr-xml-map "eth_infra_bng_intf_cfg:OuterRange1High";
          type dt1:Vlan-tag-or-native;
          description
            "High value of first range for outer tag match";
        }
        leaf inner-tag-type {
          xr:xr-xml-map "eth_infra_bng_intf_cfg:InnerTagType";
          type dt1:Match;
          description "Type of tag for inner match (if present)";
        }
        leaf inner-range1-low {
          xr:xr-xml-map "eth_infra_bng_intf_cfg:InnerRange1Low";
          type dt1:Vlan-tag-or-any;
          description
            "Low value of first range for inner tag match";
        }
        leaf inner-range1-high {
          xr:xr-xml-map "eth_infra_bng_intf_cfg:InnerRange1High";
          type dt1:Vlan-tag;
          description
            "High value of first range for inner tag match";
        }
        leaf additional-range1-low {
          xr:xr-xml-map "eth_infra_bng_intf_cfg:AdditionalRange1Low";
          type dt1:Vlan-tag-or-cvp;
          description
            "Low value of first additional range for tag
            match";
        }
        leaf additional-range1-high {
          xr:xr-xml-map "eth_infra_bng_intf_cfg:AdditionalRange1Hig"+
            "h";
          type dt1:Vlan-tag;
          description
            "High value of first additional range for tag
            match";
        }
        leaf additional-range2-low {
          xr:xr-xml-map "eth_infra_bng_intf_cfg:AdditionalRange2Low";
          type dt1:Vlan-tag-or-cvp;
          description
            "Low value of second additional range for tag
            match";
        }
        leaf additional-range2-high {
          xr:xr-xml-map "eth_infra_bng_intf_cfg:AdditionalRange2Hig"+
            "h";
          type dt1:Vlan-tag;
          description
            "High value of second additional range for tag
            match";
        }
        leaf additional-range3-low {
          xr:xr-xml-map "eth_infra_bng_intf_cfg:AdditionalRange3Low";
          type dt1:Vlan-tag-or-cvp;
          description
            "Low value of third additional range for tag
            match";
        }
        leaf additional-range3-high {
          xr:xr-xml-map "eth_infra_bng_intf_cfg:AdditionalRange3Hig"+
            "h";
          type dt1:Vlan-tag;
          description
            "High value of third additional range for tag
            match";
        }
        leaf additional-range4-low {
          xr:xr-xml-map "eth_infra_bng_intf_cfg:AdditionalRange4Low";
          type dt1:Vlan-tag-or-cvp;
          description
            "Low value of forth additional range for tag
            match";
        }
        leaf additional-range4-high {
          xr:xr-xml-map "eth_infra_bng_intf_cfg:AdditionalRange4Hig"+
            "h";
          type dt1:Vlan-tag;
          description
            "High value of forth additional range for tag
            match";
        }
        leaf additional-range5-low {
          xr:xr-xml-map "eth_infra_bng_intf_cfg:AdditionalRange5Low";
          type dt1:Vlan-tag-or-cvp;
          description
            "Low value of fifth additional range for tag
            match";
        }
        leaf additional-range5-high {
          xr:xr-xml-map "eth_infra_bng_intf_cfg:AdditionalRange5Hig"+
            "h";
          type dt1:Vlan-tag;
          description
            "High value of fifth additional range for tag
            match";
        }
        leaf additional-range6-low {
          xr:xr-xml-map "eth_infra_bng_intf_cfg:AdditionalRange6Low";
          type dt1:Vlan-tag-or-cvp;
          description
            "Low value of sixth additional range for tag
            match";
        }
        leaf additional-range6-high {
          xr:xr-xml-map "eth_infra_bng_intf_cfg:AdditionalRange6Hig"+
            "h";
          type dt1:Vlan-tag;
          description
            "High value of sixth additional range for tag
            match";
        }
        leaf additional-range7-low {
          xr:xr-xml-map "eth_infra_bng_intf_cfg:AdditionalRange7Low";
          type dt1:Vlan-tag-or-cvp;
          description
            "Low value of seventh additional range for tag
            match";
        }
        leaf additional-range7-high {
          xr:xr-xml-map "eth_infra_bng_intf_cfg:AdditionalRange7Hig"+
            "h";
          type dt1:Vlan-tag;
          description
            "High value of seventh additional range for tag
            match";
        }
        leaf additional-range8-low {
          xr:xr-xml-map "eth_infra_bng_intf_cfg:AdditionalRange8Low";
          type dt1:Vlan-tag-or-cvp;
          description
            "Low value of eighth additional range for tag
            match";
        }
        leaf additional-range8-high {
          xr:xr-xml-map "eth_infra_bng_intf_cfg:AdditionalRange8Hig"+
            "h";
          type dt1:Vlan-tag;
          description
            "High value of eighth additional range for tag
            match";
        }
        leaf outer-class-of-service {
          xr:xr-xml-map "eth_infra_bng_intf_cfg:OuterClassOfService";
          type dt1:Class-of-service;
          description
            "Value to match against Class Of Service bits
            for outer tag";
        }
        leaf inner-class-of-service {
          xr:xr-xml-map "eth_infra_bng_intf_cfg:InnerClassOfService";
          type dt1:Class-of-service;
          description
            "Value to match against Class Of Service bits
            for inner tag";
        }
        leaf payload-ethertype-match {
          xr:xr-xml-map "eth_infra_bng_intf_cfg:PayloadEthertypeMat"+
            "ch";
          type dt1:Ethertype-match;
          description "Which payload ethertype values to match";
        }
        leaf ingress-source-mac {
          xr:xr-xml-map "eth_infra_bng_intf_cfg:IngressSourceMAC";
          type yang:mac-address;
          description "Source MAC address to match on ingress";
        }
        leaf ingress-destination-mac {
          xr:xr-xml-map "eth_infra_bng_intf_cfg:IngressDestinationM"+
            "AC";
          type yang:mac-address;
          description "Destination MAC address to match on egress";
        }
        leaf exact {
          xr:xr-xml-map "eth_infra_bng_intf_cfg:Exact";
          type empty;
          description
            "Only match packets with no more tags than
            explicitly matched";
        }
      }
    }
    description
      "This augment extends the configuration data of
      'Cisco-IOS-XR-ifmgr-cfg'";
  }

  augment "/a1:interface-configurations/a1:interface-configuration" {

    container mac-accounting {
      xr:xr-xml-map "ether_mac_acc_cfg:MACAccounting";
      description "MAC Accounting Configuration";
      leaf ingress {
        xr:xr-xml-map "ether_mac_acc_cfg:Ingress";
        type empty;
        description "Per MAC address accounting statistics";
      }
      leaf egress {
        xr:xr-xml-map "ether_mac_acc_cfg:Egress";
        type empty;
        description "Per MAC address accounting statistics";
      }
    }
    description
      "This augment extends the configuration data of
      'Cisco-IOS-XR-ifmgr-cfg'";
  }

  augment "/a1:interface-configurations/a1:interface-configuration" {

    container ethernet-features {
      xr:xr-xml-map "ether_intf_feature_cfg:EthernetFeatures";
      description "Ethernet Features Configuration";
      leaf filtering {
        xr:xr-xml-map "l2protocols_ether_interface_cfg:Filtering";
        type Filtering;
        description "Ingress Ethernet frame filtering";
      }
    }
    description
      "This augment extends the configuration data of
      'Cisco-IOS-XR-ifmgr-cfg'";
  }

  augment "/a1:interface-configurations/a1:interface-configuration" {

    container carrier-delay {
      xr:xr-xml-map "vlan_interface_cfg:CarrierDelay";
      description
        "Set the carrier transition delay on an interface
        in msecs";
      leaf carrier-delay-up {
        xr:xr-xml-map "vlan_interface_cfg:CarrierDelayUp";
        type uint32 {
          range "1..65535";
        }
        description "Carrier Delay (up) in msecs";
      }
      leaf carrier-delay-down {
        xr:xr-xml-map "vlan_interface_cfg:CarrierDelayDown";
        type uint32;
        description "Carrier Delay down in msecs, must be set to 0";
      }
    }
    description
      "This augment extends the configuration data of
      'Cisco-IOS-XR-ifmgr-cfg'";
  }

  augment "/a1:interface-configurations/a1:interface-configuration" {

    container vlan-trunk-configuration {
      xr:xr-xml-map "vlan_interface_cfg:VLANTrunkConfiguration";
      description "IEEE 802.1Q VLAN trunk interface configuration";

      container native-vlan-identifier {
        xr:xr-xml-map "vlan_interface_cfg:NativeVLANIdentifier";
        presence "Indicates a native-vlan-identifier node is"+
          " configured.";
        description
          "The Native VLAN identifier associated with this
          trunk interface";
        leaf vlan-type {
          xr:xr-xml-map "vlan_interface_cfg:VlanType";
          type dt1:Vlan;
          mandatory true;
          description "Whether this interface is dot1ad or dot1Q";
        }
        leaf vlan-identifier {
          xr:xr-xml-map "vlan_interface_cfg:VLANIdentifier";
          type dt1:Vlan-tag;
          mandatory true;
          description "VLAN identifier";
        }
      }
      leaf tunneling-ethertype {
        xr:xr-xml-map "vlan_interface_cfg:TunnelingEthertype";
        type enumeration {
          enum 0x9100 {
            value 37120;
            description "0x9100";
          }
          enum 0x9200 {
            value 37376;
            description "0x9200";
          }
        }
        description
          "The outer ethertype used in Q-in-Q frames. The
          default value is 0x8100";
      }
    }
    description
      "This augment extends the configuration data of
      'Cisco-IOS-XR-ifmgr-cfg'";
  }

  augment "/a1:interface-configurations/a1:interface-configuration"+
    "/a2:l2-transport" {

    container l2-protocols {
      xr:xr-xml-map "ether_l2pt_cfg:L2ProtocolTable";
      description "Interface specific Layer 2 protocol handling";

      list l2-protocol {
        xr:xr-xml-map "ether_l2pt_cfg:L2Protocol";
        key "l2-protocol-name";
        description "Handling of a specific Layer 2 protocol";
        leaf l2-protocol-name {
          xr:xr-xml-map "ether_l2pt_cfg:L2ProtocolName";
          type L2-protocol-name;
          description "Protocol name";
        }
        leaf mode {
          xr:xr-xml-map "ether_l2pt_cfg:Mode";
          type L2-protocol-mode;
          mandatory true;
          description "How to handle the protocol's packets";
        }
        leaf mpls-exp-bits-value {
          xr:xr-xml-map "ether_l2pt_cfg:MPLSExpBitsValue";
          type L2-protocol-mpls-exp-bits-value;
          description
            "The value to set the MPLS Exp bits to within
            the PW.This value may be specified if the mode
            is forward or tunnel and must not be specified
            if the mode is drop";
        }
      }
    }
    description
      "This augment extends the configuration data of
      'Cisco-IOS-XR-l2vpn-cfg'";
  }

  augment "/a1:interface-configurations/a1:interface-configuration"+
    "/a2:l2-transport" {
    leaf propagate-remote-status {
      xr:xr-xml-map "l2protocols_ether_interface_cfg:PropagateRemot"+
        "eStatus";
      type empty;
      description
        "Enable propagation of the remote
        attachment-circuit link state to the
        localattachment-circuit link state";
    }
    description
      "This augment extends the configuration data of
      'Cisco-IOS-XR-l2vpn-cfg'";
  }

  augment "/a1:interface-configurations/a1:interface-configuration"+
    "/a2:l2-transport" {

    container l2-ethernet-features {
      xr:xr-xml-map "ether_intf_feature_cfg:L2EthernetFeatures";
      description "L2 Ethernet Features Configuration";
      leaf egress-filtering {
        xr:xr-xml-map "l2protocols_ether_interface_cfg:EgressFilter"+
          "ing";
        type Egress-filtering;
        default "egress-filtering-type-default";
        description "Egress Ethernet filtering";
      }
      leaf source-bypass-egress-filtering {
        xr:xr-xml-map "l2protocols_ether_interface_cfg:SourceBypass"+
          "EgressFiltering";
        type empty;
        description
          "Mark all ingress packets to bypass any egress
          VLAN filter";
      }
    }
    description
      "This augment extends the configuration data of
      'Cisco-IOS-XR-l2vpn-cfg'";
  }
}
