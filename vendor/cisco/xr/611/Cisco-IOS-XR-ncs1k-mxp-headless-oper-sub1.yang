submodule Cisco-IOS-XR-ncs1k-mxp-headless-oper-sub1 {

  belongs-to Cisco-IOS-XR-ncs1k-mxp-headless-oper {
    prefix Cisco-IOS-XR-ncs1k-mxp-headless-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR ncs1k-mxp-headless package operational data.

     Copyright (c) 2013-2016 by Cisco Systems, Inc.
     All rights reserved.";

  revision "2016-03-23" {
    description
      "egress stats added .";
  }

  revision "2015-11-09" {
    description
      "IOS XR 6.0 revision.";
  }


  grouping MXP-ETHER-PRIM-INFO {
    description "Ether statistics";
    leaf rx-pkts-over-sized {
      xr:xr-xml-map "mxp_show_headless:RxPktsOverSized";
      type uint64;
      description "RxPktsOverSized";
    }
    leaf rx-pkts-bad-fcs {
      xr:xr-xml-map "mxp_show_headless:RxPktsBadFcs";
      type uint64;
      description "RxPktsBadFcs";
    }
    leaf rx-error-jabbers {
      xr:xr-xml-map "mxp_show_headless:RxErrorJabbers";
      type uint64;
      description "RxErrorJabbers";
    }
    leaf rx-pkts-multicast {
      xr:xr-xml-map "mxp_show_headless:RxPktsMulticast";
      type uint64;
      description "RxPktsMulticast";
    }
    leaf rx-pkts-broadcast {
      xr:xr-xml-map "mxp_show_headless:RxPktsBroadcast";
      type uint64;
      description "RxPktsBroadcast";
    }
    leaf rx-pkts-under-sized {
      xr:xr-xml-map "mxp_show_headless:RxPktsUnderSized";
      type uint64;
      description "RxPktsUnderSized";
    }
    leaf rx-packets {
      xr:xr-xml-map "mxp_show_headless:RxPackets";
      type uint64;
      description "RxPackets";
    }
    leaf rx-total-bytes {
      xr:xr-xml-map "mxp_show_headless:RxTotalBytes";
      type uint64;
      description "RxTotalBytes";
    }
    leaf rx-bytes-good {
      xr:xr-xml-map "mxp_show_headless:RxBytesGood";
      type uint64;
      description "RxBytesGood";
    }
    leaf rx-pkts-good {
      xr:xr-xml-map "mxp_show_headless:RxPktsGood";
      type uint64;
      description "RxPktsGood";
    }
    leaf tx-bytes-good {
      xr:xr-xml-map "mxp_show_headless:TxBytesGood";
      type uint64;
      description "TxBytesGood";
    }
    leaf tx-pkts-good {
      xr:xr-xml-map "mxp_show_headless:TxPktsGood";
      type uint64;
      description "TxPktsGood";
    }
    leaf rx-recv-fragments {
      xr:xr-xml-map "mxp_show_headless:RxRecvFragments";
      type uint64;
      description "RxRecvFragments";
    }
    leaf rx-pkts64-bytes {
      xr:xr-xml-map "mxp_show_headless:RxPkts64Bytes";
      type uint64;
      description "RxPkts64Bytes";
    }
    leaf rx-pkts65-to127-bytes {
      xr:xr-xml-map "mxp_show_headless:RxPkts65To127Bytes";
      type uint64;
      description "RxPkts65To127Bytes";
    }
    leaf rx-pkts128to255-bytes {
      xr:xr-xml-map "mxp_show_headless:RxPkts128to255Bytes";
      type uint64;
      description "RxPkts128to255Bytes";
    }
    leaf rx-pkts256-to511-bytes {
      xr:xr-xml-map "mxp_show_headless:RxPkts256To511Bytes";
      type uint64;
      description "RxPkts256To511Bytes";
    }
    leaf rx-pkts512-to1023-bytes {
      xr:xr-xml-map "mxp_show_headless:RxPkts512To1023Bytes";
      type uint64;
      description "RxPkts512To1023Bytes";
    }
    leaf rx-pkts1024-to1518-bytes {
      xr:xr-xml-map "mxp_show_headless:RxPkts1024To1518Bytes";
      type uint64;
      description "RxPkts1024To1518Bytes";
    }
    leaf rx-pkts-unicast {
      xr:xr-xml-map "mxp_show_headless:RxPktsUnicast";
      type uint64;
      description "RxPktsUnicast";
    }
    leaf tx-packets {
      xr:xr-xml-map "mxp_show_headless:TxPackets";
      type uint64;
      description "TxPackets";
    }
    leaf tx-total-bytes {
      xr:xr-xml-map "mxp_show_headless:TxTotalBytes";
      type uint64;
      description "TxTotalBytes";
    }
    leaf tx-pkts-under-sized {
      xr:xr-xml-map "mxp_show_headless:TxPktsUnderSized";
      type uint64;
      description "TxPktsUnderSized";
    }
    leaf tx-pkts-over-sized {
      xr:xr-xml-map "mxp_show_headless:TxPktsOverSized";
      type uint64;
      description "TxPktsOverSized";
    }
    leaf tx-fragments {
      xr:xr-xml-map "mxp_show_headless:TxFragments";
      type uint64;
      description "TxFragments";
    }
    leaf tx-jabber {
      xr:xr-xml-map "mxp_show_headless:TxJabber";
      type uint64;
      description "TxJabber";
    }
    leaf tx-bad-fcs {
      xr:xr-xml-map "mxp_show_headless:TxBadFCS";
      type uint64;
      description "TxBadFCS";
    }
    leaf rx-pkt-drop {
      xr:xr-xml-map "mxp_show_headless:RxPktDrop";
      type uint64;
      description "RxPktDrop";
    }
    leaf rx-pause {
      xr:xr-xml-map "mxp_show_headless:RxPause";
      type uint64;
      description "RxPause";
    }
    leaf tx-pause {
      xr:xr-xml-map "mxp_show_headless:TxPause";
      type uint64;
      description "TxPause";
    }
  }

  grouping MXP-HEADLESS-ETHER-PRIM-INFO {
    description "Ether Headless Statistics";

    container ether-statistics {
      description "Ether Statistics";
      uses MXP-ETHER-PRIM-INFO;
    }
    leaf started-stateful {
      xr:xr-xml-map "mxp_show_headless:StartedStateful";
      type boolean;
      description "Started Stateful";
    }
    leaf headless-start-time {
      xr:xr-xml-map "mxp_show_headless:HeadlessStartTime";
      type string {
        length "0..64";
      }
      description "Headless Start Time";
    }
    leaf headless-end-time {
      xr:xr-xml-map "mxp_show_headless:HeadlessEndTime";
      type string {
        length "0..64";
      }
      description "Headless End Time";
    }
  }

  grouping MXP-OTN-CNT-INFO {
    description "OTN statistics";
    leaf sm-bip {
      xr:xr-xml-map "mxp_show_headless:SmBip";
      type uint64;
      description "SmBip";
    }
    leaf sm-bei {
      xr:xr-xml-map "mxp_show_headless:SmBei";
      type uint64;
      description "SmBei";
    }
    leaf fec-ec {
      xr:xr-xml-map "mxp_show_headless:FecEc";
      type uint64;
      description "FecEc";
    }
    leaf fec-uc {
      xr:xr-xml-map "mxp_show_headless:FecUc";
      type uint64;
      description "FecUc";
    }
  }

  grouping MXP-HEADLESS-OTN-CNT-INFO {
    description "OTN Headless Statistics";

    container otn-statistics {
      description "OTN statistics";
      uses MXP-OTN-CNT-INFO;
    }
    leaf started-stateful {
      xr:xr-xml-map "mxp_show_headless:StartedStateful";
      type boolean;
      description "Started Stateful";
    }
    leaf headless-start-time {
      xr:xr-xml-map "mxp_show_headless:HeadlessStartTime";
      type string {
        length "0..64";
      }
      description "Headless Start Time";
    }
    leaf headless-end-time {
      xr:xr-xml-map "mxp_show_headless:HeadlessEndTime";
      type string {
        length "0..64";
      }
      description "Headless End Time";
    }
  }
}
