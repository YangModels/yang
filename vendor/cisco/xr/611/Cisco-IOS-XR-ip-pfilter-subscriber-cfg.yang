module Cisco-IOS-XR-ip-pfilter-subscriber-cfg {

  /*** NAMESPACE / PREFIX DEFINITION ***/

  namespace "http://cisco.com/ns/yang"+
    "/Cisco-IOS-XR-ip-pfilter-subscriber-cfg";


  prefix "ip-pfilter-subscriber-cfg";

  /*** LINKAGE (IMPORTS / INCLUDES) ***/

  import Cisco-IOS-XR-types { prefix "xr"; }

  import Cisco-IOS-XR-subscriber-infra-tmplmgr-cfg { prefix "a1"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ip-pfilter-subscriber package configuration.

     This YANG module augments the
       Cisco-IOS-XR-subscriber-infra-tmplmgr-cfg
     module with configuration data.

     Copyright (c) 2013-2016 by Cisco Systems, Inc.
     All rights reserved.";

  revision "2015-11-09" {
    description
      "IOS XR 6.0 revision.";
  }


  grouping IPV6-PACKET-FILTER {
    description
      "Common node of ppp, subscriber-service,
      ip-subscriber";

    container ipv6-packet-filter {
      xr:xr-xml-map "ipv6_acl_dyn_tmpl_cfg:IPV6PacketFilter";
      description
        "IPv6 Packet Filtering configuration for the
        interface";

      container inbound {
        xr:xr-xml-map "ipv6_acl_dyn_tmpl_cfg:Inbound";
        description
          "IPv6 Packet filter to be applied to inbound
          packets";
        leaf common-acl-name {
          xr:xr-xml-map "ipv6_acl_dyn_tmpl_cfg:CommonACLName";
          type string;
          description "Not supported (Leave unspecified).";
        }
        leaf name {
          xr:xr-xml-map "ipv6_acl_dyn_tmpl_cfg:Name";
          type xr:Cisco-ios-xr-string {
            length "0..65";
          }
          description
            "IPv6 Packet Filter Name to be applied to
            Inbound  NOTE: This parameter is mandatory if
            'CommonACLName' is not specified.";
        }
        leaf interface-statistics {
          xr:xr-xml-map "ipv6_acl_dyn_tmpl_cfg:InterfaceStatistics";
          type empty;
          description "Not supported (Leave unspecified).";
        }
      }

      container outbound {
        xr:xr-xml-map "ipv6_acl_dyn_tmpl_cfg:Outbound";
        presence "Indicates a outbound node is configured.";
        description
          "IPv6 Packet filter to be applied to outbound
          packets";
        leaf common-acl-name {
          xr:xr-xml-map "ipv6_acl_dyn_tmpl_cfg:CommonACLName";
          type string;
          description "Not supported (Leave unspecified).";
        }
        leaf name {
          xr:xr-xml-map "ipv6_acl_dyn_tmpl_cfg:Name";
          type xr:Cisco-ios-xr-string {
            length "0..65";
          }
          mandatory true;
          description
            "IPv6 Packet Filter Name to be applied to
            Outbound packets.";
        }
        leaf interface-statistics {
          xr:xr-xml-map "ipv6_acl_dyn_tmpl_cfg:InterfaceStatistics";
          type empty;
          description "Not supported (Leave unspecified).";
        }
      }
    }
  }

  grouping IPV4-PACKET-FILTER {
    description
      "Common node of ppp, subscriber-service,
      ip-subscriber";

    container ipv4-packet-filter {
      xr:xr-xml-map "ipv4_acl_dyn_tmpl_cfg:IPV4PacketFilter";
      description
        "IPv4 Packet Filtering configuration for the
        template";

      container outbound {
        xr:xr-xml-map "ipv4_acl_dyn_tmpl_cfg:Outbound";
        presence "Indicates a outbound node is configured.";
        description
          "IPv4 Packet filter to be applied to outbound
          packets";
        leaf common-acl-name {
          xr:xr-xml-map "ipv4_acl_dyn_tmpl_cfg:CommonACLName";
          type string;
          description "Not supported (Leave unspecified).";
        }
        leaf name {
          xr:xr-xml-map "ipv4_acl_dyn_tmpl_cfg:Name";
          type xr:Cisco-ios-xr-string {
            length "0..65";
          }
          mandatory true;
          description
            "IPv4 Packet Filter Name to be applied to
            Outbound packets.";
        }
        leaf hardware-count {
          xr:xr-xml-map "ipv4_acl_dyn_tmpl_cfg:HardwareCount";
          type empty;
          description "Not supported (Leave unspecified).";
        }
        leaf interface-statistics {
          xr:xr-xml-map "ipv4_acl_dyn_tmpl_cfg:InterfaceStatistics";
          type empty;
          description "Not supported (Leave unspecified).";
        }
      }

      container inbound {
        xr:xr-xml-map "ipv4_acl_dyn_tmpl_cfg:Inbound";
        description
          "IPv4 Packet filter to be applied to inbound
          packets";
        leaf common-acl-name {
          xr:xr-xml-map "ipv4_acl_dyn_tmpl_cfg:CommonACLName";
          type string;
          description "Not supported (Leave unspecified).";
        }
        leaf name {
          xr:xr-xml-map "ipv4_acl_dyn_tmpl_cfg:Name";
          type xr:Cisco-ios-xr-string {
            length "0..65";
          }
          description
            "IPv4 Packet Filter Name to be applied to
            Inbound packets NOTE: This parameter is
            mandatory if 'CommonACLName' is not specified.";
        }
        leaf hardware-count {
          xr:xr-xml-map "ipv4_acl_dyn_tmpl_cfg:HardwareCount";
          type empty;
          description "Not supported (Leave unspecified).";
        }
        leaf interface-statistics {
          xr:xr-xml-map "ipv4_acl_dyn_tmpl_cfg:InterfaceStatistics";
          type empty;
          description "Not supported (Leave unspecified).";
        }
      }
    }
  }

  augment "/a1:dynamic-template/a1:ip-subscribers/a1:ip-subscriber" {
    description
      "This augment extends the configuration data of
      'Cisco-IOS-XR-subscriber-infra-tmplmgr-cfg'";
    uses IPV4-PACKET-FILTER;
  }

  augment "/a1:dynamic-template/a1:subscriber-services"+
    "/a1:subscriber-service" {
    description
      "This augment extends the configuration data of
      'Cisco-IOS-XR-subscriber-infra-tmplmgr-cfg'";
    uses IPV4-PACKET-FILTER;
  }

  augment "/a1:dynamic-template/a1:ppps/a1:ppp" {
    description
      "This augment extends the configuration data of
      'Cisco-IOS-XR-subscriber-infra-tmplmgr-cfg'";
    uses IPV4-PACKET-FILTER;
  }

  augment "/a1:dynamic-template/a1:ip-subscribers/a1:ip-subscriber" {
    description
      "This augment extends the configuration data of
      'Cisco-IOS-XR-subscriber-infra-tmplmgr-cfg'";
    uses IPV6-PACKET-FILTER;
  }

  augment "/a1:dynamic-template/a1:subscriber-services"+
    "/a1:subscriber-service" {
    description
      "This augment extends the configuration data of
      'Cisco-IOS-XR-subscriber-infra-tmplmgr-cfg'";
    uses IPV6-PACKET-FILTER;
  }

  augment "/a1:dynamic-template/a1:ppps/a1:ppp" {
    description
      "This augment extends the configuration data of
      'Cisco-IOS-XR-subscriber-infra-tmplmgr-cfg'";
    uses IPV6-PACKET-FILTER;
  }
}
