module Cisco-IOS-XR-wanphy-ui-oper {

  /*** NAMESPACE / PREFIX DEFINITION ***/

  namespace "http://cisco.com/ns/yang/Cisco-IOS-XR-wanphy-ui-oper";


  prefix "wanphy-ui-oper";

  /*** LINKAGE (IMPORTS / INCLUDES) ***/

  import Cisco-IOS-XR-types { prefix "xr"; }

  include Cisco-IOS-XR-wanphy-ui-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR wanphy-ui package operational data.

     This module contains definitions
     for the following management objects:
       wanphy: WANPHY operational data

     Copyright (c) 2013-2016 by Cisco Systems, Inc.
     All rights reserved.";

  revision "2015-11-09" {
    description
      "IOS XR 6.0 revision.";
  }


  container wanphy {
    xr:xr-xml-map "wanphy_ui_oper:WANPHY";
    config false;
    description "WANPHY operational data";

    container controllers {
      xr:xr-xml-map "wanphy_ui_oper:ControllerTable";
      description "All WANPHY controller operational data";

      list controller {
        xr:xr-xml-map "wanphy_ui_oper:Controller";
        key "controller-name";
        description "WANPHY controller operational data";

        container info {
          xr:xr-xml-map "wanphy_ui_oper:Info";
          description "WANPHY controller operational data";
          uses WANPHY-EDM-INFO;
        }
        leaf controller-name {
          xr:xr-xml-map "wanphy_ui_oper:ControllerName";
          type xr:Interface-name;
          description "Controller name";
        }
      }
    }
  }
}
