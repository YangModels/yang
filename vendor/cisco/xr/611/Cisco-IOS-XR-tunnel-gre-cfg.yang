module Cisco-IOS-XR-tunnel-gre-cfg {

  /*** NAMESPACE / PREFIX DEFINITION ***/

  namespace "http://cisco.com/ns/yang/Cisco-IOS-XR-tunnel-gre-cfg";


  prefix "tunnel-gre-cfg";

  /*** LINKAGE (IMPORTS / INCLUDES) ***/

  import ietf-inet-types { prefix "inet"; }

  import Cisco-IOS-XR-types { prefix "xr"; }

  import Cisco-IOS-XR-ifmgr-cfg { prefix "a1"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR tunnel-gre package configuration.

     This YANG module augments the
       Cisco-IOS-XR-ifmgr-cfg
     module with configuration data.

     Copyright (c) 2013-2016 by Cisco Systems, Inc.
     All rights reserved.";

  revision "2016-05-25" {
    description
      "Initial version";
  }

  revision "2015-11-09" {
    description
      "IOS XR 6.0 revision.";
  }


  augment "/a1:interface-configurations/a1:interface-configuration" {

    container tunnel-ip {
      xr:xr-xml-map "tunl_gre_ma_cfg:TunnelIP";
      description "IP over GRE encapsulation";

      container mode {
        xr:xr-xml-map "tunl_gre_ma_cfg:Mode";
        description "Tunnel encapsulation method";
        leaf value {
          xr:xr-xml-map "tunl_gre_ma_cfg:Value";
          type int32;
          description
            "GRE IPV4 - 1, GRE IPV6 - 2, MGRE IPV4 - 3,
            MGRE IPV6 -4. IPV4 - 5, IPV6 - 6";
        }
        leaf decap {
          xr:xr-xml-map "tunl_gre_ma_cfg:Decap";
          type empty;
          description "Always set to true";
        }
      }

      container source {
        xr:xr-xml-map "tunl_gre_ma_cfg:Source";
        description "Configure source of tunnel";
        leaf type {
          xr:xr-xml-map "tunl_gre_ma_cfg:Type";
          type int32;
          description
            "1 for Interface Name, 2 for IPv4 Address, 3
            for IPv6 Address";
        }
        leaf address {
          xr:xr-xml-map "tunl_gre_ma_cfg:Address";
          type inet:ipv4-address-no-zone;
          description "IPV4 address of the tunnel source";
        }
        leaf interface-name {
          xr:xr-xml-map "tunl_gre_ma_cfg:InterfaceName";
          type xr:Interface-name;
          description "Name of tunnel source interface";
        }
        leaf ipv6-address {
          xr:xr-xml-map "tunl_gre_ma_cfg:IPv6Address";
          type string;
          description "IPV6 address of the tunnel source";
        }
      }

      container key {
        xr:xr-xml-map "tunl_gre_ma_cfg:Key";
        description
          "Configure the key value for packets sent over
          this tunnel";
        leaf entropy {
          xr:xr-xml-map "tunl_gre_ma_cfg:Entropy";
          type empty;
          description "Always set to true";
        }
        leaf value {
          xr:xr-xml-map "tunl_gre_ma_cfg:Value";
          type uint32 {
            range "0..4294967295";
          }
          description "Enter the KEY value";
        }
      }

      container keepalive {
        xr:xr-xml-map "tunl_gre_ma_cfg:Keepalive";
        description "Enable keepalive packets on this tunnel";
        leaf keep-alive-period {
          xr:xr-xml-map "tunl_gre_ma_cfg:KeepAlivePeriod";
          type uint32 {
            range "1..32767";
          }
          description
            "Keepalive period in seconds (default 10
            seconds)";
        }
        leaf keep-alive-retries {
          xr:xr-xml-map "tunl_gre_ma_cfg:KeepAliveRetries";
          type uint32 {
            range "1..255";
          }
          description "Number of retries (default 3)";
        }
      }

      container destination {
        xr:xr-xml-map "tunl_gre_ma_cfg:Destination";
        description "Configure destination of tunnel";
        leaf type {
          xr:xr-xml-map "tunl_gre_ma_cfg:Type";
          type int32;
          description "1 for IPv4 Address, 2 for IPv6 Address";
        }
        leaf address {
          xr:xr-xml-map "tunl_gre_ma_cfg:Address";
          type inet:ipv4-address-no-zone;
          description "IPV4 address of the tunnel destination";
        }
        leaf ipv6-address {
          xr:xr-xml-map "tunl_gre_ma_cfg:IPv6Address";
          type string;
          description "IPV6 address of the tunnel destination";
        }
        leaf address-mask {
          xr:xr-xml-map "tunl_gre_ma_cfg:AddressMask";
          type inet:ipv4-address-no-zone;
          description
            "IPv4 prefix length of the tunnel destination";
        }
      }
      leaf allow-key {
        xr:xr-xml-map "tunl_gre_ma_cfg:AllowKey";
        type empty;
        description "Enable flag bit to allow packets with GRE key";
      }
      leaf ttl {
        xr:xr-xml-map "tunl_gre_ma_cfg:TTL";
        type uint32 {
          range "1..255";
        }
        description
          "Configure the time-to-live for packets sent
          over this tunnel";
      }
      leaf tunnel-vrf {
        xr:xr-xml-map "tunl_gre_ma_cfg:TunnelVRF";
        type xr:Cisco-ios-xr-string {
          length "0..32";
        }
        description "Tunnel vrf label name";
      }
      leaf tos {
        xr:xr-xml-map "tunl_gre_ma_cfg:TOS";
        type uint32 {
          range "0..255";
        }
        description
          "Configure Type of Service bits for this tunnel";
      }
      leaf disable {
        xr:xr-xml-map "tunl_gre_ma_cfg:Disable";
        type int32;
        description "Disable DF bit (i.e. allow fragmentation)";
      }
    }
    description
      "This augment extends the configuration data of
      'Cisco-IOS-XR-ifmgr-cfg'";
  }
}
