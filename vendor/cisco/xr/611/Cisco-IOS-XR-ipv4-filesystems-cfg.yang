module Cisco-IOS-XR-ipv4-filesystems-cfg {

  /*** NAMESPACE / PREFIX DEFINITION ***/

  namespace "http://cisco.com/ns/yang"+
    "/Cisco-IOS-XR-ipv4-filesystems-cfg";


  prefix "ipv4-filesystems-cfg";

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ipv4-filesystems package configuration.

     This module contains definitions
     for the following management objects:
       rcp: RCP configuration
       ftp: ftp
       tftp: tftp

     Copyright (c) 2013-2016 by Cisco Systems, Inc.
     All rights reserved.";

  revision "2015-11-09" {
    description
      "IOS XR 6.0 revision.";
  }


  grouping SOURCE-INTERFACE {
    description
      "Common node of ftp-client, tftp-client,
      rcp-client";
    leaf source-interface {
      xr:xr-xml-map "ipv4_filesystems_cfg:SourceInterface";
      xr:xr-cli-map "ftp source-interface <interface> ";
      xr:xr-cli-map "tftp source-interface <interface> ";
      type xr:Interface-name;
      description
        "Specify interface for source address in
        connections";
    }
  }

  container rcp {
    xr:xr-xml-map "ipv4_filesystems_cfg:RCP";
    description "RCP configuration";

    container rcp-client {
      xr:xr-xml-map "ipv4_filesystems_cfg:RCPClient";
      description "RCP client configuration";
      uses SOURCE-INTERFACE;
    }
  }

  container ftp {
    xr:xr-xml-map "ipv4_filesystems_cfg:FTP";
    description "ftp";

    container ftp-client {
      xr:xr-xml-map "ipv4_filesystems_cfg:FTPClient";
      description "FTP client configuration";
      leaf passive {
        xr:xr-xml-map "ipv4_filesystems_cfg:Passive";
        xr:xr-cli-map "ftp passive ";
        type empty;
        description "Enable connect using passive mode";
      }
      leaf password {
        xr:xr-xml-map "ipv4_filesystems_cfg:Password";
        type xr:Proprietary-password;
        description "Specify password for ftp connnection";
      }
      leaf anonymous-password {
        xr:xr-xml-map "ipv4_filesystems_cfg:AnonymousPassword";
        type string;
        description
          "Password for anonymous user (ftp server
          dependent)";
      }
      uses SOURCE-INTERFACE;
    }
  }

  container tftp {
    xr:xr-xml-map "ipv4_filesystems_cfg:TFTP";
    description "tftp";

    container tftp-client {
      xr:xr-xml-map "ipv4_filesystems_cfg:TFTPClient";
      description "TFTP client configuration";
      uses SOURCE-INTERFACE;
    }
  }
}
