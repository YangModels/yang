submodule Cisco-IOS-XR-dnx-port-mapper-oper-sub1 {

  belongs-to Cisco-IOS-XR-dnx-port-mapper-oper {
    prefix Cisco-IOS-XR-dnx-port-mapper-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR dnx-port-mapper package operational data.

     Copyright (c) 2013-2016 by Cisco Systems, Inc.
     All rights reserved.";

  revision "2015-11-09" {
    description
      "IOS XR 6.0 revision.";
  }


  grouping OOR-SUMMARY {
    description "Lists interfaces in each of the three states";
    leaf red {
      xr:xr-xml-map "dnx_port_mapper_oor_edm:RED";
      type uint32;
      description "interfaces in red state";
    }
    leaf green {
      xr:xr-xml-map "dnx_port_mapper_oor_edm:GREEN";
      type uint32;
      description "interfaces in green state";
    }
    leaf yel-low {
      xr:xr-xml-map "dnx_port_mapper_oor_edm:YELLOW";
      type uint32;
      description "interfaces in yellow state";
    }
  }

  grouping OOR-INTERFACE-SUMMARY {
    description "Overall Summary of states of all interfaces";
    leaf interface-name {
      xr:xr-xml-map "dnx_port_mapper_oor_edm:Interface_name";
      type string;
      description "Name of the interface";
    }
    leaf interface-status {
      xr:xr-xml-map "dnx_port_mapper_oor_edm:InterfaceStatus";
      type string;
      description "The current state of the interface";
    }
    leaf hardware-resource {
      xr:xr-xml-map "dnx_port_mapper_oor_edm:HardwareResource";
      type string;
      description "Type of harware resoruce";
    }
  }

  grouping OOR-INTERFACE-DETAIL {
    description "OOR specific details for the interface";
    leaf interface-name {
      xr:xr-xml-map "dnx_port_mapper_oor_edm:Interface_name";
      type string;
      description "Name of the interface";
    }
    leaf interface-status {
      xr:xr-xml-map "dnx_port_mapper_oor_edm:InterfaceStatus";
      type string;
      description "The current state of the interface";
    }
    leaf time-stamp {
      xr:xr-xml-map "dnx_port_mapper_oor_edm:TimeStamp";
      type string;
      description "Timestamp";
    }
    leaf npu-id {
      xr:xr-xml-map "dnx_port_mapper_oor_edm:NpuId";
      type string;
      description "Npuid of the interface";
    }
    leaf hardware-resource {
      xr:xr-xml-map "dnx_port_mapper_oor_edm:HardwareResource";
      type string;
      description "Type of harware resoruce";
    }
  }

  grouping OOR-BUNDLE-INTERFACE-DETAIL {
    description "OOR specific details for the bundle interface";
    leaf interface-state {
      xr:xr-xml-map "dnx_port_mapper_oor_edm:InterfaceState";
      type string;
      description "Current state of the interface";
    }
    leaf time-stamp {
      xr:xr-xml-map "dnx_port_mapper_oor_edm:TimeStamp";
      type string;
      description "Timestamp";
    }

    list member {
      max-elements "64";
      description "Member details";
      uses OOR-INTERFACE-DETAIL;
    }
  }
}
