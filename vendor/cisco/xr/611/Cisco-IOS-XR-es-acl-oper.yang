module Cisco-IOS-XR-es-acl-oper {

  /*** NAMESPACE / PREFIX DEFINITION ***/

  namespace "http://cisco.com/ns/yang/Cisco-IOS-XR-es-acl-oper";


  prefix "es-acl-oper";

  /*** LINKAGE (IMPORTS / INCLUDES) ***/

  import Cisco-IOS-XR-types { prefix "xr"; }

  import Cisco-IOS-XR-common-acl-datatypes { prefix "dt1"; }

  include Cisco-IOS-XR-es-acl-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR es-acl package operational data.

     This module contains definitions
     for the following management objects:
       es-acl: Root class of ES ACL Oper schema tree

     Copyright (c) 2013-2016 by Cisco Systems, Inc.
     All rights reserved.";

  revision "2015-11-09" {
    description
      "IOS XR 6.0 revision.";
  }

  typedef Es-acl-name {
    type xr:Cisco-ios-xr-string {
      length "0..65";
    }
    description "Es acl name";
  }

  container es-acl {
    xr:xr-xml-map "es_acl_oper:ES_ACL";
    config false;
    description "Root class of ES ACL Oper schema tree";

    container active {
      xr:xr-xml-map "es_acl_oper:Active";
      description
        "Out Of Resources, Limits to the resources
        allocatable";

      container oor {
        xr:xr-xml-map "es_acl_oper:OOR";
        description
          "Out Of Resources, Limits to the resources
          allocatable";

        container acl-summary {
          xr:xr-xml-map "es_acl_oper:ACLSummary";
          description "Resource Limits pertaining to ACLs only";

          container details {
            xr:xr-xml-map "es_acl_oper:Details";
            description
              "Details containing the resource limits of the
              ACLs";
            uses ES-ACL-EDM-OOR-DETAIL;
          }
        }
      }

      container list {
        xr:xr-xml-map "es_acl_oper:List";
        description "List containing ACLs";

        container acls {
          xr:xr-xml-map "es_acl_oper:ACLTable";
          description "ACL class displaying Usage and Entries";

          list acl {
            xr:xr-xml-map "es_acl_oper:ACL";
            key "name";
            description "Name of the Access List";

            container acl-sequence-numbers {
              xr:xr-xml-map "es_acl_oper:ACLSequenceNumberTable";
              description
                "Table of all the SequenceNumbers per ACL";

              list acl-sequence-number {
                xr:xr-xml-map "es_acl_oper:ACLSequenceNumber";
                key "sequence-number";
                description "Sequence Number of an ACL entry";
                leaf sequence-number {
                  xr:xr-xml-map "es_acl_oper:SequenceNumber";
                  type dt1:Acl-sequence-number-range;
                  description "ACLEntry Sequence Number";
                }
                uses ES-ACL-EDM-ACE;
              }
            }
            leaf name {
              xr:xr-xml-map "es_acl_oper:Name";
              type Es-acl-name;
              description "Name of the Access List";
            }
          }
        }
      }

      container oor-acls {
        xr:xr-xml-map "es_acl_oper:OOR_ACLTable";
        description "Resource occupation details for ACLs";

        list oor-acl {
          xr:xr-xml-map "es_acl_oper:OOR_ACL";
          key "name";
          description
            "Resource occupation details for a particular
            ACL";
          leaf name {
            xr:xr-xml-map "es_acl_oper:Name";
            type Es-acl-name;
            description "Name of the Access List";
          }
          uses ES-ACL-EDM-OOR-DETAIL;
        }
      }

      container usages {
        xr:xr-xml-map "es_acl_oper:UsageTable";
        description
          "Table of Usage statistics of ACLs at different
          nodes";

        list usage {
          xr:xr-xml-map "es_acl_oper:Usage";
          description "Usage statistics of an ACL at a node";
          leaf location {
            xr:xr-xml-map "es_acl_oper:Location";
            type xr:Node-id;
            description "Node where ACL is applied";
          }
          leaf application-id {
            xr:xr-xml-map "es_acl_oper:ApplicationID";
            type dt1:Acl-usage-app-id-enum;
            description "Application ID";
          }
          leaf name {
            xr:xr-xml-map "es_acl_oper:Name";
            type Es-acl-name;
            description "Name of the ACL";
          }
          leaf usage-details {
            xr:xr-xml-map "es_acl_oper:UsageDetails";
            type string;
            mandatory true;
            description "Usage Statistics Details";
          }
        }
      }
    }
  }
}
