module Cisco-IOS-XR-iedge4710-cfg {

  /*** NAMESPACE / PREFIX DEFINITION ***/

  namespace "http://cisco.com/ns/yang/Cisco-IOS-XR-iedge4710-cfg";


  prefix "iedge4710-cfg";

  /*** LINKAGE (IMPORTS / INCLUDES) ***/

  import Cisco-IOS-XR-types { prefix "xr"; }

  import Cisco-IOS-XR-ifmgr-cfg { prefix "a1"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR iedge4710 package configuration.

     This module contains definitions
     for the following management objects:
       subscriber-manager: iEdge subscriber manager configuration
       iedge-license-manager: iedge license manager

     This YANG module augments the
       Cisco-IOS-XR-ifmgr-cfg
     module with configuration data.

     Copyright (c) 2013-2016 by Cisco Systems, Inc.
     All rights reserved.";

  revision "2015-11-09" {
    description
      "IOS XR 6.0 revision.";
  }


  container subscriber-manager {
    xr:xr-xml-map "iedge_manager_cfg:SubscriberManager";
    description "iEdge subscriber manager configuration";

    container accounting {
      xr:xr-xml-map "iedge_manager_cfg:Accounting";
      description "iEdge accounting feature";

      container send-stop {
        xr:xr-xml-map "iedge_manager_cfg:SendStop";
        description "Accounting send stop feature";
        leaf setup-failure {
          xr:xr-xml-map "iedge_manager_cfg:SetupFailure";
          xr:xr-cli-map "subscriber manager default ";
          type string;
          description "Set up failure feature";
        }
      }
    }
  }

  container iedge-license-manager {
    xr:xr-xml-map "islm_cfg:iEdgeLicenseManager";
    description "iedge license manager";

    list node {
      xr:xr-xml-map "islm_cfg:Node";
      key "node-name";
      description "Location. For eg., 0/1/CPU0";
      leaf session-limit {
        xr:xr-xml-map "islm_cfg:SessionLimit";
        type int32;
        description "Session limit configured on linecard";
      }
      leaf session-threshold {
        xr:xr-xml-map "islm_cfg:SessionThreshold";
        type int32;
        description "Session threshold configured on linecard";
      }
      leaf node-name {
        xr:xr-xml-map "islm_cfg:NodeName";
        type xr:Cisco-ios-xr-string;
        description "The node id to filter on. For eg., 0/1/CPU0";
      }
    }
  }

  augment "/a1:interface-configurations/a1:interface-configuration" {

    container control-subscriber {
      xr:xr-xml-map "subscriber_service_policy_intf_cfg:ControlSubs"+
        "criber";
      description
        "Interface control subscriber policy
        configuration";
      leaf service-policy {
        xr:xr-xml-map "subscriber_service_policy_intf_cfg:ServicePo"+
          "licy";
        type string {
          length "0..63";
        }
        description
          "Service policy to be applied to access
          interface  for subscribers";
      }
    }
    description
      "This augment extends the configuration data of
      'Cisco-IOS-XR-ifmgr-cfg'";
  }
}
