module Cisco-IOS-XR-ipv4-arp-oper {

  /*** NAMESPACE / PREFIX DEFINITION ***/

  namespace "http://cisco.com/ns/yang/Cisco-IOS-XR-ipv4-arp-oper";


  prefix "ipv4-arp-oper";

  /*** LINKAGE (IMPORTS / INCLUDES) ***/

  import ietf-inet-types { prefix "inet"; }

  import Cisco-IOS-XR-types { prefix "xr"; }

  include Cisco-IOS-XR-ipv4-arp-oper-sub2 {
    revision-date 2015-11-09;
  }

  include Cisco-IOS-XR-ipv4-arp-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ipv4-arp package operational data.

     This module contains definitions
     for the following management objects:
       arp-gmp: ARP-GMP global operational data
       arp: arp

     Copyright (c) 2013-2016 by Cisco Systems, Inc.
     All rights reserved.";

  revision "2015-11-09" {
    description
      "IOS XR 6.0 revision.";
  }


  container arp-gmp {
    xr:xr-xml-map "arp_gmp_oper:ARP_GMP";
    config false;
    description "ARP-GMP global operational data";

    container vrf-infos {
      xr:xr-xml-map "arp_gmp_oper:VRFInfoTable";
      description "Table of VRF related ARP-GMP operational data";

      list vrf-info {
        xr:xr-xml-map "arp_gmp_oper:VRFInfo";
        key "vrf-name";
        description "VRF related ARP-GMP operational data";
        leaf vrf-name {
          xr:xr-xml-map "arp_gmp_oper:VRFName";
          type xr:Cisco-ios-xr-string;
          description "VRF name for the default VRF use 'default'";
        }
        uses ARP-GMP-VRF-ENTRY;
      }
    }

    container vrfs {
      xr:xr-xml-map "arp_gmp_oper:VRFTable";
      description "Table of per VRF ARP-GMP operational data";

      list vrf {
        xr:xr-xml-map "arp_gmp_oper:VRF";
        key "vrf-name";
        description "Per VRF ARP-GMP operational data";

        container configured-ip-addresses {
          xr:xr-xml-map "arp_gmp_oper:ConfiguredIPAddressTable";
          description
            "Table of ARP-GMP configured IP addresses
            information";

          list configured-ip-address {
            xr:xr-xml-map "arp_gmp_oper:ConfiguredIPAddress";
            key "address";
            description "ARP-GMP configured IP address information";
            leaf address {
              xr:xr-xml-map "arp_gmp_oper:Address";
              type inet:ipv4-address-no-zone;
              description "Configured ARP-GMP IP";
            }
            uses ARP-GMP-CONFIG-ENTRY;
          }
        }

        container routes {
          xr:xr-xml-map "arp_gmp_oper:RouteTable";
          description "Table of ARP GMP route information";

          list route {
            xr:xr-xml-map "arp_gmp_oper:Route";
            description "ARP GMP route information";
            leaf address {
              xr:xr-xml-map "arp_gmp_oper:Address";
              type inet:ipv4-address-no-zone;
              description "IP address";
            }
            leaf prefix-length {
              xr:xr-xml-map "arp_gmp_oper:PrefixLength";
              type uint32 {
                range "0..32";
              }
              description "Prefix length";
            }
            uses ARP-GMP-ROUTE-ENTRY;
          }
        }

        container interface-configured-ips {
          xr:xr-xml-map "arp_gmp_oper:InterfaceConfiguredIPTable";
          description
            "Table of ARP GMP interface and associated
            configured IP data";

          list interface-configured-ip {
            xr:xr-xml-map "arp_gmp_oper:InterfaceConfiguredIP";
            description
              "ARP GMP interface and associated configured
              IP data";
            leaf interface-name {
              xr:xr-xml-map "arp_gmp_oper:InterfaceName";
              type xr:Interface-name;
              description "Interface name";
            }
            leaf address {
              xr:xr-xml-map "arp_gmp_oper:Address";
              type inet:ipv4-address-no-zone;
              description "Configured ARP-GMP IP";
            }
            uses ARP-GMP-INTF-ENTRY;
          }
        }
        leaf vrf-name {
          xr:xr-xml-map "arp_gmp_oper:VRFName";
          type xr:Cisco-ios-xr-string;
          description "VRF name for the default VRF use 'default'";
        }
      }
    }
  }

  container arp {
    xr:xr-xml-map "arp_oper:ARP";
    config false;
    description "arp";

    container nodes {
      xr:xr-xml-map "arp_oper:NodeTable";
      description "Table of per-node ARP operational data";

      list node {
        xr:xr-xml-map "arp_oper:Node";
        key "node-name";
        description "Per-node ARP operational data";

        container resolution-history-dynamic {
          xr:xr-xml-map "arp_oper:ResolutionHistoryDynamic";
          description
            "Per node dynamically-resolved ARP resolution
            history data";
          uses ARP-RESHIST;
        }

        container traffic-vrfs {
          xr:xr-xml-map "arp_oper:TrafficVRFTable";
          description "ARP Traffic information per VRF";

          list traffic-vrf {
            xr:xr-xml-map "arp_oper:TrafficVRF";
            key "vrf-name";
            description "Per VRF traffic data";
            leaf vrf-name {
              xr:xr-xml-map "arp_oper:VRFName";
              type string;
              description "VRF name";
            }
            uses IP-ARP-STATISTICS;
          }
        }

        container traffic-node {
          xr:xr-xml-map "arp_oper:TrafficNode";
          description "Per node ARP Traffic data";
          uses IP-ARP-STATISTICS;
        }

        container resolution-history-client {
          xr:xr-xml-map "arp_oper:ResolutionHistoryClient";
          description
            "Per node client-installed ARP resolution
            history data";
          uses ARP-RESHIST;
        }

        container entries {
          xr:xr-xml-map "arp_oper:EntryTable";
          description "Table of ARP entries";

          list entry {
            xr:xr-xml-map "arp_oper:Entry";
            key "address interface-name";
            description "ARP entry";
            leaf address {
              xr:xr-xml-map "arp_oper:Address";
              type inet:ipv4-address-no-zone;
              description "IP Address of ARP entry";
            }
            leaf interface-name {
              xr:xr-xml-map "arp_oper:InterfaceName";
              type xr:Interface-name;
              description "Interface name";
            }
            uses IP-ARP-TABLE-ENTRY;
          }
        }

        container traffic-interfaces {
          xr:xr-xml-map "arp_oper:TrafficInterfaceTable";
          description "ARP Traffic information per interface";

          list traffic-interface {
            xr:xr-xml-map "arp_oper:TrafficInterface";
            key "interface-name";
            description "Per interface traffic data";
            leaf interface-name {
              xr:xr-xml-map "arp_oper:InterfaceName";
              type xr:Interface-name;
              description "Interface name";
            }
            uses IP-ARP-STATISTICS;
          }
        }
        leaf node-name {
          xr:xr-xml-map "arp_oper:NodeName";
          type xr:Node-id;
          description "Node name";
        }
      }
    }
  }
}
