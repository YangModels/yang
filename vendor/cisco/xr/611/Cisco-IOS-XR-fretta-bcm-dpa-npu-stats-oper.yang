module Cisco-IOS-XR-fretta-bcm-dpa-npu-stats-oper {

  /*** NAMESPACE / PREFIX DEFINITION ***/

  namespace "http://cisco.com/ns/yang"+
    "/Cisco-IOS-XR-fretta-bcm-dpa-npu-stats-oper";


  prefix "fretta-bcm-dpa-npu-stats-oper";

  /*** LINKAGE (IMPORTS / INCLUDES) ***/

  import Cisco-IOS-XR-types { prefix "xr"; }

  include Cisco-IOS-XR-fretta-bcm-dpa-npu-stats-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR fretta-bcm-dpa-npu-stats package operational data.

     This module contains definitions
     for the following management objects:
       dpa: DPA operational data

     Copyright (c) 2013-2016 by Cisco Systems, Inc.
     All rights reserved.";

  revision "2015-11-09" {
    description
      "IOS XR 6.0 revision.";
  }

  typedef Max-trap-s {
    type uint32 {
      range "0..4294967295";
    }
    description "Max trap s";
  }
  typedef Max-lc-intf-hand-les {
    type uint32 {
      range "0..4294967295";
    }
    description "Max lc intf hand les";
  }

  container dpa {
    xr:xr-xml-map "dpa_npu_stats_oper:DPA";
    config false;
    description "DPA operational data";

    container stats {
      xr:xr-xml-map "dpa_npu_stats_oper:STATS";
      description "DPA voq data";

      container nodes {
        xr:xr-xml-map "dpa_npu_stats_oper:NodeTable";
        description "DPA data for available nodes";

        list node {
          xr:xr-xml-map "dpa_npu_stats_oper:Node";
          key "node-name";
          description "DPA operational data for a particular node";

          container voq-base-number-stats-clears {
            xr:xr-xml-map "dpa_npu_stats_oper:ClearVoqBaseStats";
            description "Clear DPA voq base stats ";

            list voq-base-number-stats-clear {
              xr:xr-xml-map "dpa_npu_stats_oper:VoqBaseNumberStatsC"+
                "lear";
              key "npu-number";
              description "Filter by npu number";
              leaf npu-number {
                xr:xr-xml-map "dpa_npu_stats_oper:NpuNumber";
                type int32;
                description "Npu Number";
              }

              list voq-base-stats-clear-data {
                xr:xr-xml-map "dpa_npu_stats_oper:VoqBaseStatsClear"+
                  "Data";
                key "base-number";
                description
                  "Clear stats  for a particular voq base
                  number";
                leaf base-number {
                  xr:xr-xml-map "dpa_npu_stats_oper:BaseNumber";
                  type Max-lc-intf-hand-les;
                  description "Interface handle";
                }
                uses CLEAR-STATS;
              }
            }
          }

          container npu-number-for-trap-datas {
            xr:xr-xml-map "dpa_npu_stats_oper:AllTrapStats";
            description "Trap stats for all traps";

            list npu-number-for-trap-data {
              xr:xr-xml-map "dpa_npu_stats_oper:NpuNumberForTrapDat"+
                "a";
              key "npu-id";
              description "All trap stats for a particular npu";
              leaf npu-id {
                xr:xr-xml-map "dpa_npu_stats_oper:NpuId";
                type int32;
                description "NPU number";
              }

              list trap-specific-stats-data {
                xr:xr-xml-map "dpa_npu_stats_oper:TrapSpecificStats"+
                  "Data";
                key "trap-data";
                description "Filter by specific trap id";
                leaf trap-data {
                  xr:xr-xml-map "dpa_npu_stats_oper:TrapData";
                  type Max-trap-s;
                  description "Trap Number";
                }
                uses DPA-TRAP-STATS;
              }
            }
          }

          container voq-base-numbers {
            xr:xr-xml-map "dpa_npu_stats_oper:VoqBaseStats";
            description "DPA voq base stats ";

            list voq-base-number {
              xr:xr-xml-map "dpa_npu_stats_oper:VoqBaseNumber";
              key "npu-number";
              description "Filter by npu number";
              leaf npu-number {
                xr:xr-xml-map "dpa_npu_stats_oper:NpuNumber";
                type int32;
                description "Npu Number";
              }

              list voq-base-stats-data {
                xr:xr-xml-map "dpa_npu_stats_oper:VoqBaseStatsData";
                key "base-number";
                description "Voq Base Number for a particular voq";
                leaf base-number {
                  xr:xr-xml-map "dpa_npu_stats_oper:BaseNumber";
                  type Max-lc-intf-hand-les;
                  description "Interface handle";
                }
                uses DPA-VOQ-INTF-PORT;
              }
            }
          }

          container npu-number-for-voq-datas {
            xr:xr-xml-map "dpa_npu_stats_oper:AllInterfaceVoqStats";
            description "DPA voq ingress stats for all interfaces";

            list npu-number-for-voq-data {
              xr:xr-xml-map "dpa_npu_stats_oper:NpuNumberForVoqData";
              key "npu-id";
              description "All voq stats for a particular npu";
              leaf npu-id {
                xr:xr-xml-map "dpa_npu_stats_oper:NpuId";
                type int32;
                description "Npu number";
              }

              list voq-specific-stats-data {
                xr:xr-xml-map "dpa_npu_stats_oper:VoqSpecificStatsD"+
                  "ata";
                key "voq-data";
                description "Filter data by interface handle";
                leaf voq-data {
                  xr:xr-xml-map "dpa_npu_stats_oper:VoqData";
                  type int32;
                  description "Interface Handle";
                }
                uses DPA-VOQ-INTF-PORT;
              }
            }
          }

          container clear-voq-data-for-npu-numbers {
            xr:xr-xml-map "dpa_npu_stats_oper:ClearAllInterfaceVoqS"+
              "tats";
            description
              "Clear voq ingress stats for all interfaces on
              particular npu";

            list clear-voq-data-for-npu-number {
              xr:xr-xml-map "dpa_npu_stats_oper:ClearVoqDataForNpuN"+
                "umber";
              key "npu-id";
              description "Npu id on which stats will be cleared";
              leaf npu-id {
                xr:xr-xml-map "dpa_npu_stats_oper:NpuId";
                type int32;
                description "Npu number";
              }

              list voq-specific-stats-data-clear {
                xr:xr-xml-map "dpa_npu_stats_oper:VoqSpecificStatsD"+
                  "ataClear";
                key "voq-data";
                description "Filter data by interface handle";
                leaf voq-data {
                  xr:xr-xml-map "dpa_npu_stats_oper:VoqData";
                  type int32;
                  description "Interface Handle";
                }
                uses CLEAR-STATS;
              }
            }
          }

          container npu-number-for-trap-data-clears {
            xr:xr-xml-map "dpa_npu_stats_oper:ClearAllTrapStats";
            description "Trap stats for all traps";

            list npu-number-for-trap-data-clear {
              xr:xr-xml-map "dpa_npu_stats_oper:NpuNumberForTrapDat"+
                "aClear";
              key "npu-id";
              description "All trap stats for a particular npu";
              leaf npu-id {
                xr:xr-xml-map "dpa_npu_stats_oper:NpuId";
                type int32;
                description "NPU number";
              }

              list trap-specific-stats-data {
                xr:xr-xml-map "dpa_npu_stats_oper:TrapSpecificStats"+
                  "Data";
                key "trap-data";
                description "Filter by specific trap id";
                leaf trap-data {
                  xr:xr-xml-map "dpa_npu_stats_oper:TrapData";
                  type Max-trap-s;
                  description "Trap Number";
                }
                uses CLEAR-STATS;
              }
            }
          }
          leaf node-name {
            xr:xr-xml-map "dpa_npu_stats_oper:NodeName";
            type xr:Node-id;
            description "Node ID";
          }
        }
      }
    }
  }
}
