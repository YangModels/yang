module Cisco-IOS-XR-infra-rsi-cfg {

  /*** NAMESPACE / PREFIX DEFINITION ***/

  namespace "http://cisco.com/ns/yang/Cisco-IOS-XR-infra-rsi-cfg";


  prefix "infra-rsi-cfg";

  /*** LINKAGE (IMPORTS / INCLUDES) ***/

  import Cisco-IOS-XR-types { prefix "xr"; }

  import Cisco-IOS-XR-ifmgr-cfg { prefix "a1"; }

  import Cisco-IOS-XR-snmp-agent-cfg { prefix "a2"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR infra-rsi package configuration.

     This module contains definitions
     for the following management objects:
       vrfs: VRF configuration
       global-af: global af
       srlg: srlg
       vrf-groups: vrf groups
       selective-vrf-download: selective vrf download

     This YANG module augments the
       Cisco-IOS-XR-ifmgr-cfg,
       Cisco-IOS-XR-snmp-agent-cfg
     modules with configuration data.

     Copyright (c) 2013-2016 by Cisco Systems, Inc.
     All rights reserved.";

  revision "2015-07-30" {
    description
      "Descriptions updated.";
  }

  revision "2015-01-07" {
    description
      "IOS XR 5.3.1 revision.";
  }

  typedef Vrf-sub-address-family {
    type enumeration {
      enum unicast {
        value 1;
        description "Unicast";
      }
      enum multicast {
        value 2;
        description "Multicast";
      }
      enum flow-spec {
        value 133;
        description "Flow spec";
      }
    }
    description "Vrf sub address family";
  }
  typedef Vrf-address-family {
    type enumeration {
      enum ipv4 {
        value 1;
        description "IPv4";
      }
      enum ipv6 {
        value 2;
        description "IPv6";
      }
    }
    description "Vrf address family";
  }
  typedef Srlg-priority {
    type enumeration {
      enum critical {
        value 0;
        description "Critical";
      }
      enum high {
        value 1;
        description "High";
      }
      enum default {
        value 2;
        description "Default";
      }
      enum low {
        value 3;
        description "Low";
      }
      enum very-low {
        value 4;
        description "Very low";
      }
    }
    description "Srlg priority";
  }

  grouping AF-TABLE {
    description "Common node of vrf, global-af";

    container afs {
      xr:xr-xml-map "rsi_vrf_cfg:AFTable";
      description "VRF address family configuration";

      list af {
        xr:xr-xml-map "rsi_vrf_cfg:AF";
        key "af-name saf-name topology-name";
        description "VRF address family configuration";
        leaf create {
          xr:xr-xml-map "rsi_vrf_cfg:Create";
          type empty;
          description
            "VRF configuration for a particular address
            family";
        }
        leaf af-name {
          xr:xr-xml-map "rsi_vrf_cfg:AFName";
          type Vrf-address-family;
          description "Address family";
        }
        leaf saf-name {
          xr:xr-xml-map "rsi_vrf_cfg:SAFName";
          type Vrf-sub-address-family;
          description "Sub-Address family";
        }
        leaf topology-name {
          xr:xr-xml-map "rsi_vrf_cfg:TopologyName";
          type xr:Cisco-ios-xr-string {
            length "0..244";
          }
          description "Topology name";
        }
      }
    }
  }

  container vrfs {
    xr:xr-xml-map "rsi_vrf_cfg:VRFTable";
    description "VRF configuration";

    list vrf {
      xr:xr-xml-map "rsi_vrf_cfg:VRF";
      key "vrf-name";
      description "VRF configuration";

      container vpn-id {
        xr:xr-xml-map "rsi_vrf_cfg:VPN_ID";
        presence "Indicates a vpn-id node is configured.";
        description "VPN-ID for the VRF";
        leaf vpn-oui {
          xr:xr-xml-map "rsi_vrf_cfg:VPN_OUI";
          type uint32 {
            range "0..4294967295";
          }
          mandatory true;
          description "OUI of VPNID OUI";
        }
        leaf vpn-index {
          xr:xr-xml-map "rsi_vrf_cfg:VPNIndex";
          type uint32 {
            range "0..16777215";
          }
          mandatory true;
          description "Index of VPNID Index";
        }
      }
      leaf fallback-vrf {
        xr:xr-xml-map "rsi_vrf_cfg:FallbackVRF";
        xr:xr-cli-map "vrf <string> fallback-vrf <string> ";
        type xr:Cisco-ios-xr-string {
          length "0..32";
        }
        description "Fallback VRF";
      }
      leaf remote-route-filter-disable {
        xr:xr-xml-map "rsi_vrf_cfg:RemoteRouteFilterDisable";
        xr:xr-cli-map "vrf <string> remote-route-filtering disable ";
        type empty;
        description
          "For disabling remote route filtering for this
          VRF on core-facing card";
      }
      leaf create {
        xr:xr-xml-map "rsi_vrf_cfg:Create";
        type empty;
        description "VRF global configuration";
      }
      leaf mode-big {
        xr:xr-xml-map "rsi_vrf_cfg:ModeBig";
        xr:xr-cli-map "vrf <string> mode big ";
        type empty;
        description "Configuration enable of big VRF";
      }
      leaf description {
        xr:xr-xml-map "rsi_vrf_cfg:Description";
        xr:xr-cli-map "vrf <string> description <text> ";
        type string {
          length "0..244";
        }
        description "A textual description of the VRF";
      }
      leaf vrf-name {
        xr:xr-xml-map "rsi_vrf_cfg:VRFName";
        type xr:Cisco-ios-xr-string {
          length "0..32";
        }
        description "VRF name";
      }
      uses AF-TABLE;
    }
  }

  container global-af {
    xr:xr-xml-map "rsi_vrf_cfg:GlobalAF";
    description "global af";
    uses AF-TABLE;
  }

  container srlg {
    xr:xr-xml-map "rsi_srlg_cfg:SRLG";
    description "srlg";

    container interfaces {
      xr:xr-xml-map "rsi_srlg_cfg:InterfaceTable";
      description "Set of interfaces configured with SRLG";

      list interface {
        xr:xr-xml-map "rsi_srlg_cfg:Interface";
        key "interface-name";
        description "Interface configurations";

        container include-optical {
          xr:xr-xml-map "rsi_srlg_cfg:IncludeOptical";
          description
            "Include optical configuration for an interface";
          leaf enable {
            xr:xr-xml-map "rsi_srlg_cfg:Enable";
            type empty;
            description "Enable SRLG interface include optical";
          }
          leaf priority {
            xr:xr-xml-map "rsi_srlg_cfg:Priority";
            xr:xr-cli-map "srlg interface <interface> include-optic"+
              "al priority <enum> ";
            type Srlg-priority;
            default "default";
            description "Priority for optical domain values";
          }
        }

        container interface-group {
          xr:xr-xml-map "rsi_srlg_cfg:InterfaceGroup";
          description "Group configuration for an interface";

          container group-names {
            xr:xr-xml-map "rsi_srlg_cfg:GroupNameTable";
            description "Set of group name under an interface";

            list group-name {
              xr:xr-xml-map "rsi_srlg_cfg:GroupName";
              xr:xr-cli-map "srlg interface <interface> group <numb"+
                "er> <string> ";
              key "group-name-index";
              description "Group name included under interface";
              leaf group-name-index {
                xr:xr-xml-map "rsi_srlg_cfg:GroupNameIndex";
                type uint32;
                description "Group name index";
              }
              leaf group-name {
                xr:xr-xml-map "rsi_srlg_cfg:GroupName";
                type string;
                mandatory true;
                description "Group name";
              }
              leaf srlg-priority {
                xr:xr-xml-map "rsi_srlg_cfg:SRLGPriority";
                type Srlg-priority;
                default "default";
                description "SRLG priority";
              }
            }
          }
          leaf enable {
            xr:xr-xml-map "rsi_srlg_cfg:Enable";
            type empty;
            description "Enable SRLG interface group submode";
          }
        }

        container values {
          xr:xr-xml-map "rsi_srlg_cfg:ValueTable";
          description "SRLG Value configuration for an interface";

          list value {
            xr:xr-xml-map "rsi_srlg_cfg:Value";
            xr:xr-cli-map "srlg interface <interface> [<number>] va"+
              "lue <number> [priority <enum>] ";
            key "srlg-index";
            description "SRLG value data";
            leaf srlg-index {
              xr:xr-xml-map "rsi_srlg_cfg:SRLGIndex";
              type uint32 {
                range "1..65535";
              }
              description "SRLG index";
            }
            leaf srlg-value {
              xr:xr-xml-map "rsi_srlg_cfg:SRLGValue";
              type uint32 {
                range "0..4294967295";
              }
              mandatory true;
              description "SRLG value";
            }
            leaf srlg-priority {
              xr:xr-xml-map "rsi_srlg_cfg:SRLGPriority";
              type Srlg-priority;
              default "default";
              description "SRLG priority";
            }
          }
        }

        container interface-srlg-names {
          xr:xr-xml-map "rsi_srlg_cfg:InterfaceSRLGNameTable";
          description "SRLG Name configuration for an interface";

          list interface-srlg-name {
            xr:xr-xml-map "rsi_srlg_cfg:InterfaceSRLGName";
            xr:xr-cli-map "srlg interface <interface> name <string>"+
              " ";
            key "srlg-name";
            description "SRLG name data";
            leaf srlg-name {
              xr:xr-xml-map "rsi_srlg_cfg:SRLGName";
              type xr:Cisco-ios-xr-string {
                length "0..64";
              }
              description "SRLG name";
            }
          }
        }
        leaf enable {
          xr:xr-xml-map "rsi_srlg_cfg:Enable";
          type empty;
          description "Enable SRLG interface";
        }
        leaf interface-name {
          xr:xr-xml-map "rsi_srlg_cfg:InterfaceName";
          type xr:Interface-name;
          description "Interface name";
        }
      }
    }

    container srlg-names {
      xr:xr-xml-map "rsi_srlg_cfg:SRLGNameTable";
      description "Set of SRLG name configuration";

      list srlg-name {
        xr:xr-xml-map "rsi_srlg_cfg:SRLGName";
        xr:xr-cli-map "srlg name <string> value <number> ";
        key "srlg-name";
        description "SRLG name configuration";
        leaf srlg-name {
          xr:xr-xml-map "rsi_srlg_cfg:SRLGName";
          type xr:Cisco-ios-xr-string {
            length "0..64";
          }
          description "SRLG name";
        }
        leaf srlg-value {
          xr:xr-xml-map "rsi_srlg_cfg:SRLGValue";
          type uint32 {
            range "0..4294967295";
          }
          mandatory true;
          description "SRLG value";
        }
      }
    }

    container groups {
      xr:xr-xml-map "rsi_srlg_cfg:GroupTable";
      description "Set of groups configured with SRLG";

      list group {
        xr:xr-xml-map "rsi_srlg_cfg:Group";
        key "group-name";
        description "Group configurations";

        container group-values {
          xr:xr-xml-map "rsi_srlg_cfg:GroupValueTable";
          description "Set of SRLG values configured under a group";

          list group-value {
            xr:xr-xml-map "rsi_srlg_cfg:GroupValue";
            xr:xr-cli-map "srlg group <string> [<number>] value <nu"+
              "mber> [priority <enum>] ";
            key "srlg-index";
            description "Group SRLG values with attribute";
            leaf srlg-index {
              xr:xr-xml-map "rsi_srlg_cfg:SRLGIndex";
              type uint32 {
                range "1..65535";
              }
              description "SRLG index";
            }
            leaf srlg-value {
              xr:xr-xml-map "rsi_srlg_cfg:SRLGValue";
              type uint32 {
                range "0..4294967295";
              }
              mandatory true;
              description "SRLG value";
            }
            leaf srlg-priority {
              xr:xr-xml-map "rsi_srlg_cfg:SRLGPriority";
              type Srlg-priority;
              default "default";
              description "SRLG priority";
            }
          }
        }
        leaf enable {
          xr:xr-xml-map "rsi_srlg_cfg:Enable";
          type empty;
          description "Enable SRLG group";
        }
        leaf group-name {
          xr:xr-xml-map "rsi_srlg_cfg:GroupName";
          type xr:Cisco-ios-xr-string;
          description "Group name";
        }
      }
    }

    container inherit-nodes {
      xr:xr-xml-map "rsi_srlg_cfg:InheritNodeTable";
      description "Set of inherit nodes configured with SRLG";

      list inherit-node {
        xr:xr-xml-map "rsi_srlg_cfg:InheritNode";
        key "inherit-node-name";
        description "Inherit node configurations";

        container inherit-node-values {
          xr:xr-xml-map "rsi_srlg_cfg:InheritNodeValueTable";
          description
            "Set of SRLG values configured under an inherit
            node";

          list inherit-node-value {
            xr:xr-xml-map "rsi_srlg_cfg:InheritNodeValue";
            xr:xr-cli-map "srlg inherit-location <pq location> [<nu"+
              "mber>] value <number> [priority <enum>] ";
            key "srlg-index";
            description "Inherit node SRLG value with attributes";
            leaf srlg-index {
              xr:xr-xml-map "rsi_srlg_cfg:SRLGIndex";
              type uint32 {
                range "1..65535";
              }
              description "SRLG index";
            }
            leaf srlg-value {
              xr:xr-xml-map "rsi_srlg_cfg:SRLGValue";
              type uint32 {
                range "0..4294967295";
              }
              mandatory true;
              description "SRLG value";
            }
            leaf srlg-priority {
              xr:xr-xml-map "rsi_srlg_cfg:SRLGPriority";
              type Srlg-priority;
              default "default";
              description "SRLG priority";
            }
          }
        }
        leaf enable {
          xr:xr-xml-map "rsi_srlg_cfg:Enable";
          type empty;
          description "Enable SRLG inherit node";
        }
        leaf inherit-node-name {
          xr:xr-xml-map "rsi_srlg_cfg:InheritNodeName";
          type xr:Pq-node-id;
          description "The inherit node name";
        }
      }
    }
    leaf enable {
      xr:xr-xml-map "rsi_srlg_cfg:Enable";
      type empty;
      description "Enable SRLG";
    }
  }

  container vrf-groups {
    xr:xr-xml-map "rsi_vrfgroup_cfg:VRFGroupTable";
    description "vrf groups";

    list vrf-group {
      xr:xr-xml-map "rsi_vrfgroup_cfg:VRFGroup";
      key "vrf-group-name";
      description "VRF group configuration";

      container vrfs {
        xr:xr-xml-map "rsi_vrfgroup_cfg:VRFTable";
        description "Set of VRFs configured under a VRF group";

        list vrf {
          xr:xr-xml-map "rsi_vrfgroup_cfg:VRF";
          xr:xr-cli-map "vrf-group <string> vrf <string> ";
          key "vrf-name";
          description "VRF configuration";
          leaf vrf-name {
            xr:xr-xml-map "rsi_vrfgroup_cfg:VRFName";
            type xr:Cisco-ios-xr-string {
              length "0..32";
            }
            description "VRF name";
          }
        }
      }
      leaf enable {
        xr:xr-xml-map "rsi_vrfgroup_cfg:Enable";
        type empty;
        description "Enable VRF group";
      }
      leaf vrf-group-name {
        xr:xr-xml-map "rsi_vrfgroup_cfg:VRFGroupName";
        type xr:Cisco-ios-xr-string {
          length "0..32";
        }
        description "VRF group name";
      }
    }
  }

  container selective-vrf-download {
    xr:xr-xml-map "rsi_svd_cfg:SelectiveVRFDownload";
    description "selective vrf download";
    leaf disable {
      xr:xr-xml-map "rsi_svd_cfg:Disable";
      xr:xr-cli-map "selective-vrf-download disable ";
      type empty;
      description "Disable selective VRF download";
    }
  }

  augment "/a1:interface-configurations/a1:interface-configuration" {
    leaf vrf {
      xr:xr-xml-map "rsi_vrf_interface_cfg:VRF";
      type xr:Cisco-ios-xr-string {
        length "0..32";
      }
      description "Assign the interface to a VRF";
    }
    description
      "This augment extends the configuration data of
      'Cisco-IOS-XR-ifmgr-cfg'";
  }

  augment "/a1:interface-configurations/a1:interface-configuration" {

    container afs {
      xr:xr-xml-map "rsi_vrf_interface_cfg:AFTable";

      list af {
        key "af-name saf-name";
        description
          "The presence of this object enables the
          givenaddress-family and topology on the
          interface.";
        leaf af-name {
          xr:xr-xml-map "rsi_vrf_interface_cfg:AFName";
          type Vrf-address-family;
          description "Address-family";
        }
        leaf saf-name {
          xr:xr-xml-map "rsi_vrf_interface_cfg:SAFName";
          type Vrf-sub-address-family;
          description "Sub-address-family";
        }
      }

      list af-topology-name {
        key "topology-name af-name saf-name";
        description
          "The presence of this object enables the
          givenaddress-family and topology on the
          interface.";
        leaf topology-name {
          xr:xr-xml-map "rsi_vrf_interface_cfg:TopologyName";
          type xr:Cisco-ios-xr-string {
            length "0..32";
          }
          description "Topology name";
        }
        leaf af-name {
          xr:xr-xml-map "rsi_vrf_interface_cfg:AFName";
          type Vrf-address-family;
          description "Address-family";
        }
        leaf saf-name {
          xr:xr-xml-map "rsi_vrf_interface_cfg:SAFName";
          type Vrf-sub-address-family;
          description "Sub-address-family";
        }
      }
      description "Per-address-family and topology configuration";
    }
    description
      "This augment extends the configuration data of
      'Cisco-IOS-XR-ifmgr-cfg'";
  }

  augment "/a2:snmp/a2:notification" {

    container selective-vrf-download {
      xr:xr-xml-map "svd_mib_cfg:SelectiveVRFDownload";
      description
        "CISCO-SELECTIVE-VRF-DOWNLOAD-MIB notification
        configuration";
      leaf role-change {
        xr:xr-xml-map "svd_mib_cfg:RoleChange";
        type empty;
        description
          "Enable csvdEntityRoleChangeNotification
          notification";
      }
    }
    description
      "This augment extends the configuration data of
      'Cisco-IOS-XR-snmp-agent-cfg'";
  }
}
