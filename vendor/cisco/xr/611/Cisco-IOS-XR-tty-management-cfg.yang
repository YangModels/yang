module Cisco-IOS-XR-tty-management-cfg {

  /*** NAMESPACE / PREFIX DEFINITION ***/

  namespace "http://cisco.com/ns"+
    "/yang/Cisco-IOS-XR-tty-management-cfg";


  prefix "tty-management-cfg";

  /*** LINKAGE (IMPORTS / INCLUDES) ***/

  import Cisco-IOS-XR-types { prefix "xr"; }

  import Cisco-IOS-XR-tty-management-datatypes { prefix "dt1"; }

  import Cisco-IOS-XR-tty-server-cfg { prefix "a1"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR tty-management package configuration.

     This YANG module augments the
       Cisco-IOS-XR-tty-server-cfg
     module with configuration data.

     Copyright (c) 2013-2016 by Cisco Systems, Inc.
     All rights reserved.";

  revision "2015-09-25" {
    description
      "Descriptions updated.";
  }

  revision "2015-01-07" {
    description
      "IOS XR 5.3.1 revision.";
  }


  augment "/a1:tty/a1:tty-lines/a1:tty-line" {

    container connection {
      xr:xr-xml-map "tty_management_cfg:Connection";
      description "Management connection configuration";

      container transport-input {
        xr:xr-xml-map "tty_management_cfg:TransportInput";
        description
          "Protocols to use when connecting to the
          terminal server";
        leaf select {
          xr:xr-xml-map "tty_management_cfg:Select";
          type dt1:Tty-transport-protocol-select;
          default "all";
          description "Choose transport protocols";
        }
        leaf protocol1 {
          xr:xr-xml-map "tty_management_cfg:Protocol1";
          when "../select = 'some'" {
            description "../Select = 2";
          }
          type dt1:Tty-transport-protocol;
          description "Transport protocol1";
        }
        leaf protocol2 {
          xr:xr-xml-map "tty_management_cfg:Protocol2";
          when "../select = 'some'" {
            description "../Select = 2";
          }
          type dt1:Tty-transport-protocol;
          description "Transport protocol2";
        }
        leaf none {
          xr:xr-xml-map "tty_management_cfg:None";
          type int32;
          description "Not used";
        }
      }

      container transport-output {
        xr:xr-xml-map "tty_management_cfg:TransportOutput";
        presence "Indicates a transport-output node is configured.";
        description "Protocols to use for outgoing connections";
        leaf select {
          xr:xr-xml-map "tty_management_cfg:Select";
          type dt1:Tty-transport-protocol-select;
          mandatory true;
          description "Choose transport protocols";
        }
        leaf protocol1 {
          xr:xr-xml-map "tty_management_cfg:Protocol1";
          type dt1:Tty-transport-protocol;
          description "Transport protocol1";
        }
        leaf protocol2 {
          xr:xr-xml-map "tty_management_cfg:Protocol2";
          type dt1:Tty-transport-protocol;
          description "Transport protocol2";
        }
        leaf none {
          xr:xr-xml-map "tty_management_cfg:None";
          type int32;
          description "Not used";
        }
      }

      container session-timeout {
        xr:xr-xml-map "tty_management_cfg:SessionTimeout";
        presence "Indicates a session-timeout node is configured.";
        description
          "Interval for closing connection when there is
          no input traffic";
        leaf timeout {
          xr:xr-xml-map "tty_management_cfg:Timeout";
          type uint32 {
            range "0..35791";
          }
          mandatory true;
          description "Session timeout interval in minutes";
        }
        leaf direction {
          xr:xr-xml-map "tty_management_cfg:Direction";
          type dt1:Tty-session-timeout-direction;
          mandatory true;
          description
            "Include output traffic as well as input
            traffic";
        }
      }
      leaf disconnect-character {
        xr:xr-xml-map "tty_management_cfg:DisconnectCharacter";
        type xr:Char-num;
        description
          "Disconnect character's decimal equivalent value
          or Character ";
      }
      leaf acl-in {
        xr:xr-xml-map "tty_management_cfg:ACLIn";
        type string;
        description "ACL to filter ingoing connections";
      }
      leaf acl-out {
        xr:xr-xml-map "tty_management_cfg:ACLOut";
        type string;
        description "ACL to filter outgoing connections";
      }
      leaf cli-white-space-completion {
        xr:xr-xml-map "tty_management_cfg:CLIWhiteSpaceCompletion";
        type empty;
        description "Command completion on whitespace";
      }
      leaf session-limit {
        xr:xr-xml-map "tty_management_cfg:SessionLimit";
        type uint32 {
          range "0..20";
        }
        default "6";
        description "The number of outgoing connections";
      }
      leaf escape-character {
        xr:xr-xml-map "tty_management_cfg:EscapeCharacter";
        type xr:Tty-escape-char-num;
        default "30";
        description
          "Escape character or ASCII decimal equivalent
          value orspecial strings NONE,DEFAULT,BREAK";
      }
      leaf transport-preferred {
        xr:xr-xml-map "tty_management_cfg:TransportPreferred";
        type dt1:Tty-transport-protocol;
        description "The preferred protocol to use";
      }
    }
    description
      "This augment extends the configuration data of
      'Cisco-IOS-XR-tty-server-cfg'";
  }

  augment "/a1:tty/a1:tty-lines/a1:tty-line" {

    container exec-mode {
      xr:xr-xml-map "tty_management_cfg:ExecMode";
      description "Exec Mode Pager  configurtion";
      leaf pager {
        xr:xr-xml-map "tty_management_cfg:Pager";
        type dt1:Tty-pager;
        default "more";
        description "Preferred Paging Utility";
      }
    }
    description
      "This augment extends the configuration data of
      'Cisco-IOS-XR-tty-server-cfg'";
  }
}
