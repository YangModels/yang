submodule Cisco-IOS-XR-icpe-infra-oper-sub3 {

  belongs-to Cisco-IOS-XR-icpe-infra-oper {
    prefix Cisco-IOS-XR-icpe-infra-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR icpe-infra package operational data.

     Copyright (c) 2013-2016 by Cisco Systems, Inc.
     All rights reserved.";

  revision "2015-11-09" {
    description
      "IOS XR 6.0 revision.";
  }


  grouping ICPE-INSTALL-PROGRESS {
    description "Current percentage of install";
    leaf progress-percentage-xr {
      xr:xr-xml-map "icpe_install_progress_data_gen:progress-percen"+
        "tage-xr";
      type uint16;
      units "percentage";
      description "Progress percentage";
    }
    leaf satellite-count {
      xr:xr-xml-map "icpe_install_progress_data_gen:SatelliteCount";
      type uint32;
      description "Satellite count";
    }
  }
}
