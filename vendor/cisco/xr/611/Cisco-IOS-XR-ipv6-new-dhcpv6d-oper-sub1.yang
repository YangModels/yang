submodule Cisco-IOS-XR-ipv6-new-dhcpv6d-oper-sub1 {

  belongs-to Cisco-IOS-XR-ipv6-new-dhcpv6d-oper {
    prefix Cisco-IOS-XR-ipv6-new-dhcpv6d-oper;
  }

  /*** LINKAGE (IMPORTS / INCLUDES) ***/

  import ietf-inet-types { prefix "inet"; }

  import ietf-yang-types { prefix "yang"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR ipv6-new-dhcpv6d package operational data.

     Copyright (c) 2013-2016 by Cisco Systems, Inc.
     All rights reserved.";

  revision "2015-11-09" {
    description
      "IOS XR 6.0 revision.";
  }

  typedef Bag-dhcpv6d-fsm-state {
    type enumeration {
      enum server-initializing {
        value 0;
        description "Server initializing state for client binding";
      }
      enum server-waiting-dpm {
        value 1;
        description "Server waiting on DPM to validate subscriber";
      }
      enum server-waiting-daps {
        value 2;
        description
          "Server waiting on DAPS to assign/free
          addr/prefix";
      }
      enum server-waiting-client {
        value 3;
        description "Server waiting for a request from the client";
      }
      enum server-waiting-subscriber {
        value 4;
        description
          "Server waiting for iedge response for the
          session";
      }
      enum server-waiting-rib {
        value 5;
        description "Server waiting for RIB response for route add";
      }
      enum server-bound-client {
        value 6;
        description "Server bound state to the client";
      }
      enum proxy-initializing {
        value 10;
        description "Proxy initializing state for client binding";
      }
      enum proxy-waiting-dpm {
        value 11;
        description "Proxy waiting on DPM to validate subscriber";
      }
      enum proxy-waiting-daps {
        value 12;
        description
          "Proxy waiting on DAPS to assign/free prefix(ND)";
      }
      enum proxy-waiting-client-server {
        value 13;
        description "Proxy waiting for a msg from the client/srv";
      }
      enum proxy-waiting-subscriber {
        value 14;
        description "Proxy waiting on iedge to sub session resp";
      }
      enum proxy-waiting-rib {
        value 15;
        description "Proxy waiting on RIB response";
      }
      enum proxy-bound-client {
        value 16;
        description "Proxy bound state to the client";
      }
    }
    description "Bag dhcpv6d fsm state";
  }
  typedef Bag-dhcpv6d-ia-id {
    type enumeration {
      enum iana {
        value 0;
        description "Non-temporary Addresses assigned ";
      }
      enum iapd {
        value 1;
        description "Prefix delegeated to client      ";
      }
      enum iata {
        value 2;
        description "Temporary Addresses - not supported ";
      }
    }
    description "Bag dhcpv6d ia id";
  }
  typedef String-ifname {
    type string {
      length "0..65";
    }
    description "String ifname";
  }
  typedef String-vrf {
    type string {
      length "0..33";
    }
    description "String vrf";
  }
  typedef Ipv6-address {
    type inet:ipv6-address;
    description "IPV6 Address type";
  }

  grouping IPV6-DHCPV6D-RELAY-ROUTE-BINDING {
    description "DHCPv6 relay route entry";
    leaf duid {
      xr:xr-xml-map "ipv6_dhcpv6d:DUID";
      type string;
      description "Client DUID";
    }
    leaf client-id-xr {
      xr:xr-xml-map "ipv6_dhcpv6d:client-id-xr";
      type uint32;
      description "Client unique identifier";
    }
    leaf prefix-length {
      xr:xr-xml-map "ipv6_dhcpv6d:PrefixLength";
      type uint8;
      description "length of prefix";
    }
    leaf prefix {
      xr:xr-xml-map "ipv6_dhcpv6d:Prefix";
      type Ipv6-address;
      description "DHCPV6 IPv6 Prefix allotted to client";
    }
    leaf vrf-name {
      xr:xr-xml-map "ipv6_dhcpv6d:VrfName";
      type string {
        length "0..33";
      }
      description "DHCPv6 client/subscriber Vrf name";
    }
    leaf lifetime {
      xr:xr-xml-map "ipv6_dhcpv6d:Lifetime";
      type uint32;
      description "Client route lifetime";
    }
    leaf rem-life-time {
      xr:xr-xml-map "ipv6_dhcpv6d:RemLifeTime";
      type uint32;
      description "Client route remaining lifetime";
    }
    leaf interface-name {
      xr:xr-xml-map "ipv6_dhcpv6d:InterfaceName";
      type string {
        length "0..65";
      }
      description "Interface name";
    }
    leaf next-hop-addr {
      xr:xr-xml-map "ipv6_dhcpv6d:NextHopAddr";
      type Ipv6-address;
      description "Next hop is our address";
    }
    leaf ia-id {
      xr:xr-xml-map "ipv6_dhcpv6d:IA_ID";
      type uint32;
      description "IA_ID of this IA";
    }
    leaf relay-profile-name {
      xr:xr-xml-map "ipv6_dhcpv6d:RelayProfileName";
      type string {
        length "0..65";
      }
      description "Relay Profile name";
    }
  }

  grouping IPV6-DHCPV6D-RELAY-BINDINGS-SUMMARY {
    description "DHCPv6 relay binding summary";
    leaf clients {
      xr:xr-xml-map "ipv6_dhcpv6d:Clients";
      type uint32;
      description "Total number of clients";
    }
  }

  grouping IPV6-DHCPV6D-RELAY-STATS {
    description "DHCPv6 relay statistics";

    list ipv6-dhcpv6d-relay-stat {
      description "ipv6 dhcpv6d relay stat";

      container statistics {
        description "Relay statistics";
        uses IPV6-DHCPV6D-FILTERED-STATS;
      }
      leaf vrf-name {
        type string {
          length "0..33";
        }
        description "DHCPv6 L3 VRF name";
      }
    }
  }

  grouping IPV6-DHCPV6D-SERVER-BINDING-OPTIONS {
    description "DHCPv6 server binding inserted option values";
    leaf mac-address-xr {
      xr:xr-xml-map "ipv6_dhcpv6d:mac-address-xr";
      type string;
      description "Client MAC address";
    }
    leaf duid-xr {
      xr:xr-xml-map "ipv6_dhcpv6d:duid-xr";
      type string;
      description "Client DUID";
    }
    leaf dns-count {
      xr:xr-xml-map "ipv6_dhcpv6d:DNSCount";
      type uint8;
      description "DNS address count";
    }
    leaf opt17 {
      xr:xr-xml-map "ipv6_dhcpv6d:Opt17";
      type string;
      description "Client Option 17 value";
    }
    leaf-list dns-address {
      xr:xr-xml-map "ipv6_dhcpv6d:DNSAddress";
      type Ipv6-address;
      max-elements "8";
      description "DNS addresses";
    }
  }

  grouping IPV6-DHCPV6D-SERVER-STATS {
    description "DHCPv6 server statistics";

    list ipv6-dhcpv6d-server-stat {
      description "ipv6 dhcpv6d server stat";

      container statistics {
        description "Server statistics";
        uses IPV6-DHCPV6D-FILTERED-STATS;
      }
      leaf vrf-name {
        type string {
          length "0..33";
        }
        description "DHCPv6 L3 VRF name";
      }
    }
  }

  grouping IPV6-DHCPV6D-SERVER-INTERFACE-REFERENCE {
    description "DHCPv6 server profile reference";

    list ipv6-dhcpv6d-server-interface-reference {
      description "ipv6 dhcpv6d server interface reference";
      leaf server-reference-interface-name {
        type string {
          length "0..65";
        }
        description "Interface name";
      }
    }
  }

  grouping TIME-BAG {
    description "Time in diffrent formats";
    leaf seconds {
      xr:xr-xml-map "ipv6_dhcpv6d:Seconds";
      type uint32;
      units "second";
      description "DHCPV6 client lease in seconds";
    }
    leaf time {
      xr:xr-xml-map "ipv6_dhcpv6d:Time";
      type string {
        length "0..10";
      }
      description "Time in format HH:MM:SS";
    }
  }

  grouping IPV6-DHCPV6D-SERVER-PROFILE {
    description "DHCPv6 server profile parameters";

    container lease {
      description "Server lease time";
      uses TIME-BAG;
    }

    container interface-references {
      description "Interface references";
      uses IPV6-DHCPV6D-SERVER-INTERFACE-REFERENCE;
    }
    leaf profile-name {
      xr:xr-xml-map "ipv6_dhcpv6d:ProfileName";
      type string {
        length "0..65";
      }
      description "Server profile name";
    }
    leaf domain-name {
      xr:xr-xml-map "ipv6_dhcpv6d:DomainName";
      type string {
        length "0..65";
      }
      description "Server domain name";
    }
    leaf profile-dns {
      xr:xr-xml-map "ipv6_dhcpv6d:ProfileDNS";
      type uint8;
      description "DNS address count";
    }
    leaf aftr-name {
      xr:xr-xml-map "ipv6_dhcpv6d:AFTRName";
      type string {
        length "0..65";
      }
      description "Server aftr name";
    }
    leaf framed-addr-pool-name {
      xr:xr-xml-map "ipv6_dhcpv6d:FramedAddrPoolName";
      type string {
        length "0..65";
      }
      description "Server framed address pool name";
    }
    leaf delegated-prefix-pool-name {
      xr:xr-xml-map "ipv6_dhcpv6d:DelegatedPrefixPoolName";
      type string {
        length "0..65";
      }
      description "Server delegated prefix pool name";
    }
    leaf rapid-commit {
      xr:xr-xml-map "ipv6_dhcpv6d:RapidCommit";
      type boolean;
      description "Rapid Commit";
    }
    leaf-list profile-dns-address {
      xr:xr-xml-map "ipv6_dhcpv6d:ProfileDNSAddress";
      type Ipv6-address;
      max-elements "8";
      description "DNS addresses";
    }
  }

  grouping IPV6-DHCPV6D-SERVER-BINDING {
    description "DHCPv6 server binding entry";

    container ia-id-pd {
      description "List of DHCPv6 IA_ID/PDs";
      uses BAG-DHCPV6D-IA-ID-PD-INFO;
    }
    leaf duid {
      xr:xr-xml-map "ipv6_dhcpv6d:DUID";
      type string;
      description "Client DUID";
    }
    leaf client-id-xr {
      xr:xr-xml-map "ipv6_dhcpv6d:client-id-xr";
      type uint32;
      description "Client unique identifier";
    }
    leaf client-flag {
      xr:xr-xml-map "ipv6_dhcpv6d:ClientFlag";
      type uint32;
      description "DHCPV6 client flag";
    }
    leaf subscriber-label {
      xr:xr-xml-map "ipv6_dhcpv6d:SubscriberLabel";
      type uint32;
      description "DHCPV6 subscriber label";
    }
    leaf vrf-name {
      xr:xr-xml-map "ipv6_dhcpv6d:VRFName";
      type string {
        length "0..33";
      }
      description "DHCPVV6 client/subscriber VRF name";
    }
    leaf mac-address {
      xr:xr-xml-map "ipv6_dhcpv6d:MACAddress";
      type string;
      description "Client MAC address";
    }
    leaf ia-id-p-ds {
      xr:xr-xml-map "ipv6_dhcpv6d:IA_ID_PDs";
      type uint32;
      description "Number of ia_id/pd";
    }
    leaf link-local-address {
      xr:xr-xml-map "ipv6_dhcpv6d:LinkLocalAddress";
      type Ipv6-address;
      description "DHCPV6 IPv6 client link local address";
    }
    leaf interface-name {
      xr:xr-xml-map "ipv6_dhcpv6d:InterfaceName";
      type xr:Interface-name;
      description "DHCPV6 access interface to client";
    }
    leaf access-vrf-name {
      xr:xr-xml-map "ipv6_dhcpv6d:AccessVRFName";
      type string {
        length "0..33";
      }
      description "DHCPV6 access VRF name to client";
    }
    leaf server-binding-tags {
      xr:xr-xml-map "ipv6_dhcpv6d:ServerBindingTags";
      type uint8;
      description "DHCPV6 VLAN tag count";
    }
    leaf server-binding-outer-tag {
      xr:xr-xml-map "ipv6_dhcpv6d:ServerBindingOuterTag";
      type uint32;
      description "DHCPV6 VLAN Outer VLAN";
    }
    leaf server-binding-inner-tag {
      xr:xr-xml-map "ipv6_dhcpv6d:ServerBindingInnerTag";
      type uint32;
      description "DHCPV6 VLAN Inner VLAN";
    }
    leaf pool-name {
      xr:xr-xml-map "ipv6_dhcpv6d:PoolName";
      type string {
        length "0..64";
      }
      description "DHCPV6 pool name";
    }
    leaf profile-name {
      xr:xr-xml-map "ipv6_dhcpv6d:ProfileName";
      type string {
        length "0..64";
      }
      description "DHCPV6 profile name";
    }
    leaf framed-ipv6-prefix {
      xr:xr-xml-map "ipv6_dhcpv6d:FramedIPv6Prefix";
      type Ipv6-address;
      description "DHCPV6 framed ipv6 addess used by ND";
    }
    leaf framed-prefix-length {
      xr:xr-xml-map "ipv6_dhcpv6d:FramedPrefixLength";
      type uint8;
      description "DHCPV6 framed ipv6 prefix length used by ND";
    }
    leaf class-name {
      xr:xr-xml-map "ipv6_dhcpv6d:ClassName";
      type string {
        length "0..64";
      }
      description "DHCPV6 class name";
    }
    leaf rx-remote-id {
      xr:xr-xml-map "ipv6_dhcpv6d:RxRemoteID";
      type string {
        length "0..771";
      }
      description "DHCPV6 received Remote ID";
    }
    leaf rx-interface-id {
      xr:xr-xml-map "ipv6_dhcpv6d:RxInterfaceID";
      type string {
        length "0..771";
      }
      description "DHCPV6 received Interface ID";
    }
    leaf prefix-pool-name {
      xr:xr-xml-map "ipv6_dhcpv6d:PrefixPoolName";
      type string {
        length "0..64";
      }
      description "DHCPV6 server prefix pool name";
    }
    leaf address-pool-name {
      xr:xr-xml-map "ipv6_dhcpv6d:AddressPoolName";
      type string {
        length "0..64";
      }
      description "DHCPV6 server address pool name";
    }
    leaf dns-server-count {
      xr:xr-xml-map "ipv6_dhcpv6d:DNSServerCount";
      type uint32;
      description "DNS server count";
    }
    leaf is-nak-next-renew {
      xr:xr-xml-map "ipv6_dhcpv6d:IsNAKNextRenew";
      type boolean;
      description
        "Is true if DHCPv6 next renew from client will be
        NAK'd";
    }
    leaf srg-state {
      xr:xr-xml-map "ipv6_dhcpv6d:SRG_STATE";
      type uint32;
      description "DHCPV6 SRG state";
    }
    leaf srg-intf-role {
      xr:xr-xml-map "ipv6_dhcpv6d:SRG_INTF_ROLE";
      type uint32;
      description "DHCPV6 SRG Intf Role";
    }
    leaf srgp2p {
      xr:xr-xml-map "ipv6_dhcpv6d:SRGP2P";
      type boolean;
      description "SRG P2P Status";
    }
    leaf srg-vrf-name {
      xr:xr-xml-map "ipv6_dhcpv6d:SRG_VRF_NAME";
      type string {
        length "0..33";
      }
      description "DHCPV6 SRG VRF NAME";
    }
  }

  grouping BAG-DHCPV6D-SERVER-BINDINGS-SUMMARY {
    description "DHCPv6 server bindings summary for IANA/IAPD";
    leaf initializing-clients {
      xr:xr-xml-map "ipv6_dhcpv6d:InitializingClients";
      type uint32;
      description "Number of clients in init state";
    }
    leaf dpm-waiting-clients {
      xr:xr-xml-map "ipv6_dhcpv6d:DPMWaitingClients";
      type uint32;
      description
        "Number of clients waiting on DPM to validate
        subscriber";
    }
    leaf daps-waiting-clients {
      xr:xr-xml-map "ipv6_dhcpv6d:DAPSWaitingClients";
      type uint32;
      description
        "Number of clients waiting on DAPS to assign/free
        addr/prefix";
    }
    leaf request-waiting-clients {
      xr:xr-xml-map "ipv6_dhcpv6d:RequestWaitingClients";
      type uint32;
      description
        "Number of clients waiting for a request from the
        client";
    }
    leaf iedge-waiting-clients {
      xr:xr-xml-map "ipv6_dhcpv6d:IedgeWaitingClients";
      type uint32;
      description
        "Number of clients waiting for iedge for the
        session";
    }
    leaf rib-waiting-clients {
      xr:xr-xml-map "ipv6_dhcpv6d:RIBWaitingClients";
      type uint32;
      description "Number of clients in waiting for RIB response";
    }
    leaf bound-clients {
      xr:xr-xml-map "ipv6_dhcpv6d:BoundClients";
      type uint32;
      description "Number of clients in bound state";
    }
  }

  grouping IPV6-DHCPV6D-SERVER-BINDINGS-SUMMARY {
    description "DHCPv6 server bindings summary";

    container iana {
      description "IANA server binding summary";
      uses BAG-DHCPV6D-SERVER-BINDINGS-SUMMARY;
    }

    container iapd {
      description "IAPD server binding summary";
      uses BAG-DHCPV6D-SERVER-BINDINGS-SUMMARY;
    }
    leaf clients {
      xr:xr-xml-map "ipv6_dhcpv6d:Clients";
      type uint32;
      description "Total number of clients";
    }
  }

  grouping BAG-DHCPV6D-PROXY-BINDINGS-SUMMARY {
    description "DHCPv6 proxy bindings summary for IANA/IAPD";
    leaf initializing-clients {
      xr:xr-xml-map "ipv6_dhcpv6d:InitializingClients";
      type uint32;
      description "Number of clients in init state";
    }
    leaf dpm-waiting-clients {
      xr:xr-xml-map "ipv6_dhcpv6d:DPMWaitingClients";
      type uint32;
      description
        "Number of clients waiting on DPM to validate
        subscriber";
    }
    leaf daps-waiting-clients {
      xr:xr-xml-map "ipv6_dhcpv6d:DAPSWaitingClients";
      type uint32;
      description
        "Number of clients waiting on DAPS to assign/free
        prefix(ND)";
    }
    leaf msg-waiting-clients {
      xr:xr-xml-map "ipv6_dhcpv6d:MSGWaitingClients";
      type uint32;
      description
        "Number of clients waiting for a message from the
        client/server";
    }
    leaf iedge-waiting-clients {
      xr:xr-xml-map "ipv6_dhcpv6d:IedgeWaitingClients";
      type uint32;
      description
        "Number of clients waiting on iedge to subscriber
        session";
    }
    leaf rib-waiting-clients {
      xr:xr-xml-map "ipv6_dhcpv6d:RIBWaitingClients";
      type uint32;
      description "Number of clients in waiting on RIB response";
    }
    leaf bound-clients {
      xr:xr-xml-map "ipv6_dhcpv6d:BoundClients";
      type uint32;
      description "Number of clients in bound state";
    }
  }

  grouping IPV6-DHCPV6D-PROXY-BINDINGS-SUMMARY {
    description "DHCPv6 proxy bindings summary";

    container iana {
      description "IANA proxy binding summary";
      uses BAG-DHCPV6D-PROXY-BINDINGS-SUMMARY;
    }

    container iapd {
      description "IAPD proxy binding summary";
      uses BAG-DHCPV6D-PROXY-BINDINGS-SUMMARY;
    }
    leaf clients {
      xr:xr-xml-map "ipv6_dhcpv6d:Clients";
      type uint32;
      description "Total number of clients";
    }
  }

  grouping BAG-DHCPV6D-ADDR-ATTRB {
    description "BAG DHCPV6D ADDR ATTRB";

    list bag-dhcpv6d-addr-attrb {
      description "bag dhcpv6d addr attrb";
      leaf prefix {
        type inet:ipv6-address;
        description "IPv6 prefix";
      }
      leaf prefix-length {
        type uint8;
        description "Prefix length";
      }
      leaf lease-time {
        type uint32;
        units "second";
        description "Lease time in seconds";
      }
      leaf remaining-lease-time {
        type uint32;
        units "second";
        description "Remaining lease time in seconds";
      }
    }
  }

  grouping BAG-DHCPV6D-IA-ID-PD-INFO {
    description "BAG DHCPV6D IA ID PD INFO";

    list bag-dhcpv6d-ia-id-pd-info {
      description "bag dhcpv6d ia id pd info";

      container addresses {
        description "List of addresses in this IA";
        uses BAG-DHCPV6D-ADDR-ATTRB;
      }
      leaf ia-type {
        type Bag-dhcpv6d-ia-id;
        description "IA type";
      }
      leaf ia-id {
        type uint32;
        description "IA_ID of this IA";
      }
      leaf flags {
        type uint32;
        description "FSM Flag for this IA";
      }
      leaf total-address {
        type uint16;
        description "Total address in this IA";
      }
      leaf state {
        type Bag-dhcpv6d-fsm-state;
        description "State";
      }
    }
  }

  grouping IPV6-DHCPV6D-PROXY-BINDING {
    description "DHCPv6 proxy binding entry";

    container ia-id-pd {
      description "List of DHCPv6 IA_ID/PDs";
      uses BAG-DHCPV6D-IA-ID-PD-INFO;
    }
    leaf duid {
      xr:xr-xml-map "ipv6_dhcpv6d:DUID";
      type string;
      description "Client DUID";
    }
    leaf client-flag {
      xr:xr-xml-map "ipv6_dhcpv6d:ClientFlag";
      type uint32;
      description "DHCPV6 client flag";
    }
    leaf subscriber-label {
      xr:xr-xml-map "ipv6_dhcpv6d:SubscriberLabel";
      type uint32;
      description "DHCPV6 subscriber label";
    }
    leaf vrf-name {
      xr:xr-xml-map "ipv6_dhcpv6d:VRFName";
      type string {
        length "0..33";
      }
      description "DHCPVV6 client/subscriber VRF name";
    }
    leaf mac-address {
      xr:xr-xml-map "ipv6_dhcpv6d:MACAddress";
      type string;
      description "Client MAC address";
    }
    leaf ia-id-p-ds {
      xr:xr-xml-map "ipv6_dhcpv6d:IA_ID_PDs";
      type uint32;
      description "Number of ia_id/pd";
    }
    leaf interface-name {
      xr:xr-xml-map "ipv6_dhcpv6d:InterfaceName";
      type xr:Interface-name;
      description "DHCPV6 access interface to client";
    }
    leaf access-vrf-name {
      xr:xr-xml-map "ipv6_dhcpv6d:AccessVRFName";
      type string {
        length "0..33";
      }
      description "DHCPV6 access VRF name to client";
    }
    leaf proxy-binding-tags {
      xr:xr-xml-map "ipv6_dhcpv6d:ProxyBindingTags";
      type uint8;
      description "DHCPV6 VLAN tag count";
    }
    leaf proxy-binding-outer-tag {
      xr:xr-xml-map "ipv6_dhcpv6d:ProxyBindingOuterTag";
      type uint32;
      description "DHCPV6 VLAN Outer VLAN";
    }
    leaf proxy-binding-inner-tag {
      xr:xr-xml-map "ipv6_dhcpv6d:ProxyBindingInnerTag";
      type uint32;
      description "DHCPV6 VLAN Inner VLAN";
    }
    leaf class-name {
      xr:xr-xml-map "ipv6_dhcpv6d:ClassName";
      type string {
        length "0..64";
      }
      description "DHCPV6 class name";
    }
    leaf pool-name {
      xr:xr-xml-map "ipv6_dhcpv6d:PoolName";
      type string {
        length "0..64";
      }
      description "DHCPV6 pool name";
    }
    leaf rx-remote-id {
      xr:xr-xml-map "ipv6_dhcpv6d:RxRemoteID";
      type string {
        length "0..771";
      }
      description "DHCPV6 received Remote ID";
    }
    leaf tx-remote-id {
      xr:xr-xml-map "ipv6_dhcpv6d:TxRemoteID";
      type string {
        length "0..771";
      }
      description "DHCPV6 transmitted Remote ID";
    }
    leaf rx-interface-id {
      xr:xr-xml-map "ipv6_dhcpv6d:RxInterfaceID";
      type string {
        length "0..771";
      }
      description "DHCPV6 received Interface ID";
    }
    leaf tx-interface-id {
      xr:xr-xml-map "ipv6_dhcpv6d:TxInterfaceID";
      type string {
        length "0..771";
      }
      description "DHCPV6 transmitted Interface ID";
    }
    leaf server-ipv6-address {
      xr:xr-xml-map "ipv6_dhcpv6d:ServerIPv6Address";
      type Ipv6-address;
      description "DHCPV6 server IPv6 address";
    }
    leaf profile-name {
      xr:xr-xml-map "ipv6_dhcpv6d:ProfileName";
      type string {
        length "0..65";
      }
      description "DHCPV6 profile name";
    }
    leaf framed-ipv6-prefix {
      xr:xr-xml-map "ipv6_dhcpv6d:FramedIPv6Prefix";
      type Ipv6-address;
      description "DHCPV6 framed ipv6 addess used by ND";
    }
    leaf framed-prefix-length {
      xr:xr-xml-map "ipv6_dhcpv6d:FramedPrefixLength";
      type uint8;
      description "DHCPV6 framed ipv6 prefix length used by ND";
    }
    leaf is-nak-next-renew {
      xr:xr-xml-map "ipv6_dhcpv6d:IsNAKNextRenew";
      type boolean;
      description
        "Is true if DHCP next renew from client will be
        NAK'd";
    }
    leaf srg-state {
      xr:xr-xml-map "ipv6_dhcpv6d:SRG_STATE";
      type uint32;
      description "DHCPV6 SRG state";
    }
    leaf srg-intf-role {
      xr:xr-xml-map "ipv6_dhcpv6d:SRG_INTF_ROLE";
      type uint32;
      description "DHCPV6 SRG Intf Role";
    }
    leaf srgp2p {
      xr:xr-xml-map "ipv6_dhcpv6d:SRGP2P";
      type boolean;
      description "SRG P2P Status";
    }
    leaf srg-vrf-name {
      xr:xr-xml-map "ipv6_dhcpv6d:SRG_VRF_NAME";
      type string {
        length "0..33";
      }
      description "DHCPV6 SRG VRF NAME";
    }
  }

  grouping IPV6-DHCPV6D-PROXY-STATS {
    description "DHCPv6 proxy statistics";

    list ipv6-dhcpv6d-proxy-stat {
      description "ipv6 dhcpv6d proxy stat";

      container statistics {
        description "Proxy statistics";
        uses IPV6-DHCPV6D-FILTERED-STATS;
      }
      leaf vrf-name {
        type string {
          length "0..33";
        }
        description "DHCPv6 L3 VRF name";
      }
    }
  }

  grouping IPV6-DHCPV6D-PROXY-INTERFACE-REFERENCE {
    description "DHCPv6 proxy profile reference";

    list ipv6-dhcpv6d-proxy-interface-reference {
      description "ipv6 dhcpv6d proxy interface reference";
      leaf proxy-reference-interface-name {
        type string {
          length "0..65";
        }
        description "Interface name";
      }
    }
  }

  grouping IPV6-DHCPV6D-PROXY-VRF-REFERENCE {
    description "DHCPv6 proxy profile reference";

    list ipv6-dhcpv6d-proxy-vrf-reference {
      description "ipv6 dhcpv6d proxy vrf reference";
      leaf proxy-reference-vrf-name {
        type string {
          length "0..33";
        }
        description "VRF name";
      }
    }
  }

  grouping IPV6-DHCPV6D-PROXY-IID-REFERENCE {
    description "DHCPv6 proxy profile iid reference";

    list ipv6-dhcpv6d-proxy-iid-reference {
      description "ipv6 dhcpv6d proxy iid reference";
      leaf proxy-iid-interface-name {
        type string {
          length "0..65";
        }
        description "Interface name for interface id";
      }
      leaf proxy-interface-id {
        type string {
          length "0..257";
        }
        description "Interface id";
      }
    }
  }

  grouping IPV6-DHCPV6D-PROXY-PROFILE {
    description "DHCPv6 proxy profile parameters";

    container interface-id-references {
      description "Interface id references";
      uses IPV6-DHCPV6D-PROXY-IID-REFERENCE;
    }

    container vrf-references {
      description "VRF references";
      uses IPV6-DHCPV6D-PROXY-VRF-REFERENCE;
    }

    container interface-references {
      description "Interface references";
      uses IPV6-DHCPV6D-PROXY-INTERFACE-REFERENCE;
    }
    leaf profile-name {
      xr:xr-xml-map "ipv6_dhcpv6d:ProfileName";
      type string {
        length "0..65";
      }
      description "Proxy profile name";
    }
    leaf remote-id {
      xr:xr-xml-map "ipv6_dhcpv6d:RemoteID";
      type string {
        length "0..257";
      }
      description "Remote id";
    }
    leaf profile-link-address {
      xr:xr-xml-map "ipv6_dhcpv6d:ProfileLinkAddress";
      type Ipv6-address;
      description "Link address";
    }
    leaf-list profile-helper-address {
      xr:xr-xml-map "ipv6_dhcpv6d:ProfileHelperAddress";
      type Ipv6-address;
      max-elements "8";
      description "Helper addresses";
    }
    leaf-list vrf-name {
      xr:xr-xml-map "ipv6_dhcpv6d:VRFName";
      type String-vrf;
      max-elements "8";
      description "VRF names";
    }
    leaf-list interface-name {
      xr:xr-xml-map "ipv6_dhcpv6d:InterfaceName";
      type String-ifname;
      max-elements "8";
      description "Interface names";
    }
  }

  grouping IPV6-DHCPV6D-MAC-THROTTLE {
    description "IPv6 DHCP Mac Throttle";
    leaf binding-chaddr {
      xr:xr-xml-map "ipv6_dhcpv6d:binding_chaddr";
      type yang:hex-string;
      description "Client MAC address";
    }
    leaf ifname {
      xr:xr-xml-map "ipv6_dhcpv6d:ifname";
      type string {
        length "0..65";
      }
      description "DHCP access interface";
    }
    leaf state {
      xr:xr-xml-map "ipv6_dhcpv6d:State";
      type uint32;
      description "State of entry";
    }
    leaf time-left {
      xr:xr-xml-map "ipv6_dhcpv6d:TimeLeft";
      type uint32;
      units "second";
      description "Time Left in secs";
    }
  }

  grouping IPV6-DHCPV6D-FILTERED-STATS {
    description "DHCPv6 filtered statistics";
    leaf received-packets {
      xr:xr-xml-map "ipv6_dhcpv6d:ReceivedPackets";
      type uint64;
      description "Received packets";
    }
    leaf transmitted-packets {
      xr:xr-xml-map "ipv6_dhcpv6d:TransmittedPackets";
      type uint64;
      description "Transmitted packets";
    }
    leaf dropped-packets {
      xr:xr-xml-map "ipv6_dhcpv6d:DroppedPackets";
      type uint64;
      description "Dropped packets";
    }
  }

  grouping IPV6-DHCPV6D-TYPE {
    description "DHCPv6 packets";

    container solicit {
      description "DHCPV6 solicit packets";
      uses IPV6-DHCPV6D-FILTERED-STATS;
    }

    container advertise {
      description "DHCPV6 advertise packets";
      uses IPV6-DHCPV6D-FILTERED-STATS;
    }

    container request {
      description "DHCPV6 request packets";
      uses IPV6-DHCPV6D-FILTERED-STATS;
    }

    container reply {
      description "DHCPV6 reply packets";
      uses IPV6-DHCPV6D-FILTERED-STATS;
    }

    container confirm {
      description "DHCPV6 confirm packets";
      uses IPV6-DHCPV6D-FILTERED-STATS;
    }

    container decline {
      description "DHCPV6 decline packets";
      uses IPV6-DHCPV6D-FILTERED-STATS;
    }

    container renew {
      description "DHCPV6 renew packets";
      uses IPV6-DHCPV6D-FILTERED-STATS;
    }

    container rebind {
      description "DHCPV6 rebind packets";
      uses IPV6-DHCPV6D-FILTERED-STATS;
    }

    container release {
      description "DHCPV6 release packets";
      uses IPV6-DHCPV6D-FILTERED-STATS;
    }

    container reconfig {
      description "DHCPV6 reconfig packets";
      uses IPV6-DHCPV6D-FILTERED-STATS;
    }

    container inform {
      description "DHCPV6 inform packets";
      uses IPV6-DHCPV6D-FILTERED-STATS;
    }

    container relay-forward {
      description "DHCPV6 relay forward packets";
      uses IPV6-DHCPV6D-FILTERED-STATS;
    }

    container relay-reply {
      description "DHCPV6 relay reply packets";
      uses IPV6-DHCPV6D-FILTERED-STATS;
    }

    container lease-query {
      description "DHCPV6 lease query packets";
      uses IPV6-DHCPV6D-FILTERED-STATS;
    }

    container lease-query-reply {
      description "DHCPV6 lease query reply packets";
      uses IPV6-DHCPV6D-FILTERED-STATS;
    }

    container lease-query-done {
      description "DHCPV6 lease query done packets";
      uses IPV6-DHCPV6D-FILTERED-STATS;
    }

    container lease-query-data {
      description "DHCPV6 lease query data packets";
      uses IPV6-DHCPV6D-FILTERED-STATS;
    }
  }

  grouping IPV6-DHCPD-DATABASE {
    description "IPv6 DHCP database";
    leaf configured {
      xr:xr-xml-map "ipv6_dhcpv6d:Configured";
      type boolean;
      description "Database feature configured";
    }
    leaf version {
      xr:xr-xml-map "ipv6_dhcpv6d:Version";
      type uint32;
      description "Current file version";
    }
    leaf full-file-write-interval {
      xr:xr-xml-map "ipv6_dhcpv6d:FullFileWriteInterval";
      type uint32;
      units "minute";
      description "Full file write interval in minutes";
    }
    leaf last-full-write-file-name {
      xr:xr-xml-map "ipv6_dhcpv6d:LastFullWriteFileName";
      type string {
        length "0..64";
      }
      description "Last full write file name";
    }
    leaf last-full-write-time {
      xr:xr-xml-map "ipv6_dhcpv6d:LastFullWriteTime";
      type uint32;
      description "Last full write time since epoch";
    }
    leaf full-file-write-count {
      xr:xr-xml-map "ipv6_dhcpv6d:FullFileWriteCount";
      type uint32;
      description "Full file write count";
    }
    leaf failed-full-file-write-count {
      xr:xr-xml-map "ipv6_dhcpv6d:FailedFullFileWriteCount";
      type uint32;
      description "Failed full file write count";
    }
    leaf full-file-record-count {
      xr:xr-xml-map "ipv6_dhcpv6d:FullFileRecordCount";
      type uint32;
      description "Full file record count";
    }
    leaf last-full-file-write-error-timestamp {
      xr:xr-xml-map "ipv6_dhcpv6d:LastFullFileWriteErrorTimestamp";
      type uint32;
      description
        "Last full file write error timestamp since epoch";
    }
    leaf incremental-file-write-interval {
      xr:xr-xml-map "ipv6_dhcpv6d:IncrementalFileWriteInterval";
      type uint32;
      units "minute";
      description "Incremental file write interval in minutes";
    }
    leaf last-incremental-write-file-name {
      xr:xr-xml-map "ipv6_dhcpv6d:LastIncrementalWriteFileName";
      type string {
        length "0..64";
      }
      description "Last incremental write file name";
    }
    leaf last-incremental-write-time {
      xr:xr-xml-map "ipv6_dhcpv6d:LastIncrementalWriteTime";
      type uint32;
      description "Last incremental write time since epoch";
    }
    leaf incremental-file-write-count {
      xr:xr-xml-map "ipv6_dhcpv6d:IncrementalFileWriteCount";
      type uint32;
      description "Incremental file write count";
    }
    leaf failed-incremental-file-write-count {
      xr:xr-xml-map "ipv6_dhcpv6d:FailedIncrementalFileWriteCount";
      type uint32;
      description "Failed incremental file write count";
    }
    leaf incremental-file-record-count {
      xr:xr-xml-map "ipv6_dhcpv6d:IncrementalFileRecordCount";
      type uint32;
      description "Incremental file record count";
    }
    leaf last-incremental-file-write-error-timestamp {
      xr:xr-xml-map "ipv6_dhcpv6d:LastIncrementalFileWriteErrorTime"+
        "stamp";
      type uint32;
      description
        "Last incremental file write error timestamp
        since epoch";
    }
  }
}
