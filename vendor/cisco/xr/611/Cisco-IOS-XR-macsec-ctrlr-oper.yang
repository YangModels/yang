module Cisco-IOS-XR-macsec-ctrlr-oper {

  /*** NAMESPACE / PREFIX DEFINITION ***/

  namespace "http://cisco.com/ns"+
    "/yang/Cisco-IOS-XR-macsec-ctrlr-oper";


  prefix "macsec-ctrlr-oper";

  /*** LINKAGE (IMPORTS / INCLUDES) ***/

  import Cisco-IOS-XR-types { prefix "xr"; }

  include Cisco-IOS-XR-macsec-ctrlr-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR macsec-ctrlr package operational data.

     This module contains definitions
     for the following management objects:
       macsec-ctrlr-oper: Macsec controller data

     Copyright (c) 2013-2016 by Cisco Systems, Inc.
     All rights reserved.";

  revision "2015-11-09" {
    description
      "IOS XR 6.0 revision.";
  }


  container macsec-ctrlr-oper {
    xr:xr-xml-map "macsec_ctrlr_oper:MacsecCtrlrOper";
    config false;
    description "Macsec controller data";

    container macsec-ctrlr-ports {
      xr:xr-xml-map "macsec_ctrlr_oper:MacsecCtrlrPortTable";
      description "All Macsec Controller Port operational data";

      list macsec-ctrlr-port {
        xr:xr-xml-map "macsec_ctrlr_oper:MacsecCtrlrPort";
        key "name";
        description "Controller name";

        container macsec-ctrlr-info {
          xr:xr-xml-map "macsec_ctrlr_oper:MacsecCtrlrInfo";
          description "Macsec Controller operational data";
          uses MACSEC-CTRLR-IF-STATUS;
        }
        leaf name {
          xr:xr-xml-map "macsec_ctrlr_oper:Name";
          type xr:Interface-name;
          description "Port name";
        }
      }
    }
  }
}
