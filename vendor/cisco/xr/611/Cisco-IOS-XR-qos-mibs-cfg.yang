module Cisco-IOS-XR-qos-mibs-cfg {

  /*** NAMESPACE / PREFIX DEFINITION ***/

  namespace "http://cisco.com/ns/yang/Cisco-IOS-XR-qos-mibs-cfg";


  prefix "qos-mibs-cfg";

  /*** LINKAGE (IMPORTS / INCLUDES) ***/

  import Cisco-IOS-XR-types { prefix "xr"; }

  import Cisco-IOS-XR-snmp-agent-cfg { prefix "a1"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR qos-mibs package configuration.

     This YANG module augments the
       Cisco-IOS-XR-snmp-agent-cfg
     module with configuration data.

     Copyright (c) 2013-2016 by Cisco Systems, Inc.
     All rights reserved.";

  revision "2015-11-09" {
    description
      "IOS XR 6.0 revision.";
  }


  augment "/a1:mib" {

    container cb-qosmib {
      xr:xr-xml-map "cbqosmib_cfg:CBQoSMIB";
      description "CBQoSMIB configuration";

      container cache {
        xr:xr-xml-map "cbqosmib_cfg:Cache";
        description "CBQoSMIB statistics data caching";
        leaf enable {
          xr:xr-xml-map "cbqosmib_cfg:Enable";
          type empty;
          description "Enable CBQoSMIB statistics data caching";
        }
        leaf refresh-time {
          xr:xr-xml-map "cbqosmib_cfg:RefreshTime";
          type uint32 {
            range "5..60";
          }
          units "second";
          description "Cache refresh time in seconds";
        }
        leaf service-policy-count {
          xr:xr-xml-map "cbqosmib_cfg:ServicePolicyCount";
          type uint32 {
            range "1..5000";
          }
          description
            "Maximum number of service policies to cache
            the statistics for";
        }
      }
      leaf member-interface-stats {
        xr:xr-xml-map "cbqosmib_cfg:MemberInterfaceStats";
        type empty;
        description
          "Enable bundle member interface statistics
          retrieval.";
      }
      leaf persist {
        xr:xr-xml-map "cbqosmib_cfg:Persist";
        type empty;
        description
          "Persist CBQoSMIB config, service-policy and
          object indices";
      }
    }
    description
      "This augment extends the configuration data of
      'Cisco-IOS-XR-snmp-agent-cfg'";
  }
}
