module Cisco-IOS-XR-ipv6-ospfv3-oper {

  /*** NAMESPACE / PREFIX DEFINITION ***/

  namespace "http://cisco.com/ns/yang/Cisco-IOS-XR-ipv6-ospfv3-oper";


  prefix "ipv6-ospfv3-oper";

  /*** LINKAGE (IMPORTS / INCLUDES) ***/

  import ietf-inet-types { prefix "inet"; }

  import Cisco-IOS-XR-types { prefix "xr"; }

  include Cisco-IOS-XR-ipv6-ospfv3-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ipv6-ospfv3 package operational data.

     This module contains definitions
     for the following management objects:
       ospfv3: OSPFv3 operational information 

     Copyright (c) 2013-2016 by Cisco Systems, Inc.
     All rights reserved.";

  revision "2015-11-09" {
    description
      "IOS XR 6.0 revision.";
  }

  typedef Ospfv3-lsa {
    type enumeration {
      enum link-lsa {
        value 8;
        description "Link LSA";
      }
      enum grace-lsa {
        value 11;
        description "Grace LSA";
      }
      enum router {
        value 8193;
        description "Router LSA";
      }
      enum network {
        value 8194;
        description "Network LSA";
      }
      enum inter-area-prefix {
        value 8195;
        description "Inter-Area Prefix LSA";
      }
      enum inter-area-router {
        value 8196;
        description "Inter-Area Router LSA";
      }
      enum nssa-external {
        value 8199;
        description "NSSA External LSA";
      }
      enum intra-area-prefix {
        value 8201;
        description "Intra-Area Prefix LSA";
      }
      enum external {
        value 16389;
        description "External LSA";
      }
      enum opaque-link {
        value 32768;
        description "Opaque LSALink Scope";
      }
      enum opaque-area {
        value 40960;
        description "Opaque LSA Area Scope";
      }
      enum opaque-as {
        value 49152;
        description "Opaque LSA AS Scope";
      }
      enum unknown {
        value 57344;
        description "Unknown Reserved Scope LSAs";
      }
    }
    description "Ospfv3 lsa";
  }

  grouping FLOOD-LIST-PROCESS-TABLE {
    description "Common node of default-vrf, vrf";

    container flood-list-process-table {
      xr:xr-xml-map "ipv6-ospfv3_oper:FloodListProcessTable";
      description
        "OSPFv3 flood list information table for all
        areas";
      uses FLOOD-LIST;
    }
  }

  grouping FLOOD-LIST {
    description
      "Common node of flood-list-table,
      flood-list-process-table";

    list flood {
      xr:xr-xml-map "ipv6-ospfv3_oper:FloodList";
      key "interface-name";
      description "OSPFv3 flood list information";
      leaf interface-name {
        xr:xr-xml-map "ipv6-ospfv3_oper:InterfaceName";
        type xr:Interface-name;
        description "Interface name";
      }
      uses OSPFV3-EDM-FLOOD-LIST;
    }
  }

  grouping BORDER-ROUTER-TABLE {
    description "Common node of default-vrf, vrf";

    container border-routers {
      xr:xr-xml-map "ipv6-ospfv3_oper:BorderRouterTable";
      description "OSPFv3 border router information table";

      list border-router {
        xr:xr-xml-map "ipv6-ospfv3_oper:BorderRouter";
        key "border-router-id";
        description "OSPFv3 border router information";
        leaf border-router-id {
          xr:xr-xml-map "ipv6-ospfv3_oper:BorderRouterID";
          type inet:ipv4-address-no-zone;
          description "Router address";
        }
        uses OSPFV3-EDM-BORDER-ROUTER;
      }
    }
  }

  grouping FAST-REROUTE-TABLE {
    description "Common node of default-vrf, vrf";

    container fast-reroutes {
      xr:xr-xml-map "ipv6-ospfv3_oper:FastRerouteTable";
      description "OSPFv3 fast reroute topology information table";

      list fast-reroute {
        xr:xr-xml-map "ipv6-ospfv3_oper:FastReroute";
        description "OSPFv3 fast reroute topology information";
        leaf router-id {
          xr:xr-xml-map "ipv6-ospfv3_oper:RouterID";
          type inet:ipv4-address-no-zone;
          description "Router ID";
        }
        leaf area-id {
          xr:xr-xml-map "ipv6-ospfv3_oper:AreaID";
          type int32;
          description "AreaID";
        }
        uses OSPFV3-SH-IPFRR-TOPO;
      }
    }
  }

  grouping AREA-TABLE {
    description "Common node of default-vrf, vrf";

    container areas {
      xr:xr-xml-map "ipv6-ospfv3_oper:AreaTable";
      description "OSPFv3 area table";

      list area {
        xr:xr-xml-map "ipv6-ospfv3_oper:Area";
        key "area-id";
        description "Per-area information";

        container neighbor-detail-table {
          xr:xr-xml-map "ipv6-ospfv3_oper:NeighborDetailTable";
          description "OSPFv3 area neighbor information table";
          uses NEIGHBOR-DETAIL;
        }

        container interface-brief-table {
          xr:xr-xml-map "ipv6-ospfv3_oper:InterfaceBriefTable";
          description
            "OSPFv3 interface brief information table for
            an area";
          uses INTERFACE-BRIEF;
        }

        container request-list-table {
          xr:xr-xml-map "ipv6-ospfv3_oper:RequestListTable";
          description "OSPFv3 request list information in an area";
          uses REQUEST-LIST;
        }

        container neighbor-table {
          xr:xr-xml-map "ipv6-ospfv3_oper:NeighborTable";
          description "OSPFv3 neighbor information table";
          uses NEIGHBOR;
        }

        container interface-table {
          xr:xr-xml-map "ipv6-ospfv3_oper:InterfaceTable";
          description
            "OSPFv3 interface information table for an area";
          uses INTERFACE;
        }

        container flood-list-table {
          xr:xr-xml-map "ipv6-ospfv3_oper:FloodListTable";
          description
            "OSPFv3 flood list information table for an
            area";
          uses FLOOD-LIST;
        }

        container retransmission-list-table {
          xr:xr-xml-map "ipv6-ospfv3_oper:RetransmissionListTable";
          description
            "OSPFv3 retransmission list information table
            in an area";
          uses RETRANSMISSION-LIST;
        }
        leaf area-id {
          xr:xr-xml-map "ipv6-ospfv3_oper:AreaID";
          type int32;
          description "Area ID";
        }
        uses DATABASE-TABLE;
        uses DATABASE-SUMMARY-TABLE;
      }
    }
  }

  grouping EXTERNAL-ROUTE-TABLE {
    description "Common node of default-vrf, vrf";

    container external-routes {
      xr:xr-xml-map "ipv6-ospfv3_oper:ExternalRouteTable";
      description "OSPFv3 external route information table";

      list external-route {
        xr:xr-xml-map "ipv6-ospfv3_oper:ExternalRoute";
        description "OSPFv3 external route information";
        leaf prefix {
          xr:xr-xml-map "ipv6-ospfv3_oper:Prefix";
          type inet:ipv6-address-no-zone;
          description "Route prefix";
        }
        leaf prefix-length {
          xr:xr-xml-map "ipv6-ospfv3_oper:PrefixLength";
          type xr:Ipv6-prefix-length;
          description "Prefix length";
        }
        uses OSPFV3-EDM-TOPOLOGY-EXTERNAL;
      }
    }
  }

  grouping NEIGHBOR-DETAIL-PROCESS-TABLE {
    description "Common node of default-vrf, vrf";

    container neighbor-detail-process-table {
      xr:xr-xml-map "ipv6-ospfv3_oper:NeighborDetailProcessTable";
      description "OSPFv3 neighbor information table for all areas";
      uses NEIGHBOR-DETAIL;
    }
  }

  grouping INTERFACE {
    description
      "Common node of interface-table,
      interface-process-table";

    list interface {
      xr:xr-xml-map "ipv6-ospfv3_oper:Interface";
      key "interface-name";
      description "OSPFv3 interface information";
      leaf interface-name {
        xr:xr-xml-map "ipv6-ospfv3_oper:InterfaceName";
        type xr:Interface-name;
        description "Interface name";
      }
      uses OSPFV3-EDM-INTERFACE;
    }
  }

  grouping INTERFACE-BRIEF {
    description
      "Common node of interface-brief-table,
      interface-brief-process-table";

    list interface-brief {
      xr:xr-xml-map "ipv6-ospfv3_oper:InterfaceBrief";
      key "interface-name";
      description "Interface brief information";
      leaf interface-name {
        xr:xr-xml-map "ipv6-ospfv3_oper:InterfaceName";
        type xr:Interface-name;
        description "Interface name";
      }
      uses OSPFV3-EDM-INTF-BRIEF;
    }
  }

  grouping ROUTE-SUMMARY {
    description "Common node of default-vrf, vrf";

    container route-summary {
      xr:xr-xml-map "ipv6-ospfv3_oper:RouteSummary";
      description "Summarize OSPFv3 local RIB tables";
      uses OSPFV3-EDM-ROUTE-SUM;
    }
  }

  grouping NEIGHBOR-DETAIL {
    description
      "Common node of neighbor-detail-process-table,
      neighbor-detail-table";

    list neighbor-detail {
      xr:xr-xml-map "ipv6-ospfv3_oper:NeighborDetail";
      description "OSPFv3 neighbor detail information";
      leaf interface-name {
        xr:xr-xml-map "ipv6-ospfv3_oper:InterfaceName";
        type xr:Interface-name;
        description "Interface name";
      }
      leaf neighbor-address {
        xr:xr-xml-map "ipv6-ospfv3_oper:NeighborAddress";
        type inet:ipv4-address-no-zone;
        description "Neighbor ID";
      }
      uses OSPFV3-EDM-NEIGHBOR;
    }
  }

  grouping LSA {
    description "Common node of lsa-table, lsa-internal-table";

    list lsa {
      xr:xr-xml-map "ipv6-ospfv3_oper:LSA";
      description "Database LSA information";
      leaf area-id {
        xr:xr-xml-map "ipv6-ospfv3_oper:AreaID";
        type int32;
        description "Area ID";
      }
      leaf ls-type {
        xr:xr-xml-map "ipv6-ospfv3_oper:LSType";
        type Ospfv3-lsa;
        description "LSA type";
      }
      leaf advertising-router {
        xr:xr-xml-map "ipv6-ospfv3_oper:AdvertisingRouter";
        type inet:ipv4-address-no-zone;
        description "Advertising Router ID";
      }
      leaf ls-id {
        xr:xr-xml-map "ipv6-ospfv3_oper:LS_ID";
        type int32;
        description "Link state ID";
      }
      leaf interface-name {
        xr:xr-xml-map "ipv6-ospfv3_oper:InterfaceName";
        type xr:Interface-name;
        description "InterfaceName";
      }
      uses OSPFV3-EDM-DATABASE-LSAINFO;
    }
  }

  grouping VIRTUAL-LINK {
    description "Common node of default-vrf, vrf";

    container virtual-link {
      xr:xr-xml-map "ipv6-ospfv3_oper:VirtualLink";
      description "Virtual link information";
      uses OSPFV3-EDM-VIRTUAL-LINKS;
    }
  }

  grouping RETRANSMISSION-LIST {
    description
      "Common node of retransmission-list-process-table,
      retransmission-list-table";

    list retransmission {
      xr:xr-xml-map "ipv6-ospfv3_oper:RetransmissionList";
      description "OSPFv3 retransmission list information";
      leaf interface-name {
        xr:xr-xml-map "ipv6-ospfv3_oper:InterfaceName";
        type xr:Interface-name;
        description "Interface name";
      }
      leaf neighbor-address {
        xr:xr-xml-map "ipv6-ospfv3_oper:NeighborAddress";
        type inet:ipv4-address-no-zone;
        description "Neighbor address";
      }
      uses OSPFV3-EDM-RETRANS;
    }
  }

  grouping RETRANSMISSION-LIST-PROCESS-TABLE {
    description "Common node of default-vrf, vrf";

    container retransmission-list-process-table {
      xr:xr-xml-map "ipv6-ospfv3_oper:RetransmissionListProcessTabl"+
        "e";
      description
        "OSPFv3 retransmission list information table for
        all areas";
      uses RETRANSMISSION-LIST;
    }
  }

  grouping SUMMARY-PREFIX-TABLE {
    description "Common node of default-vrf, vrf";

    container summary-prefixes {
      xr:xr-xml-map "ipv6-ospfv3_oper:SummaryPrefixTable";
      description "Summary prefix information table";

      list summary-prefix {
        xr:xr-xml-map "ipv6-ospfv3_oper:SummaryPrefix";
        description "Summary prefix information";
        leaf prefix {
          xr:xr-xml-map "ipv6-ospfv3_oper:Prefix";
          type inet:ipv6-address-no-zone;
          description "Summary prefix";
        }
        leaf prefix-length {
          xr:xr-xml-map "ipv6-ospfv3_oper:PrefixLength";
          type xr:Ipv6-prefix-length;
          description "Prefix length";
        }
        uses OSPFV3-EDM-SUMMARY-PREFIX;
      }
    }
  }

  grouping AREA-INFORMATION-TABLE {
    description "Common node of default-vrf, vrf";

    container area-informations {
      xr:xr-xml-map "ipv6-ospfv3_area_oper:AreaInformationTable";
      description "OSPFv3 area information table";

      list area-information {
        xr:xr-xml-map "ipv6-ospfv3_area_oper:AreaInformation";
        key "area-id";
        description "OSPFv3 area information";
        leaf area-id {
          xr:xr-xml-map "ipv6-ospfv3_area_oper:AreaID";
          type int32;
          description "Area ID";
        }
        uses OSPFV3-EDM-AREA;
      }
    }
  }

  grouping SHAM-LINK-TABLE {
    description "Common node of default-vrf, vrf";

    container sham-link-table {
      xr:xr-xml-map "ipv6-ospfv3_oper:ShamLinkTable";
      description "Sham link information";
      uses OSPFV3-SH-SHAM-LINKS;
    }
  }

  grouping NEIGHBOR {
    description
      "Common node of neighbor-process-table,
      neighbor-table";

    list neighbor {
      xr:xr-xml-map "ipv6-ospfv3_oper:Neighbor";
      description "OSPFv3 neighbor detail information";
      leaf interface-name {
        xr:xr-xml-map "ipv6-ospfv3_oper:InterfaceName";
        type xr:Interface-name;
        description "Interface name";
      }
      leaf neighbor-address {
        xr:xr-xml-map "ipv6-ospfv3_oper:NeighborAddress";
        type inet:ipv4-address-no-zone;
        description "Neighbor ID";
      }
      uses OSPFV3-EDM-NEIGHBOR;
    }
  }

  grouping SUMMARY {
    description "Common node of default-vrf, vrf";

    container summary {
      xr:xr-xml-map "ipv6-ospfv3_oper:Summary";
      description "OSPFv3 summary";

      container protocol {
        xr:xr-xml-map "ipv6-ospfv3_oper:Protocol";
        description "OSPFv3 protocol summary";
        uses OSPFV3-EDM-PROTOCOL;
      }

      container ospfv3 {
        xr:xr-xml-map "ipv6-ospfv3_oper:OSPFv3";
        description "OSPFv3 summary";
        uses OSPFV3-EDM-SUMMARY;
      }

      container route {
        xr:xr-xml-map "ipv6-ospfv3_oper:Route";
        description "OSPFv3 route summary";
        uses OSPFV3-EDM-ROUTE-SUM;
      }
    }
  }

  grouping REQUEST-LIST-PROCESS-TABLE {
    description "Common node of default-vrf, vrf";

    container request-list-process-table {
      xr:xr-xml-map "ipv6-ospfv3_oper:RequestListProcessTable";
      description "OSPFv3 request list information for all areas";
      uses REQUEST-LIST;
    }
  }

  grouping DATABASE-TABLE {
    description "Common node of area, default-vrf, vrf";

    container database-table {
      xr:xr-xml-map "ipv6-ospfv3_oper:DatabaseTable";
      description "OSPF Link State Database";

      container lsa-table {
        xr:xr-xml-map "ipv6-ospfv3_oper:LSATable";
        description "Database LSA information";
        uses LSA;
      }

      container lsa-internal-table {
        xr:xr-xml-map "ipv6-ospfv3_oper:LSAInternalTable";
        description "Database LSA information";
        uses LSA;
      }
    }
  }

  grouping CONNECTED-ROUTE-TABLE {
    description "Common node of default-vrf, vrf";

    container connected-routes {
      xr:xr-xml-map "ipv6-ospfv3_oper:ConnectedRouteTable";
      description "OSPFv3 connected route information table";

      list connected-route {
        xr:xr-xml-map "ipv6-ospfv3_oper:ConnectedRoute";
        description "OSPFv3 connected route information";
        leaf prefix {
          xr:xr-xml-map "ipv6-ospfv3_oper:Prefix";
          type inet:ipv6-address-no-zone;
          description "Route prefix";
        }
        leaf prefix-length {
          xr:xr-xml-map "ipv6-ospfv3_oper:PrefixLength";
          type xr:Ipv6-prefix-length;
          description "Prefix length";
        }
        uses OSPFV3-EDM-TOPOLOGY-CONNECTED;
      }
    }
  }

  grouping BAD-CHECKSUM-TABLE {
    description "Common node of default-vrf, vrf";

    container bad-checksums {
      xr:xr-xml-map "ipv6-ospfv3_oper:BadChecksumTable";
      description "Bad Checksum Packets information table";

      list bad-checksum {
        xr:xr-xml-map "ipv6-ospfv3_oper:BadChecksum";
        key "packet-number";
        description "Bad Checksum Packet information";
        leaf packet-number {
          xr:xr-xml-map "ipv6-ospfv3_oper:PacketNumber";
          type uint32 {
            range "0..9";
          }
          description "Bad Checksum Packets number";
        }
        uses OSPFV3-SH-BAD-CHECKSUM;
      }
    }
  }

  grouping DATABASE-SUMMARY-TABLE {
    description "Common node of default-vrf, vrf, area";

    container database-summary-table {
      xr:xr-xml-map "ipv6-ospfv3_oper:DatabaseSummaryTable";
      description "Database summary table";

      container database-summary {
        xr:xr-xml-map "ipv6-ospfv3_oper:DatabaseSummary";
        description "Database Summary information";
        uses OSPFV3-EDM-DB-SUMMARY;
      }
    }
  }

  grouping REQUEST-LIST {
    description
      "Common node of request-list-process-table,
      request-list-table";

    list request {
      xr:xr-xml-map "ipv6-ospfv3_oper:RequestList";
      description "OSPFv3 request list information";
      leaf interface-name {
        xr:xr-xml-map "ipv6-ospfv3_oper:InterfaceName";
        type xr:Interface-name;
        description "Interface name";
      }
      leaf neighbor-address {
        xr:xr-xml-map "ipv6-ospfv3_oper:NeighborAddress";
        type inet:ipv4-address-no-zone;
        description "Neighbor address";
      }
      uses OSPFV3-EDM-REQUEST;
    }
  }

  grouping INTERFACE-BRIEF-PROCESS-TABLE {
    description "Common node of default-vrf, vrf";

    container interface-brief-process-table {
      xr:xr-xml-map "ipv6-ospfv3_oper:InterfaceBriefProcessTable";
      description
        "OSPFv3 interface brief information table for all
        areas";
      uses INTERFACE-BRIEF;
    }
  }

  grouping NEIGHBOR-PROCESS-TABLE {
    description "Common node of default-vrf, vrf";

    container neighbor-process-table {
      xr:xr-xml-map "ipv6-ospfv3_oper:NeighborProcessTable";
      description "OSPFv3 neighbor information table for all areas";
      uses NEIGHBOR;
    }
  }

  grouping INTERNAL-ROUTE-TABLE {
    description "Common node of default-vrf, vrf";

    container internal-routes {
      xr:xr-xml-map "ipv6-ospfv3_oper:InternalRouteTable";
      description "OSPFv3 internal route information table";

      list internal-route {
        xr:xr-xml-map "ipv6-ospfv3_oper:InternalRoute";
        description "OSPFv3 internal route information";
        leaf prefix {
          xr:xr-xml-map "ipv6-ospfv3_oper:Prefix";
          type inet:ipv6-address-no-zone;
          description "Route prefix";
        }
        leaf prefix-length {
          xr:xr-xml-map "ipv6-ospfv3_oper:PrefixLength";
          type xr:Ipv6-prefix-length;
          description "Prefix length";
        }
        uses OSPFV3-EDM-TOPOLOGY-INTERNAL;
      }
    }
  }

  grouping REDISTRIBUTION-TABLE {
    description "Common node of default-vrf, vrf";

    container redistributions {
      xr:xr-xml-map "ipv6-ospfv3_oper:RedistributionTable";
      description "Redistribution information table";

      list redistribution {
        xr:xr-xml-map "ipv6-ospfv3_oper:Redistribution";
        description "Redistribution information";
        leaf protocol-name {
          xr:xr-xml-map "ipv6-ospfv3_oper:ProtocolName";
          type xr:Cisco-ios-xr-string;
          description "Protocol name that is redistributed";
        }
        leaf process-name {
          xr:xr-xml-map "ipv6-ospfv3_oper:ProcessName";
          type xr:Cisco-ios-xr-string;
          description
            "Process name of a protocolbeing redistributed ";
        }
        uses OSPFV3-EDM-REDIST;
      }
    }
  }

  grouping INTERFACE-PROCESS-TABLE {
    description "Common node of default-vrf, vrf";

    container interface-process-table {
      xr:xr-xml-map "ipv6-ospfv3_oper:InterfaceProcessTable";
      description
        "OSPFv3 interface information table for all areas";
      uses INTERFACE;
    }
  }

  grouping PROTOCOL-AREA-TABLE {
    description "Common node of default-vrf, vrf";

    container protocol-areas {
      xr:xr-xml-map "ipv6-ospfv3_oper:ProtocolAreaTable";
      description "Protocol area table ";

      list protocol-area {
        xr:xr-xml-map "ipv6-ospfv3_oper:ProtocolArea";
        key "area-id";
        description "Area information ";
        leaf area-id {
          xr:xr-xml-map "ipv6-ospfv3_oper:AreaID";
          type inet:ipv4-address-no-zone;
          description "Area ID";
        }
        uses OSPFV3-EDM-PROTO-AREA;
      }
    }
  }

  container ospfv3 {
    xr:xr-xml-map "ipv6-ospfv3_oper:OSPFv3";
    config false;
    description "OSPFv3 operational information ";

    container processes {
      xr:xr-xml-map "ipv6-ospfv3_oper:ProcessTable";
      description "OSPFv3 Process Table";

      list process {
        xr:xr-xml-map "ipv6-ospfv3_oper:Process";
        key "process-name";
        description
          "OSPFv3 Operational data for a particular OSPFv3
          process ";

        container vrfs {
          xr:xr-xml-map "ipv6-ospfv3_oper:VRFTable";
          description "Table for each VRF";

          list vrf {
            xr:xr-xml-map "ipv6-ospfv3_oper:VRF";
            key "vrf-name";
            description
              "Operational data for a particular VRF
              (instance) in the OSPFv3 process";
            leaf vrf-name {
              xr:xr-xml-map "ipv6-ospfv3_oper:VRFName";
              type xr:Cisco-ios-xr-string;
              description "VRF Name";
            }
            uses SUMMARY-PREFIX-TABLE;
            uses BORDER-ROUTER-TABLE;
            uses SHAM-LINK-TABLE;
            uses AREA-INFORMATION-TABLE;
            uses DATABASE-TABLE;
            uses INTERFACE-PROCESS-TABLE;
            uses REDISTRIBUTION-TABLE;
            uses EXTERNAL-ROUTE-TABLE;
            uses REQUEST-LIST-PROCESS-TABLE;
            uses VIRTUAL-LINK;
            uses FLOOD-LIST-PROCESS-TABLE;
            uses ROUTE-SUMMARY;
            uses AREA-TABLE;
            uses INTERNAL-ROUTE-TABLE;
            uses PROTOCOL-AREA-TABLE;
            uses CONNECTED-ROUTE-TABLE;
            uses SUMMARY;
            uses RETRANSMISSION-LIST-PROCESS-TABLE;
            uses BAD-CHECKSUM-TABLE;
            uses DATABASE-SUMMARY-TABLE;
            uses NEIGHBOR-PROCESS-TABLE;
            uses FAST-REROUTE-TABLE;
            uses INTERFACE-BRIEF-PROCESS-TABLE;
            uses NEIGHBOR-DETAIL-PROCESS-TABLE;
          }
        }

        container default-vrf {
          xr:xr-xml-map "ipv6-ospfv3_oper:DefaultVRF";
          description
            "Operational data for the default VRF
            (instance) in the OSPFv3 process";
          uses SUMMARY-PREFIX-TABLE;
          uses BORDER-ROUTER-TABLE;
          uses SHAM-LINK-TABLE;
          uses AREA-INFORMATION-TABLE;
          uses DATABASE-TABLE;
          uses INTERFACE-PROCESS-TABLE;
          uses REDISTRIBUTION-TABLE;
          uses EXTERNAL-ROUTE-TABLE;
          uses REQUEST-LIST-PROCESS-TABLE;
          uses VIRTUAL-LINK;
          uses FLOOD-LIST-PROCESS-TABLE;
          uses ROUTE-SUMMARY;
          uses AREA-TABLE;
          uses INTERNAL-ROUTE-TABLE;
          uses PROTOCOL-AREA-TABLE;
          uses CONNECTED-ROUTE-TABLE;
          uses SUMMARY;
          uses RETRANSMISSION-LIST-PROCESS-TABLE;
          uses BAD-CHECKSUM-TABLE;
          uses DATABASE-SUMMARY-TABLE;
          uses NEIGHBOR-PROCESS-TABLE;
          uses FAST-REROUTE-TABLE;
          uses INTERFACE-BRIEF-PROCESS-TABLE;
          uses NEIGHBOR-DETAIL-PROCESS-TABLE;
        }
        leaf process-name {
          xr:xr-xml-map "ipv6-ospfv3_oper:ProcessName";
          type xr:Cisco-ios-xr-string;
          description "Particular OSPFv3 process";
        }
      }
    }
  }
}
