module Cisco-IOS-XR-bundlemgr-oper {

  /*** NAMESPACE / PREFIX DEFINITION ***/

  namespace "http://cisco.com/ns/yang/Cisco-IOS-XR-bundlemgr-oper";


  prefix "bundlemgr-oper";

  /*** LINKAGE (IMPORTS / INCLUDES) ***/

  import Cisco-IOS-XR-types { prefix "xr"; }

  include Cisco-IOS-XR-bundlemgr-oper-sub2 {
    revision-date 2015-11-09;
  }

  include Cisco-IOS-XR-bundlemgr-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR bundlemgr package operational data.

     This module contains definitions
     for the following management objects:
       lacp-bundles: LACP bundle data
       bundle-information: bundle information
       lacp-data: lacp data
       bundles: bundles
       lacp-bundle-members: lacp bundle members
       bundles-adjacency: bundles adjacency

     Copyright (c) 2013-2016 by Cisco Systems, Inc.
     All rights reserved.";

  revision "2015-11-09" {
    description
      "IOS XR 6.0 revision.";
  }


  container lacp-bundles {
    xr:xr-xml-map "bundlemgr_lacp_bdl_oper:LACPBundles";
    config false;
    description "LACP bundle data";

    container bundles {
      xr:xr-xml-map "bundlemgr_lacp_bdl_oper:BundleTable";
      description "LACP bundle data";

      list bundle {
        xr:xr-xml-map "bundlemgr_lacp_bdl_oper:Bundle";
        key "bundle-interface";
        description "LACP Bundle interface";

        container data {
          xr:xr-xml-map "bundlemgr_lacp_bdl_oper:Data";
          description "Data for each Bundle";
          uses LACP-BUNDLE-DATA;
        }

        container members {
          xr:xr-xml-map "bundlemgr_lacp_bdl_oper:MemberTable";
          description "LACP Member interface";

          list member {
            xr:xr-xml-map "bundlemgr_lacp_bdl_oper:Member";
            key "member-interface";
            description "Member information";
            leaf member-interface {
              xr:xr-xml-map "bundlemgr_lacp_bdl_oper:MemberInterfac"+
                "e";
              type xr:Interface-name;
              description "Member interface";
            }
            uses BM-MEMBER-DATA;
          }
        }
        leaf bundle-interface {
          xr:xr-xml-map "bundlemgr_lacp_bdl_oper:BundleInterface";
          type xr:Interface-name;
          description "LACP Bundle interface";
        }
      }
    }
  }

  container bundle-information {
    xr:xr-xml-map "bundlemgr_bmd_oper:BundleInformation";
    config false;
    description "bundle information";

    container bfd-counters {
      xr:xr-xml-map "bundlemgr_bmd_oper:BFDCounters";
      description
        "BFD counters information for bundles and members";

      container bfd-counters-bundles {
        xr:xr-xml-map "bundlemgr_bmd_oper:BFDCountersBundleTable";
        description
          "Bundle interfaces with BFD counters information";

        list bfd-counters-bundle {
          xr:xr-xml-map "bundlemgr_bmd_oper:BFDCountersBundle";
          key "bundle-interface";
          description "Bundle interface";

          container bfd-counters-bundle-descendant {
            xr:xr-xml-map "bundlemgr_bmd_oper:BFDCountersBundleDesc"+
              "endant";
            description "Data for this item and all its members";
            uses BMD-BFD-COUNTER-BAG-MULTIPLE;
          }

          container bfd-counters-bundle-children-members {
            xr:xr-xml-map "bundlemgr_bmd_oper:BFDCountersBundleChil"+
              "dren";
            description
              "Children of bundle with BFD counters
              information";

            list bfd-counters-bundle-children-member {
              xr:xr-xml-map "bundlemgr_bmd_oper:BFDCountersBundleCh"+
                "ildrenMember";
              key "member-interface";
              description
                "Bundle member item with BFD counters
                information";
              leaf member-interface {
                xr:xr-xml-map "bundlemgr_bmd_oper:MemberInterface";
                type string;
                description "Member interface";
              }
              uses BMD-BFD-COUNTER-BAG;
            }
          }

          container bfd-counters-bundle-item {
            xr:xr-xml-map "bundlemgr_bmd_oper:BFDCountersBundleItem";
            description "Data for this item";
            uses BM-NAME-BAG;
          }
          leaf bundle-interface {
            xr:xr-xml-map "bundlemgr_bmd_oper:BundleInterface";
            type xr:Interface-name;
            description "Bundle interface";
          }
        }
      }

      container bfd-counters-members {
        xr:xr-xml-map "bundlemgr_bmd_oper:BFDCountersMemberTable";
        description
          "Member interfaces with BFD counters information";

        list bfd-counters-member {
          xr:xr-xml-map "bundlemgr_bmd_oper:BFDCountersMember";
          key "member-interface";
          description "Member interface";

          container bfd-counters-member-item {
            xr:xr-xml-map "bundlemgr_bmd_oper:BFDCountersMemberItem";
            description "Data for this item";
            uses BMD-BFD-COUNTER-BAG;
          }
          leaf member-interface {
            xr:xr-xml-map "bundlemgr_bmd_oper:MemberInterface";
            type string;
            description "Member interface";
          }
        }
      }
    }

    container scheduled-actions {
      xr:xr-xml-map "bundlemgr_bmd_oper:ScheduledActions";
      description "Scheduled actions on a bundle";

      container scheduled-actions-bundles {
        xr:xr-xml-map "bundlemgr_bmd_oper:ScheduledActionsBundleTab"+
          "le";
        description "Bundles with actions scheduled";

        list scheduled-actions-bundle {
          xr:xr-xml-map "bundlemgr_bmd_oper:ScheduledActionsBundle";
          key "bundle-interface";
          description "Bundle interface";

          container scheduled-actions-bundle-item {
            xr:xr-xml-map "bundlemgr_bmd_oper:ScheduledActionsBundl"+
              "eItem";
            description "Data for this item";
            uses BMD-SCH-ACTION-BAG;
          }
          leaf bundle-interface {
            xr:xr-xml-map "bundlemgr_bmd_oper:BundleInterface";
            type xr:Interface-name;
            description "Bundle interface";
          }
        }
      }
    }

    container bundle {
      xr:xr-xml-map "bundlemgr_bmd_oper:Bundle";
      description "Generic information for bundles and members";

      container bundle-bundles {
        xr:xr-xml-map "bundlemgr_bmd_oper:BundleBundleTable";
        description
          "Bundle interfaces with common bundle
          information";

        list bundle-bundle {
          xr:xr-xml-map "bundlemgr_bmd_oper:BundleBundle";
          key "bundle-interface";
          description "Bundle interface";

          container bundle-bundle-descendant {
            xr:xr-xml-map "bundlemgr_bmd_oper:BundleBundleDescendan"+
              "t";
            description "Data for this item and all its members";
            uses BM-BUNDLE-COMBINED-DATA;
          }

          container bundle-bundle-children-members {
            xr:xr-xml-map "bundlemgr_bmd_oper:BundleBundleChildren";
            description
              "Children of bundle with common bundle
              information";

            list bundle-bundle-children-member {
              xr:xr-xml-map "bundlemgr_bmd_oper:BundleBundleChildre"+
                "nMember";
              key "member-interface";
              description
                "Bundle member item with common bundle
                information";
              leaf member-interface {
                xr:xr-xml-map "bundlemgr_bmd_oper:MemberInterface";
                type string;
                description "Member interface";
              }
              uses BM-MEMBER-DATA;
            }
          }

          container bundle-bundle-item {
            xr:xr-xml-map "bundlemgr_bmd_oper:BundleBundleItem";
            description "Data for this item";
            uses BM-BUNDLE-DATA;
          }
          leaf bundle-interface {
            xr:xr-xml-map "bundlemgr_bmd_oper:BundleInterface";
            type xr:Interface-name;
            description "Bundle interface";
          }
        }
      }

      container bundle-members {
        xr:xr-xml-map "bundlemgr_bmd_oper:BundleMemberTable";
        description
          "Member interfaces with common bundle
          information";

        list bundle-member {
          xr:xr-xml-map "bundlemgr_bmd_oper:BundleMember";
          key "member-interface";
          description "Member interface";

          container bundle-member-ancestor {
            xr:xr-xml-map "bundlemgr_bmd_oper:BundleMemberAncestor";
            description "Data for this item and its parent bundle";
            uses BM-BUNDLE-COMBINED-DATA;
          }

          container bundle-member-item {
            xr:xr-xml-map "bundlemgr_bmd_oper:BundleMemberItem";
            description "Data for this item";
            uses BM-MEMBER-DATA;
          }
          leaf member-interface {
            xr:xr-xml-map "bundlemgr_bmd_oper:MemberInterface";
            type string;
            description "Member interface";
          }
        }
      }
    }

    container events-rg {
      xr:xr-xml-map "bundlemgr_bmd_oper:EventsRG";
      description
        "Bundle ICCP events information for bundles and
        members";

      container events-rg-members {
        xr:xr-xml-map "bundlemgr_bmd_oper:EventsRGMemberTable";
        description
          "Bundle Member interfaces with ICCP events
          information";

        list events-rg-member {
          xr:xr-xml-map "bundlemgr_bmd_oper:EventsRGMember";
          key "member-interface";
          description "Member interface";

          container events-rg-member-ancestor {
            xr:xr-xml-map "bundlemgr_bmd_oper:EventsRGMemberAncesto"+
              "r";
            description "Data for this item and its parent bundle";
            uses BMD-EVENT-BAG;
          }
          leaf member-interface {
            xr:xr-xml-map "bundlemgr_bmd_oper:MemberInterface";
            type string;
            description "Member interface";
          }
        }
      }

      container events-rg-iccp-groups {
        xr:xr-xml-map "bundlemgr_bmd_oper:EventsRG_ICCPGroupTable";
        description "ICCP events for all ICCP Groups";

        list events-rg-iccp-group {
          xr:xr-xml-map "bundlemgr_bmd_oper:EventsRG_ICCPGroup";
          key "iccp-group";
          description "ICCP Group ID";

          container events-rg-bundle-item-iccp-group {
            xr:xr-xml-map "bundlemgr_bmd_oper:EventsRGBundleItem_IC"+
              "CPGroup";
            description "Data for this item";
            uses BMD-EVENT-BAG;
          }
          leaf iccp-group {
            xr:xr-xml-map "bundlemgr_bmd_oper:ICCPGroup";
            type uint32 {
              range "1..4294967295";
            }
            description "ICCP Group ID";
          }
        }
      }

      container events-rg-bundles {
        xr:xr-xml-map "bundlemgr_bmd_oper:EventsRGBundleTable";
        description
          "Bundle interfaces with ICCP events information";

        list events-rg-bundle {
          xr:xr-xml-map "bundlemgr_bmd_oper:EventsRGBundle";
          key "bundle-interface";
          description "Bundle interface";

          container events-rg-bundle-ancestor {
            xr:xr-xml-map "bundlemgr_bmd_oper:EventsRGBundleAncesto"+
              "r";
            description "Data for this item and its parent bundle";
            uses BMD-EVENT-BAG;
          }
          leaf bundle-interface {
            xr:xr-xml-map "bundlemgr_bmd_oper:BundleInterface";
            type xr:Interface-name;
            description "Bundle interface";
          }
        }
      }
    }

    container lacp {
      xr:xr-xml-map "bundlemgr_bmd_oper:LACP";
      description "LACP information for bundles and members";

      container lacp-bundles {
        xr:xr-xml-map "bundlemgr_bmd_oper:LACPBundleTable";
        description "Bundle interfaces with LACP information";

        list lacp-bundle {
          xr:xr-xml-map "bundlemgr_bmd_oper:LACPBundle";
          key "bundle-interface";
          description "Bundle interface";

          container lacp-bundle-item {
            xr:xr-xml-map "bundlemgr_bmd_oper:LACPBundleItem";
            description "Data for this item";
            uses LACP-BUNDLE-DATA;
          }

          container lacp-bundle-descendant {
            xr:xr-xml-map "bundlemgr_bmd_oper:LACPBundleDescendant";
            description "Data for this item and all its members";
            uses LACP-COMBINED-DATA;
          }

          container lacp-bundle-children-members {
            xr:xr-xml-map "bundlemgr_bmd_oper:LACPBundleChildren";
            description "Children of bundle with LACP information";

            list lacp-bundle-children-member {
              xr:xr-xml-map "bundlemgr_bmd_oper:LACPBundleChildrenM"+
                "ember";
              key "member-interface";
              description
                "Bundle member item with LACP information";
              leaf member-interface {
                xr:xr-xml-map "bundlemgr_bmd_oper:MemberInterface";
                type string;
                description "Member interface";
              }
              uses LACP-MBR-DATA;
            }
          }
          leaf bundle-interface {
            xr:xr-xml-map "bundlemgr_bmd_oper:BundleInterface";
            type xr:Interface-name;
            description "Bundle interface";
          }
        }
      }

      container lacp-members {
        xr:xr-xml-map "bundlemgr_bmd_oper:LACPMemberTable";
        description "Member interfaces with LACP information";

        list lacp-member {
          xr:xr-xml-map "bundlemgr_bmd_oper:LACPMember";
          key "member-interface";
          description "Member interface";

          container lacp-member-ancestor {
            xr:xr-xml-map "bundlemgr_bmd_oper:LACPMemberAncestor";
            description "Data for this item and its parent bundle";
            uses LACP-COMBINED-DATA;
          }

          container lacp-member-item {
            xr:xr-xml-map "bundlemgr_bmd_oper:LACPMemberItem";
            description "Data for this item";
            uses LACP-MBR-DATA;
          }
          leaf member-interface {
            xr:xr-xml-map "bundlemgr_bmd_oper:MemberInterface";
            type string;
            description "Member interface";
          }
        }
      }
    }

    container mlacp-bundle-counters {
      xr:xr-xml-map "bundlemgr_mlacp_bdl_ctrs_oper:mLACPBundleCount"+
        "ers";
      description "Bundle specific counters of mLACP events";

      container iccp-groups {
        xr:xr-xml-map "bundlemgr_mlacp_bdl_ctrs_oper:ICCPGroupTable";
        description
          "ICCP Groups with counters of their bundle's
          mLACP events";

        list iccp-group {
          xr:xr-xml-map "bundlemgr_mlacp_bdl_ctrs_oper:ICCPGroup";
          key "iccp-group";
          description "ICCP Group ID";

          container iccp-group-item {
            xr:xr-xml-map "bundlemgr_mlacp_bdl_ctrs_oper:ICCPGroupI"+
              "tem";
            description "Data for this item";
            uses BMD-BAG-BDL-INFO-MLACP-COUNTERS-RG;
          }
          leaf iccp-group {
            xr:xr-xml-map "bundlemgr_mlacp_bdl_ctrs_oper:ICCPGroup";
            type uint32 {
              range "1..4294967295";
            }
            description "ICCP Group ID";
          }
        }
      }

      container bundles {
        xr:xr-xml-map "bundlemgr_mlacp_bdl_ctrs_oper:BundleTable";
        description
          "Bundle interfaces with counters of mLACP events";

        list bundle {
          xr:xr-xml-map "bundlemgr_mlacp_bdl_ctrs_oper:Bundle";
          key "bundle-interface";
          description "Bundle interface";

          container bundle-item {
            xr:xr-xml-map "bundlemgr_mlacp_bdl_ctrs_oper:BundleItem";
            description "Data for this item";
            uses BMD-BAG-BDL-INFO-MLACP-COUNTERS-RG-MULTIPLE;
          }
          leaf bundle-interface {
            xr:xr-xml-map "bundlemgr_mlacp_bdl_ctrs_oper:BundleInte"+
              "rface";
            type xr:Interface-name;
            description "Bundle interface";
          }
        }
      }

      container nodes {
        xr:xr-xml-map "bundlemgr_mlacp_bdl_ctrs_oper:NodeTable";
        description
          "Devices with counters of their bundle's mLACP
          events";

        list node {
          xr:xr-xml-map "bundlemgr_mlacp_bdl_ctrs_oper:Node";
          key "node";
          description "Node ID";

          container node-item {
            xr:xr-xml-map "bundlemgr_mlacp_bdl_ctrs_oper:NodeItem";
            description "Data for this item";
            uses BMD-BAG-BDL-INFO-MLACP-COUNTERS-RG;
          }
          leaf node {
            xr:xr-xml-map "bundlemgr_mlacp_bdl_ctrs_oper:Node";
            type string;
            description
              "For a local device the Node ID e.g.
              '0_0_CPU0', for a peer device the LDP ID
              followed by the ICCP Group ID e.g. '5.4.3.2
              ,4'";
          }
        }
      }
    }

    container protect {
      xr:xr-xml-map "bundlemgr_bmd_oper:Protect";
      description
        "Information for bundles and members that are in
        the protect database";

      container protect-bundles {
        xr:xr-xml-map "bundlemgr_bmd_oper:ProtectBundleTable";
        description
          "Bundle interfaces with information in the
          protect database";

        list protect-bundle {
          xr:xr-xml-map "bundlemgr_bmd_oper:ProtectBundle";
          key "bundle-interface";
          description "Bundle interface";

          container protect-bundle-item {
            xr:xr-xml-map "bundlemgr_bmd_oper:ProtectBundleItem";
            description "Data for this item";
            uses BMD-BAG-PROT-BDL-INFO;
          }
          leaf bundle-interface {
            xr:xr-xml-map "bundlemgr_bmd_oper:BundleInterface";
            type xr:Interface-name;
            description "Bundle interface";
          }
        }
      }
    }

    container mlacp-brief {
      xr:xr-xml-map "bundlemgr_bmd_oper:mLACPBrief";
      description
        "mLACP Information for Interchassis Groups and
        bundles";

      container mlacp-bundle-briefs {
        xr:xr-xml-map "bundlemgr_bmd_oper:mLACPBundleTableBrief";
        description
          "Bundle interfaces with brief mLACP information";

        list mlacp-bundle-brief {
          xr:xr-xml-map "bundlemgr_bmd_oper:mLACPBundleBrief";
          key "bundle-interface";
          description "Bundle interface";

          container mlacp-bundle-item-brief {
            xr:xr-xml-map "bundlemgr_bmd_oper:mLACPBundleItemBrief";
            description "Data for this item";
            uses BMD-BAG-MLACP-DATA-MULTIPLE;
          }
          leaf bundle-interface {
            xr:xr-xml-map "bundlemgr_bmd_oper:BundleInterface";
            type xr:Interface-name;
            description "Bundle interface";
          }
        }
      }

      container mlacp-brief-iccp-groups {
        xr:xr-xml-map "bundlemgr_bmd_oper:mLACPBrief_ICCPGroupTable";
        description "ICCP Groups with brief mLACP information";

        list mlacp-brief-iccp-group {
          xr:xr-xml-map "bundlemgr_bmd_oper:mLACPBrief_ICCPGroup";
          key "iccp-group";
          description "ICCP Group ID";

          container mlacp-brief-iccp-group-item {
            xr:xr-xml-map "bundlemgr_bmd_oper:mLACPBrief_ICCPGroupI"+
              "tem";
            description "Data for this item";
            uses BMD-BAG-MLACP-DATA;
          }
          leaf iccp-group {
            xr:xr-xml-map "bundlemgr_bmd_oper:ICCPGroup";
            type uint32 {
              range "1..4294967295";
            }
            description "ICCP Group ID";
          }
        }
      }
    }

    container mlacp {
      xr:xr-xml-map "bundlemgr_bmd_oper:mLACP";
      description
        "mLACP Information for Interchassis Groups and
        bundles";

      container mlacp-bundles {
        xr:xr-xml-map "bundlemgr_bmd_oper:mLACPBundleTable";
        description "Bundle interfaces with mLACP information";

        list mlacp-bundle {
          xr:xr-xml-map "bundlemgr_bmd_oper:mLACPBundle";
          key "bundle-interface";
          description "Bundle interface";

          container mlacp-bundle-item {
            xr:xr-xml-map "bundlemgr_bmd_oper:mLACPBundleItem";
            description "Data for this item";
            uses BMD-BAG-MLACP-DATA-MULTIPLE;
          }
          leaf bundle-interface {
            xr:xr-xml-map "bundlemgr_bmd_oper:BundleInterface";
            type xr:Interface-name;
            description "Bundle interface";
          }
        }
      }

      container mlacp-iccp-groups {
        xr:xr-xml-map "bundlemgr_bmd_oper:mLACP_ICCPGroupTable";
        description "ICCP Groups with mLACP information";

        list mlacp-iccp-group {
          xr:xr-xml-map "bundlemgr_bmd_oper:mLACP_ICCPGroup";
          key "iccp-group";
          description "ICCP Group ID";

          container mlacp-iccp-group-item {
            xr:xr-xml-map "bundlemgr_bmd_oper:mLACP_ICCPGroupItem";
            description "Data for this item";
            uses BMD-BAG-MLACP-DATA;
          }
          leaf iccp-group {
            xr:xr-xml-map "bundlemgr_bmd_oper:ICCPGroup";
            type uint32 {
              range "1..4294967295";
            }
            description "ICCP Group ID";
          }
        }
      }
    }

    container mac-allocation {
      xr:xr-xml-map "bundlemgr_bmd_oper:MACAllocation";
      description
        "Information about allocated MAC addresses that
        are not in use";

      container mac-allocation-global {
        xr:xr-xml-map "bundlemgr_bmd_oper:MACAllocationGlobal";
        description
          "All MAC addresses that are allocated but
          currently not in use";

        container mac-allocation-global-item {
          xr:xr-xml-map "bundlemgr_bmd_oper:MACAllocationGlobalItem";
          description "Data for this item";
          uses BM-MAC-ALLOC;
        }
      }
    }

    container events {
      xr:xr-xml-map "bundlemgr_bmd_oper:Events";
      description "Events information for bundles and members";

      container events-members {
        xr:xr-xml-map "bundlemgr_bmd_oper:EventsMemberTable";
        description "Member interfaces with events information";

        list events-member {
          xr:xr-xml-map "bundlemgr_bmd_oper:EventsMember";
          key "member-interface";
          description "Member interface";

          container events-member-item {
            xr:xr-xml-map "bundlemgr_bmd_oper:EventsMemberItem";
            description "Data for this item";
            uses BMD-EVENT-BAG;
          }

          container events-member-ancestor {
            xr:xr-xml-map "bundlemgr_bmd_oper:EventsMemberAncestor";
            description "Data for this item and its parent bundle";
            uses BMD-EVENT-BAG;
          }
          leaf member-interface {
            xr:xr-xml-map "bundlemgr_bmd_oper:MemberInterface";
            type string;
            description "Member interface";
          }
        }
      }

      container events-bundles {
        xr:xr-xml-map "bundlemgr_bmd_oper:EventsBundleTable";
        description "Bundle interfaces with events information";

        list events-bundle {
          xr:xr-xml-map "bundlemgr_bmd_oper:EventsBundle";
          key "bundle-interface";
          description "Bundle interface";

          container events-bundle-ancestor {
            xr:xr-xml-map "bundlemgr_bmd_oper:EventsBundleAncestor";
            description "Data for this item and its parent bundle";
            uses BMD-EVENT-BAG;
          }

          container events-bundle-item {
            xr:xr-xml-map "bundlemgr_bmd_oper:EventsBundleItem";
            description "Data for this item";
            uses BMD-EVENT-BAG;
          }

          container events-bundle-descendant {
            xr:xr-xml-map "bundlemgr_bmd_oper:EventsBundleDescendan"+
              "t";
            description "Data for this item and all its members";
            uses BMD-EVENT-BAG-MULTIPLE;
          }

          container events-bundle-children-members {
            xr:xr-xml-map "bundlemgr_bmd_oper:EventsBundleChildren";
            description
              "Children of bundle with events information";

            list events-bundle-children-member {
              xr:xr-xml-map "bundlemgr_bmd_oper:EventsBundleChildre"+
                "nMember";
              key "member-interface";
              description
                "Bundle member item with events information";
              leaf member-interface {
                xr:xr-xml-map "bundlemgr_bmd_oper:MemberInterface";
                type string;
                description "Member interface";
              }
              uses BMD-EVENT-BAG;
            }
          }
          leaf bundle-interface {
            xr:xr-xml-map "bundlemgr_bmd_oper:BundleInterface";
            type xr:Interface-name;
            description "Bundle interface";
          }
        }
      }
    }

    container events-bdl {
      xr:xr-xml-map "bundlemgr_bmd_oper:EventsBDL";
      description
        "Bundle events information for bundles and
        members";

      container events-bdl-members {
        xr:xr-xml-map "bundlemgr_bmd_oper:EventsBDLMemberTable";
        description
          "Member interfaces with bundle events
          information";

        list events-bdl-member {
          xr:xr-xml-map "bundlemgr_bmd_oper:EventsBDLMember";
          key "member-interface";
          description "Member interface";

          container events-bdl-member-ancestor {
            xr:xr-xml-map "bundlemgr_bmd_oper:EventsBDLMemberAncest"+
              "or";
            description "Data for this item and its parent bundle";
            uses BMD-EVENT-BAG;
          }
          leaf member-interface {
            xr:xr-xml-map "bundlemgr_bmd_oper:MemberInterface";
            type string;
            description "Member interface";
          }
        }
      }

      container events-bdl-bundles {
        xr:xr-xml-map "bundlemgr_bmd_oper:EventsBDLBundleTable";
        description
          "Bundle interfaces with bundle events
          information";

        list events-bdl-bundle {
          xr:xr-xml-map "bundlemgr_bmd_oper:EventsBDLBundle";
          key "bundle-interface";
          description "Bundle interface";

          container events-bdl-bundle-item {
            xr:xr-xml-map "bundlemgr_bmd_oper:EventsBDLBundleItem";
            description "Data for this item";
            uses BMD-EVENT-BAG;
          }
          leaf bundle-interface {
            xr:xr-xml-map "bundlemgr_bmd_oper:BundleInterface";
            type xr:Interface-name;
            description "Bundle interface";
          }
        }
      }

      container events-bdl-iccp-groups {
        xr:xr-xml-map "bundlemgr_bmd_oper:EventsBDL_ICCPGroupTable";
        description "Bundle events for all ICCP Groups";

        list events-bdl-iccp-group {
          xr:xr-xml-map "bundlemgr_bmd_oper:EventsBDL_ICCPGroup";
          key "iccp-group";
          description "ICCP Group ID";

          container events-bdl-bundle-descendant-iccp-group {
            xr:xr-xml-map "bundlemgr_bmd_oper:EventsBDLBundleDescen"+
              "dant_ICCPGroup";
            description "Data for this item and all its members";
            uses BMD-EVENT-BAG-MULTIPLE;
          }
          leaf iccp-group {
            xr:xr-xml-map "bundlemgr_bmd_oper:ICCPGroup";
            type uint32 {
              range "1..4294967295";
            }
            description "ICCP Group ID";
          }
        }
      }
    }

    container bundle-briefs {
      xr:xr-xml-map "bundlemgr_bmd_oper:BundleBriefTable";
      description
        "Bundle interfaces with common bundle information";

      list bundle-brief {
        xr:xr-xml-map "bundlemgr_bmd_oper:BundleBrief";
        key "bundle-interface";
        description "Bundle interface";

        container bundle-brief-item {
          xr:xr-xml-map "bundlemgr_bmd_oper:BundleBriefItem";
          description "Data for this item";
          uses BM-BUNDLE-DATA;
        }
        leaf bundle-interface {
          xr:xr-xml-map "bundlemgr_bmd_oper:BundleInterface";
          type xr:Interface-name;
          description "Bundle interface";
        }
      }
    }

    container events-mbr {
      xr:xr-xml-map "bundlemgr_bmd_oper:EventsMBR";
      description
        "Bundle member events information for bundles and
        members";

      container events-mbr-bundles {
        xr:xr-xml-map "bundlemgr_bmd_oper:EventsMBRBundleTable";
        description
          "Bundle interfaces with member events
          information";

        list events-mbr-bundle {
          xr:xr-xml-map "bundlemgr_bmd_oper:EventsMBRBundle";
          key "bundle-interface";
          description "Bundle interface";

          container events-mbr-bundle-children-members {
            xr:xr-xml-map "bundlemgr_bmd_oper:EventsMBRBundleChildr"+
              "en";
            description
              "Children of bundle with member events
              information";

            list events-mbr-bundle-children-member {
              xr:xr-xml-map "bundlemgr_bmd_oper:EventsMBRBundleChil"+
                "drenMember";
              key "member-interface";
              description
                "Bundle member item with member events
                information";
              leaf member-interface {
                xr:xr-xml-map "bundlemgr_bmd_oper:MemberInterface";
                type string;
                description "Member interface";
              }
              uses BMD-EVENT-BAG;
            }
          }

          container events-mbr-bundle-descendant {
            xr:xr-xml-map "bundlemgr_bmd_oper:EventsMBRBundleDescen"+
              "dant";
            description "Data for this item and all its members";
            uses BMD-EVENT-BAG-MULTIPLE;
          }
          leaf bundle-interface {
            xr:xr-xml-map "bundlemgr_bmd_oper:BundleInterface";
            type xr:Interface-name;
            description "Bundle interface";
          }
        }
      }

      container events-mbr-members {
        xr:xr-xml-map "bundlemgr_bmd_oper:EventsMBRMemberTable";
        description
          "Member interfaces with bundle member events
          information";

        list events-mbr-member {
          xr:xr-xml-map "bundlemgr_bmd_oper:EventsMBRMember";
          key "member-interface";
          description "Member interface";

          container events-mbr-member-item {
            xr:xr-xml-map "bundlemgr_bmd_oper:EventsMBRMemberItem";
            description "Data for this item";
            uses BMD-EVENT-BAG;
          }
          leaf member-interface {
            xr:xr-xml-map "bundlemgr_bmd_oper:MemberInterface";
            type string;
            description "Member interface";
          }
        }
      }

      container events-mbr-iccp-groups {
        xr:xr-xml-map "bundlemgr_bmd_oper:EventsMBR_ICCPGroupTable";
        description "Member events for all ICCP Groups";

        list events-mbr-iccp-group {
          xr:xr-xml-map "bundlemgr_bmd_oper:EventsMBR_ICCPGroup";
          key "iccp-group";
          description "ICCP Group ID";

          container events-mbr-bundle-children-member-iccp-groups {
            xr:xr-xml-map "bundlemgr_bmd_oper:EventsMBRBundleChildr"+
              "en_ICCPGroup";
            description
              "Children of bundle with member events
              information";

            list events-mbr-bundle-children-member-iccp-group {
              xr:xr-xml-map "bundlemgr_bmd_oper:EventsMBRBundleChil"+
                "drenMember_ICCPGroup";
              key "member-interface";
              description
                "Bundle member item with ICCP events
                information";
              leaf member-interface {
                xr:xr-xml-map "bundlemgr_bmd_oper:MemberInterface";
                type string;
                description "Member interface";
              }
              uses BMD-EVENT-BAG;
            }
          }

          container events-mbr-bundle-descendant-iccp-group {
            xr:xr-xml-map "bundlemgr_bmd_oper:EventsMBRBundleDescen"+
              "dant_ICCPGroup";
            description "Data for this item and all its members";
            uses BMD-EVENT-BAG-MULTIPLE;
          }
          leaf iccp-group {
            xr:xr-xml-map "bundlemgr_bmd_oper:ICCPGroup";
            type uint32 {
              range "1..4294967295";
            }
            description "ICCP Group ID";
          }
        }
      }
    }

    container mlacp-iccp-group-counters {
      xr:xr-xml-map "bundlemgr_mlacp_rg_ctrs_oper:mLACP_ICCPGroupCo"+
        "unters";
      description "ICCP Group specific counters of mLACP events";

      container iccp-groups {
        xr:xr-xml-map "bundlemgr_mlacp_rg_ctrs_oper:ICCPGroupTable";
        description "ICCP Groups with counters of mLACP events";

        list iccp-group {
          xr:xr-xml-map "bundlemgr_mlacp_rg_ctrs_oper:ICCPGroup";
          key "iccp-group";
          description "ICCP Group ID";

          container iccp-group-ancestor-bundle {
            xr:xr-xml-map "bundlemgr_mlacp_rg_ctrs_oper:ICCPGroupAn"+
              "cestorBundle";
            description "Data for this item and its parent RG";
            uses BMD-BAG-RG-INFO-MLACP-COUNTERS-RG;
          }

          container iccp-group-ancestor-member {
            xr:xr-xml-map "bundlemgr_mlacp_rg_ctrs_oper:ICCPGroupAn"+
              "cestorMember";
            description "Data for this item and its parent RG";
            uses BMD-BAG-RG-INFO-MLACP-COUNTERS-RG;
          }

          container iccp-group-ancestor-node {
            xr:xr-xml-map "bundlemgr_mlacp_rg_ctrs_oper:ICCPGroupAn"+
              "cestorNode";
            description "Data for this item and its parent RG";
            uses BMD-BAG-RG-INFO-MLACP-COUNTERS-RG;
          }

          container iccp-group-item {
            xr:xr-xml-map "bundlemgr_mlacp_rg_ctrs_oper:ICCPGroupIt"+
              "em";
            description "Data for this item";
            uses BMD-BAG-RG-INFO-MLACP-COUNTERS-RG;
          }
          leaf iccp-group {
            xr:xr-xml-map "bundlemgr_mlacp_rg_ctrs_oper:ICCPGroup";
            type uint32 {
              range "1..4294967295";
            }
            description "ICCP Group ID";
          }
        }
      }
    }

    container system-id {
      xr:xr-xml-map "bundlemgr_bmd_oper:SystemID";
      description
        "System Identifiers for the local system and all
        ICCP Groups";

      container system-id-global {
        xr:xr-xml-map "bundlemgr_bmd_oper:SystemIDGlobal";
        description "System Identifier for the local system";

        container system-id-global-item {
          xr:xr-xml-map "bundlemgr_bmd_oper:SystemIDGlobalItem";
          description "Data for this item";
          uses LACP-SYSTEM-ID;
        }
      }

      container system-id-iccp-groups {
        xr:xr-xml-map "bundlemgr_bmd_oper:SystemID_ICCPGroupTable";
        description "System Identifiers for all ICCP Groups";

        list system-id-iccp-group {
          xr:xr-xml-map "bundlemgr_bmd_oper:SystemID_ICCPGroup";
          key "iccp-group";
          description "ICCP Group ID";

          container system-id-iccp-group-item {
            xr:xr-xml-map "bundlemgr_bmd_oper:SystemID_ICCPGroupIte"+
              "m";
            description "Data for this item";
            uses LACP-SYSTEM-ID;
          }
          leaf iccp-group {
            xr:xr-xml-map "bundlemgr_bmd_oper:ICCPGroup";
            type uint32 {
              range "1..4294967295";
            }
            description "ICCP Group ID";
          }
        }
      }
    }

    container mlacp-member-counters {
      xr:xr-xml-map "bundlemgr_mlacp_mbr_ctrs_oper:mLACPMemberCount"+
        "ers";
      description "Member specific counters of mLACP events";

      container iccp-groups {
        xr:xr-xml-map "bundlemgr_mlacp_mbr_ctrs_oper:ICCPGroupTable";
        description
          "ICCP Groups with counters of their member's
          mLACP events";

        list iccp-group {
          xr:xr-xml-map "bundlemgr_mlacp_mbr_ctrs_oper:ICCPGroup";
          key "iccp-group";
          description "ICCP Group ID";

          container iccp-group-item {
            xr:xr-xml-map "bundlemgr_mlacp_mbr_ctrs_oper:ICCPGroupI"+
              "tem";
            description "Data for this item and all its members";
            uses BMD-BAG-MBR-INFO-MLACP-COUNTERS-RG;
          }
          leaf iccp-group {
            xr:xr-xml-map "bundlemgr_mlacp_mbr_ctrs_oper:ICCPGroup";
            type uint32 {
              range "1..4294967295";
            }
            description "ICCP Group ID";
          }
        }
      }

      container members {
        xr:xr-xml-map "bundlemgr_mlacp_mbr_ctrs_oper:MemberTable";
        description
          "Member interfaces with counters of mLACP events";

        list member {
          xr:xr-xml-map "bundlemgr_mlacp_mbr_ctrs_oper:Member";
          key "member-interface";
          description "Member interface";

          container member-item {
            xr:xr-xml-map "bundlemgr_mlacp_mbr_ctrs_oper:MemberItem";
            description "Data for this item";
            uses BMD-BAG-MBR-INFO-MLACP-COUNTERS-RG;
          }
          leaf member-interface {
            xr:xr-xml-map "bundlemgr_mlacp_mbr_ctrs_oper:MemberInte"+
              "rface";
            type string;
            description "Member interface";
          }
        }
      }

      container bundles {
        xr:xr-xml-map "bundlemgr_mlacp_mbr_ctrs_oper:BundleTable";
        description
          "Bundle interfaces with counters of their
          member's mLACP events";

        list bundle {
          xr:xr-xml-map "bundlemgr_mlacp_mbr_ctrs_oper:Bundle";
          key "bundle-interface";
          description "Bundle interface";

          container bundle-item {
            xr:xr-xml-map "bundlemgr_mlacp_mbr_ctrs_oper:BundleItem";
            description "Data for this item";
            uses BMD-BAG-MBR-INFO-MLACP-COUNTERS-BDL;
          }
          leaf bundle-interface {
            xr:xr-xml-map "bundlemgr_mlacp_mbr_ctrs_oper:BundleInte"+
              "rface";
            type xr:Interface-name;
            description "Bundle interface";
          }
        }
      }

      container nodes {
        xr:xr-xml-map "bundlemgr_mlacp_mbr_ctrs_oper:NodeTable";
        description
          "Devices with counters of their member's mLACP
          events";

        list node {
          xr:xr-xml-map "bundlemgr_mlacp_mbr_ctrs_oper:Node";
          key "node";
          description "Node ID";

          container node-item {
            xr:xr-xml-map "bundlemgr_mlacp_mbr_ctrs_oper:NodeItem";
            description "Data for this item";
            uses BMD-BAG-MBR-INFO-MLACP-COUNTERS-RG;
          }
          leaf node {
            xr:xr-xml-map "bundlemgr_mlacp_mbr_ctrs_oper:Node";
            type string;
            description
              "For a local device the Node ID e.g.
              '0_0_CPU0', for a peer device the LDP ID
              followed by the ICCP Group ID e.g. '5.4.3.2
              ,4'";
          }
        }
      }
    }
  }

  container lacp-data {
    xr:xr-xml-map "bundlemgr_lacp_oper:LACPData";
    config false;
    description "lacp data";

    container global {
      xr:xr-xml-map "bundlemgr_lacp_oper:Global";
      description "Global LACP data";

      container system-id {
        xr:xr-xml-map "bundlemgr_lacp_oper:SystemID";
        description "LACP System ID";
        uses LACP-SYSTEM-ID;
      }
    }
  }

  container bundles {
    xr:xr-xml-map "bundlemgr_bm_bdl_oper:Bundles";
    config false;
    description "bundles";

    container bundles {
      xr:xr-xml-map "bundlemgr_bm_bdl_oper:BundleTable";
      description "Per bundle operational data";

      list bundle {
        xr:xr-xml-map "bundlemgr_bm_bdl_oper:Bundle";
        key "bundle-interface";
        description "Bundle interface";

        container data {
          xr:xr-xml-map "bundlemgr_bm_bdl_oper:Data";
          description "Data for each Bundle";
          uses BM-BUNDLE-DATA;
        }

        container members {
          xr:xr-xml-map "bundlemgr_bm_bdl_oper:MemberTable";
          description "Member interface";

          list member {
            xr:xr-xml-map "bundlemgr_bm_bdl_oper:Member";
            key "member-interface";
            description "Member information";
            leaf member-interface {
              xr:xr-xml-map "bundlemgr_bm_bdl_oper:MemberInterface";
              type xr:Interface-name;
              description "Member interface";
            }
            uses BM-MEMBER-DATA;
          }
        }
        leaf bundle-interface {
          xr:xr-xml-map "bundlemgr_bm_bdl_oper:BundleInterface";
          type xr:Interface-name;
          description "Bundle interface";
        }
      }
    }
  }

  container lacp-bundle-members {
    xr:xr-xml-map "bundlemgr_lacp_mbr_oper:LACPBundleMembers";
    config false;
    description "lacp bundle members";

    container nodes {
      xr:xr-xml-map "bundlemgr_lacp_mbr_oper:NodeTable";
      description
        "Table of devices with their LACP bundle member
        interfaces";

      list node {
        xr:xr-xml-map "bundlemgr_lacp_mbr_oper:Node";
        key "node";
        description "Node ID";

        container counters {
          xr:xr-xml-map "bundlemgr_lacp_mbr_oper:Counters";
          description
            "Link counters for LACP bundle members per node";
          uses LACP-DROPS;
        }
        leaf node {
          xr:xr-xml-map "bundlemgr_lacp_mbr_oper:Node";
          type string;
          description
            "For a local device the Node ID e.g. '0_0_CPU0'
            , for a peer device the LDP ID followed by the
            ICCP Group ID e.g. '5.4.3.2,4'";
        }
      }
    }

    container members {
      xr:xr-xml-map "bundlemgr_lacp_mbr_oper:MemberTable";
      description "Table of LACP bundle member interfaces";

      list member {
        xr:xr-xml-map "bundlemgr_lacp_mbr_oper:Member";
        key "member-interface";
        description "LACP bundle member interface data";

        container data {
          xr:xr-xml-map "bundlemgr_lacp_mbr_oper:Data";
          description "Link data for LACP bundle members";
          uses LACP-LINK-DATA;
        }

        container counters {
          xr:xr-xml-map "bundlemgr_lacp_mbr_oper:Counters";
          description "Link counters for LACP bundle members";
          uses LACP-COUNTERS;
        }
        leaf member-interface {
          xr:xr-xml-map "bundlemgr_lacp_mbr_oper:MemberInterface";
          type xr:Interface-name;
          description "Member interface";
        }
      }
    }
  }

  container bundles-adjacency {
    xr:xr-xml-map "bundlemgr_adj_oper:BundlesAdjacency";
    config false;
    description "bundles adjacency";

    container nodes {
      xr:xr-xml-map "bundlemgr_adj_oper:NodeTable";
      description "Per bundle operational data";

      list node {
        xr:xr-xml-map "bundlemgr_adj_oper:Node";
        key "node-name";
        description "Location";

        container brief {
          xr:xr-xml-map "bundlemgr_adj_oper:Brief";
          description "Brief load-balance information for the node";
          uses BMA-BRIEF-DATA;
        }

        container bundles {
          xr:xr-xml-map "bundlemgr_adj_oper:BundleTable";
          description "Per bundle operational data";

          list bundle {
            xr:xr-xml-map "bundlemgr_adj_oper:Bundle";
            key "bundle-name";
            description "Bundle information";

            container bundle-info {
              xr:xr-xml-map "bundlemgr_adj_oper:BundleInfo";
              description "Data for each Bundle";
              uses BMA-BUNDLE-DATA;
            }
            leaf bundle-name {
              xr:xr-xml-map "bundlemgr_adj_oper:BundleName";
              type xr:Interface-name;
              description "Bundle interface";
            }
          }
        }
        leaf node-name {
          xr:xr-xml-map "bundlemgr_adj_oper:NodeName";
          type xr:Node-id;
          description "Node ID";
        }
      }
    }
  }
}
