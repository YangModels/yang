submodule Cisco-IOS-XR-asr9k-lpts-oper-sub1 {

  belongs-to Cisco-IOS-XR-asr9k-lpts-oper {
    prefix Cisco-IOS-XR-asr9k-lpts-oper;
  }

  /*** LINKAGE (IMPORTS / INCLUDES) ***/

  import ietf-yang-types { prefix "yang"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR asr9k-lpts package operational data.

     Copyright (c) 2013-2016 by Cisco Systems, Inc.
     All rights reserved.";

  revision "2015-11-09" {
    description
      "IOS XR 6.0 revision.";
  }


  grouping PL-PIFIB-SHOW-STATS {
    description "Pre-IFIB global statistics";
    leaf accepted {
      xr:xr-xml-map "platform_pifib:accepted";
      type uint64;
      description "Deleted-entry accepted packets counter";
    }
    leaf dropped {
      xr:xr-xml-map "platform_pifib:dropped";
      type uint64;
      description "Deleted-entry dropped packets counter";
    }
    leaf clear-ts {
      xr:xr-xml-map "platform_pifib:clear_ts";
      type uint64;
      description "Statistics clear timestamp";
    }
    leaf no-stats-mem-err {
      xr:xr-xml-map "platform_pifib:no_stats_mem_err";
      type uint64;
      description "No statistics memory error";
    }
  }

  grouping PL-PIFIB-POLICE-INFO {
    description "PL PIFIB POLICE INFO";
    leaf avgrate {
      xr:xr-xml-map "platform_pifib:avgrate";
      type uint32;
      description "avgrate";
    }
    leaf burst {
      xr:xr-xml-map "platform_pifib:burst";
      type uint32;
      description "burst";
    }
    leaf static-avgrate {
      xr:xr-xml-map "platform_pifib:static_avgrate";
      type uint32;
      description "static avgrate";
    }
    leaf avgrate-type {
      xr:xr-xml-map "platform_pifib:avgrate_type";
      type string {
        length "0..50";
      }
      description "avgrate type";
    }
    leaf flow-type {
      xr:xr-xml-map "platform_pifib:flow_type";
      type string {
        length "0..50";
      }
      description "flow type";
    }
    leaf accepted-stats {
      xr:xr-xml-map "platform_pifib:accepted_stats";
      type uint64;
      description "accepted stats";
    }
    leaf dropped-stats {
      xr:xr-xml-map "platform_pifib:dropped_stats";
      type uint64;
      description "dropped stats";
    }
    leaf policer {
      xr:xr-xml-map "platform_pifib:policer";
      type uint32;
      description "policer";
    }
    leaf iptos-value {
      xr:xr-xml-map "platform_pifib:iptos_value";
      type uint8;
      description "iptos value";
    }
    leaf change-type {
      xr:xr-xml-map "platform_pifib:change_type";
      type uint8;
      description "change type";
    }
    leaf acl-config {
      xr:xr-xml-map "platform_pifib:acl_config";
      type uint8;
      description "acl config";
    }
    leaf acl-str {
      xr:xr-xml-map "platform_pifib:acl_str";
      type yang:hex-string;
      description "acl str";
    }
    leaf np {
      xr:xr-xml-map "platform_pifib:np";
      type uint8;
      description "np";
    }
  }

  grouping PL-PIFIB-SHOW-POLICE {
    description "Pre-IFIB platform specific police data structure";

    list police-info {
      description "Per flow type police info";
      uses PL-PIFIB-POLICE-INFO;
    }
  }
}
