module Cisco-IOS-XR-tty-vty-cfg {

  /*** NAMESPACE / PREFIX DEFINITION ***/

  namespace "http://cisco.com/ns/yang/Cisco-IOS-XR-tty-vty-cfg";


  prefix "tty-vty-cfg";

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR tty-vty package configuration.

     This module contains definitions
     for the following management objects:
       vty: VTY Pools configuration

     Copyright (c) 2013-2016 by Cisco Systems, Inc.
     All rights reserved.";

  revision "2015-01-07" {
    description
      "IOS XR 5.3.1 revision.";
  }


  container vty {
    xr:xr-xml-map "tty_vty_cfg:VTY";
    description "VTY Pools configuration";

    container vty-pools {
      xr:xr-xml-map "tty_vty_cfg:VTYPoolTable";
      description "List of VTY Pools";

      list vty-pool {
        xr:xr-xml-map "tty_vty_cfg:VTYPool";
        key "pool-name";
        description "VTY Pool";
        leaf pool-name {
          xr:xr-xml-map "tty_vty_cfg:PoolName";
          type xr:Cisco-ios-xr-string;
          description
            "For configuring range for default pool use
            'default',For configuring range for
            fault-manager pool use 'fm',For configuring
            range for any user defined pool use any other
            string";
        }
        leaf first-vty {
          xr:xr-xml-map "tty_vty_cfg:FirstVTY";
          type int32;
          mandatory true;
          description
            "First VTY number,For default VTY use 0,For
            user-defined use 5,For fault-manager use 100";
        }
        leaf last-vty {
          xr:xr-xml-map "tty_vty_cfg:LastVTY";
          type int32;
          mandatory true;
          description
            "Last VTY number,For default configure between
            0-99,For user-defined configure between 5-99
            ,For fault-manager configure between 100-199";
        }
        leaf line-template {
          xr:xr-xml-map "tty_vty_cfg:LineTemplate";
          type string;
          description "Name of line template";
        }
        leaf none {
          xr:xr-xml-map "tty_vty_cfg:None";
          type string;
          description "Empty Option";
        }
      }
    }
  }
}
