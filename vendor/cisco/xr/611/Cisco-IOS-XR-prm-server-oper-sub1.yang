submodule Cisco-IOS-XR-prm-server-oper-sub1 {

  belongs-to Cisco-IOS-XR-prm-server-oper {
    prefix Cisco-IOS-XR-prm-server-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR prm-server package operational data.

     Copyright (c) 2013-2016 by Cisco Systems, Inc.
     All rights reserved.";

  revision "2016-02-22" {
    description
      "Initial revision.";
  }

  revision "2015-11-09" {
    description
      "IOS XR 6.0 revision.";
  }


  grouping RESOURCE-EDM-DATA {
    description "Resource Summary Data";
    leaf resource-name {
      xr:xr-xml-map "prm_edm_bcm:ResourceName";
      type string {
        length "0..1024";
      }
      description "Resource Name";
    }
    leaf resource-type {
      xr:xr-xml-map "prm_edm_bcm:ResourceType";
      type uint32;
      description "Resource Type";
    }
    leaf total-num {
      xr:xr-xml-map "prm_edm_bcm:TotalNum";
      type uint32;
      description "Total Resource Count";
    }
    leaf free-num {
      xr:xr-xml-map "prm_edm_bcm:FreeNum";
      type uint32;
      description "Free Resource Count";
    }
    leaf first-available-index {
      xr:xr-xml-map "prm_edm_bcm:FirstAvailableIndex";
      type uint32;
      description "Next Free Index";
    }
    leaf start-index {
      xr:xr-xml-map "prm_edm_bcm:StartIndex";
      type uint32;
      description "Start Index";
    }
    leaf availability-status {
      xr:xr-xml-map "prm_edm_bcm:AvailabilityStatus";
      type boolean;
      description "Availability Status";
    }
    leaf flags {
      xr:xr-xml-map "prm_edm_bcm:Flags";
      type uint8;
      description "Resource Flags";
    }
    leaf inconsistent {
      xr:xr-xml-map "prm_edm_bcm:Inconsistent";
      type boolean;
      description "Inconsistice Flags";
    }
  }

  grouping PLAT-DROP-STATS-INFO {
    description "Plat drop stats data";
    leaf drop-reason {
      xr:xr-xml-map "prm_edm_bcm:DropReason";
      type string {
        length "0..1024";
      }
      description "Drop Reason";
    }
    leaf counters {
      xr:xr-xml-map "prm_edm_bcm:Counters";
      type uint32;
      description "Counter";
    }
  }

  grouping PLAT-DROP-CAPTURED-PAK {
    description "Plat drop captured packets";
    leaf total-captured {
      xr:xr-xml-map "prm_edm_bcm:TotalCaptured";
      type uint32;
      description "Total packets Captured";
    }
    leaf captured-pak {
      xr:xr-xml-map "prm_edm_bcm:CapturedPak";
      type string {
        length "0..1024";
      }
      description "Captured Packet";
    }
    leaf pkt-index {
      xr:xr-xml-map "prm_edm_bcm:PktIndex";
      type uint8;
      description "Packet Index";
    }
    leaf ifhandle {
      xr:xr-xml-map "prm_edm_bcm:Ifhandle";
      type uint32;
      description "If Handle";
    }
    leaf buffer-len {
      xr:xr-xml-map "prm_edm_bcm:BufferLen";
      type uint32;
      description "Buffer Length";
    }
    leaf reason-hi {
      xr:xr-xml-map "prm_edm_bcm:ReasonHi";
      type uint32;
      description "Reason Hi";
    }
    leaf reason {
      xr:xr-xml-map "prm_edm_bcm:Reason";
      type uint32;
      description "Reason";
    }
    leaf years {
      xr:xr-xml-map "prm_edm_bcm:Years";
      type uint64;
      description "Year";
    }
    leaf hours {
      xr:xr-xml-map "prm_edm_bcm:Hours";
      type uint64;
      units "hour";
      description "Hours";
    }
    leaf days {
      xr:xr-xml-map "prm_edm_bcm:Days";
      type uint64;
      units "day";
      description "Days";
    }
    leaf mins {
      xr:xr-xml-map "prm_edm_bcm:Mins";
      type uint64;
      units "minute";
      description "Minutes";
    }
    leaf secs {
      xr:xr-xml-map "prm_edm_bcm:Secs";
      type uint64;
      units "second";
      description "Seconds";
    }
  }

  grouping BCM-EDM-COSQ-INFO {
    description "BCM CosQ EDM data";
    leaf cos-q-name {
      xr:xr-xml-map "prm_edm_bcm:CosQName";
      type string {
        length "0..1024";
      }
      description "CosQ Name";
    }
    leaf cos-q {
      xr:xr-xml-map "prm_edm_bcm:CosQ";
      type uint8;
      description "CosQ No";
    }
    leaf rx-channel {
      xr:xr-xml-map "prm_edm_bcm:RxChannel";
      type uint32;
      description "Rx DMA Channel";
    }
    leaf flow-rate {
      xr:xr-xml-map "prm_edm_bcm:FlowRate";
      type uint32;
      description "Flow Rate";
    }
    leaf burst {
      xr:xr-xml-map "prm_edm_bcm:Burst";
      type uint32;
      description "Burst";
    }
    leaf accepted {
      xr:xr-xml-map "prm_edm_bcm:Accepted";
      type uint32;
      description "Accepted";
    }
    leaf dropped {
      xr:xr-xml-map "prm_edm_bcm:Dropped";
      type uint32;
      description "Dropped";
    }
  }
}
