submodule Cisco-IOS-XR-tty-server-oper-sub4 {

  belongs-to Cisco-IOS-XR-tty-server-oper {
    prefix Cisco-IOS-XR-tty-server-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR tty-server package operational data.

     Copyright (c) 2013-2016 by Cisco Systems, Inc.
     All rights reserved.";

  revision "2015-07-30" {
    description
      "Descriptions updated.";
  }

  revision "2015-01-07" {
    description
      "IOS XR 5.3.1 revision.";
  }


  grouping TTY-GENERAL-STATS {
    description "TTY Server general statistics";
    leaf terminal-length {
      xr:xr-xml-map "tty_general:TerminalLength";
      type uint32;
      description "Terminal length";
    }
    leaf terminal-width {
      xr:xr-xml-map "tty_general:TerminalWidth";
      type uint32;
      description "Line width";
    }
    leaf async-interface {
      xr:xr-xml-map "tty_general:AsyncInterface";
      type boolean;
      description "Usable as async interface";
    }
    leaf flow-control-start-character {
      xr:xr-xml-map "tty_general:FlowControlStartCharacter";
      type int8;
      description "Software flow control start char";
    }
    leaf flow-control-stop-character {
      xr:xr-xml-map "tty_general:FlowControlStopCharacter";
      type int8;
      description "Software flow control stop char";
    }
    leaf domain-lookup-enabled {
      xr:xr-xml-map "tty_general:DomainLookupEnabled";
      type boolean;
      description "DNS resolution enabled";
    }
    leaf motd-banner-enabled {
      xr:xr-xml-map "tty_general:MOTDBannerEnabled";
      type boolean;
      description "MOTD banner enabled";
    }
    leaf private-flag {
      xr:xr-xml-map "tty_general:PrivateFlag";
      type boolean;
      description "TTY private flag";
    }
    leaf terminal-type {
      xr:xr-xml-map "tty_general:TerminalType";
      type string;
      description "Terminal type";
    }
    leaf absolute-timeout {
      xr:xr-xml-map "tty_general:AbsoluteTimeout";
      type uint32;
      description "Absolute timeout period";
    }
    leaf idle-time {
      xr:xr-xml-map "tty_general:IdleTime";
      type uint32;
      description "TTY idle time";
    }
  }
}
