module Cisco-IOS-XR-aaa-locald-admin-cfg {

  /*** NAMESPACE / PREFIX DEFINITION ***/

  namespace "http://cisco.com/ns/yang"+
    "/Cisco-IOS-XR-aaa-locald-admin-cfg";


  prefix "aaa-locald-admin-cfg";

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR aaa-locald package admin-plane configuration.

     This module contains definitions
     for the following management objects:
       aaa: Admin plane AAA configuration

     Copyright (c) 2013-2016 by Cisco Systems, Inc.
     All rights reserved.";

  revision "2015-11-09" {
    description
      "IOS XR 6.0 revision.";
  }


  container aaa {
    xr:xr-xml-map "aaa_locald_admincfg:AAA";
    description "Admin plane AAA configuration";

    container usernames {
      xr:xr-xml-map "aaa_locald_admincfg:UsernameTable";
      description "Configure local username";

      list username {
        xr:xr-xml-map "aaa_locald_admincfg:Username";
        key "name";
        description "Admin Username";

        container usergroup-under-usernames {
          xr:xr-xml-map "aaa_locald_admincfg:UsergroupsUnderUsernam"+
            "e";
          description
            "Specify the usergroup to which this admin user
            belongs";

          list usergroup-under-username {
            xr:xr-xml-map "aaa_locald_admincfg:UsergroupUnderUserna"+
              "me";
            xr:xr-cli-map "username <string> group (root-system)|(c"+
              "isco-support) ";
            key "name";
            description "Name of the usergroup";
            leaf name {
              xr:xr-xml-map "aaa_locald_admincfg:Name";
              type xr:Cisco-ios-xr-string;
              description "Name of the usergroup";
            }
          }
        }
        leaf secret {
          xr:xr-xml-map "aaa_locald_admincfg:Secret";
          type xr:Md5-password;
          description "Specify the secret for the admin user";
        }
        leaf name {
          xr:xr-xml-map "aaa_locald_admincfg:Name";
          type string;
          description "Username";
        }
      }
    }
  }
}
