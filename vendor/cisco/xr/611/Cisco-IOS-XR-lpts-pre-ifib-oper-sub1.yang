submodule Cisco-IOS-XR-lpts-pre-ifib-oper-sub1 {

  belongs-to Cisco-IOS-XR-lpts-pre-ifib-oper {
    prefix Cisco-IOS-XR-lpts-pre-ifib-oper;
  }

  /*** LINKAGE (IMPORTS / INCLUDES) ***/

  import ietf-yang-types { prefix "yang"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR lpts-pre-ifib package operational data.

     Copyright (c) 2013-2016 by Cisco Systems, Inc.
     All rights reserved.";

  revision "2016-02-22" {
    description
      "Initial revision for pre-ifib oper yang.";
  }

  revision "2015-11-09" {
    description
      "IOS XR 6.0 revision.";
  }


  grouping TIMEVAL-ENTRY {
    description "Creatation or Update Time";
    leaf usectime {
      xr:xr-xml-map "pifib:usectime";
      type uint32;
      description "Time";
    }
    leaf umilitime {
      xr:xr-xml-map "pifib:umilitime";
      type uint32;
      description "Mili Time";
    }
  }

  grouping PIFIB-SHOW-ENTRY {
    description "LPTS Pre-IFIB Entry Information";

    container utime {
      description "Creatation or Update Time";
      uses TIMEVAL-ENTRY;
    }
    leaf vid {
      xr:xr-xml-map "pifib:vID";
      type uint32;
      description "VRF ID";
    }
    leaf l3protocol {
      xr:xr-xml-map "pifib:l3protocol";
      type uint32;
      description "Layer 3 Protocol";
    }
    leaf l4protocol {
      xr:xr-xml-map "pifib:l4protocol";
      type uint32;
      description "Layer 4 Protocol";
    }
    leaf intf-handle {
      xr:xr-xml-map "pifib:intf_handle";
      type uint32;
      description "Interface Handle";
    }
    leaf local-addr {
      xr:xr-xml-map "pifib:local_addr";
      type yang:hex-string;
      description "Local IP Address";
    }
    leaf local-prefix-len {
      xr:xr-xml-map "pifib:local_prefix_len";
      type uint32;
      description "Local Prefix Length";
    }
    leaf remote-addr {
      xr:xr-xml-map "pifib:remote_addr";
      type yang:hex-string;
      description "Remote IP Address";
    }
    leaf remote-prefix-len {
      xr:xr-xml-map "pifib:remote_prefix_len";
      type uint32;
      description "Remote Prefix Length";
    }
    leaf u-type {
      xr:xr-xml-map "pifib:u_type";
      type uint8;
      description "Union Key Type";
    }
    leaf u-value {
      xr:xr-xml-map "pifib:u_value";
      type uint32;
      description "Local Port/ICMP Type/IGMP Type";
    }
    leaf u-len {
      xr:xr-xml-map "pifib:u_len";
      type uint32;
      description "Union Key Length";
    }
    leaf remote-port {
      xr:xr-xml-map "pifib:remote_port";
      type uint16;
      description "Remote port";
    }
    leaf is-frag {
      xr:xr-xml-map "pifib:is_frag";
      type uint8;
      description "Is Fragment";
    }
    leaf is-syn {
      xr:xr-xml-map "pifib:is_syn";
      type uint8;
      description "Is SYN";
    }
    leaf opcode {
      xr:xr-xml-map "pifib:opcode";
      type uint8;
      description "Opcode";
    }
    leaf flow-type {
      xr:xr-xml-map "pifib:flow_type";
      type uint32;
      description "Flow type";
    }
    leaf listener-tag {
      xr:xr-xml-map "pifib:listener_tag";
      type uint8;
      description "Listener Tag";
    }
    leaf local-flag {
      xr:xr-xml-map "pifib:local_flag";
      type uint8;
      description "Local Flag";
    }
    leaf is-fgid {
      xr:xr-xml-map "pifib:is_fgid";
      type uint8;
      description "Is FGID or not";
    }
    leaf deliver-list {
      xr:xr-xml-map "pifib:deliver_list";
      type uint32;
      description "Deliver List";
    }
    leaf deliver-list-str {
      xr:xr-xml-map "pifib:deliver_list_str";
      type string {
        length "0..1024";
      }
      description "Deliver List String";
    }
    leaf min-ttl {
      xr:xr-xml-map "pifib:min_ttl";
      type uint8;
      description "Minimum TTL";
    }
    leaf accepts {
      xr:xr-xml-map "pifib:accepts";
      type uint64;
      description "Packets matched to accept";
    }
    leaf drops {
      xr:xr-xml-map "pifib:drops";
      type uint64;
      description "Packets matched for drop";
    }
    leaf stale {
      xr:xr-xml-map "pifib:stale";
      type uint8;
      description "Is Stale";
    }
    leaf pifib-type {
      xr:xr-xml-map "pifib:pifib_type";
      type uint8;
      description "sub Pre-IFIB type";
    }
  }
}
