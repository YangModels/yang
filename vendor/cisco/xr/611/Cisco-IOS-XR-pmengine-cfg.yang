module Cisco-IOS-XR-pmengine-cfg {

  /*** NAMESPACE / PREFIX DEFINITION ***/

  namespace "http://cisco.com/ns/yang/Cisco-IOS-XR-pmengine-cfg";


  prefix "pmengine-cfg";

  /*** LINKAGE (IMPORTS / INCLUDES) ***/

  import Cisco-IOS-XR-types { prefix "xr"; }

  import Cisco-IOS-XR-ifmgr-cfg { prefix "a1"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR pmengine package configuration.

     This YANG module augments the
       Cisco-IOS-XR-ifmgr-cfg
     module with configuration data.

     Copyright (c) 2013-2016 by Cisco Systems, Inc.
     All rights reserved.";

  revision "2015-11-09" {
    description
      "IOS XR 6.0 revision.";
  }

  typedef Gfp-report {
    type enumeration {
      enum report-rx-bit-err {
        value 6291456;
        description "PM GFP rx bit err report";
      }
      enum report-rx-inv-typ {
        value 6291457;
        description "PM GFP rx inv type report";
      }
      enum report-rx-crc {
        value 6291458;
        description "PM GFP rx crc report";
      }
      enum report-rx-lfd {
        value 6291459;
        description "PM GFP rx lfd report";
      }
      enum report-rx-csf {
        value 6291460;
        description "PM GFP rx csf report";
      }
    }
    description "Gfp report";
  }
  typedef Ho-vc-threshold {
    type enumeration {
      enum thresh-eb {
        value 33554432;
        description "PM EB threshold";
      }
      enum thresh-es {
        value 33554433;
        description "PM ES threshold";
      }
      enum thresh-esr {
        value 33554434;
        description "PM ESR threshold";
      }
      enum thresh-ses {
        value 33554435;
        description "PM SES threshold";
      }
      enum thresh-sesr {
        value 33554436;
        description "PM SESR threshold";
      }
      enum thresh-bbe {
        value 33554437;
        description "PM BBE threshold";
      }
      enum thresh-bber {
        value 33554438;
        description "PM BBER threshold";
      }
      enum thresh-uass {
        value 33554439;
        description "PM UASS threshold";
      }
    }
    description "Ho vc threshold";
  }
  typedef Ether-threshold {
    type enumeration {
      enum thresh-rx-pkt {
        value 8388608;
        description "PM Ether rx pkt threshold";
      }
      enum thresh-rx-util {
        value 8388609;
        description "PM Ether rx util threshold";
      }
      enum thresh-tx-util {
        value 8388610;
        description "PM Ether tx util threshold";
      }
      enum thresh-stat-pkt {
        value 8388611;
        description "PM ether stat pkt threshold";
      }
      enum thresh-octet-stat {
        value 8388612;
        description "PM Ether octet stat threshold";
      }
      enum thresh-over-size-pkt {
        value 8388613;
        description "PM Ether oversize pkt threshold";
      }
      enum thresh-fcs-err {
        value 8388614;
        description "PMEther fcs error threshold";
      }
      enum thresh-long-frame-s {
        value 8388615;
        description "PM Ether long frames threshold";
      }
      enum thresh-jabber-stats {
        value 8388616;
        description "PM Ether jabber stats threshold";
      }
      enum thresh-64-octet {
        value 8388617;
        description "PM Ether 64 octet threshold";
      }
      enum thresh-65-127-octet {
        value 8388618;
        description "PM Ether 65 to 127 octet threshold";
      }
      enum thresh-128-255-octet {
        value 8388619;
        description "PM Ether 128 to 255 octet threshold";
      }
      enum thresh-256-511-octet {
        value 8388620;
        description "PM Ether 256 to 511 octet threshold";
      }
      enum thresh-512-1023-octet {
        value 8388621;
        description "PM Ether 512 to 1023 octet threshold";
      }
      enum thresh-1024-1518-octet {
        value 8388622;
        description "PM Ether 1024 to 1518 threshold";
      }
      enum thresh-in-ucast {
        value 8388623;
        description "PM Ether rx ucast threshold";
      }
      enum thresh-in-mcast {
        value 8388624;
        description "PM Ether rx mcast threshold";
      }
      enum thresh-in-bcast {
        value 8388625;
        description "PM Ether rx bcast threshold";
      }
      enum thresh-out-ucast {
        value 8388626;
        description "PM Ether tx ucast threshold";
      }
      enum thresh-out-mcast {
        value 8388627;
        description "PM Ether tx mcast threshold";
      }
      enum thresh-out-bcast {
        value 8388628;
        description "PM Ether tx bcast threshold";
      }
      enum thresh-tx-pkt {
        value 8388629;
        description "PM Ether tx pkt threshold";
      }
      enum thresh-ifin-error-s {
        value 8388630;
        description "PM ether ifIn errors threshold";
      }
      enum thresh-ifin-octets {
        value 8388631;
        description "PM ether ifInOctets threshold";
      }
      enum thresh-ether-stat-multicast-pkt {
        value 8388632;
        description "PM ether stat multicast pkt threshold";
      }
      enum thresh-ether-stat-broadcast-pkt {
        value 8388633;
        description "PM ether stat broadcast pkt threshold";
      }
      enum thresh-ether-stat-under-size-d-pkt {
        value 8388634;
        description "PM ether stat undersized pkt threshold";
      }
      enum thresh-out-octet {
        value 8388635;
        description "PM ether out octets threshold";
      }
      enum thresh-in-pause-frame {
        value 8388636;
        description "PM in pause frame threshold";
      }
      enum thresh-in-go-od-bytes {
        value 8388637;
        description "PM in good bytes threshold";
      }
      enum thresh-in-802-1q-frame-s {
        value 8388638;
        description "PM in 802_1 Q threshold";
      }
      enum thresh-in-pkts-1519-max-octets {
        value 8388639;
        description "PM in pkts 1519 max octets threshold";
      }
      enum thresh-in-go-od-pkts {
        value 8388640;
        description "PM in good pkts threshold";
      }
      enum thresh-in-drop-overrun {
        value 8388641;
        description "PM in drop overrun threshold";
      }
      enum thresh-in-drop-abort {
        value 8388642;
        description "PM in drop abort threshold";
      }
      enum thresh-in-drop-invalid-vlan {
        value 8388643;
        description "PM in drop invalid vlan threshold";
      }
      enum thresh-in-drop-invalid-dmac {
        value 8388644;
        description "PM in drop invalid DMAC threshold";
      }
      enum thresh-in-drop-invalid-encap {
        value 8388645;
        description "PM in drop invalid encap threshold";
      }
      enum thresh-in-drop-other {
        value 8388646;
        description "PM in drop other threshold";
      }
      enum thresh-in-mib-giant {
        value 8388647;
        description "PM in MIB giant threshold";
      }
      enum thresh-in-mib-jabber {
        value 8388648;
        description "PM in MIB jabber threshold";
      }
      enum thresh-in-mib-crc {
        value 8388649;
        description "PM in MIB CRC threshold";
      }
      enum thresh-in-error-collision-s {
        value 8388650;
        description "PM in error collisions threshold";
      }
      enum thresh-in-error-symbol {
        value 8388651;
        description "PM in error symbol threshold";
      }
      enum thresh-out-go-od-bytes {
        value 8388652;
        description "PM out good bytes threshold";
      }
      enum thresh-out-802-1q-frame-s {
        value 8388653;
        description "PM out 802_1 Q threshold";
      }
      enum thresh-out-pause-frame-s {
        value 8388654;
        description "PM out pause frame threshold";
      }
      enum thresh-out-pkts-1519-max-octets {
        value 8388655;
        description "PM out pkts 1519 max octets threshold";
      }
      enum thresh-out-go-od-pkts {
        value 8388656;
        description "PM out good pkts threshold";
      }
      enum thresh-out-drop-under-run {
        value 8388657;
        description "PM out drop underrun threshold";
      }
      enum thresh-out-drop-abort {
        value 8388658;
        description "PM out drop abort threshold";
      }
      enum thresh-out-drop-other {
        value 8388659;
        description "PM out drop other threshold";
      }
      enum thresh-out-error-other {
        value 8388660;
        description "PM out error other threshold";
      }
      enum thresh-in-error-giant {
        value 8388661;
        description "PM in error giant threshold";
      }
      enum thresh-in-error-runt {
        value 8388662;
        description "PM in error runt threshold";
      }
      enum thresh-in-error-jabbers {
        value 8388663;
        description "PM in error jabber threshold";
      }
      enum thresh-in-error-fragments {
        value 8388664;
        description "PM in error fragments threshold";
      }
      enum thresh-in-error-other {
        value 8388665;
        description "PM in error other threshold";
      }
      enum thresh-in-pkt-64-octet {
        value 8388666;
        description "PM in pkt 64 octet threshold";
      }
      enum thresh-in-pkts-65-127octets {
        value 8388667;
        description "PM in pkts 65_127 octets threshold";
      }
      enum thresh-in-pkts-128-255-octets {
        value 8388668;
        description "PM in pkts 128_255 octets threshold";
      }
      enum thresh-in-pkts-256-511-octets {
        value 8388669;
        description "PM in pkts 256_511 octets threshold";
      }
      enum thresh-in-pkts-512-1023-octets {
        value 8388670;
        description "PM in pkts 512_1023 octets threshold";
      }
      enum thresh-in-pkts-1024-1518-octets {
        value 8388671;
        description "PM in pkts 1024_1058 octets threshold";
      }
      enum thresh-out-pkt-64-octet {
        value 8388672;
        description "PM out pkt 64 octet threshold";
      }
      enum thresh-out-pkts-65-127octets {
        value 8388673;
        description "PM out pkts 65_127 octets threshold";
      }
      enum thresh-out-pkts-128-255-octets {
        value 8388674;
        description "PM out pkts 128_255 octets threshold";
      }
      enum thresh-out-pkts-256-511-octets {
        value 8388675;
        description "PM out pkts 256_511 octets threshold";
      }
      enum thresh-out-pkts-512-1023-octets {
        value 8388676;
        description "PM out pkts 512_1023 octets threshold";
      }
      enum thresh-out-pkts-1024-1518-octets {
        value 8388677;
        description "PM out pkts 1024_1058 octets threshold";
      }
      enum thresh-tx-under-size-d-pkt {
        value 8388678;
        description "PM tx undersized pkt threshold";
      }
      enum thresh-tx-over-size-d-pkt {
        value 8388679;
        description "PM tx oversized pkt threshold";
      }
      enum thresh-tx-fragments {
        value 8388680;
        description "PM tx fragments threshold";
      }
      enum thresh-tx-jabber {
        value 8388681;
        description "PM tx jabber threshold";
      }
      enum thresh-tx-bad-fcs {
        value 8388682;
        description "PM tx bad fcs threshold";
      }
    }
    description "Ether threshold";
  }
  typedef Path-threshold {
    type enumeration {
      enum thresh-cv {
        value 5242880;
        description "PM CV threshold";
      }
      enum thresh-es {
        value 5242881;
        description "PM ES threshold";
      }
      enum thresh-ses {
        value 5242882;
        description "PM SES threshold";
      }
      enum thresh-uas {
        value 5242883;
        description "PM UAS threshold";
      }
    }
    description "Path threshold";
  }
  typedef Sts-threshold {
    type enumeration {
      enum thresh-cv {
        value 4194304;
        description "PM CV threshold";
      }
      enum thresh-es {
        value 4194305;
        description "PM ES threshold";
      }
      enum thresh-ses {
        value 4194306;
        description "PM SES threshold";
      }
      enum thresh-uas {
        value 4194307;
        description "PM UAS threshold";
      }
    }
    description "Sts threshold";
  }
  typedef Ocn-report {
    type enumeration {
      enum report-sefss {
        value 3145728;
        description "PM SEFSS threshold";
      }
      enum report-cvs {
        value 3145729;
        description "PM CVS threshold";
      }
      enum report-ess {
        value 3145730;
        description "PM ESS threshold";
      }
      enum report-sess {
        value 3145731;
        description "PM SESS threshold";
      }
      enum report-cvl-ne {
        value 3145734;
        description "PM CVL-NE threshold";
      }
      enum report-esl-ne {
        value 3145735;
        description "PM ESL-NE threshold";
      }
      enum report-sesl-ne {
        value 3145736;
        description "PM SESL-NE threshold";
      }
      enum report-uasl-ne {
        value 3145738;
        description "PM UASL-NE threshold";
      }
      enum report-fcl-ne {
        value 3145739;
        description "PM FCL-NE threshold";
      }
      enum report-fcl-fe {
        value 3145751;
        description "PM FCL_FE threshold";
      }
      enum report-cvl-fe {
        value 3145752;
        description "PM CVL-FE threshold";
      }
      enum report-esl-fe {
        value 3145753;
        description "PM ESL_FE threshold";
      }
      enum report-sesl-fe {
        value 3145754;
        description "PM SESL_FE threshold";
      }
      enum report-uasl-fe {
        value 3145756;
        description "PM UASL_FEthreshold";
      }
    }
    description "Ocn report";
  }
  typedef Ho-vc-report {
    type enumeration {
      enum report-eb {
        value 33554432;
        description "PM EB report";
      }
      enum report-es {
        value 33554433;
        description "PM ES report";
      }
      enum report-esr {
        value 33554434;
        description "PM ESR report";
      }
      enum report-ses {
        value 33554435;
        description "PM SES report";
      }
      enum report-sesr {
        value 33554436;
        description "PM SESR report";
      }
      enum report-bbe {
        value 33554437;
        description "PM BBE report";
      }
      enum report-bber {
        value 33554438;
        description "PM BBER report";
      }
      enum report-uass {
        value 33554439;
        description "PM UASS report";
      }
    }
    description "Ho vc report";
  }
  typedef Otn-threshold {
    type enumeration {
      enum thresh-es-sm-ne {
        value 262144;
        description "PM Otn es sm ne threshold";
      }
      enum thresh-ses-sm-ne {
        value 262145;
        description "PM Otn ses sm ne threshold";
      }
      enum thresh-uas-sm-ne {
        value 262146;
        description "PM Otn uas sm ne threshold";
      }
      enum thresh-bbe-sm-ne {
        value 262147;
        description "PM Otn bbe sm ne threshold";
      }
      enum thresh-fc-sm-ne {
        value 262148;
        description "PM Otn fc sm ne threshold";
      }
      enum thresh-esr-sm-ne {
        value 262149;
        description "PM Otn esr sm ne threshold";
      }
      enum thresh-sesr-sm-ne {
        value 262150;
        description "PM Otn sesr sm ne threshold";
      }
      enum thresh-bber-sm-ne {
        value 262151;
        description "PM Otn bber sm ne threshold";
      }
      enum thresh-es-pm-ne {
        value 524288;
        description "PM Otn es pm ne threshold";
      }
      enum thresh-ses-pm-ne {
        value 524289;
        description "PM Otn ses pm ne threshold";
      }
      enum thresh-uas-pm-ne {
        value 524290;
        description "PM Otn uas pm ne threshold";
      }
      enum thresh-bbe-pm-ne {
        value 524291;
        description "PM Otn bbe pm ne threshold";
      }
      enum thresh-fc-pm-ne {
        value 524292;
        description "PM Otn fc pm ne threshold";
      }
      enum thresh-esr-pm-ne {
        value 524293;
        description "PM Otn esr pm ne threshold";
      }
      enum thresh-sesr-pm-ne {
        value 524294;
        description "PM Otn sesr pm ne threshold";
      }
      enum thresh-bber-pm-ne {
        value 524295;
        description "PM Otn bber pm ne threshold";
      }
      enum thresh-es-sm-fe {
        value 1048584;
        description "PM Otn es sm fe threshold";
      }
      enum thresh-ses-sm-fe {
        value 1048585;
        description "PM Otn ses sm fe threshold";
      }
      enum thresh-uas-sm-fe {
        value 1048586;
        description "PM Otn uas sm fe threshold";
      }
      enum thresh-bbe-sm-fe {
        value 1048587;
        description "PM Otn bbe sm fe threshold";
      }
      enum thresh-fc-sm-fe {
        value 1048588;
        description "PM Otn fc sm fe threshold";
      }
      enum thresh-esr-sm-fe {
        value 1048589;
        description "PM Otn esr sm fe threshold";
      }
      enum thresh-sesr-sm-fe {
        value 1048590;
        description "PM Otn sesr sm fe threshold";
      }
      enum thresh-bber-sm-fe {
        value 1048591;
        description "PM Otn bber sm fe threshold";
      }
      enum thresh-es-pm-fe {
        value 2097160;
        description "PM Otn es pm fe threshold";
      }
      enum thresh-ses-pm-fe {
        value 2097161;
        description "PM Otn ses pm fe threshold";
      }
      enum thresh-uas-pm-fe {
        value 2097162;
        description "PM Otn uas pm fe threshold";
      }
      enum thresh-bbe-pm-fe {
        value 2097163;
        description "PM Otn bbe pm fe threshold";
      }
      enum thresh-fc-pm-fe {
        value 2097164;
        description "PM Otn fc pm fe threshold";
      }
      enum thresh-esr-pm-fe {
        value 2097165;
        description "PM Otn esr pm fe threshold";
      }
      enum thresh-sesr-pm-fe {
        value 2097166;
        description "PM Otn sesr pm fe threshold";
      }
      enum thresh-bber-pm-fe {
        value 2097167;
        description "PM Otn bber pm fe threshold";
      }
    }
    description "Otn threshold";
  }
  typedef Optics-threshold {
    type enumeration {
      enum thresh-opt-min {
        value 65550;
        description "PM Optics opt min threshold in dbm or uW";
      }
      enum thresh-opr-min {
        value 65551;
        description "PM Optics opr min threshold in dbm or uW";
      }
      enum thresh-lbc-min {
        value 65552;
        description "PM Optics lbc min threshold";
      }
      enum thresh-lbc-pc-min {
        value 65553;
        description "PM Optics lbcpc min threshold";
      }
      enum thresh-cd-min {
        value 65557;
        description "PM Optics cd min threshold";
      }
      enum thresh-dgd-min {
        value 65558;
        description "PM Optics dgd min threshold";
      }
      enum thresh-pmd-min {
        value 65559;
        description "PM Optics sopmd min threshold";
      }
      enum thresh-osnr-min {
        value 65560;
        description "PM Optics osnr min threshold";
      }
      enum thresh-pdl-min {
        value 65561;
        description "PM Optics pdl min threshold";
      }
      enum thresh-pcr-min {
        value 65562;
        description "PM Optics pcr min threshold";
      }
      enum thresh-pn-min {
        value 65563;
        description "PM Optics pn min threshold";
      }
      enum thresh-opt-max {
        value 65564;
        description "PM Optics opt max threshold in dbm or uW";
      }
      enum thresh-opr-max {
        value 65565;
        description "PM Optics opr max threshold in dbm or uW";
      }
      enum thresh-lbc-max {
        value 65566;
        description "PM Optics lbc max threshold";
      }
      enum thresh-lbc-pc-max {
        value 65567;
        description "PM Optics lbcpc max threshold";
      }
      enum thresh-cd-max {
        value 65571;
        description "PM Optics cd max threshold";
      }
      enum thresh-dgd-max {
        value 65572;
        description "PM Optics dgd max threshold";
      }
      enum thresh-pmd-max {
        value 65573;
        description "PM Optics sopmd max threshold";
      }
      enum thresh-osnr-max {
        value 65574;
        description "PM Optics osnr max threshold";
      }
      enum thresh-pdl-max {
        value 65575;
        description "PM Optics pdl max threshold";
      }
      enum thresh-pcr-max {
        value 65576;
        description "PM Optics pcr max threshold";
      }
      enum thresh-pn-max {
        value 65577;
        description "PM Optics pn max threshold";
      }
    }
    description "Optics threshold";
  }
  typedef Ocn-threshold {
    type enumeration {
      enum thresh-sefss {
        value 3145728;
        description "PM SEFSS threshold";
      }
      enum thresh-cvs {
        value 3145729;
        description "PM CVS threshold";
      }
      enum thresh-ess {
        value 3145730;
        description "PM ESS threshold";
      }
      enum thresh-sess {
        value 3145731;
        description "PM SESS threshold";
      }
      enum thresh-cvl-ne {
        value 3145734;
        description "PM CVL-NE threshold";
      }
      enum thresh-esl-ne {
        value 3145735;
        description "PM ESL-NE threshold";
      }
      enum thresh-sesl-ne {
        value 3145736;
        description "PM SESL-NE threshold";
      }
      enum thresh-uasl-ne {
        value 3145738;
        description "PM UASL-NE threshold";
      }
      enum thresh-fcl-ne {
        value 3145739;
        description "PM FCL-NE threshold";
      }
      enum thresh-fcl-fe {
        value 3145751;
        description "PM FCL_FE threshold";
      }
      enum thresh-cvl-fe {
        value 3145752;
        description "PM CVL-FE threshold";
      }
      enum thresh-esl-fe {
        value 3145753;
        description "PM ESL_FE threshold";
      }
      enum thresh-sesl-fe {
        value 3145754;
        description "PM SESL_FE threshold";
      }
      enum thresh-uasl-fe {
        value 3145756;
        description "PM UASL_FEthreshold";
      }
    }
    description "Ocn threshold";
  }
  typedef Optics-report {
    type enumeration {
      enum report-opt-min {
        value 65550;
        description "PM Optics opt min report";
      }
      enum report-opr-min {
        value 65551;
        description "PM Optics opr min report";
      }
      enum report-lbc-min {
        value 65552;
        description "PM Optics lbc min report";
      }
      enum report-lbc-pc-min {
        value 65553;
        description "PM Optics lbcpc min report";
      }
      enum report-cd-min {
        value 65557;
        description "PM Optics cd min report";
      }
      enum report-dgd-min {
        value 65558;
        description "PM Optics dgd min report";
      }
      enum report-pmd-min {
        value 65559;
        description "PM Optics sopmd min report";
      }
      enum report-osnr-min {
        value 65560;
        description "PM Optics osnr min report";
      }
      enum report-pdl-min {
        value 65561;
        description "PM Optics pdl min report";
      }
      enum report-pcr-min {
        value 65562;
        description "PM Optics pcr min report";
      }
      enum report-pn-min {
        value 65563;
        description "PM Optics pn min report";
      }
      enum report-opt-max {
        value 65564;
        description "PM Optics opt max report";
      }
      enum report-opr-max {
        value 65565;
        description "PM Optics opr max report";
      }
      enum report-lbc-max {
        value 65566;
        description "PM Optics lbc max report";
      }
      enum report-lbc-pc-max {
        value 65567;
        description "PM Optics lbcpc max report";
      }
      enum report-cd-max {
        value 65571;
        description "PM Optics cd max report";
      }
      enum report-dgd-max {
        value 65572;
        description "PM Optics dgd max report";
      }
      enum report-pmd-max {
        value 65573;
        description "PM Optics sopmd max report";
      }
      enum report-osnr-max {
        value 65574;
        description "PM Optics osnr max report";
      }
      enum report-pdl-max {
        value 65575;
        description "PM Optics pdl max report";
      }
      enum report-pcr-max {
        value 65576;
        description "PM Optics pcr max report";
      }
      enum report-pn-max {
        value 65577;
        description "PM Optics pn max report";
      }
    }
    description "Optics report";
  }
  typedef Ether-report {
    type enumeration {
      enum report-rx-pkt {
        value 524288;
        description "PM Ether rx pkt report";
      }
      enum report-rx-util {
        value 524289;
        description "PM Ether rx util report";
      }
      enum report-tx-util {
        value 524290;
        description "PM Ether tx util report";
      }
      enum report-stat-pkt {
        value 524291;
        description "PM ether stat pkt threshold";
      }
      enum report-octet-stat {
        value 524292;
        description "PM Ether octet stat report";
      }
      enum report-over-size-pkt {
        value 524293;
        description "PM Ether oversize pkt report";
      }
      enum report-fcs-err {
        value 524294;
        description "PM Ether fcs error report";
      }
      enum report-long-frame-s {
        value 524295;
        description "PM Ether long frames report";
      }
      enum report-jabber-stats {
        value 524296;
        description "PM Ether jabber stats report";
      }
      enum report-64-octet {
        value 524297;
        description "PM Ether 64 octet report";
      }
      enum report-65-127-octet {
        value 524298;
        description "PM Ether 65 to 127 octet report";
      }
      enum report-128-255-octet {
        value 524299;
        description "PM Ether 128 to 255 octet report";
      }
      enum report-256-511-octet {
        value 524300;
        description "PM Ether 256 to 511 octet report";
      }
      enum report-512-1023-octet {
        value 524301;
        description "PM Ether 512 to 1023 octet report";
      }
      enum report-1024-1518-octet {
        value 524302;
        description "PM Ether 1024 to 1518 report";
      }
      enum report-in-ucast {
        value 524303;
        description "PM Ether rx ucast report";
      }
      enum report-in-mcast {
        value 524304;
        description "PM Ether rx mcast report";
      }
      enum report-in-bcast {
        value 524305;
        description "PM Ether rx bcast report";
      }
      enum report-out-ucast {
        value 524306;
        description "PM Ether tx ucast report";
      }
      enum report-out-mcast {
        value 524307;
        description "PM Ether tx mcast report";
      }
      enum report-out-bcast {
        value 524308;
        description "PM Ether tx bcast report";
      }
      enum report-tx-pkt {
        value 524309;
        description "PM Ether tx pkt threshold";
      }
      enum report-ifin-error-s {
        value 524310;
        description "PM ether ifIn errors threshold";
      }
      enum report-ifin-octets {
        value 524311;
        description "PM ether ifInOctets threshold";
      }
      enum report-ether-stat-multicast-pkt {
        value 524312;
        description "PM ether stat multicast pkt threshold";
      }
      enum report-ether-stat-broadcast-pkt {
        value 524313;
        description "PM ether stat broadcast pkt threshold";
      }
      enum report-ether-stat-under-size-d-pkt {
        value 524314;
        description "PM ether stat undersized pkt threshold";
      }
      enum report-out-octet {
        value 524315;
        description "PM ether out octets threshold";
      }
      enum report-in-pause-frame {
        value 524316;
        description "PM ether in pause frame report";
      }
      enum report-in-go-od-bytes {
        value 524317;
        description "PM in good bytes report";
      }
      enum report-in-802-1q-frame-s {
        value 524318;
        description "PM in 802_1 Q report";
      }
      enum report-in-pkts-1519-max-octets {
        value 524319;
        description "PM in pkts 1519 max octets report";
      }
      enum report-in-go-od-pkts {
        value 524320;
        description "PM in good pkts report";
      }
      enum report-in-drop-overrun {
        value 524321;
        description "PM in drop overrun report";
      }
      enum report-in-drop-abort {
        value 524322;
        description "PM in drop abort report";
      }
      enum report-in-drop-invalid-vlan {
        value 524323;
        description "PM in drop invalid vlan report";
      }
      enum report-in-drop-invalid-dmac {
        value 524324;
        description "PM in drop invalid DMAC report";
      }
      enum report-in-drop-invalid-encap {
        value 524325;
        description "PM in drop invalid encap report";
      }
      enum report-in-drop-other {
        value 524326;
        description "PM in drop other report";
      }
      enum report-in-mib-giant {
        value 524327;
        description "PM in MIB giant report";
      }
      enum report-in-mib-jabber {
        value 524328;
        description "PM in MIB jabber report";
      }
      enum report-in-mib-crc {
        value 524329;
        description "PM in MIB CRC report";
      }
      enum report-in-error-collision-s {
        value 524330;
        description "PM in error collisions report";
      }
      enum report-in-error-symbol {
        value 524331;
        description "PM in error symbol report";
      }
      enum report-out-go-od-bytes {
        value 524332;
        description "PM out good bytes report";
      }
      enum report-out-802-1q-frame-s {
        value 524333;
        description "PM out 802_1 Q report";
      }
      enum report-out-pause-frame-s {
        value 524334;
        description "PM out pause frame report";
      }
      enum report-out-pkts-1519-max-octets {
        value 524335;
        description "PM out pkts 1519 max octets report";
      }
      enum report-out-go-od-pkts {
        value 524336;
        description "PM out good pkts report";
      }
      enum report-out-drop-under-run {
        value 524337;
        description "PM out drop underrun report";
      }
      enum report-out-drop-abort {
        value 524338;
        description "PM out drop abort report";
      }
      enum report-out-drop-other {
        value 524339;
        description "PM out drop other report";
      }
      enum report-out-error-other {
        value 524340;
        description "PM out error other report";
      }
      enum report-in-error-giant {
        value 524341;
        description "PM in error giant report";
      }
      enum report-in-error-runt {
        value 524342;
        description "PM in error runt report";
      }
      enum report-in-error-jabbers {
        value 524343;
        description "PM in error jabber report";
      }
      enum report-in-error-fragments {
        value 524344;
        description "PM in error fragments report";
      }
      enum report-in-error-other {
        value 524345;
        description "PM in error other report";
      }
      enum report-in-pkt-64-octet {
        value 524346;
        description "PM in pkt 64 octet report";
      }
      enum report-in-pkts-65-127octets {
        value 524347;
        description "PM in pkts 65_127 octets report";
      }
      enum report-in-pkts-128-255-octets {
        value 524348;
        description "PM in pkts 128_255 octets report";
      }
      enum report-in-pkts-256-511-octets {
        value 524349;
        description "PM in pkts 256_511 octets report";
      }
      enum report-in-pkts-512-1023-octets {
        value 524350;
        description "PM in pkts 512_1023 octets report";
      }
      enum report-in-pkts-1024-1518-octets {
        value 524351;
        description "PM in pkts 1024_1058 octets report";
      }
      enum report-out-pkt-64-octet {
        value 524352;
        description "PM out pkt 64 octet report";
      }
      enum report-out-pkts-65-127octets {
        value 524353;
        description "PM out pkts 65_127 octets report";
      }
      enum report-out-pkts-128-255-octets {
        value 524354;
        description "PM out pkts 128_255 octets report";
      }
      enum report-out-pkts-256-511-octets {
        value 524355;
        description "PM out pkts 256_511 octets report";
      }
      enum report-out-pkts-512-1023-octets {
        value 524356;
        description "PM out pkts 512_1023 octets report";
      }
      enum report-out-pkts-1024-1518-octets {
        value 524357;
        description "PM out pkts 1024_1058 octets report";
      }
      enum report-tx-under-size-d-pkt {
        value 524358;
        description "PM tx undersized pkt report";
      }
      enum report-tx-over-size-d-pkt {
        value 524359;
        description "PM tx oversized pkt report";
      }
      enum report-tx-fragments {
        value 524360;
        description "PM tx fragments report";
      }
      enum report-tx-jabber {
        value 524361;
        description "PM tx jabber report";
      }
      enum report-tx-bad-fcs {
        value 524362;
        description "PM tx bad fcs report";
      }
    }
    description "Ether report";
  }
  typedef Otn-tcm-report {
    type enumeration {
      enum report-es-tcm-fe {
        value 16777224;
        description "PM Otn es TCM fe report";
      }
      enum report-ses-tcm-fe {
        value 16777225;
        description "PM Otn ses TCM fe report";
      }
      enum report-uas-tcm-fe {
        value 16777226;
        description "PM Otn uas TCM fe report";
      }
      enum report-bbe-tcm-fe {
        value 16777227;
        description "PM Otn bbe TCM fe report";
      }
      enum report-fc-tcm-fe {
        value 16777228;
        description "PM Otn fc TCM fe report";
      }
      enum report-esr-tcm-fe {
        value 16777229;
        description "PM Otn esr TCM fe report";
      }
      enum report-sesr-tcm-fe {
        value 16777230;
        description "PM Otn sesr TCM fe report";
      }
      enum report-bber-tcm-fe {
        value 16777231;
        description "PM Otn bber TCM fe report";
      }
      enum report-es-tcm-ne {
        value 33554432;
        description "PM Otn es TCM ne report";
      }
      enum report-ses-tcm-ne {
        value 33554433;
        description "PM Otn ses TCM ne report";
      }
      enum report-uas-tcm-ne {
        value 33554434;
        description "PM Otn uas TCM ne report";
      }
      enum report-bbe-tcm-ne {
        value 33554435;
        description "PM Otn bbe TCM ne report";
      }
      enum report-fc-tcm-ne {
        value 33554436;
        description "PM Otn fc TCM ne report";
      }
      enum report-esr-tcm-ne {
        value 33554437;
        description "PM Otn esr TCM ne report";
      }
      enum report-sesr-tcm-ne {
        value 33554438;
        description "PM Otn sesr TCM ne report";
      }
      enum report-bber-tcm-ne {
        value 33554439;
        description "PM Otn bber TCM ne report";
      }
    }
    description "Otn tcm report";
  }
  typedef Fec-threshold {
    type enumeration {
      enum thresh-ec-bits {
        value 131072;
        description "PM Fec ec bits threshold";
      }
      enum thresh-uc-words {
        value 131076;
        description "PM Fec uc words threshold";
      }
      enum thresh-pre-fec-ber-max {
        value 131081;
        description "PM Fec pre-fe-ber max threshold";
      }
      enum thresh-post-fec-ber-max {
        value 131082;
        description "PM Fec post-fec-ber max threshold";
      }
      enum thresh-q-max {
        value 131083;
        description "PM Fec Q max threshold";
      }
      enum thresh-q-margin-max {
        value 131084;
        description "PM Fec uc words max threshold";
      }
      enum thresh-pre-fec-ber-min {
        value 131085;
        description "PM Fec pre-fe-ber min threshold";
      }
      enum thresh-post-fec-ber-min {
        value 131086;
        description "PM Fec post-fec-ber min threshold";
      }
      enum thresh-q-min {
        value 131087;
        description "PM Fec Q min threshold";
      }
      enum thresh-q-margin-min {
        value 131088;
        description "PM Fec uc words min threshold";
      }
    }
    description "Fec threshold";
  }
  typedef Sts-report {
    type enumeration {
      enum report-cv {
        value 4194304;
        description "PM CV threshold";
      }
      enum report-es {
        value 4194305;
        description "PM ES threshold";
      }
      enum report-ses {
        value 4194306;
        description "PM SES threshold";
      }
      enum report-uas {
        value 4194307;
        description "PM UAS threshold";
      }
    }
    description "Sts report";
  }
  typedef Stm-threshold {
    type enumeration {
      enum thresh-ebs {
        value 16777217;
        description "PM EBS threshold";
      }
      enum thresh-ess {
        value 16777218;
        description "PM ESS threshold";
      }
      enum thresh-esrs {
        value 16777219;
        description "PM ESRS threshold";
      }
      enum thresh-sess {
        value 16777220;
        description "PM SES threshold";
      }
      enum thresh-sesrs {
        value 16777221;
        description "PM SESR threshold";
      }
      enum thresh-bbes {
        value 16777222;
        description "PM BBES threshold";
      }
      enum thresh-bbesr {
        value 16777223;
        description "PM BBESR threshold";
      }
      enum thresh-uass {
        value 16777224;
        description "PM UASS threshold";
      }
      enum thresh-ebl-ne {
        value 16777225;
        description "PM EBLNE threshold";
      }
      enum thresh-esl-ne {
        value 16777226;
        description "PM ESLNE threshold";
      }
      enum thresh-eslr-ne {
        value 16777227;
        description "PM ESLRNE threshold";
      }
      enum thresh-sesl-ne {
        value 16777228;
        description "PM SESL threshold";
      }
      enum thresh-sesrl-ne {
        value 16777229;
        description "PM SESRL threshold";
      }
      enum thresh-bbel-ne {
        value 16777230;
        description "PM BBERLNE threshold";
      }
      enum thresh-bberl-ne {
        value 16777231;
        description "PM BBERLNE threshold";
      }
      enum thresh-uasl-ne {
        value 16777232;
        description "PM UASNE threshold";
      }
      enum thresh-ebl-fe {
        value 16777245;
        description "PM EBFE threshold";
      }
      enum thresh-esl-fe {
        value 16777246;
        description "PM ESFE threshold";
      }
      enum thresh-esrl-fe {
        value 16777247;
        description "PM EBFE threshold";
      }
      enum thresh-sesl-fe {
        value 16777248;
        description "PM SESFE threshold";
      }
      enum thresh-sesrl-fe {
        value 16777249;
        description "PM SESRLFE threshold";
      }
      enum thresh-bbel-fe {
        value 16777250;
        description "PM BBEL threshold";
      }
      enum thresh-bberl-fe {
        value 16777251;
        description "PM BBELFE threshold";
      }
      enum thresh-uasl-fe {
        value 16777252;
        description "PM UASLFE threshold";
      }
    }
    description "Stm threshold";
  }
  typedef Otn-tcm-threshold {
    type enumeration {
      enum thresh-es-tcm-fe {
        value 16777224;
        description "PM Otn es TCM fe threshold";
      }
      enum thresh-ses-tcm-fe {
        value 16777225;
        description "PM Otn ses TCM fe threshold";
      }
      enum thresh-uas-tcm-fe {
        value 16777226;
        description "PM Otn uas TCM fe threshold";
      }
      enum thresh-bbe-tcm-fe {
        value 16777227;
        description "PM Otn bbe TCM fe threshold";
      }
      enum thresh-fc-tcm-fe {
        value 16777228;
        description "PM Otn fc TCM fe threshold";
      }
      enum thresh-esr-tcm-fe {
        value 16777229;
        description "PM Otn esr TCM fe threshold";
      }
      enum thresh-sesr-tcm-fe {
        value 16777230;
        description "PM Otn sesr TCM fe threshold";
      }
      enum thresh-bber-tcm-fe {
        value 16777231;
        description "PM Otn bber TCM fe threshold";
      }
      enum thresh-es-tcm-ne {
        value 33554432;
        description "PM Otn es TCM ne threshold";
      }
      enum thresh-ses-tcm-ne {
        value 33554433;
        description "PM Otn ses TCM ne threshold";
      }
      enum thresh-uas-tcm-ne {
        value 33554434;
        description "PM Otn uas TCM ne threshold";
      }
      enum thresh-bbe-tcm-ne {
        value 33554435;
        description "PM Otn bbe TCM ne threshold";
      }
      enum thresh-fc-tcm-ne {
        value 33554436;
        description "PM Otn fc TCM ne threshold";
      }
      enum thresh-esr-tcm-ne {
        value 33554437;
        description "PM Otn esr TCM ne threshold";
      }
      enum thresh-sesr-tcm-ne {
        value 33554438;
        description "PM Otn sesr TCM ne threshold";
      }
      enum thresh-bber-tcm-ne {
        value 33554439;
        description "PM Otn bber TCM ne threshold";
      }
    }
    description "Otn tcm threshold";
  }
  typedef Report {
    type enumeration {
      enum false {
        value 0;
        description "Performance Monitoring Disabled";
      }
      enum true {
        value 1;
        description "Performance Monitoring Enabled";
      }
    }
    description "Report";
  }
  typedef Otn-report {
    type enumeration {
      enum report-es-sm-ne {
        value 262144;
        description "PM Otn es sm ne report";
      }
      enum report-ses-sm-ne {
        value 262145;
        description "PM Otn ses sm ne report";
      }
      enum report-uas-sm-ne {
        value 262146;
        description "PM Otn uas sm ne report";
      }
      enum report-bbe-sm-ne {
        value 262147;
        description "PM Otn bbe sm ne report";
      }
      enum report-fc-sm-ne {
        value 262148;
        description "PM Otn fc sm ne report";
      }
      enum report-esr-sm-ne {
        value 262149;
        description "PM Otn esr sm ne report";
      }
      enum report-sesr-sm-ne {
        value 262150;
        description "PM Otn sesr sm ne report";
      }
      enum report-bber-sm-ne {
        value 262151;
        description "PM Otn bber sm ne report";
      }
      enum report-es-pm-ne {
        value 524288;
        description "PM Otn es pm ne report";
      }
      enum report-ses-pm-ne {
        value 524289;
        description "PM Otn ses pm ne report";
      }
      enum report-uas-pm-ne {
        value 524290;
        description "PM Otn uas pm ne report";
      }
      enum report-bbe-pm-ne {
        value 524291;
        description "PM Otn bbe pm ne report";
      }
      enum report-fc-pm-ne {
        value 524292;
        description "PM Otn fc pm ne report";
      }
      enum report-esr-pm-ne {
        value 524293;
        description "PM Otn esr pm ne report";
      }
      enum report-sesr-pm-ne {
        value 524294;
        description "PM Otn sesr pm ne report";
      }
      enum report-bber-pm-ne {
        value 524295;
        description "PM Otn bber pm ne report";
      }
      enum report-es-sm-fe {
        value 1048584;
        description "PM Otn es sm fe report";
      }
      enum report-ses-sm-fe {
        value 1048585;
        description "PM Otn ses sm fe report";
      }
      enum report-uas-sm-fe {
        value 1048586;
        description "PM Otn uas sm fe report";
      }
      enum report-bbe-sm-fe {
        value 1048587;
        description "PM Otn bbe sm fe report";
      }
      enum report-fc-sm-fe {
        value 1048588;
        description "PM Otn fc sm fe report";
      }
      enum report-esr-sm-fe {
        value 1048589;
        description "PM Otn esr sm fe report";
      }
      enum report-sesr-sm-fe {
        value 1048590;
        description "PM Otn sesr sm fe report";
      }
      enum report-bber-sm-fe {
        value 1048591;
        description "PM Otn bber sm fe report";
      }
      enum report-es-pm-fe {
        value 2097160;
        description "PM Otn es pm fe report";
      }
      enum report-ses-pm-fe {
        value 2097161;
        description "PM Otn ses pm fe report";
      }
      enum report-uas-pm-fe {
        value 2097162;
        description "PM Otn uas pm fe report";
      }
      enum report-bbe-pm-fe {
        value 2097163;
        description "PM Otn bbe pm fe report";
      }
      enum report-fc-pm-fe {
        value 2097164;
        description "PM Otn fc pm fe report";
      }
      enum report-esr-pm-fe {
        value 2097165;
        description "PM Otn esr pm fe report";
      }
      enum report-sesr-pm-fe {
        value 2097166;
        description "PM Otn sesr pm fe report";
      }
      enum report-bber-pm-fe {
        value 2097167;
        description "PM Otn bber pm fe report";
      }
    }
    description "Otn report";
  }
  typedef Fec-report {
    type enumeration {
      enum report-ec-bits {
        value 131072;
        description "PM Fec ec bits report";
      }
      enum report-uc-words {
        value 131076;
        description "PM Fec uc words report";
      }
      enum report-pre-fec-ber-max {
        value 131081;
        description "PM Fec pre fec ber max report";
      }
      enum report-post-fec-ber-max {
        value 131082;
        description "PM Fec post fec ber max report";
      }
      enum report-q-max {
        value 131083;
        description "PM Fec Q max report";
      }
      enum report-q-margin-max {
        value 131084;
        description "PM Fec Q_margin max report";
      }
      enum report-pre-fec-ber-min {
        value 131085;
        description "PM Fec pre fec ber min report";
      }
      enum report-post-fec-ber-min {
        value 131086;
        description "PM Fec post fec ber min report";
      }
      enum report-q-min {
        value 131087;
        description "PM Fec Q min report";
      }
      enum report-q-margin-min {
        value 131088;
        description "PM Fec Q_margin min report";
      }
    }
    description "Fec report";
  }
  typedef Path-report {
    type enumeration {
      enum report-cv {
        value 5242880;
        description "PM CV threshold";
      }
      enum report-es {
        value 5242881;
        description "PM ES threshold";
      }
      enum report-ses {
        value 5242882;
        description "PM SES threshold";
      }
      enum report-uas {
        value 5242883;
        description "PM UAS threshold";
      }
    }
    description "Path report";
  }
  typedef Gfp-threshold {
    type enumeration {
      enum thresh-rx-bit-err {
        value 67108864;
        description "PM GFP rx bit err threshold";
      }
      enum thresh-rx-inv-typ {
        value 67108865;
        description "PM GFP rx inv type threshold";
      }
      enum thresh-rx-crc {
        value 67108866;
        description "PM GFP rx crc threshold";
      }
      enum thresh-rx-lfd {
        value 67108867;
        description "PM GFP rx lfd threshold";
      }
      enum thresh-rx-csf {
        value 67108868;
        description "PM GFP rx csf threshold";
      }
    }
    description "Gfp threshold";
  }
  typedef Stm-report {
    type enumeration {
      enum report-ebs {
        value 16777217;
        description "PM EBS REPORT";
      }
      enum report-ess {
        value 16777218;
        description "PM ESS REPORT";
      }
      enum report-esrs {
        value 16777219;
        description "PM ESRS REPORT";
      }
      enum report-sess {
        value 16777220;
        description "PM SES REPORT";
      }
      enum report-sesrs {
        value 16777221;
        description "PM SESR REPORT";
      }
      enum report-bbes {
        value 16777222;
        description "PM BBES REPORT";
      }
      enum report-bbesr {
        value 16777223;
        description "PM BBESR REPORT";
      }
      enum report-uass {
        value 16777224;
        description "PM UASS REPORT";
      }
      enum report-ebl-ne {
        value 16777225;
        description "PM EBLNE REPORT";
      }
      enum report-esl-ne {
        value 16777226;
        description "PM ESLNE REPORT";
      }
      enum report-eslr-ne {
        value 16777227;
        description "PM ESLRNE REPORT";
      }
      enum report-sesl-ne {
        value 16777228;
        description "PM SESL REPORT";
      }
      enum report-sesrl-ne {
        value 16777229;
        description "PM SESRL REPORT";
      }
      enum report-bbel-ne {
        value 16777230;
        description "PM BBELNE REPORT";
      }
      enum report-bberl-ne {
        value 16777231;
        description "PM BBERLNE REPORT";
      }
      enum report-uasl-ne {
        value 16777232;
        description "PM UASNE REPORT";
      }
      enum report-ebl-fe {
        value 16777245;
        description "PM EBFE REPORT";
      }
      enum report-esl-fe {
        value 16777246;
        description "PM ESFE REPORT";
      }
      enum report-esrl-fe {
        value 16777247;
        description "PM EBFE REPORT";
      }
      enum report-sesl-fe {
        value 16777248;
        description "PM SESFE REPORT";
      }
      enum report-sesrl-fe {
        value 16777249;
        description "PM SESRLFE REPORT";
      }
      enum report-bbel-fe {
        value 16777250;
        description "PM BBELFE REPORT";
      }
      enum report-bberl-fe {
        value 16777251;
        description "PM ESFE REPORT";
      }
      enum report-uasl-fe {
        value 16777252;
        description "PM UASLFE REPORT";
      }
    }
    description "Stm report";
  }

  augment "/a1:interface-configurations/a1:interface-configuration" {

    container performance-management {
      xr:xr-xml-map "pmengine_ui_cfg:PerformanceManagement";
      description "Configure pm parameters";

      container stm-hour24 {
        xr:xr-xml-map "pmengine_ui_cfg:STMHour24";
        description "set STM threshold";

        container stm-hour24-stm {
          xr:xr-xml-map "pmengine_ui_cfg:STMHour24Stm";
          description "Configure stm performance monitoring";

          container stm-hour24-stm-reports {
            xr:xr-xml-map "pmengine_ui_cfg:STMHour24StmReportTable";
            description "set stm TCA reporting status";

            list stm-hour24-stm-report {
              xr:xr-xml-map "pmengine_ui_cfg:STMHour24StmReport";
              key "stm-report";
              description "none";
              leaf stm-report {
                xr:xr-xml-map "pmengine_ui_cfg:StmReport";
                type Stm-report;
                description "Stm Report Type";
              }
              leaf enable {
                xr:xr-xml-map "pmengine_ui_cfg:Enable";
                type Report;
                mandatory true;
                description "Stm Report";
              }
            }
          }

          container stm-hour24-stm-thresholds {
            xr:xr-xml-map "pmengine_ui_cfg:STMHour24StmThresholdTab"+
              "le";
            description "Configure threshold on stm parameters";

            list stm-hour24-stm-threshold {
              xr:xr-xml-map "pmengine_ui_cfg:STMHour24StmThreshold";
              key "stm-threshold";
              description "none";
              leaf stm-threshold {
                xr:xr-xml-map "pmengine_ui_cfg:StmThreshold";
                type Stm-threshold;
                description "Stm Threshold Type";
              }
              leaf stm-threshold-value {
                xr:xr-xml-map "pmengine_ui_cfg:StmThresholdValue";
                type int32;
                mandatory true;
                description "Stm Thresh Value";
              }
            }
          }
        }
      }

      container minute15-gfp {
        xr:xr-xml-map "pmengine_ui_cfg:Minute15_GFP";
        description "set opr min threshold";

        container minute15-gfp {
          xr:xr-xml-map "pmengine_ui_cfg:Minute15Gfp";
          description "Configure gfp performance monitoring";

          container minute15-gfp-reports {
            xr:xr-xml-map "pmengine_ui_cfg:Minute15GfpReportTable";
            description "set gfp TCA reporting status";

            list minute15-gfp-report {
              xr:xr-xml-map "pmengine_ui_cfg:Minute15GfpReport";
              key "gfp-report";
              description "none";
              leaf gfp-report {
                xr:xr-xml-map "pmengine_ui_cfg:GfpReport";
                type Gfp-report;
                description "Gfp Report Type";
              }
            }
          }

          container minute15-gfp-thresholds {
            xr:xr-xml-map "pmengine_ui_cfg:Minute15GfpThresholdTabl"+
              "e";
            description "Configure threshold on gfp parameters";

            list minute15-gfp-threshold {
              xr:xr-xml-map "pmengine_ui_cfg:Minute15GfpThreshold";
              key "gfp-threshold";
              description "none";
              leaf gfp-threshold {
                xr:xr-xml-map "pmengine_ui_cfg:GfpThreshold";
                type Gfp-threshold;
                description "Gfp Threshold Type";
              }
              leaf gfp-threshold-value {
                xr:xr-xml-map "pmengine_ui_cfg:GfpThresholdValue";
                type int32;
                mandatory true;
                description "Gfp Threshold Value";
              }
            }
          }
        }
      }

      container sonet-minute15 {
        xr:xr-xml-map "pmengine_ui_cfg:SonetMinute15";
        description "set Sonet threshold";

        container sonet-minute15-path {
          xr:xr-xml-map "pmengine_ui_cfg:SonetMinute15Path";
          description "Configure Path performance monitoring";

          container sonet-minute15-path-reports {
            xr:xr-xml-map "pmengine_ui_cfg:SonetMinute15PathReportT"+
              "able";
            description "set Path TCA reporting status";

            list sonet-minute15-path-report {
              xr:xr-xml-map "pmengine_ui_cfg:SonetMinute15PathRepor"+
                "t";
              key "path-report";
              description "none";
              leaf path-report {
                xr:xr-xml-map "pmengine_ui_cfg:PathReport";
                type Path-report;
                description "Path Report Type";
              }
            }
          }

          container sonet-minute15-path-thresholds {
            xr:xr-xml-map "pmengine_ui_cfg:SonetMinute15PathThresho"+
              "ldTable";
            description "Configure threshold on Path parameters";

            list sonet-minute15-path-threshold {
              xr:xr-xml-map "pmengine_ui_cfg:SonetMinute15PathThres"+
                "hold";
              key "path-threshold";
              description "none";
              leaf path-threshold {
                xr:xr-xml-map "pmengine_ui_cfg:PathThreshold";
                type Path-threshold;
                description "Path Threshold Type";
              }
              leaf path-threshold-value {
                xr:xr-xml-map "pmengine_ui_cfg:PathThresholdValue";
                type int32;
                mandatory true;
                description "Path Threshold Value";
              }
            }
          }
        }

        container sonet-minute15-ocn {
          xr:xr-xml-map "pmengine_ui_cfg:SonetMinute15Ocn";
          description "Configure ocn performance monitoring";

          container sonet-minute15-ocn-reports {
            xr:xr-xml-map "pmengine_ui_cfg:SonetMinute15OcnReportTa"+
              "ble";
            description "set ocn TCA reporting status";

            list sonet-minute15-ocn-report {
              xr:xr-xml-map "pmengine_ui_cfg:SonetMinute15OcnReport";
              key "ocn-report";
              description "none";
              leaf ocn-report {
                xr:xr-xml-map "pmengine_ui_cfg:OcnReport";
                type Ocn-report;
                description "Ocn Report Type";
              }
            }
          }

          container sonet-minute15-ocn-thresholds {
            xr:xr-xml-map "pmengine_ui_cfg:SonetMinute15OcnThreshol"+
              "dTable";
            description "Configure threshold on ocn parameters";

            list sonet-minute15-ocn-threshold {
              xr:xr-xml-map "pmengine_ui_cfg:SonetMinute15OcnThresh"+
                "old";
              key "ocn-threshold";
              description "none";
              leaf ocn-threshold {
                xr:xr-xml-map "pmengine_ui_cfg:OcnThreshold";
                type Ocn-threshold;
                description "Ocn Threshold Type";
              }
              leaf ocn-threshold-value {
                xr:xr-xml-map "pmengine_ui_cfg:OcnThresholdValue";
                type int32;
                mandatory true;
                description "Ocn Threshold Value";
              }
            }
          }
        }
      }

      container hour24-gfp {
        xr:xr-xml-map "pmengine_ui_cfg:Hour24_GFP";
        description
          "Configure pm parameters of gfp 24 hour interval";

        container hour24-gfp {
          xr:xr-xml-map "pmengine_ui_cfg:Hour24Gfp";
          description "Configure gfp performance monitoring";

          container hour24-gfp-reports {
            xr:xr-xml-map "pmengine_ui_cfg:Hour24GfpReportTable";
            description "set gfp TCA reporting status";

            list hour24-gfp-report {
              xr:xr-xml-map "pmengine_ui_cfg:Hour24GfpReport";
              key "gfp-report";
              description "none";
              leaf gfp-report {
                xr:xr-xml-map "pmengine_ui_cfg:GfpReport";
                type Gfp-report;
                description "Gfp Report Type";
              }
            }
          }

          container hour24-gfp-thresholds {
            xr:xr-xml-map "pmengine_ui_cfg:Hour24GfpThresholdTable";
            description "Configure threshold on gfp parameters";

            list hour24-gfp-threshold {
              xr:xr-xml-map "pmengine_ui_cfg:Hour24GfpThreshold";
              key "gfp-threshold";
              description "none";
              leaf gfp-threshold {
                xr:xr-xml-map "pmengine_ui_cfg:GfpThreshold";
                type Gfp-threshold;
                description "Gfp Threshold Type";
              }
              leaf gfp-threshold-value {
                xr:xr-xml-map "pmengine_ui_cfg:GfpThresholdValue";
                type int32;
                mandatory true;
                description "Gfp Thresh Value";
              }
            }
          }
        }
      }

      container ethernet-hour24 {
        xr:xr-xml-map "pmengine_ui_cfg:EthernetHour24";
        description "Configure pm parameters of 24 hour interval";

        container hour24-ether {
          xr:xr-xml-map "pmengine_ui_cfg:Hour24Ether";
          description "Configure ether performance monitoring";

          container hour24-ether-thresholds {
            xr:xr-xml-map "pmengine_ui_cfg:Hour24EtherThresholdTabl"+
              "e";
            description "Configure threshold on ether parameters";

            list hour24-ether-threshold {
              xr:xr-xml-map "pmengine_ui_cfg:Hour24EtherThreshold";
              key "ether-threshold";
              description "none";
              leaf ether-threshold {
                xr:xr-xml-map "pmengine_ui_cfg:EtherThreshold";
                type Ether-threshold;
                description "Ether Threshold Type";
              }
              leaf ether-threshold-value {
                xr:xr-xml-map "pmengine_ui_cfg:EtherThresholdValue";
                type int32;
                mandatory true;
                description "Ether Thresh Value";
              }
            }
          }

          container hour24-ether-reports {
            xr:xr-xml-map "pmengine_ui_cfg:Hour24EtherReportTable";
            description "set ether TCA reporting status";

            list hour24-ether-report {
              xr:xr-xml-map "pmengine_ui_cfg:Hour24EtherReport";
              key "ether-report";
              description "none";
              leaf ether-report {
                xr:xr-xml-map "pmengine_ui_cfg:EtherReport";
                type Ether-report;
                description "Ether Report Type";
              }
            }
          }
        }
      }

      container minute15otn-tcms {
        xr:xr-xml-map "pmengine_ui_cfg:Minute15_TCM";
        description "set opr min threshold";

        list minute15otn-tcm {
          xr:xr-xml-map "pmengine_ui_cfg:Minute15OTN_TCM";
          key "tcm-number";
          description
            "configure otn g709 tcm's performance
            monitoring";

          container min15-otn-tcm-threshes {
            xr:xr-xml-map "pmengine_ui_cfg:Minute15OTN_TCMThreshold"+
              "Table";
            description "Configure threshold on otn parameters";

            list min15-otn-tcm-thresh {
              xr:xr-xml-map "pmengine_ui_cfg:Min15Otn_TCMThresh";
              key "otn-threshold";
              description "none";
              leaf otn-threshold {
                xr:xr-xml-map "pmengine_ui_cfg:OTNThreshold";
                type Otn-tcm-threshold;
                description "Otn Threshold Type";
              }
              leaf otn-threshold-value {
                xr:xr-xml-map "pmengine_ui_cfg:OtnThresholdValue";
                type int32;
                mandatory true;
                description "Otn Threshold Value";
              }
            }
          }

          container minute15otn-tcm-reports {
            xr:xr-xml-map "pmengine_ui_cfg:Minute15OTN_TCMReportTab"+
              "le";
            description "set otn TCA reporting status";

            list minute15otn-tcm-report {
              xr:xr-xml-map "pmengine_ui_cfg:Minute15OTN_TCMReport";
              key "otn-report";
              description "none";
              leaf otn-report {
                xr:xr-xml-map "pmengine_ui_cfg:OTNReport";
                type Otn-tcm-report;
                description "Otn Report Type";
              }
              leaf enable {
                xr:xr-xml-map "pmengine_ui_cfg:Enable";
                type Report;
                mandatory true;
                description "Otn Report";
              }
            }
          }
          leaf tcm-number {
            xr:xr-xml-map "pmengine_ui_cfg:TcmNumber";
            type int32;
            description "TCM number";
          }
        }
      }

      container oc-hour24 {
        xr:xr-xml-map "pmengine_ui_cfg:OcHour24";
        description "set Oc threshold";

        container oc-hour24-ocn {
          xr:xr-xml-map "pmengine_ui_cfg:OcHour24Ocn";
          description "Configure ocn performance monitoring";

          container oc-hour24-ocn-reports {
            xr:xr-xml-map "pmengine_ui_cfg:OcHour24OcnReportTable";
            description "set ocn TCA reporting status";

            list oc-hour24-ocn-report {
              xr:xr-xml-map "pmengine_ui_cfg:OcHour24OcnReport";
              key "ocn-report";
              description "none";
              leaf ocn-report {
                xr:xr-xml-map "pmengine_ui_cfg:OcnReport";
                type Ocn-report;
                description "Ocn Report Type";
              }
              leaf enable {
                xr:xr-xml-map "pmengine_ui_cfg:Enable";
                type Report;
                mandatory true;
                description "Ocn Report";
              }
            }
          }

          container oc-hour24-ocn-thresholds {
            xr:xr-xml-map "pmengine_ui_cfg:OcHour24OcnThresholdTabl"+
              "e";
            description "Configure threshold on ocn parameters";

            list oc-hour24-ocn-threshold {
              xr:xr-xml-map "pmengine_ui_cfg:OcHour24OcnThreshold";
              key "ocn-threshold";
              description "none";
              leaf ocn-threshold {
                xr:xr-xml-map "pmengine_ui_cfg:OcnThreshold";
                type Ocn-threshold;
                description "Ocn Threshold Type";
              }
              leaf ocn-threshold-value {
                xr:xr-xml-map "pmengine_ui_cfg:OcnThresholdValue";
                type int32;
                mandatory true;
                description "Ocn Thresh Value";
              }
            }
          }
        }
      }

      container ethernet-minute15 {
        xr:xr-xml-map "pmengine_ui_cfg:EthernetMinute15";
        description "set opr min threshold";

        container minute15-ether {
          xr:xr-xml-map "pmengine_ui_cfg:Minute15Ether";
          description "Configure ether performance monitoring";

          container minute15-ether-thresholds {
            xr:xr-xml-map "pmengine_ui_cfg:Minute15EtherThresholdTa"+
              "ble";
            description "Configure threshold on ether parameters";

            list minute15-ether-threshold {
              xr:xr-xml-map "pmengine_ui_cfg:Minute15EtherThreshold";
              key "ether-threshold";
              description "none";
              leaf ether-threshold {
                xr:xr-xml-map "pmengine_ui_cfg:EtherThreshold";
                type Ether-threshold;
                description "Ether Threshold Type";
              }
              leaf ether-threshold-value {
                xr:xr-xml-map "pmengine_ui_cfg:EtherThresholdValue";
                type int32;
                mandatory true;
                description "Ether Threshold Value";
              }
            }
          }

          container minute15-ether-reports {
            xr:xr-xml-map "pmengine_ui_cfg:Minute15EtherReportTable";
            description "set ether TCA reporting status";

            list minute15-ether-report {
              xr:xr-xml-map "pmengine_ui_cfg:Minute15EtherReport";
              key "ether-report";
              description "none";
              leaf ether-report {
                xr:xr-xml-map "pmengine_ui_cfg:EtherReport";
                type Ether-report;
                description "Ether Report Type";
              }
            }
          }
        }
      }

      container ho-vc-hour24 {
        xr:xr-xml-map "pmengine_ui_cfg:HO_VCHour24";
        description "set HO_VC threshold";

        container ho-vc-hour24ho-vc {
          xr:xr-xml-map "pmengine_ui_cfg:HO_VCHour24ho_vc";
          description "Configure ho_vc performance monitoring";

          container ho-vc-hour24ho-vc-reports {
            xr:xr-xml-map "pmengine_ui_cfg:HO_VCHour24ho_vcReportTa"+
              "ble";
            description "set ho_vc TCA reporting status";

            list ho-vc-hour24ho-vc-report {
              xr:xr-xml-map "pmengine_ui_cfg:HO_VCHour24ho_vcReport";
              key "ho-vc-report";
              description "none";
              leaf ho-vc-report {
                xr:xr-xml-map "pmengine_ui_cfg:Ho_vcReport";
                type Ho-vc-report;
                description "ho_vc Report Type";
              }
              leaf enable {
                xr:xr-xml-map "pmengine_ui_cfg:Enable";
                type Report;
                mandatory true;
                description "ho_vc Report";
              }
            }
          }

          container ho-vc-hour24ho-vc-thresholds {
            xr:xr-xml-map "pmengine_ui_cfg:HO_VCHour24ho_vcThreshol"+
              "dTable";
            description "Configure threshold on ho_vc parameters";

            list ho-vc-hour24ho-vc-threshold {
              xr:xr-xml-map "pmengine_ui_cfg:HO_VCHour24ho_vcThresh"+
                "old";
              key "ho-vc-threshold";
              description "none";
              leaf ho-vc-threshold {
                xr:xr-xml-map "pmengine_ui_cfg:Ho_vcThreshold";
                type Ho-vc-threshold;
                description "ho_vc Threshold Type";
              }
              leaf ho-vc-threshold-value {
                xr:xr-xml-map "pmengine_ui_cfg:Ho_vcThresholdValue";
                type int32;
                mandatory true;
                description "ho_vc Thresh Value";
              }
            }
          }
        }
      }

      container second30 {
        xr:xr-xml-map "pmengine_ui_cfg:Second30";
        description
          "Configure optics performance monitoring for 30
          sec";

        container second30fec {
          xr:xr-xml-map "pmengine_ui_cfg:Second30FEC";
          description "Configure fec g709 performance monitoring";

          container second30fec-thresholds {
            xr:xr-xml-map "pmengine_ui_cfg:Second30FECThresholdTabl"+
              "e";
            description "Configure fec threshold";

            list second30fec-threshold {
              xr:xr-xml-map "pmengine_ui_cfg:Second30FECThreshold";
              key "fec-threshold";
              description "none";
              leaf fec-threshold {
                xr:xr-xml-map "pmengine_ui_cfg:FECThreshold";
                type Fec-threshold;
                description "Fec Threshold Type";
              }
              leaf fec-threshold-value {
                xr:xr-xml-map "pmengine_ui_cfg:FecThresholdValue";
                type string {
                  length "0..16";
                }
                mandatory true;
                description "Fec Threshold Value";
              }
            }
          }

          container second30fec-reports {
            xr:xr-xml-map "pmengine_ui_cfg:Second30FECReportTable";
            description "set fec TCA reporting status";

            list second30fec-report {
              xr:xr-xml-map "pmengine_ui_cfg:Second30FECReport";
              key "fec-report";
              description "none";
              leaf fec-report {
                xr:xr-xml-map "pmengine_ui_cfg:FECReport";
                type Fec-report;
                description "Fec Report Type";
              }
              leaf enable {
                xr:xr-xml-map "pmengine_ui_cfg:Enable";
                type Report;
                mandatory true;
                description "Fec Report";
              }
            }
          }
        }

        container second30-optics {
          xr:xr-xml-map "pmengine_ui_cfg:Second30Optics";
          description "Configure optics performance monitoring";

          container second30-optics-reports {
            xr:xr-xml-map "pmengine_ui_cfg:Second30OpticsReportTabl"+
              "e";
            description "set optics TCA reporting status";

            list second30-optics-report {
              xr:xr-xml-map "pmengine_ui_cfg:Second30OpticsReport";
              key "optics-report";
              description "none";
              leaf optics-report {
                xr:xr-xml-map "pmengine_ui_cfg:OpticsReport";
                type Optics-report;
                description "Optics Report Type";
              }
            }
          }

          container second30-optics-thresholds {
            xr:xr-xml-map "pmengine_ui_cfg:Second30OpticsThresholdT"+
              "able";
            description "Configure threshold on optics parameters";

            list second30-optics-threshold {
              xr:xr-xml-map "pmengine_ui_cfg:Second30OpticsThreshol"+
                "d";
              key "optics-threshold";
              description "none";
              leaf optics-threshold {
                xr:xr-xml-map "pmengine_ui_cfg:OpticsThreshold";
                type Optics-threshold;
                description "Optics Threshold Type";
              }
              leaf optics-threshold-value {
                xr:xr-xml-map "pmengine_ui_cfg:OpticsThresholdValue";
                type int32;
                mandatory true;
                description "Optics Threshold Value";
              }
            }
          }
        }

        container second30otn {
          xr:xr-xml-map "pmengine_ui_cfg:Second30OTN";
          description "configure otn g709 performance monitoring";

          container second30-otn-threshes {
            xr:xr-xml-map "pmengine_ui_cfg:Second30OTNThresholdTabl"+
              "e";
            description "Configure threshold on otn parameters";

            list second30-otn-thresh {
              xr:xr-xml-map "pmengine_ui_cfg:Second30OtnThresh";
              key "otn-threshold";
              description "none";
              leaf otn-threshold {
                xr:xr-xml-map "pmengine_ui_cfg:OTNThreshold";
                type Otn-threshold;
                description "Otn Threshold Type";
              }
              leaf otn-threshold-value {
                xr:xr-xml-map "pmengine_ui_cfg:OtnThresholdValue";
                type int32;
                mandatory true;
                description "Otn Threshold Value";
              }
            }
          }

          container second30otn-reports {
            xr:xr-xml-map "pmengine_ui_cfg:Second30OTNReportTable";
            description "set otn TCA reporting status";

            list second30otn-report {
              xr:xr-xml-map "pmengine_ui_cfg:Second30OTNReport";
              key "otn-report";
              description "none";
              leaf otn-report {
                xr:xr-xml-map "pmengine_ui_cfg:OTNReport";
                type Otn-report;
                description "Otn Report Type";
              }
              leaf enable {
                xr:xr-xml-map "pmengine_ui_cfg:Enable";
                type Report;
                mandatory true;
                description "Otn Report";
              }
            }
          }
        }
      }

      container hour24otn-tcms {
        xr:xr-xml-map "pmengine_ui_cfg:Hour24_TCM";
        description
          "Configure pm parameters of tcm's 24 hour
          interval";

        list hour24otn-tcm {
          xr:xr-xml-map "pmengine_ui_cfg:Hour24OTN_TCM";
          key "tcm-number";
          description
            "configure otn g709 tcm's performance
            monitoring";

          container hour24otn-tcm-thresholds {
            xr:xr-xml-map "pmengine_ui_cfg:Hour24OTN_TCMThresholdTa"+
              "ble";
            description "Configure threshold on otn parameters";

            list hour24otn-tcm-threshold {
              xr:xr-xml-map "pmengine_ui_cfg:Hour24OTN_TCMThreshold";
              key "otn-threshold";
              description "none";
              leaf otn-threshold {
                xr:xr-xml-map "pmengine_ui_cfg:OTNThreshold";
                type Otn-tcm-threshold;
                description "Otn Threshold Type";
              }
              leaf otn-threshold-value {
                xr:xr-xml-map "pmengine_ui_cfg:OtnThresholdValue";
                type int32;
                mandatory true;
                description "Otn Threshold Value";
              }
            }
          }

          container hour24otn-tcm-reports {
            xr:xr-xml-map "pmengine_ui_cfg:Hour24OTN_TCMReportTable";
            description "set otn TCA reporting status";

            list hour24otn-tcm-report {
              xr:xr-xml-map "pmengine_ui_cfg:Hour24OTN_TCMReport";
              key "otn-report";
              description "none";
              leaf otn-report {
                xr:xr-xml-map "pmengine_ui_cfg:OTNReport";
                type Otn-tcm-report;
                description "Otn Report Type";
              }
              leaf enable {
                xr:xr-xml-map "pmengine_ui_cfg:Enable";
                type Report;
                mandatory true;
                description "Otn Report";
              }
            }
          }
          leaf tcm-number {
            xr:xr-xml-map "pmengine_ui_cfg:TcmNumber";
            type int32;
            description "TCM number";
          }
        }
      }

      container sts-minute15 {
        xr:xr-xml-map "pmengine_ui_cfg:STSMinute15";
        description "set STS threshold";

        container sts-minute15-path {
          xr:xr-xml-map "pmengine_ui_cfg:STSMinute15Path";
          description "Configure Path performance monitoring";

          container sts-minute15-path-reports {
            xr:xr-xml-map "pmengine_ui_cfg:STSMinute15PathReportTab"+
              "le";
            description "set Path TCA reporting status";

            list sts-minute15-path-report {
              xr:xr-xml-map "pmengine_ui_cfg:STSMinute15PathReport";
              key "path-report";
              description "none";
              leaf path-report {
                xr:xr-xml-map "pmengine_ui_cfg:PathReport";
                type Sts-report;
                description "Path Report Type";
              }
              leaf enable {
                xr:xr-xml-map "pmengine_ui_cfg:Enable";
                type Report;
                mandatory true;
                description "Path Report";
              }
            }
          }

          container sts-minute15-path-thresholds {
            xr:xr-xml-map "pmengine_ui_cfg:STSMinute15PathThreshold"+
              "Table";
            description "Configure threshold on Path parameters";

            list sts-minute15-path-threshold {
              xr:xr-xml-map "pmengine_ui_cfg:STSMinute15PathThresho"+
                "ld";
              key "path-threshold";
              description "none";
              leaf path-threshold {
                xr:xr-xml-map "pmengine_ui_cfg:PathThreshold";
                type Sts-threshold;
                description "Path Threshold Type";
              }
              leaf path-threshold-value {
                xr:xr-xml-map "pmengine_ui_cfg:PathThresholdValue";
                type int32;
                mandatory true;
                description "Path Threshold Value";
              }
            }
          }
        }
      }

      container hour24 {
        xr:xr-xml-map "pmengine_ui_cfg:Hour24";
        description "Configure pm parameters of 24 hour interval";

        container hour24otn {
          xr:xr-xml-map "pmengine_ui_cfg:Hour24OTN";
          description "configure otn g709 performance monitoring";

          container hour24otn-thresholds {
            xr:xr-xml-map "pmengine_ui_cfg:Hour24OTNThresholdTable";
            description "Configure threshold on otn parameters";

            list hour24otn-threshold {
              xr:xr-xml-map "pmengine_ui_cfg:Hour24OTNThreshold";
              key "otn-threshold";
              description "none";
              leaf otn-threshold {
                xr:xr-xml-map "pmengine_ui_cfg:OTNThreshold";
                type Otn-threshold;
                description "Otn Threshold Type";
              }
              leaf otn-threshold-value {
                xr:xr-xml-map "pmengine_ui_cfg:OtnThresholdValue";
                type int32;
                mandatory true;
                description "Otn Threshold Value";
              }
            }
          }

          container hour24otn-reports {
            xr:xr-xml-map "pmengine_ui_cfg:Hour24OTNReportTable";
            description "set otn TCA reporting status";

            list hour24otn-report {
              xr:xr-xml-map "pmengine_ui_cfg:Hour24OTNReport";
              key "otn-report";
              description "none";
              leaf otn-report {
                xr:xr-xml-map "pmengine_ui_cfg:OTNReport";
                type Otn-report;
                description "Otn Report Type";
              }
              leaf enable {
                xr:xr-xml-map "pmengine_ui_cfg:Enable";
                type Report;
                mandatory true;
                description "Otn Report";
              }
            }
          }
        }

        container hour24-optics {
          xr:xr-xml-map "pmengine_ui_cfg:Hour24Optics";
          description "Configure optics performance monitoring";

          container hour24-optics-thresholds {
            xr:xr-xml-map "pmengine_ui_cfg:Hour24OpticsThresholdTab"+
              "le";
            description "Configure threshold on optics parameters";

            list hour24-optics-threshold {
              xr:xr-xml-map "pmengine_ui_cfg:Hour24OpticsThreshold";
              key "optics-threshold";
              description "none";
              leaf optics-threshold {
                xr:xr-xml-map "pmengine_ui_cfg:OpticsThreshold";
                type Optics-threshold;
                description "Optics Threshold Type";
              }
              leaf optics-threshold-value {
                xr:xr-xml-map "pmengine_ui_cfg:OpticsThresholdValue";
                type int32;
                description "Optics Thresh Value";
              }
              leaf dbm {
                xr:xr-xml-map "pmengine_ui_cfg:Dbm";
                type int32;
                default "0";
                description
                  "Used only for Opt and Opr,To Enter
                  Threshold in dbm use 1";
              }
            }
          }

          container hour24-optics-reports {
            xr:xr-xml-map "pmengine_ui_cfg:Hour24OpticsReportTable";
            description "set optics TCA reporting status";

            list hour24-optics-report {
              xr:xr-xml-map "pmengine_ui_cfg:Hour24OpticsReport";
              key "optics-report";
              description "none";
              leaf optics-report {
                xr:xr-xml-map "pmengine_ui_cfg:OpticsReport";
                type Optics-report;
                description "Optics Report Type";
              }
            }
          }
        }

        container hour24fec {
          xr:xr-xml-map "pmengine_ui_cfg:Hour24FEC";
          description "Configure fec g709 performance monitoring";

          container hour24fec-thresholds {
            xr:xr-xml-map "pmengine_ui_cfg:Hour24FECThresholdTable";
            description "Configure fec threshold";

            list hour24fec-threshold {
              xr:xr-xml-map "pmengine_ui_cfg:Hour24FECThreshold";
              key "fec-threshold";
              description "none";
              leaf fec-threshold {
                xr:xr-xml-map "pmengine_ui_cfg:FECThreshold";
                type Fec-threshold;
                description "Fec Threshold Type";
              }
              leaf fec-threshold-value {
                xr:xr-xml-map "pmengine_ui_cfg:FecThresholdValue";
                type string {
                  length "0..16";
                }
                mandatory true;
                description "Fec threshold value";
              }
            }
          }

          container hour24fec-reports {
            xr:xr-xml-map "pmengine_ui_cfg:Hour24FECReportTable";
            description "set fec TCA reporting status";

            list hour24fec-report {
              xr:xr-xml-map "pmengine_ui_cfg:Hour24FECReport";
              key "fec-report";
              description "none";
              leaf fec-report {
                xr:xr-xml-map "pmengine_ui_cfg:FECReport";
                type Fec-report;
                description "Fec Report type";
              }
              leaf enable {
                xr:xr-xml-map "pmengine_ui_cfg:Enable";
                type Report;
                mandatory true;
                description "Fec Report";
              }
            }
          }
        }
      }

      container ho-vc-minute15 {
        xr:xr-xml-map "pmengine_ui_cfg:HO_VCMinute15";
        description "set HO_VC threshold";

        container ho-vc-minute15ho-vc {
          xr:xr-xml-map "pmengine_ui_cfg:HO_VCMinute15ho_vc";
          description "Configure ho_vc performance monitoring";

          container ho-vc-minute15ho-vc-reports {
            xr:xr-xml-map "pmengine_ui_cfg:HO_VCMinute15ho_vcReport"+
              "Table";
            description "set ho_vc TCA reporting status";

            list ho-vc-minute15ho-vc-report {
              xr:xr-xml-map "pmengine_ui_cfg:HO_VCMinute15ho_vcRepo"+
                "rt";
              key "ho-vc-report";
              description "none";
              leaf ho-vc-report {
                xr:xr-xml-map "pmengine_ui_cfg:Ho_vcReport";
                type Ho-vc-report;
                description "ho_vc Report Type";
              }
              leaf enable {
                xr:xr-xml-map "pmengine_ui_cfg:Enable";
                type Report;
                mandatory true;
                description "ho_vc Report";
              }
            }
          }

          container ho-vc-minute15ho-vc-thresholds {
            xr:xr-xml-map "pmengine_ui_cfg:HO_VCMinute15ho_vcThresh"+
              "oldTable";
            description "Configure threshold on ho_vc parameters";

            list ho-vc-minute15ho-vc-threshold {
              xr:xr-xml-map "pmengine_ui_cfg:HO_VCMinute15ho_vcThre"+
                "shold";
              key "ho-vc-threshold";
              description "none";
              leaf ho-vc-threshold {
                xr:xr-xml-map "pmengine_ui_cfg:Ho_vcThreshold";
                type Ho-vc-threshold;
                description "ho_vc Threshold Type";
              }
              leaf ho-vc-threshold-value {
                xr:xr-xml-map "pmengine_ui_cfg:Ho_vcThresholdValue";
                type int32;
                mandatory true;
                description "ho_vc Threshold Value";
              }
            }
          }
        }
      }

      container sts-hour24 {
        xr:xr-xml-map "pmengine_ui_cfg:STSHour24";
        description "set STS threshold";

        container sts-hour24-path {
          xr:xr-xml-map "pmengine_ui_cfg:STSHour24Path";
          description "Configure Path performance monitoring";

          container sts-hour24-path-thresholds {
            xr:xr-xml-map "pmengine_ui_cfg:STSHour24PathThresholdTa"+
              "ble";
            description "Configure threshold on Path parameters";

            list sts-hour24-path-threshold {
              xr:xr-xml-map "pmengine_ui_cfg:STSHour24PathThreshold";
              key "path-threshold";
              description "none";
              leaf path-threshold {
                xr:xr-xml-map "pmengine_ui_cfg:PathThreshold";
                type Sts-threshold;
                description "Path Threshold Type";
              }
              leaf path-threshold-value {
                xr:xr-xml-map "pmengine_ui_cfg:PathThresholdValue";
                type int32;
                mandatory true;
                description "Path Thresh Value";
              }
            }
          }

          container sts-hour24-path-reports {
            xr:xr-xml-map "pmengine_ui_cfg:STSHour24PathReportTable";
            description "set Path TCA reporting status";

            list sts-hour24-path-report {
              xr:xr-xml-map "pmengine_ui_cfg:STSHour24PathReport";
              key "path-report";
              description "none";
              leaf path-report {
                xr:xr-xml-map "pmengine_ui_cfg:PathReport";
                type Sts-report;
                description "Path Report Type";
              }
              leaf enable {
                xr:xr-xml-map "pmengine_ui_cfg:Enable";
                type Report;
                mandatory true;
                description "Path Report";
              }
            }
          }
        }
      }

      container stm-minute15 {
        xr:xr-xml-map "pmengine_ui_cfg:STMMinute15";
        description "set STM threshold";

        container stm-minute15-stm {
          xr:xr-xml-map "pmengine_ui_cfg:STMMinute15Stm";
          description "Configure stm performance monitoring";

          container stm-minute15-stm-reports {
            xr:xr-xml-map "pmengine_ui_cfg:STMMinute15StmReportTabl"+
              "e";
            description "set stm TCA reporting status";

            list stm-minute15-stm-report {
              xr:xr-xml-map "pmengine_ui_cfg:STMMinute15StmReport";
              key "stm-report";
              description "none";
              leaf stm-report {
                xr:xr-xml-map "pmengine_ui_cfg:StmReport";
                type Stm-report;
                description "Stm Report Type";
              }
              leaf enable {
                xr:xr-xml-map "pmengine_ui_cfg:Enable";
                type Report;
                mandatory true;
                description "Stm Report";
              }
            }
          }

          container stm-minute15-stm-thresholds {
            xr:xr-xml-map "pmengine_ui_cfg:STMMinute15StmThresholdT"+
              "able";
            description "Configure threshold on stm parameters";

            list stm-minute15-stm-threshold {
              xr:xr-xml-map "pmengine_ui_cfg:STMMinute15StmThreshol"+
                "d";
              key "stm-threshold";
              description "none";
              leaf stm-threshold {
                xr:xr-xml-map "pmengine_ui_cfg:StmThreshold";
                type Stm-threshold;
                description "Stm Threshold Type";
              }
              leaf stm-threshold-value {
                xr:xr-xml-map "pmengine_ui_cfg:StmThresholdValue";
                type int32;
                mandatory true;
                description "Stm Threshold Value";
              }
            }
          }
        }
      }

      container sonet-hour24 {
        xr:xr-xml-map "pmengine_ui_cfg:SonetHour24";
        description "set Sonet threshold";

        container sonet-hour24-path {
          xr:xr-xml-map "pmengine_ui_cfg:SonetHour24Path";
          description "Configure Path performance monitoring";

          container sonet-hour24-path-thresholds {
            xr:xr-xml-map "pmengine_ui_cfg:SonetHour24PathThreshold"+
              "Table";
            description "Configure threshold on Path parameters";

            list sonet-hour24-path-threshold {
              xr:xr-xml-map "pmengine_ui_cfg:SonetHour24PathThresho"+
                "ld";
              key "path-threshold";
              description "none";
              leaf path-threshold {
                xr:xr-xml-map "pmengine_ui_cfg:PathThreshold";
                type Path-threshold;
                description "Path Threshold Type";
              }
              leaf path-threshold-value {
                xr:xr-xml-map "pmengine_ui_cfg:PathThresholdValue";
                type int32;
                mandatory true;
                description "Path Thresh Value";
              }
            }
          }

          container sonet-hour24-path-reports {
            xr:xr-xml-map "pmengine_ui_cfg:SonetHour24PathReportTab"+
              "le";
            description "set Path TCA reporting status";

            list sonet-hour24-path-report {
              xr:xr-xml-map "pmengine_ui_cfg:SonetHour24PathReport";
              key "path-report";
              description "none";
              leaf path-report {
                xr:xr-xml-map "pmengine_ui_cfg:PathReport";
                type Path-report;
                description "Path Report Type";
              }
            }
          }
        }

        container sonet-hour24-ocn {
          xr:xr-xml-map "pmengine_ui_cfg:SonetHour24Ocn";
          description "Configure ocn performance monitoring";

          container sonet-hour24-ocn-thresholds {
            xr:xr-xml-map "pmengine_ui_cfg:SonetHour24OcnThresholdT"+
              "able";
            description "Configure threshold on ocn parameters";

            list sonet-hour24-ocn-threshold {
              xr:xr-xml-map "pmengine_ui_cfg:SonetHour24OcnThreshol"+
                "d";
              key "ocn-threshold";
              description "none";
              leaf ocn-threshold {
                xr:xr-xml-map "pmengine_ui_cfg:OcnThreshold";
                type Ocn-threshold;
                description "Ocn Threshold Type";
              }
              leaf ocn-threshold-value {
                xr:xr-xml-map "pmengine_ui_cfg:OcnThresholdValue";
                type int32;
                mandatory true;
                description "Ocn Thresh Value";
              }
            }
          }

          container sonet-hour24-ocn-reports {
            xr:xr-xml-map "pmengine_ui_cfg:SonetHour24OcnReportTabl"+
              "e";
            description "set ocn TCA reporting status";

            list sonet-hour24-ocn-report {
              xr:xr-xml-map "pmengine_ui_cfg:SonetHour24OcnReport";
              key "ocn-report";
              description "none";
              leaf ocn-report {
                xr:xr-xml-map "pmengine_ui_cfg:OcnReport";
                type Ocn-report;
                description "Ocn Report Type";
              }
            }
          }
        }
      }

      container minute15-path {
        xr:xr-xml-map "pmengine_ui_cfg:Minute15_Path";
        description "set opr min threshold";

        container minute15otn-path {
          xr:xr-xml-map "pmengine_ui_cfg:Minute15OTN_Path";
          description "configure otn g709 performance monitoring";

          container minute15otn-path-reports {
            xr:xr-xml-map "pmengine_ui_cfg:Minute15OTN_PathReportTa"+
              "ble";
            description "set otn TCA reporting status";

            list minute15otn-path-report {
              xr:xr-xml-map "pmengine_ui_cfg:Minute15OTN_PathReport";
              key "otn-report";
              description "none";
              leaf otn-report {
                xr:xr-xml-map "pmengine_ui_cfg:OTNReport";
                type Otn-report;
                description "Otn Report Type";
              }
              leaf enable {
                xr:xr-xml-map "pmengine_ui_cfg:Enable";
                type Report;
                mandatory true;
                description "Otn Report";
              }
            }
          }

          container min15-otn-path-threshes {
            xr:xr-xml-map "pmengine_ui_cfg:Minute15OTN_PathThreshol"+
              "dTable";
            description "Configure threshold on otn parameters";

            list min15-otn-path-thresh {
              xr:xr-xml-map "pmengine_ui_cfg:Min15Otn_PathThresh";
              key "otn-threshold";
              description "none";
              leaf otn-threshold {
                xr:xr-xml-map "pmengine_ui_cfg:OTNThreshold";
                type Otn-threshold;
                description "Otn Threshold Type";
              }
              leaf otn-threshold-value {
                xr:xr-xml-map "pmengine_ui_cfg:OtnThresholdValue";
                type int32;
                mandatory true;
                description "Otn Threshold Value";
              }
            }
          }
        }
      }

      container oc-minute15 {
        xr:xr-xml-map "pmengine_ui_cfg:OcMinute15";
        description "set OC threshold";

        container oc-minute15-ocn {
          xr:xr-xml-map "pmengine_ui_cfg:OcMinute15Ocn";
          description "Configure ocn performance monitoring";

          container oc-minute15-ocn-reports {
            xr:xr-xml-map "pmengine_ui_cfg:OcMinute15OcnReportTable";
            description "set ocn TCA reporting status";

            list oc-minute15-ocn-report {
              xr:xr-xml-map "pmengine_ui_cfg:OcMinute15OcnReport";
              key "ocn-report";
              description "none";
              leaf ocn-report {
                xr:xr-xml-map "pmengine_ui_cfg:OcnReport";
                type Ocn-report;
                description "Ocn Report Type";
              }
              leaf enable {
                xr:xr-xml-map "pmengine_ui_cfg:Enable";
                type Report;
                mandatory true;
                description "Ocn Report";
              }
            }
          }

          container oc-minute15-ocn-thresholds {
            xr:xr-xml-map "pmengine_ui_cfg:OcMinute15OcnThresholdTa"+
              "ble";
            description "Configure threshold on ocn parameters";

            list oc-minute15-ocn-threshold {
              xr:xr-xml-map "pmengine_ui_cfg:OcMinute15OcnThreshold";
              key "ocn-threshold";
              description "none";
              leaf ocn-threshold {
                xr:xr-xml-map "pmengine_ui_cfg:OcnThreshold";
                type Ocn-threshold;
                description "Ocn Threshold Type";
              }
              leaf ocn-threshold-value {
                xr:xr-xml-map "pmengine_ui_cfg:OcnThresholdValue";
                type int32;
                mandatory true;
                description "Ocn Threshold Value";
              }
            }
          }
        }
      }

      container ethernet-second30 {
        xr:xr-xml-map "pmengine_ui_cfg:EthernetSecond30";
        description
          "Configure ethernet performance monitoring for
          30 sec";

        container second30-ether {
          xr:xr-xml-map "pmengine_ui_cfg:Second30Ether";
          description "Configure ether performance monitoring";

          container second30-ether-thresholds {
            xr:xr-xml-map "pmengine_ui_cfg:Second30EtherThresholdTa"+
              "ble";
            description "Configure threshold on ether parameters";

            list second30-ether-threshold {
              xr:xr-xml-map "pmengine_ui_cfg:Second30EtherThreshold";
              key "ether-threshold";
              description "none";
              leaf ether-threshold {
                xr:xr-xml-map "pmengine_ui_cfg:EtherThreshold";
                type Ether-threshold;
                description "Ether Threshold Type";
              }
              leaf ether-threshold-value {
                xr:xr-xml-map "pmengine_ui_cfg:EtherThresholdValue";
                type int32;
                mandatory true;
                description "Ether Threshold Value";
              }
            }
          }

          container second30-ether-reports {
            xr:xr-xml-map "pmengine_ui_cfg:Second30EtherReportTable";
            description "set ether TCA reporting status";

            list second30-ether-report {
              xr:xr-xml-map "pmengine_ui_cfg:Second30EtherReport";
              key "ether-report";
              description "none";
              leaf ether-report {
                xr:xr-xml-map "pmengine_ui_cfg:EtherReport";
                type Ether-report;
                description "Ether Report Type";
              }
            }
          }
        }
      }

      container hour24-path {
        xr:xr-xml-map "pmengine_ui_cfg:Hour24_Path";
        description
          "Configure pm parameters of pathmonitor 24 hour
          interval";

        container hour24otn-path {
          xr:xr-xml-map "pmengine_ui_cfg:Hour24OTN_Path";
          description "configure otn g709 performance monitoring";

          container hour24otn-path-reports {
            xr:xr-xml-map "pmengine_ui_cfg:Hour24OTN_PathReportTabl"+
              "e";
            description "set otn TCA reporting status";

            list hour24otn-path-report {
              xr:xr-xml-map "pmengine_ui_cfg:Hour24OTN_PathReport";
              key "otn-report";
              description "none";
              leaf otn-report {
                xr:xr-xml-map "pmengine_ui_cfg:OTNReport";
                type Otn-report;
                description "Otn Report Type";
              }
              leaf enable {
                xr:xr-xml-map "pmengine_ui_cfg:Enable";
                type Report;
                mandatory true;
                description "Otn Report";
              }
            }
          }

          container hour24otn-path-thresholds {
            xr:xr-xml-map "pmengine_ui_cfg:Hour24OTN_PathThresholdT"+
              "able";
            description "Configure threshold on otn parameters";

            list hour24otn-path-threshold {
              xr:xr-xml-map "pmengine_ui_cfg:Hour24OTN_PathThreshol"+
                "d";
              key "otn-threshold";
              description "none";
              leaf otn-threshold {
                xr:xr-xml-map "pmengine_ui_cfg:OTNThreshold";
                type Otn-threshold;
                description "Otn Threshold Type";
              }
              leaf otn-threshold-value {
                xr:xr-xml-map "pmengine_ui_cfg:OtnThresholdValue";
                type int32;
                mandatory true;
                description "Otn Threshold Value";
              }
            }
          }
        }
      }

      container minute15 {
        xr:xr-xml-map "pmengine_ui_cfg:Minute15";
        description "set opr min threshold";

        container minute15-optics {
          xr:xr-xml-map "pmengine_ui_cfg:Minute15Optics";
          description "Configure optics performance monitoring";

          container minute15-optics-thresholds {
            xr:xr-xml-map "pmengine_ui_cfg:Minute15OpticsThresholdT"+
              "able";
            description "Configure threshold on optics parameters";

            list minute15-optics-threshold {
              xr:xr-xml-map "pmengine_ui_cfg:Minute15OpticsThreshol"+
                "d";
              key "optics-threshold";
              description "none";
              leaf optics-threshold {
                xr:xr-xml-map "pmengine_ui_cfg:OpticsThreshold";
                type Optics-threshold;
                description "Optics Threshold Type";
              }
              leaf optics-threshold-value {
                xr:xr-xml-map "pmengine_ui_cfg:OpticsThresholdValue";
                type int32;
                description "Optics Threshold Value";
              }
              leaf dbm {
                xr:xr-xml-map "pmengine_ui_cfg:Dbm";
                type int32;
                default "0";
                description
                  "Used only for Opt and Opr,To Enter
                  Threshold in dbm use 1";
              }
            }
          }

          container minute15-optics-reports {
            xr:xr-xml-map "pmengine_ui_cfg:Minute15OpticsReportTabl"+
              "e";
            description "set optics TCA reporting status";

            list minute15-optics-report {
              xr:xr-xml-map "pmengine_ui_cfg:Minute15OpticsReport";
              key "optics-report";
              description "none";
              leaf optics-report {
                xr:xr-xml-map "pmengine_ui_cfg:OpticsReport";
                type Optics-report;
                description "Optics Report Type";
              }
            }
          }
        }

        container minute15fec {
          xr:xr-xml-map "pmengine_ui_cfg:Minute15FEC";
          description "Configure fec g709 performance monitoring";

          container minute15fec-thresholds {
            xr:xr-xml-map "pmengine_ui_cfg:Minute15FECThresholdTabl"+
              "e";
            description "Configure fec threshold";

            list minute15fec-threshold {
              xr:xr-xml-map "pmengine_ui_cfg:Minute15FECThreshold";
              key "fec-threshold";
              description "none";
              leaf fec-threshold {
                xr:xr-xml-map "pmengine_ui_cfg:FECThreshold";
                type Fec-threshold;
                description "Fec Threshold Type";
              }
              leaf fec-threshold-value {
                xr:xr-xml-map "pmengine_ui_cfg:FecThresholdValue";
                type string {
                  length "0..16";
                }
                mandatory true;
                description "Fec Threshold Value";
              }
            }
          }

          container minute15fec-reports {
            xr:xr-xml-map "pmengine_ui_cfg:Minute15FECReportTable";
            description "set fec TCA reporting status";

            list minute15fec-report {
              xr:xr-xml-map "pmengine_ui_cfg:Minute15FECReport";
              key "fec-report";
              description "none";
              leaf fec-report {
                xr:xr-xml-map "pmengine_ui_cfg:FECReport";
                type Fec-report;
                description "Fec Report Type";
              }
              leaf enable {
                xr:xr-xml-map "pmengine_ui_cfg:Enable";
                type Report;
                mandatory true;
                description "Fec Report";
              }
            }
          }
        }

        container minute15otn {
          xr:xr-xml-map "pmengine_ui_cfg:Minute15OTN";
          description "configure otn g709 performance monitoring";

          container min15-otn-threshes {
            xr:xr-xml-map "pmengine_ui_cfg:Minute15OTNThresholdTabl"+
              "e";
            description "Configure threshold on otn parameters";

            list min15-otn-thresh {
              xr:xr-xml-map "pmengine_ui_cfg:Min15OtnThresh";
              key "otn-threshold";
              description "none";
              leaf otn-threshold {
                xr:xr-xml-map "pmengine_ui_cfg:OTNThreshold";
                type Otn-threshold;
                description "Otn Threshold Type";
              }
              leaf otn-threshold-value {
                xr:xr-xml-map "pmengine_ui_cfg:OtnThresholdValue";
                type int32;
                mandatory true;
                description "Otn Threshold Value";
              }
            }
          }

          container minute15otn-reports {
            xr:xr-xml-map "pmengine_ui_cfg:Minute15OTNReportTable";
            description "set otn TCA reporting status";

            list minute15otn-report {
              xr:xr-xml-map "pmengine_ui_cfg:Minute15OTNReport";
              key "otn-report";
              description "none";
              leaf otn-report {
                xr:xr-xml-map "pmengine_ui_cfg:OTNReport";
                type Otn-report;
                description "Otn Report Type";
              }
              leaf enable {
                xr:xr-xml-map "pmengine_ui_cfg:Enable";
                type Report;
                mandatory true;
                description "Otn Report";
              }
            }
          }
        }
      }
    }
    description
      "This augment extends the configuration data of
      'Cisco-IOS-XR-ifmgr-cfg'";
  }
}
