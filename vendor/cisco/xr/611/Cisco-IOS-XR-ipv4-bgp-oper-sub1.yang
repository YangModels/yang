submodule Cisco-IOS-XR-ipv4-bgp-oper-sub1 {

  belongs-to Cisco-IOS-XR-ipv4-bgp-oper {
    prefix Cisco-IOS-XR-ipv4-bgp-oper;
  }

  /*** LINKAGE (IMPORTS / INCLUDES) ***/

  import ietf-inet-types { prefix "inet"; }

  import ietf-yang-types { prefix "yang"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR ipv4-bgp package operational data.

     Copyright (c) 2013-2016 by Cisco Systems, Inc.
     All rights reserved.";

  revision "2015-08-27" {
    description
      "IOS XR 5.3.2 revision.";
  }

  typedef Bgp-label-rpf-install {
    type enumeration {
      enum bgp-label-rpf-install-rib {
        value 0;
        description "Install via RIB";
      }
      enum bgp-label-rpf-install-lsd {
        value 1;
        description "Install via LSD";
      }
    }
    description "BGP Label RPF Install Path";
  }
  typedef Bgp-rpki-perror {
    type enumeration {
      enum none {
        description "No protocol error";
      }
      enum message-version {
        description "Message version error";
      }
      enum message-type {
        description "Message type error";
      }
      enum message-length {
        description "Message length error";
      }
      enum nonce-mismatch {
        description "Server nonce mismatch";
      }
      enum bad-prefix {
        description "Bad ROA";
      }
      enum fsm {
        description "FSM error";
      }
      enum no-response {
        description "No response from server";
      }
      enum error-report {
        description "Server sent error-report";
      }
    }
    description "Bgp rpki perror";
  }
  typedef Bgp-rpki-pstate {
    type enumeration {
      enum not-started {
        description "Server protocol has not started";
      }
      enum reset {
        description "Server protocol reset";
      }
      enum refresh {
        description "Server protocol resumed";
      }
      enum reset-query-sent {
        description "Reset query sent to server";
      }
      enum serial-query-sent {
        description "Serial query sent to server";
      }
      enum data-start {
        description "Server started sending data";
      }
      enum data-end {
        description "Server ended sending data";
      }
    }
    description "Bgp rpki pstate";
  }
  typedef Bgp-rpki-creason {
    type enumeration {
      enum no-close-reason {
        value 0;
        description "No close reason";
      }
      enum read-error {
        value 1;
        description "Socket Read error";
      }
      enum write-error {
        value 2;
        description "Socket Write error";
      }
      enum proto-error {
        value 3;
        description "Protocol error";
      }
      enum config-shutdown {
        value 4;
        description "Shutdown by configuration";
      }
      enum config-removed {
        value 5;
        description "Configuration removed";
      }
      enum config-changed {
        value 6;
        description "Configuration changed";
      }
      enum nsr-disabled {
        value 7;
        description "NSR disabled";
      }
      enum user-clear {
        value 8;
        description "Explicity user clear";
      }
      enum ssh-died {
        value 9;
        description "SSH process died";
      }
      enum tcp-died {
        value 10;
        description "TCP process died";
      }
    }
    description "Bgp rpki creason";
  }
  typedef Bgp-rpki-state {
    type enumeration {
      enum idle {
        value 0;
        description "Server is idle";
      }
      enum attempt-connect {
        value 1;
        description "Connect attempt made to server";
      }
      enum connected {
        value 2;
        description "Server is connected";
      }
    }
    description "Bgp rpki state";
  }
  typedef Bgp-ism-conn-state {
    type enumeration {
      enum none {
        description "None - ST 0";
      }
      enum connect-init {
        description "ISSUMgr connection initiated - ST 1";
      }
      enum connect-fail {
        description "ISSUMgr connection failed - ST 2";
      }
      enum connect-done {
        description "ISSUMgr connection done - ST 3";
      }
      enum disconnect-init {
        description "ISSUMgr dis-connection initiated - ST 4";
      }
      enum disconnect-fail {
        description "ISSUMgr dis-connection failed - ST 5";
      }
      enum disconnect-done {
        description "ISSUMgr dis-connection done - ST 6";
      }
    }
    description "Bgp ism conn state";
  }
  typedef Bgp-ds-conn-state {
    type enumeration {
      enum none {
        description "DS connection not initiated - ST 0";
      }
      enum connect-init {
        description "DS connection initiated - ST 1";
      }
      enum connect-fail {
        description "DS connection failed - ST 2";
      }
      enum connect-estb {
        description "DS connection established - ST 3";
      }
      enum disconnect-init {
        description "DS disconnect initiated - ST 4";
      }
      enum disconnect-fail {
        description "DS disconnect failed - ST 5";
      }
      enum disconnect-done {
        description "DS disconnect done - ST 6";
      }
    }
    description "Bgp ds conn state";
  }
  typedef Bgp-scoped-sync-state {
    type enumeration {
      enum bgp-scope-sync-state-none {
        description "State none";
      }
      enum bgp-scope-sync-state-not-nsr-ready {
        description "Oper Down when NSR not ready";
      }
      enum bgp-scope-sync-state-timer-start {
        description "Timer started for active batch";
      }
      enum bgp-scope-sync-state-add-list {
        description "Start adding neighbors to pending batch";
      }
      enum bgp-scope-sync-state-batch-acitve {
        description "Active batch";
      }
    }
    description "Bgp scoped sync state";
  }
  typedef Bgp-bmp-state {
    type enumeration {
      enum none {
        value 0;
        description "BMP NOT Connected";
      }
      enum connecting {
        value 1;
        description "BMP Under Connection";
      }
      enum established {
        value 2;
        description "BMP Connection Established";
      }
    }
    description "BMP Connection State";
  }
  typedef Bgp-bag-upd-filter-action {
    type enumeration {
      enum none {
        value 0;
        description "No Action";
      }
      enum withdraw {
        value 1;
        description "Withdraw NLRI";
      }
      enum attribute-discard {
        value 2;
        description "Discard Attribute";
      }
    }
    description "Bgp bag upd filter action";
  }
  typedef Bgp-bag-upd-err-action {
    type enumeration {
      enum bgp-bag-upd-err-action-none {
        value 0;
        description "No Action";
      }
      enum bgp-bag-upd-err-action-discard-msg {
        value 1;
        description "Discard Message";
      }
      enum bgp-bag-upd-err-action-reset {
        value 2;
        description "Session Reset";
      }
      enum bgp-bag-upd-err-action-wdr-or-reset {
        value 3;
        description "Withdraw NLRI or Reset";
      }
      enum bgp-bag-upd-err-action-wdr {
        value 4;
        description "Withdraw NLRI";
      }
      enum bgp-bag-upd-err-action-discard-attr {
        value 5;
        description "Discard Attribute";
      }
      enum bgp-bag-upd-err-action-local-repair {
        value 6;
        description "Local Repair";
      }
      enum bgp-bag-upd-err-action-max {
        value 7;
        description "Maximum number of actions";
      }
    }
    description "Bgp bag upd err action";
  }
  typedef Bgp-sync-nbr-nsr-state {
    type enumeration {
      enum bgp-nbr-nsr-st-none {
        description "None - ST 0";
      }
      enum bgp-nbr-nsr-st-oper-down {
        description "TCP OPER_DOWN notfn received - ST 1";
      }
      enum bgp-nbr-nsr-st-tcp-init-sync {
        description "TCP initial sync in progress - ST 2";
      }
      enum bgp-nbr-nsr-st-tcp-phase-two {
        description "TCP initial sync phase two in progress - ST 3";
      }
      enum bgp-nbr-nsr-st-bgp-init-sync {
        description "BGP initial sync in progress - ST 4";
      }
      enum bgp-nbr-nsr-st-nsr-ready {
        description "Neighbor NSR ready - ST 5";
      }
    }
    description "Bgp sync nbr nsr state";
  }
  typedef Bgp-peer-reset-reason-index {
    type enumeration {
      enum bgp-read-remote-closed {
        value 1;
        description "Remote closed the session";
      }
      enum bgp-read-failed {
        value 2;
        description "Read failed";
      }
      enum bgp-write-failed {
        value 3;
        description "Write failed";
      }
      enum bgp-sock-disconnected {
        value 4;
        description "Socket disconnected";
      }
      enum bgp-sock-select-failed {
        value 5;
        description "Socket select failed";
      }
      enum bgp-peer-reset-reason-none {
        value 6;
        description "None";
      }
    }
    description "Bgp peer reset reason index";
  }
  typedef Bgp-reset-reason-index {
    type enumeration {
      enum bgp-none {
        value 0;
        description "None";
      }
      enum bgp-init {
        value 1;
        description "BGP neighbor initialized";
      }
      enum bgp-no-memory {
        value 2;
        description "No memory";
      }
      enum not-received {
        value 3;
        description "BGP Notification received";
      }
      enum not-sent {
        value 4;
        description "BGP Notification sent";
      }
      enum conn-collision {
        value 5;
        description "Error during connection collision";
      }
      enum peer-closed {
        value 6;
        description "Peer closing down the session";
      }
      enum max-prefix-exceeded {
        value 7;
        description "Peer exceeding maximum prefix limit";
      }
      enum interface-flap {
        value 8;
        description "Interface flap";
      }
      enum neighbor-deleted {
        value 9;
        description "Neighbor deleted";
      }
      enum admin-shutdown {
        value 10;
        description "Admin. shutdown";
      }
      enum af-activated {
        value 11;
        description "Address family activated";
      }
      enum af-deactivated {
        value 12;
        description "Address family removed";
      }
      enum protocol-error {
        value 13;
        description "Protocol Error";
      }
      enum listen-closed {
        value 14;
        description "Listen socket was closed";
      }
      enum rib-failed {
        value 15;
        description "Routing Table process not responding";
      }
      enum user-clear {
        value 16;
        description "User clear requested";
      }
      enum user-clear-gr {
        value 17;
        description "User clear with graceful restart requested";
      }
      enum router-id-changed {
        value 18;
        description "Router ID changed";
      }
      enum remote-as-changed {
        value 19;
        description "Remote AS configuration changed";
      }
      enum orf-changed {
        value 20;
        description "Outbound route filter configuration changed";
      }
      enum rr-client-changed {
        value 21;
        description "RR client configuration changed";
      }
      enum legacy-pe-rt-changed {
        value 22;
        description "Legacy-pe-RT configuration changed";
      }
      enum softre-config-changed {
        value 23;
        description "Soft reconfiguration configuration changed";
      }
      enum local-as-changed {
        value 24;
        description "Local AS configuration changed";
      }
      enum low-memory {
        value 25;
        description "Shutdown during SEVERE low memory condition";
      }
      enum bfd-down {
        value 26;
        description
          "BFD (Bidirectional forwarding detection)
          session down";
      }
      enum allow-as-in-changed {
        value 27;
        description "Allowas-in configuration has changed";
      }
      enum recv-dmz-cfg {
        value 28;
        description "Recv DMZ Config changed";
      }
      enum cap-4byteas-changed {
        value 29;
        description "Capablity 4-byte-as configuration has changed";
      }
      enum tcp-oper-down {
        value 30;
        description "Received tcp oper down";
      }
      enum scoped-sync-retry {
        value 31;
        description
          "Scoped sync is repeated due to strict          
          prefix check failure";
      }
      enum cluster-id-changed {
        value 32;
        description "Neighbor moved to a new cluster";
      }
      enum rr-disable-changed {
        value 33;
        description
          "Client-to-client reflection disabled/enabled   
          for cluster to which neighbor belongs";
      }
      enum aigp-changed {
        value 34;
        description
          "AIGP configuration has changed                 
          for cluster to which neighbor belongs";
      }
      enum signalling-changed {
        value 35;
        description "L2VPN Signalling Changed";
      }
      enum open-check-s-failed {
        value 36;
        description "Session open checks failed";
      }
      enum ao-changed {
        value 37;
        description "Accept-own changed";
      }
      enum llgr-staletime-changed {
        value 38;
        description
          "Long-lived graceful-restart stale-time
          configuration changed";
      }
      enum llgr-capable-changed {
        value 39;
        description
          "Long-lived graceful-restart capable
          configuration changed";
      }
      enum nbr-local-addr-changed {
        value 40;
        description "Neighbor local address configuration changed";
      }
      enum internal-vpn-client-changed {
        value 41;
        description "Internal-vpn-client configuration changed";
      }
      enum cap-suppress-all-changed {
        value 42;
        description "All capabilities suppression changed";
      }
    }
    description "Bgp reset reason index";
  }
  typedef Bgp-bfd-enable-mode {
    type enumeration {
      enum bgp-bfd-enable-mode-disable {
        value 0;
        description "BFD fast detect disabled ";
      }
      enum bgp-bfd-enable-mode-def {
        value 1;
        description "BFD fast detect default mode ";
      }
      enum bgp-bfd-enable-mode-strict {
        value 2;
        description "BFD fast detect hold down aka strict mode";
      }
    }
    description "BFD enable mode";
  }
  typedef Bgp-bfd-state {
    type enumeration {
      enum bgp-bfd-state-not-configured {
        value 0;
        description "BFD not configured";
      }
      enum bgp-bfd-state-admin-down {
        value 1;
        description "BFD session disabled (neighbor shutdown)";
      }
      enum bgp-bfd-state-not-supported {
        value 2;
        description
          "BFD session disabled (interface type not
          supported)";
      }
      enum bgp-bfd-state-not-created {
        value 3;
        description "BFD session configured, not yet created";
      }
      enum bgp-bfd-state-created {
        value 4;
        description
          "BFD session created, state notification not
          received";
      }
      enum bgp-bfd-state-up {
        value 5;
        description "BFD session up";
      }
      enum bgp-bfd-state-down {
        value 6;
        description "BFD session down";
      }
      enum bgp-bfd-state-nbr-not-configured {
        value 7;
        description "BFD session down (peer not configured)";
      }
      enum bgp-bfd-state-none {
        value 8;
        description "BFD session (yet ro rcv Notification)";
      }
    }
    description "BFD session state";
  }
  typedef Bgp-open-check-err {
    type enumeration {
      enum none {
        value 0;
        description "No error";
      }
      enum neighbor-down {
        value 1;
        description "Neighbor down";
      }
      enum no-update-group-set {
        value 2;
        description "No update-group set";
      }
      enum no-af-config {
        value 3;
        description "No AF configured";
      }
      enum update-group-pending {
        value 4;
        description "Update-group pending";
      }
      enum low-memory {
        value 5;
        description "Low memory";
      }
      enum neighbor-shutdown {
        value 6;
        description "Neighbor shutdown";
      }
      enum ebgp-neighbor-remote {
        value 7;
        description "eBGP neighbor is remote";
      }
      enum update-source-interface-null {
        value 8;
        description "Update source invalid";
      }
      enum no-ipv6-address {
        value 9;
        description "No global IPv6 address found";
      }
      enum first-hop-interface-null {
        value 10;
        description "First-hop interface invalid";
      }
      enum no-ipv6ll-address {
        value 11;
        description "No LL IPv6 address found";
      }
      enum no-update-source-config {
        value 12;
        description "No update-source configured";
      }
      enum no-router-id {
        value 13;
        description "No router-identifier";
      }
      enum update-source-interface-get-failed {
        value 14;
        description "Update-source interface get failed";
      }
      enum update-source-interface-state-get-failed {
        value 15;
        description "Update-source interface state get failed";
      }
      enum update-source-interface-down {
        value 16;
        description "Update-source interface down";
      }
      enum update-source-interface-ll-get-failed {
        value 17;
        description "Update-source interface LL get failed";
      }
      enum update-source-interface-address-get-failed {
        value 18;
        description "Update-source interface address get failed";
      }
      enum source-address-af-invalid {
        value 19;
        description "Source-address AF invalid";
      }
      enum no-update-source-ll-peering {
        value 20;
        description "No update-source for LL peering";
      }
      enum local-address-get-failed {
        value 21;
        description "Local-address get failed";
      }
      enum no-best-local-address {
        value 22;
        description "No best local-address";
      }
      enum neighbor-address-equals-local-address {
        value 23;
        description "Neighbor address is local address";
      }
      enum neighbor-closing {
        value 24;
        description "Neighbor in closing state";
      }
      enum neighbor-pending-reset {
        value 25;
        description "Neighbor in pending reset state";
      }
      enum out-interface-set-failed {
        value 26;
        description "Out-interface set failed";
      }
      enum local-address-mismatch {
        value 27;
        description "Local-address mismatch";
      }
      enum neighbor-active-only {
        value 28;
        description "Neighbor in active only mode";
      }
      enum socket-init-failed {
        value 29;
        description "Socket init failed";
      }
      enum socket-operation-failed {
        value 30;
        description "Socket operation failed";
      }
      enum local-neighbor {
        value 31;
        description "Neighbor is local";
      }
      enum multi-hop-neighbor {
        value 32;
        description "No router to multi-hop neighbor";
      }
    }
    description "BGP open check error types";
  }
  typedef Bgp-conn-state {
    type enumeration {
      enum bgp-st-dont-care {
        value 0;
        description "DontCare";
      }
      enum bgp-st-idle {
        value 1;
        description "Idle";
      }
      enum bgp-st-connect {
        value 2;
        description "Connect";
      }
      enum bgp-st-active {
        value 3;
        description "Active";
      }
      enum bgp-st-open-sent {
        value 4;
        description "OpenSent";
      }
      enum bgp-st-open-confirm {
        value 5;
        description "OpenConfirm";
      }
      enum bgp-st-estab {
        value 6;
        description "Established";
      }
      enum bgp-st-closing {
        value 7;
        description "Closing";
      }
      enum bgp-st-closing-sync {
        value 8;
        description "ClosingSync";
      }
    }
    description "Bgp conn state";
  }
  typedef Bgp-nh-validate {
    type enumeration {
      enum bgp-nh-validate-sync {
        description "bgp nh validate sync";
      }
      enum bgp-nh-validate-async {
        description "bgp nh validate async";
      }
      enum bgp-nh-validate-none {
        description "bgp nh validate none";
      }
    }
    description "Bgp nh validate";
  }
  typedef Bgp-nh-update {
    type enumeration {
      enum bgp-nh-update-none {
        value 0;
        description "No nh update yet";
      }
      enum bgp-nh-update-crit-not-f {
        value 1;
        description "Last nh update is crit notf";
      }
      enum bgp-nh-update-crit-sync {
        value 2;
        description "Last nh update is crit sync update";
      }
      enum bgp-nh-update-crit-rib-conv {
        value 3;
        description
          "Last nh update is crit update caused by rib
          converge";
      }
      enum bgp-nh-update-crit-table-down {
        value 4;
        description
          "Last nh update is crit update caused by table
          down";
      }
      enum bgp-nh-update-non-crit-not-f {
        value 5;
        description "Last nh update is non-crit notf";
      }
      enum bgp-nh-update-non-crit-sync {
        value 6;
        description "Last nh update is non-crit sync update";
      }
      enum bgp-nh-update-non-crit-rib-conv {
        value 7;
        description
          "Last nh update is non-crit update caused by rib
          converge";
      }
      enum bgp-nh-update-non-crit-table-down {
        value 8;
        description
          "Last nh update is non-crit update caused by
          table down";
      }
    }
    description "Bgp nh update";
  }
  typedef Bgp-nh-event {
    type enumeration {
      enum bgp-nh-event-crit-not-f {
        value 0;
        description "Last event received is a crit notf";
      }
      enum bgp-nh-event-non-crit-not-f {
        value 1;
        description "Last event received is a non-crit notf";
      }
      enum bgp-nh-event-registration {
        value 2;
        description "Last event sent is a registration";
      }
    }
    description "Bgp nh event";
  }
  typedef Bgp-rtr-state {
    type enumeration {
      enum bgp-router-read-only {
        value 0;
        description "Read only mode";
      }
      enum bgp-router-do-best-path {
        value 1;
        description "Bestpath calculation mode";
      }
      enum bgp-router-do-tunnel-update {
        value 2;
        description "Tunnel update mode";
      }
      enum bgp-router-do-import {
        value 3;
        description "Import mode";
      }
      enum bgp-router-do-label-alloc {
        value 4;
        description "Label Allocation mode";
      }
      enum bgp-router-do-ribupd {
        value 5;
        description "RIB update mode";
      }
      enum bgp-router-read-write {
        value 6;
        description "Normal (read/write) mode";
      }
      enum bgp-router-mode-count {
        value 7;
        description "Number of router modes";
      }
    }
    description "Bgp rtr state";
  }
  typedef Mac-address {
    type yang:mac-address;
    description "MAC Address type";
  }
  typedef Bgp-rnh-addr-len {
    type enumeration {
      enum none {
        value 0;
        description "NO address length";
      }
      enum v4 {
        value 4;
        description "IP v4 address length";
      }
      enum mac {
        value 6;
        description "MAC address length";
      }
      enum v6 {
        value 16;
        description "IP v6 address length";
      }
    }
    description "BGP RNH Address Length";
  }
  typedef Bgp-bp-stage {
    type enumeration {
      enum bgp-bp-comp-not-compared {
        value 0;
        description "Best path comparison not performed";
      }
      enum bgp-bp-comp-imulti-path {
        value 1;
        description "Path is an iBGP multipath";
      }
      enum bgp-bp-comp-emulti-path {
        value 2;
        description "Path is an eBGP multipath";
      }
      enum bgp-bp-comp-eimulti-path {
        value 3;
        description "Path is an eiBGP multipath";
      }
      enum bgp-bp-invalid-path {
        value 4;
        description "Invalid path";
      }
      enum bgp-bp-comp-pre-cost-comm {
        value 5;
        description "TODO";
      }
      enum bgp-bp-comp-weight {
        value 6;
        description "Path has a lower weight";
      }
      enum bgp-bp-comp-locpref {
        value 7;
        description "Path has a lower local preference";
      }
      enum bgp-bp-comp-rpki {
        value 8;
        description "Path has worse origin validation state";
      }
      enum bgp-bp-comp-aigp {
        value 9;
        description "TODO";
      }
      enum bgp-bp-comp-local {
        value 10;
        description "Path is not local";
      }
      enum bgp-bp-comp-local-rib {
        value 11;
        description "TODO";
      }
      enum bgp-bp-comp-as-path-len {
        value 12;
        description "Path has a longer AS path";
      }
      enum bgp-bp-comp-origin {
        value 13;
        description "Path has a less favorable origin";
      }
      enum bgp-bp-comp-med {
        value 14;
        description "Path has a lower MED";
      }
      enum bgp-bp-comp-ebgp {
        value 15;
        description "Path lost to an eBGP path";
      }
      enum bgp-bp-comp-ao {
        value 16;
        description "Path has Accept-Own community";
      }
      enum bgp-bp-comp-igp-metric {
        value 17;
        description "Path has a higher IGP metric";
      }
      enum bgp-bp-comp-igp-cost-comm {
        value 18;
        description "TODO";
      }
      enum bgp-bp-comp-rtr-id {
        value 19;
        description "Path has a higher router ID";
      }
      enum bgp-bp-comp-clstr-len {
        value 20;
        description "Path has a longer cluster length";
      }
      enum bgp-bp-comp-nbr-addr {
        value 21;
        description "Path has a higher neighbor address";
      }
      enum bgp-bp-comp-suppressed {
        value 22;
        description "Path is newer than best path";
      }
      enum bgp-bp-comp-mismatch {
        value 23;
        description
          "Best path comparison failed, perhaps due to
          recent configuration changes";
      }
      enum bgp-bp-comp-persistence {
        value 24;
        description "Path is persistent";
      }
    }
    description "Bgp bp stage";
  }
  typedef Bgp-gw-addr-len {
    type enumeration {
      enum gwnone {
        value 0;
        description "NO address length";
      }
      enum gwipv4 {
        value 4;
        description "IP v4 address length";
      }
      enum gwipv6 {
        value 16;
        description "IP v6 address length";
      }
    }
    description "BGP GW Address Length";
  }
  typedef Bgp-route1 {
    type enumeration {
      enum bgp-route-type-used {
        value 0;
        description "Used path from neighbor";
      }
      enum bgp-route-type-rcvd-only {
        value 1;
        description "Received only path from neighbor";
      }
      enum bgp-route-type-rib {
        value 2;
        description "Redistributed from the RIB";
      }
      enum bgp-route-type-aggregate {
        value 3;
        description "Locally generated aggregate";
      }
      enum bgp-route-type-max {
        value 4;
        description "Number of route types";
      }
    }
    description "Bgp route1";
  }
  typedef Bgp-rpki-af {
    type enumeration {
      enum ipv4 {
        value 2;
        description "IPv4";
      }
      enum ipv6 {
        value 26;
        description "IPv6";
      }
    }
    description "Bgp rpki af";
  }
  typedef Bgp-tcp-mode {
    type enumeration {
      enum bgp-tcp-mode-type-either {
        value 0;
        description "Use either active or passive mode";
      }
      enum bgp-tcp-mode-type-active-only {
        value 1;
        description "Use active mode only";
      }
      enum bgp-tcp-mode-type-passive-only {
        value 2;
        description "Use passive mode only";
      }
    }
    description "Bgp tcp mode";
  }
  typedef Bgp-ebgp-send-dmz-enable-mode {
    type enumeration {
      enum bgp-ebgp-send-dmz-disable {
        value 0;
        description
          "EBGP send extended community dmz link bandwidth
          disabled ";
      }
      enum bgp-ebgp-send-dmz-dflt {
        value 1;
        description
          "EBGP send extended community dmz link bandwidth
          default mode ";
      }
      enum bgp-ebgp-send-dmz-cumulative {
        value 2;
        description
          "EBGP send extended community dmz link bandwidth
          cumulative mode";
      }
    }
    description
      "EBGP send extended community dmz link bandwidth
      enable mode";
  }
  typedef Bgp-entities {
    type enumeration {
      enum af-group {
        value 0;
        description "AF groups";
      }
      enum session-group {
        value 1;
        description "Session Groups";
      }
      enum neighbor-group {
        value 2;
        description "Neighbor Groups";
      }
      enum neighbor {
        value 3;
        description "Neighbors";
      }
    }
    description "Entity type";
  }
  typedef Ipv6-flowspec-address {
    type xr:Bgp-ipv6-flowspec-address;
    description "IPv6 Flowspec Address type";
  }
  typedef Ipv4-flowspec-address {
    type xr:Bgp-ipv4-flowspec-address;
    description "IPv4 Flowspec Address type";
  }
  typedef Ls-ls-address {
    type xr:Bgp-ls-addr;
    description "LINKSTATE LINKSTATE Address type";
  }
  typedef L2vpnevpn-address {
    type xr:Bgp-l2vpn-evpn-addrs;
    description "L2VPN EVPN Address type";
  }
  typedef Ipv4mvpn-address {
    type xr:Bgp-ipv4-mvpn-addr;
    description "IPV4 MVPN Address type";
  }
  typedef Ipv6mvpn-address {
    type xr:Bgp-ipv6-mvpn-addr;
    description "IPV6 MVPN Address type";
  }
  typedef Rt-constraint-address {
    type xr:Bgp-rt-constrt-addr;
    description "IPV4 RTConstraint Address type";
  }
  typedef Ipv6-address {
    type inet:ipv6-address;
    description "IPV6 Address type";
  }
  typedef Ipv4mdt-address {
    type xr:Bgp-ipv4-mdt-addr;
    description "IPV4MDT Address type";
  }
  typedef Ipv4-tunnel-address {
    type xr:Bgp-ipv4-tunnel-addr;
    description "IPV4Tunnel Address type";
  }
  typedef Bgp-afi {
    type enumeration {
      enum ipv4 {
        value 0;
        description "IP v4 unicast";
      }
      enum ipv4-multicast {
        value 1;
        description "IP v4 multicast";
      }
      enum ipv4-labeled {
        value 2;
        description "IP v4 label";
      }
      enum ipv4-tunnel {
        value 3;
        description "IP v4 Tunnel";
      }
      enum vp-nv4 {
        value 4;
        description "IP v4 virtual private network";
      }
      enum ipv6 {
        value 5;
        description "IP v6 unicast";
      }
      enum ipv6-multicast {
        value 6;
        description "IP v6 multicast";
      }
      enum ipv6-labeled {
        value 7;
        description "IP v6 label";
      }
      enum vp-nv6 {
        value 8;
        description "IP v6 virtual private network";
      }
      enum ipv4mdt {
        value 9;
        description "IP v4 Multicast  Distribution Tree";
      }
      enum l2vpn-vpls {
        value 10;
        description "L2VPN VPLS";
      }
      enum rt-constraint {
        value 11;
        description "IP RT-Constraint";
      }
      enum ipv4mvpn {
        value 12;
        description "IP v4 mvpn";
      }
      enum ipv6mvpn {
        value 13;
        description "IP v6 mvpn";
      }
      enum l2vpn-evpn {
        value 14;
        description "L2VPN EVPN";
      }
      enum ls-ls {
        value 15;
        description "Link-state Link-state";
      }
      enum vp-nv4-multicast {
        value 16;
        description "IP v4 virtual private network for multicast";
      }
      enum vp-nv6-multicast {
        value 17;
        description "IP v6 virtual private network for multicast";
      }
      enum ipv4-flowspec {
        value 18;
        description "IP v4 flowspec";
      }
      enum ipv6-flowspec {
        value 19;
        description "IP v6 flowspec";
      }
      enum vp-nv4-flowspec {
        value 20;
        description "IP v4 vpn flowspec";
      }
      enum vp-nv6-flowspec {
        value 21;
        description "IP v6 vpn flowspec";
      }
      enum l2vpn-mspw {
        value 22;
        description "L2VPN Multi-segment pseudowire";
      }
      enum no-address-family {
        value 23;
        description "Address-family not applicable";
      }
      enum all-address-families {
        value 24;
        description "All address-families";
      }
    }
    description "BGP Address family";
  }

  grouping BGP-INSTANCE-INFO {
    description "BGP instance information";
    leaf instance-identifier {
      xr:xr-xml-map "bgp:InstanceIdentifier";
      type uint16;
      description "Instance Identifier";
    }
    leaf placed-group-id {
      xr:xr-xml-map "bgp:PlacedGroupID";
      type uint16;
      description "Placed Group Identifier";
    }
    leaf instance-name-str {
      xr:xr-xml-map "bgp:InstanceNameStr";
      type string;
      description "Instance Name";
    }
    leaf as-number {
      xr:xr-xml-map "bgp:ASNumber";
      type uint32;
      description "AS Number";
    }
    leaf number-of-vrfs {
      xr:xr-xml-map "bgp:NumberOfVrfs";
      type uint32;
      description "Number of VRFs";
    }
    leaf read-only-enabled {
      xr:xr-xml-map "bgp:ReadOnlyEnabled";
      type boolean;
      description "Read-only is enabled";
    }
    leaf install-diversion-enabled {
      xr:xr-xml-map "bgp:InstallDiversionEnabled";
      type boolean;
      description "Install diversion is enabled";
    }
    leaf srgb-start-configured {
      xr:xr-xml-map "bgp:SRGBStartConfigured";
      type uint32;
      description
        "Configured start value of Segment-routing global
        block";
    }
    leaf srgb-end-configured {
      xr:xr-xml-map "bgp:SRGBEndConfigured";
      type uint32;
      description
        "Configured end value of Segment-routing global
        block";
    }

    list af-array {
      min-elements "23";
      max-elements "23";
      description "Array of Address Families";
      leaf entry {
        type boolean;
        description "Array entry.";
      }
    }
  }

  grouping BGP-INSTANCES-INFO-BAG {
    description "BGP instances information bag";

    list instance {
      description "Array of instance information";
      uses BGP-INSTANCE-INFO;
    }
  }

  grouping BGP-EDM-LABEL-RPF-NBR {
    description "BGP EDM LABEL RPF NBR";
    leaf ip {
      xr:xr-xml-map "bgp:ip";
      type inet:ipv4-address;
      description "ip";
    }
    leaf ip6 {
      xr:xr-xml-map "bgp:ip6";
      type inet:ipv6-address;
      description "ip6";
    }
    leaf count {
      xr:xr-xml-map "bgp:count";
      type uint32;
      description "count";
    }
    leaf flags {
      xr:xr-xml-map "bgp:flags";
      type uint32;
      description "flags";
    }
  }

  grouping BGP-EDM-LABEL-RPF-INFO {
    description "BGP EDM LABEL RPF INFO";
    leaf label {
      xr:xr-xml-map "bgp:label";
      type uint32;
      description "label";
    }
    leaf flags {
      xr:xr-xml-map "bgp:flags";
      type uint32;
      description "flags";
    }
    leaf install {
      xr:xr-xml-map "bgp:install";
      type Bgp-label-rpf-install;
      description "install";
    }

    list rpf {
      description "rpf";
      uses BGP-EDM-LABEL-RPF-NBR;
    }
  }

  grouping BGP-LABEL-RPF-BAG {
    description "BGP LABEL RPF BAG";

    container rpf {
      description "rpf";
      uses BGP-EDM-LABEL-RPF-INFO;
    }
  }

  grouping BGP-RPKI-SUMMARY-BAG {
    description "BGP RPKI SUMMARY BAG";
    leaf servers {
      xr:xr-xml-map "bgp:Servers";
      type uint32;
      description "Number of RPKI Servers configured";
    }
    leaf ipv4roa-nets {
      xr:xr-xml-map "bgp:IPv4ROANets";
      type uint32;
      description "Number of IPv4 ROA Nets";
    }
    leaf ipv4roa-paths {
      xr:xr-xml-map "bgp:IPv4ROAPaths";
      type uint32;
      description "Number of IPv4 ROA Paths";
    }
    leaf ipv6roa-nets {
      xr:xr-xml-map "bgp:IPv6ROANets";
      type uint32;
      description "Number of IPv6 ROA Nets";
    }
    leaf ipv6roa-paths {
      xr:xr-xml-map "bgp:IPv6ROAPaths";
      type uint32;
      description "Number of IPv6 ROA Paths";
    }
    leaf rpki-disabled {
      xr:xr-xml-map "bgp:RPKIDisabled";
      type boolean;
      description "RPKI Knob disabled";
    }
    leaf rpki-use-validity {
      xr:xr-xml-map "bgp:RPKIUseValidity";
      type boolean;
      description "Use RPKI validity for bestpath calculation";
    }
    leaf rpki-allow-invalid {
      xr:xr-xml-map "bgp:RPKIAllowInvalid";
      type boolean;
      description "Allow invalid paths";
    }
    leaf rpki-signal-ibgp {
      xr:xr-xml-map "bgp:RPKISignalIBGP";
      type boolean;
      description "Signal RPKI validity to iBGP peers";
    }
  }

  grouping BGP-UPDERR-PROC-BAG {
    description "BGP Update error-handling Process information";

    container last-update-malformed-timestamp {
      description
        "Last malformed messages received time: time
        elapsed since 00:00:00 UTC, January 1, 1970";
      uses BGP-TIMESPEC;
    }
    leaf update-error-handling-basic-ebgp {
      xr:xr-xml-map "bgp:UpdateErrorHandlingBasicEBGP";
      type boolean;
      description "Is basic error-handling for EBGP enabled";
    }
    leaf update-error-handling-basic-ibgp {
      xr:xr-xml-map "bgp:UpdateErrorHandlingBasicIBGP";
      type boolean;
      description "Is basic error-handling for IBGP enabled";
    }
    leaf update-error-handling-extended-ebgp {
      xr:xr-xml-map "bgp:UpdateErrorHandlingExtendedEBGP";
      type boolean;
      description "Is extended error-handling for EBGP enabled";
    }
    leaf update-error-handling-extended-ibgp {
      xr:xr-xml-map "bgp:UpdateErrorHandlingExtendedIBGP";
      type boolean;
      description "Is extended error-handling for IBGP enabled";
    }
    leaf update-malformed-message-count {
      xr:xr-xml-map "bgp:UpdateMalformedMessageCount";
      type uint32;
      description "Malformed messages count";
    }
    leaf update-malformed-neighbor-count {
      xr:xr-xml-map "bgp:UpdateMalformedNeighborCount";
      type uint32;
      description
        "Count of neighbors that received malformed
        messages";
    }
    leaf last-update-malformed-age {
      xr:xr-xml-map "bgp:LastUpdateMalformedAge";
      type uint32;
      units "second";
      description
        "Time since last malformed messages received
        event (in seconds)";
    }
  }

  grouping BGP-EDM-RPKI-ROUTE {
    description "BGP EDM RPKI ROUTE";
    leaf af-name {
      xr:xr-xml-map "bgp:AFName";
      type Bgp-rpki-af;
      description "Address Family";
    }
    leaf address {
      xr:xr-xml-map "bgp:Address";
      type string;
      description "Address Prefix";
    }
    leaf min-prefix-len {
      xr:xr-xml-map "bgp:MinPrefixLen";
      type uint8;
      description "Minimum Prefix Length";
    }
    leaf max-prefix-len {
      xr:xr-xml-map "bgp:MaxPrefixLen";
      type uint8;
      description "Maximum Prefix Length";
    }
    leaf as {
      xr:xr-xml-map "bgp:AS";
      type uint32;
      description "AS number";
    }
    leaf refcount {
      xr:xr-xml-map "bgp:Refcount";
      type uint16;
      description "Refcount";
    }
    leaf server {
      xr:xr-xml-map "bgp:Server";
      type string;
      description "Source Server";
    }
    leaf stale {
      xr:xr-xml-map "bgp:Stale";
      type boolean;
      description "ROA is stale";
    }
  }

  grouping BGP-RPKI-ROUTES-BAG {
    description "BGP RPKI ROUTES BAG";

    list rpki-route {
      description "Array or RPKI routes";
      uses BGP-EDM-RPKI-ROUTE;
    }
  }

  grouping BGP-EDM-LABEL-STATS {
    description "BGP EDM LABEL STATS";
    leaf nbgp-label-alloc-type-gbl-ipv4 {
      xr:xr-xml-map "bgp:nBGP_LABEL_ALLOC_TYPE_GBL_IPv4";
      type uint32;
      description "nBGP LABEL ALLOC TYPE GBL IPv4";
    }
    leaf nbgp-label-alloc-type-gbl-ipv6 {
      xr:xr-xml-map "bgp:nBGP_LABEL_ALLOC_TYPE_GBL_IPv6";
      type uint32;
      description "nBGP LABEL ALLOC TYPE GBL IPv6";
    }
    leaf nbgp-label-alloc-type-vrf-ipv4 {
      xr:xr-xml-map "bgp:nBGP_LABEL_ALLOC_TYPE_VRF_IPv4";
      type uint32;
      description "nBGP LABEL ALLOC TYPE VRF IPv4";
    }
    leaf nbgp-label-alloc-type-vrf-ipv6 {
      xr:xr-xml-map "bgp:nBGP_LABEL_ALLOC_TYPE_VRF_IPv6";
      type uint32;
      description "nBGP LABEL ALLOC TYPE VRF IPv6";
    }
    leaf nbgp-label-alloc-type-ce-ipv4 {
      xr:xr-xml-map "bgp:nBGP_LABEL_ALLOC_TYPE_CE_IPv4";
      type uint32;
      description "nBGP LABEL ALLOC TYPE CE IPv4";
    }
    leaf nbgp-label-alloc-type-ce-ipv6 {
      xr:xr-xml-map "bgp:nBGP_LABEL_ALLOC_TYPE_CE_IPv6";
      type uint32;
      description "nBGP LABEL ALLOC TYPE CE IPv6";
    }
    leaf nbgp-label-alloc-type-tbl-ipv4 {
      xr:xr-xml-map "bgp:nBGP_LABEL_ALLOC_TYPE_TBL_IPv4";
      type uint32;
      description "nBGP LABEL ALLOC TYPE TBL IPv4";
    }
    leaf nbgp-label-alloc-type-tbl-ipv6 {
      xr:xr-xml-map "bgp:nBGP_LABEL_ALLOC_TYPE_TBL_IPv6";
      type uint32;
      description "nBGP LABEL ALLOC TYPE TBL IPv6";
    }
    leaf nbgp-label-alloc-type-vpn-ipv4 {
      xr:xr-xml-map "bgp:nBGP_LABEL_ALLOC_TYPE_VPN_IPv4";
      type uint32;
      description "nBGP LABEL ALLOC TYPE VPN IPv4";
    }
    leaf nbgp-label-alloc-type-vpn-ipv6 {
      xr:xr-xml-map "bgp:nBGP_LABEL_ALLOC_TYPE_VPN_IPv6";
      type uint32;
      description "nBGP LABEL ALLOC TYPE VPN IPv6";
    }
    leaf nbgp-label-alloc-type-asbr-nh {
      xr:xr-xml-map "bgp:nBGP_LABEL_ALLOC_TYPE_ASBR_NH";
      type uint32;
      description "nBGP LABEL ALLOC TYPE ASBR NH";
    }
    leaf nbgp-labels {
      xr:xr-xml-map "bgp:nBGP_LABELS";
      type uint32;
      description "nBGP LABELS";
    }
    leaf bgp-label-rpf-lists {
      xr:xr-xml-map "bgp:bgp_label_rpf_lists";
      type uint32;
      description "bgp label rpf lists";
    }
    leaf bgp-label-rpf-nodes {
      xr:xr-xml-map "bgp:bgp_label_rpf_nodes";
      type uint32;
      description "bgp label rpf nodes";
    }
  }

  grouping BGP-LABEL-SUMMARY-BAG {
    description "BGP LABEL SUMMARY BAG";

    container stats {
      description "stats";
      uses BGP-EDM-LABEL-STATS;
    }
  }

  grouping BGP-EDM-RPKI-CACHE {
    description "BGP EDM RPKI CACHE";
    leaf name {
      xr:xr-xml-map "bgp:Name";
      type string;
      description "Server Name";
    }
    leaf preference {
      xr:xr-xml-map "bgp:Preference";
      type uint32;
      description "Server Preference";
    }
    leaf port {
      xr:xr-xml-map "bgp:Port";
      type uint32;
      description "Server TCP Port number";
    }
    leaf state {
      xr:xr-xml-map "bgp:State";
      type Bgp-rpki-state;
      description "Server Internal State";
    }
    leaf state-time {
      xr:xr-xml-map "bgp:StateTime";
      type uint32;
      description "Server Internal State timestamp (unix time)";
    }
    leaf shutdown {
      xr:xr-xml-map "bgp:Shutdown";
      type boolean;
      description "Server Shutdown";
    }
    leaf retries {
      xr:xr-xml-map "bgp:Retries";
      type uint32;
      description "Number of connection retries";
    }
    leaf close-reason {
      xr:xr-xml-map "bgp:CloseReason";
      type Bgp-rpki-creason;
      description "Server close reason";
    }
    leaf close-time {
      xr:xr-xml-map "bgp:CloseTime";
      type uint32;
      description "Server close elapsed time";
    }
    leaf close-time-real {
      xr:xr-xml-map "bgp:CloseTimeReal";
      type uint32;
      description "Server close real timestamp (unix time)";
    }
    leaf read-bytes {
      xr:xr-xml-map "bgp:ReadBytes";
      type uint32;
      units "byte";
      description "Number of bytes read from the server";
    }
    leaf write-bytes {
      xr:xr-xml-map "bgp:WriteBytes";
      type uint32;
      units "byte";
      description "Number of bytes written to the server";
    }
    leaf transport {
      xr:xr-xml-map "bgp:Transport";
      type uint32;
      description "Server transport type";
    }
    leaf username {
      xr:xr-xml-map "bgp:Username";
      type string;
      description "Server SSH username";
    }
    leaf password {
      xr:xr-xml-map "bgp:Password";
      type string;
      description "Server SSH password";
    }
    leaf sshpid {
      xr:xr-xml-map "bgp:SSHPID";
      type uint32;
      description "Server SSH process ID";
    }
    leaf proto-state {
      xr:xr-xml-map "bgp:ProtoState";
      type Bgp-rpki-pstate;
      description "Server Protocol state";
    }
    leaf proto-state-time {
      xr:xr-xml-map "bgp:ProtoStateTime";
      type uint32;
      description "Server Protocol state timestamp (unix time)";
    }
    leaf serial {
      xr:xr-xml-map "bgp:Serial";
      type uint32;
      description "Server serial number";
    }
    leaf nonce {
      xr:xr-xml-map "bgp:Nonce";
      type uint32;
      description "Server nonce";
    }
    leaf refresh-time {
      xr:xr-xml-map "bgp:RefreshTime";
      type int32;
      units "second";
      description "Server refresh time (seconds)";
    }
    leaf response-time {
      xr:xr-xml-map "bgp:ResponseTime";
      type int32;
      units "second";
      description "Server response time (seconds)";
    }
    leaf purge-time {
      xr:xr-xml-map "bgp:PurgeTime";
      type int32;
      units "second";
      description "Server purge time (seconds)";
    }
    leaf ipv4roa {
      xr:xr-xml-map "bgp:IPv4ROA";
      type uint32;
      description "Total IPv4 ROAs currently recv'd from server";
    }
    leaf ipv4roa-announce {
      xr:xr-xml-map "bgp:IPv4ROAAnnounce";
      type uint32;
      description "Total IPv4 ROAs announced by the server";
    }
    leaf ipv4roa-withdraw {
      xr:xr-xml-map "bgp:IPv4ROAWithdraw";
      type uint32;
      description "Total IPv4 ROAs withdrawn by the server";
    }
    leaf ipv6roa {
      xr:xr-xml-map "bgp:IPv6ROA";
      type uint32;
      description "Total IPv6 ROAs currently recv'd from server";
    }
    leaf ipv6roa-announce {
      xr:xr-xml-map "bgp:IPv6ROAAnnounce";
      type uint32;
      description "Total IPv6 ROAs announced by the server";
    }
    leaf ipv6roa-withdraw {
      xr:xr-xml-map "bgp:IPv6ROAWithdraw";
      type uint32;
      description "Total IPv6 ROAs withdrawn by the server";
    }
    leaf proto-error {
      xr:xr-xml-map "bgp:ProtoError";
      type Bgp-rpki-perror;
      description "Protocol Error Reason";
    }
  }

  grouping BGP-RPKI-CACHES-BAG {
    description "BGP RPKI CACHES BAG";

    list rpki-server {
      description "Array of RPKI servers";
      uses BGP-EDM-RPKI-CACHE;
    }
  }

  grouping BGP-ATTRFILTER-ENTRY-BAG {
    description "BGP attribute-filter entry information";
    leaf attribute-filter-entry-requested-action {
      xr:xr-xml-map "bgp:AttributeFilterEntryRequestedAction";
      type Bgp-bag-upd-filter-action;
      description "Requested filtering action";
    }
    leaf attribute-filter-entry-range-start {
      xr:xr-xml-map "bgp:AttributeFilterEntryRangeStart";
      type uint32;
      description "Start of attribute range";
    }
    leaf attribute-filter-entry-range-end {
      xr:xr-xml-map "bgp:AttributeFilterEntryRangeEnd";
      type uint32;
      description "End of attribute range";
    }
  }

  grouping BGP-ATTRFILTER-GROUP-BAG {
    description "BGP attribute-filter group information";
    leaf attribute-filter-group-name {
      xr:xr-xml-map "bgp:AttributeFilterGroupName";
      type string;
      description "Attribute-filter group name";
    }
    leaf attribute-filter-total-group-count {
      xr:xr-xml-map "bgp:AttributeFilterTotalGroupCount";
      type uint32;
      description "Total number of attriute-filter groups";
    }

    list attribute-filter-entry {
      description "List of attriute-filter entries";
      uses BGP-ATTRFILTER-ENTRY-BAG;
    }
  }

  grouping BGP-EDM-LABEL-ENTRY {
    description "BGP EDM LABEL ENTRY";
    leaf label {
      xr:xr-xml-map "bgp:label";
      type uint32;
      description "label";
    }
    leaf rds {
      xr:xr-xml-map "bgp:rds";
      type string;
      description "rds";
    }
    leaf vrf {
      xr:xr-xml-map "bgp:vrf";
      type string;
      description "vrf";
    }
    leaf ip {
      xr:xr-xml-map "bgp:ip";
      type inet:ipv4-address;
      description "ip";
    }
    leaf ip6 {
      xr:xr-xml-map "bgp:ip6";
      type inet:ipv6-address;
      description "ip6";
    }
    leaf rpc-set-id {
      xr:xr-xml-map "bgp:rpc_set_id";
      type uint32;
      description "rpc set id";
    }
    leaf masklen {
      xr:xr-xml-map "bgp:masklen";
      type uint16;
      description "masklen";
    }
    leaf ts-sec {
      xr:xr-xml-map "bgp:ts_sec";
      type uint32;
      description "ts sec";
    }
    leaf ts-ssec {
      xr:xr-xml-map "bgp:ts_ssec";
      type uint32;
      description "ts ssec";
    }
    leaf info {
      xr:xr-xml-map "bgp:info";
      type uint16;
      description "info";
    }
    leaf refcount {
      xr:xr-xml-map "bgp:refcount";
      type uint32;
      description "refcount";
    }
    leaf inactive {
      xr:xr-xml-map "bgp:inactive";
      type boolean;
      description "inactive";
    }
  }

  grouping BGP-LABEL-BAG {
    description "BGP LABEL BAG";

    container entry {
      description "entry";
      uses BGP-EDM-LABEL-ENTRY;
    }
  }

  grouping BGP-EDM-RT-ENTRY {
    description "BGP EDM RT ENTRY";
    leaf route-target {
      xr:xr-xml-map "bgp:route_target";
      type string;
      description "route target";
    }
  }

  grouping BGP-VRF-RT-BAG {
    description "BGP VRF RT BAG";

    container rt {
      description "rt";
      uses BGP-EDM-RT-ENTRY;
    }
    leaf afs {
      xr:xr-xml-map "bgp:afs";
      type string;
      description "afs";
    }
  }

  grouping BGP-UPDFILTER-PROC-BAG {
    description "BGP Update filtering Process information";

    container last-update-filtered-timestamp {
      description
        "Last filtered messages received time: time
        elapsed since 00:00:00 UTC, January 1, 1970";
      uses BGP-TIMESPEC;
    }
    leaf update-filtered-message-count {
      xr:xr-xml-map "bgp:UpdateFilteredMessageCount";
      type uint32;
      description "Filtered messages count";
    }
    leaf update-filtered-neighbor-count {
      xr:xr-xml-map "bgp:UpdateFilteredNeighborCount";
      type uint32;
      description
        "Count of neighbors that received filtered
        messages";
    }
    leaf last-update-filtered-age {
      xr:xr-xml-map "bgp:LastUpdateFilteredAge";
      type uint32;
      units "second";
      description
        "Time since last filtered messages received event
        (in seconds)";
    }
  }

  grouping BGP-NBR-MSG {
    description "Neighbor In/Out Message entry";

    container message-timestamp {
      description
        "message received time: time elapsed since 00:00
        :00 UTC, January 1, 1970";
      uses BGP-TIMESPEC;
    }
    leaf message-type-received {
      xr:xr-xml-map "bgp:MessageTypeReceived";
      type uint8;
      description "Type of messages Received";
    }
    leaf total-logged-message-count {
      xr:xr-xml-map "bgp:TotalLoggedMessageCount";
      type uint32;
      description "Total logged messages count";
    }
    leaf message-data-length {
      xr:xr-xml-map "bgp:MessageDataLength";
      type uint16;
      description "Message data length";
    }
    leaf-list logged-message-data {
      xr:xr-xml-map "bgp:LoggedMessageData";
      type uint8;
      description "Raw Message data in binary format";
    }
  }

  grouping BGP-MSGLOG-NBR-BAG {
    description "BGP Message logging Neighbor information";

    list neighbor-message {
      description "Array of Neighbor Messages in one direction";
      uses BGP-NBR-MSG;
    }
  }

  grouping BGP-NEXTHOP-VRF-BAG {
    description "BGP nexthop processing information for a VRF";
    leaf total-processing-time {
      xr:xr-xml-map "bgp:TotalProcessingTime";
      type uint32;
      description "Total time spent in processing";
    }
    leaf max-proc-notification-time {
      xr:xr-xml-map "bgp:MaxProcNotificationTime";
      type uint32;
      description
        "How long since the maximum processing time
        notifcation was received";
    }
    leaf max-notification-bestpath-deletes {
      xr:xr-xml-map "bgp:MaxNotificationBestpathDeletes";
      type uint32;
      description
        "Number of bestpath deletes caused by
        notification which resulted in maximum
        processing";
    }
    leaf max-notification-bestpath-changes {
      xr:xr-xml-map "bgp:MaxNotificationBestpathChanges";
      type uint32;
      description
        "Number of bestpath changes caused by
        notification which resulted in maximum
        processing";
    }
    leaf maximum-processing-time {
      xr:xr-xml-map "bgp:MaximumProcessingTime";
      type uint32;
      description
        "Maximum time spent procesing a single batch
        notification";
    }
    leaf last-notificationication-time {
      xr:xr-xml-map "bgp:LastNotificationicationTime";
      type uint32;
      description "Time since the last notification was received";
    }
    leaf last-notification-processing-time {
      xr:xr-xml-map "bgp:LastNotificationProcessingTime";
      type uint32;
      description "Processing time for the last notification";
    }
  }

  grouping BGP-NBR-BRIEF-BAG {
    description "BGP Neighbor brief Information";

    container connection-local-address {
      description "Local address for the connection";
      uses BGP-ADDRTYPE;
    }

    container connection-remote-address {
      description "Remote address for the connection";
      uses BGP-ADDRTYPE;
    }
    leaf speaker-id {
      xr:xr-xml-map "bgp:SpeakerID";
      type uint8;
      description "Speaker this neighbor is allocated to";
    }
    leaf description {
      xr:xr-xml-map "bgp:Description";
      type string;
      description "Description";
    }
    leaf local-as {
      xr:xr-xml-map "bgp:LocalAS";
      type uint32;
      description "Local AS number";
    }
    leaf remote-as {
      xr:xr-xml-map "bgp:RemoteAS";
      type uint32;
      description "Remote AS number";
    }
    leaf messages-queued-in {
      xr:xr-xml-map "bgp:MessagesQueuedIn";
      type uint32;
      description "No. of msgs on receive queue";
    }
    leaf messages-queued-out {
      xr:xr-xml-map "bgp:MessagesQueuedOut";
      type uint32;
      description "No. of messages on send queue";
    }
    leaf connection-state {
      xr:xr-xml-map "bgp:ConnectionState";
      type Bgp-conn-state;
      description "State of connection";
    }
    leaf is-local-address-configured {
      xr:xr-xml-map "bgp:IsLocalAddressConfigured";
      type boolean;
      description
        "Local address configured for the neighbor
        connection";
    }
    leaf vrf-name {
      xr:xr-xml-map "bgp:VRFName";
      type string;
      description "Name of the VRF";
    }
    leaf nsr-enabled {
      xr:xr-xml-map "bgp:NSREnabled";
      type boolean;
      description "Neighbor supports NSR";
    }
    leaf nsr-state {
      xr:xr-xml-map "bgp:NSRState";
      type Bgp-sync-nbr-nsr-state;
      description "NSR state";
    }
    leaf postit-pending {
      xr:xr-xml-map "bgp:PostitPending";
      type boolean;
      description "Nbr has postits pending";
    }
  }

  grouping BGP-PERF-PROCESS-VRF {
    description "BGP PERF PROCESS VRF";
    leaf lpts-set-up-time {
      xr:xr-xml-map "bgp:LPTSSetUpTime";
      type uint32;
      description "Time spent setting up LPTS socket opt (ms)";
    }
    leaf lpts-calls {
      xr:xr-xml-map "bgp:LPTSCalls";
      type uint32;
      description "Number of times LPTS socket opt set up";
    }
    leaf read-throttles-count {
      xr:xr-xml-map "bgp:ReadThrottlesCount";
      type uint32;
      description "Number of partial read throttles";
    }
    leaf low-throttled-read-count {
      xr:xr-xml-map "bgp:LowThrottledReadCount";
      type uint32;
      description
        "Number of socket reads for nbrs above low
        threshold";
    }
    leaf high-throttled-read-count {
      xr:xr-xml-map "bgp:HighThrottledReadCount";
      type uint32;
      description
        "Number of socket reads for nbrs above high
        threshold";
    }
    leaf read-calls-count {
      xr:xr-xml-map "bgp:ReadCallsCount";
      type uint32;
      description "No. of calls to function to read inbound data";
    }
    leaf read-messages-count {
      xr:xr-xml-map "bgp:ReadMessagesCount";
      type uint32;
      description "Number of BGP messages read";
    }
    leaf data-bytes-read {
      xr:xr-xml-map "bgp:DataBytesRead";
      type uint32;
      units "byte";
      description "No. of bytes of data read";
    }
    leaf io-read-time {
      xr:xr-xml-map "bgp:IOReadTime";
      type uint32;
      description "Time spent reading inbound data (ms)";
    }
    leaf write-calls-count {
      xr:xr-xml-map "bgp:WriteCallsCount";
      type uint32;
      description "No. of calls to function to write outbound data";
    }
    leaf data-bytes-written {
      xr:xr-xml-map "bgp:DataBytesWritten";
      type uint32;
      units "byte";
      description "Number of bytes of data written";
    }
    leaf io-write-time {
      xr:xr-xml-map "bgp:IOWriteTime";
      type uint32;
      description "Time spent writing outbound data (ms)";
    }
    leaf write-subgroup-calls-count {
      xr:xr-xml-map "bgp:WriteSubgroupCallsCount";
      type uint32;
      description
        "No. of calls to to funvction to process
        sub-group message list";
    }
    leaf write-subgroup-messages-count {
      xr:xr-xml-map "bgp:WriteSubgroupMessagesCount";
      type uint32;
      description "Number of sub-group messages processed";
    }
    leaf subgroup-list-time {
      xr:xr-xml-map "bgp:SubgroupListTime";
      type uint32;
      units "millisecond";
      description
        "Time spent processing sub-group message list
        (milliseconds)";
    }
    leaf write-queue-calls-count {
      xr:xr-xml-map "bgp:WriteQueueCallsCount";
      type uint32;
      description "No. of Calls to function to process write queue";
    }
    leaf write-queue-messages-count {
      xr:xr-xml-map "bgp:WriteQueueMessagesCount";
      type uint32;
      description "Number of write queue messages processed";
    }
    leaf write-queue-time {
      xr:xr-xml-map "bgp:WriteQueueTime";
      type uint32;
      description "Time spent processing write queue (ms)";
    }
    leaf inbound-update-messages {
      xr:xr-xml-map "bgp:InboundUpdateMessages";
      type uint32;
      description "Number of inbound update messages processed";
    }
    leaf inbound-update-messages-time {
      xr:xr-xml-map "bgp:InboundUpdateMessagesTime";
      type uint32;
      units "millisecond";
      description
        "Time spent processing imbound update messages
        (milliseconds)";
    }
  }

  grouping BGP-PERF-NPL-ENDP-INFO-BAG {
    description "BGP PERF NPL ENDP INFO BAG";
    leaf endpoint-name {
      xr:xr-xml-map "bgp:EndpointName";
      type string;
      description "Endpoint name";
    }
    leaf sync-group-name {
      xr:xr-xml-map "bgp:SyncGroupName";
      type string;
      description "Syncgroup associated with this endpoint";
    }
    leaf node-id {
      xr:xr-xml-map "bgp:NodeID";
      type xr:Node-id;
      description "Node ID";
    }
    leaf endpoint-handle {
      xr:xr-xml-map "bgp:EndpointHandle";
      type uint64;
      description "NCD endpoint handle";
    }
    leaf endpoint-stale-flag {
      xr:xr-xml-map "bgp:EndpointStaleFlag";
      type boolean;
      description "Endpoint stale flag";
    }
    leaf endpoint-issu-role {
      xr:xr-xml-map "bgp:EndpointISSURole";
      type string;
      description
        "Endpoint's ISSU Role. Values are 'Primary',
        'Secondary' and 'Tertiary'";
    }
    leaf endpoint-active-flag {
      xr:xr-xml-map "bgp:EndpointActiveFlag";
      type boolean;
      description "Endpoint active flag";
    }
    leaf msg-size {
      xr:xr-xml-map "bgp:MsgSize";
      type uint32;
      description "Message size for this entity";
    }
    leaf wheel-id {
      xr:xr-xml-map "bgp:WheelID";
      type uint32;
      description "Wheel ID for this endpoint";
    }
    leaf expected-sequence-num {
      xr:xr-xml-map "bgp:ExpectedSequenceNum";
      type uint32;
      description "Expected sequence number";
    }
    leaf-list endpoint {
      xr:xr-xml-map "bgp:Endpoint";
      type uint8;
      units "byte";
      description "NCD endpoint bytestream";
    }
  }

  grouping NSR-PL-RECV-DROP-ARRAY {
    description "NSR PL RECV DROP ARRAY";
    leaf-list nsr-pl-recv-drop-array {
      xr:xr-xml-map "bgp:nsr_pl_recv_drop_array_t";
      type uint32;
      max-elements "15";
      description "nsr pl recv drop array";
    }
  }

  grouping NSR-PL-SEND-DROP-ARRAY {
    description "NSR PL SEND DROP ARRAY";
    leaf-list nsr-pl-send-drop-array {
      xr:xr-xml-map "bgp:nsr_pl_send_drop_array_t";
      type uint32;
      max-elements "7";
      description "nsr pl send drop array";
    }
  }

  grouping NSR-PL-CLIENT-STATS-TYPE {
    description "NSR PL stats information";
    leaf-list num-sent {
      xr:xr-xml-map "bgp:num_sent";
      type uint64;
      max-elements "5";
      description "Total sent";
    }
    leaf-list num-recv {
      xr:xr-xml-map "bgp:num_recv";
      type uint64;
      max-elements "6";
      description "Total recvd";
    }

    list num-sent-drop {
      max-elements "5";
      description "Sent Error/drops";
      uses NSR-PL-SEND-DROP-ARRAY;
    }

    list num-recv-drop {
      max-elements "6";
      description "Recv Errors/drops";
      uses NSR-PL-RECV-DROP-ARRAY;
    }
  }

  grouping BGP-PERF-DS-NPL-INFO-BAG {
    description "BGP PERF DS NPL INFO BAG";
    leaf dir-service-conn-state {
      xr:xr-xml-map "bgp:DirServiceConnState";
      type Bgp-ds-conn-state;
      description "Current Directory Service connectionstate";
    }
    leaf issu-mgr-conn-state {
      xr:xr-xml-map "bgp:ISSUMgrConnState";
      type Bgp-ism-conn-state;
      description "Current ISSU Mgr connection state";
    }
    leaf issu-phase {
      xr:xr-xml-map "bgp:ISSUPhase";
      type string;
      description "Current ISSU Phase";
    }
    leaf issu-type-ng {
      xr:xr-xml-map "bgp:ISSUTypeNG";
      type boolean;
      description "ISSU type is Next Gen";
    }
    leaf issuha-option {
      xr:xr-xml-map "bgp:ISSUHAOption";
      type string;
      description "Current ISSU HA option";
    }
    leaf local-ds-handle {
      xr:xr-xml-map "bgp:LocalDSHandle";
      type uint64;
      description "Local Directory Service handle";
    }
    leaf service-name {
      xr:xr-xml-map "bgp:ServiceName";
      type string;
      description "Local DS service name";
    }
    leaf dsissu-status-flag {
      xr:xr-xml-map "bgp:DSISSUStatusFlag";
      type uint32;
      description "DS ISSU status flag";
    }

    list npl-priority-statistic {
      max-elements "2";
      description "NPL priority statistics";
      uses NSR-PL-CLIENT-STATS-TYPE;
    }

    list npl-endpoint {
      description "NPL endpoint information";
      uses BGP-PERF-NPL-ENDP-INFO-BAG;
    }
  }

  grouping BGP-PERF-SERVER-CONN-STAT-BAG {
    description "BGP PERF SERVER CONN STAT BAG";

    container first-connection-up-timestamp {
      description "First connection Up event timestamp";
      uses BGP-TIMESPEC;
    }

    container last-connection-up-timestamp {
      description "Last connection Up event timestamp";
      uses BGP-TIMESPEC;
    }

    container first-connection-down-timestamp {
      description "First connection Down event timestamp";
      uses BGP-TIMESPEC;
    }

    container last-connection-down-timestamp {
      description "Last connection Down event timestamp";
      uses BGP-TIMESPEC;
    }
    leaf is-connection-up {
      xr:xr-xml-map "bgp:IsConnectionUp";
      type boolean;
      description "Is Connection Up?";
    }
    leaf connection-up-count {
      xr:xr-xml-map "bgp:ConnectionUpCount";
      type uint32;
      description "Number of connection Up events";
    }
    leaf last-connection-up-age {
      xr:xr-xml-map "bgp:LastConnectionUpAge";
      type uint32;
      units "second";
      description
        "Time since last connection Up event (in seconds)";
    }
    leaf connection-down-count {
      xr:xr-xml-map "bgp:ConnectionDownCount";
      type uint32;
      description "Number of connection down events";
    }
    leaf last-connection-down-age {
      xr:xr-xml-map "bgp:LastConnectionDownAge";
      type uint32;
      units "second";
      description
        "Time since last connection Down event (in
        seconds)";
    }
  }

  grouping BGP-PERF-RIB-GBL-INFO-BAG {
    description "BGP PERF RIB GBL INFO BAG";

    container first-rib-connection-up-timestamp {
      description "First RIB connection Up event timestamp";
      uses BGP-TIMESPEC;
    }

    container last-rib-connection-up-timestamp {
      description "Last RIB connection Up event timestamp";
      uses BGP-TIMESPEC;
    }

    container first-rib-connection-down-timestamp {
      description "First RIB connection Down event timestamp";
      uses BGP-TIMESPEC;
    }

    container last-rib-connection-down-timestamp {
      description "Last RIB connection Down event timestamp";
      uses BGP-TIMESPEC;
    }
    leaf is-rib-connection-up {
      xr:xr-xml-map "bgp:IsRIBConnectionUp";
      type boolean;
      description "Is RIB Connection Up?";
    }
    leaf rib-connection-up-count {
      xr:xr-xml-map "bgp:RIBConnectionUpCount";
      type uint32;
      description "Number of RIB connection Up events";
    }
    leaf last-rib-connection-up-age {
      xr:xr-xml-map "bgp:LastRIBConnectionUpAge";
      type uint32;
      units "second";
      description
        "Time since last RIB connection Up event (in
        seconds)";
    }
    leaf rib-connection-down-count {
      xr:xr-xml-map "bgp:RIBConnectionDownCount";
      type uint32;
      description "Number of RIB connection Down events";
    }
    leaf last-rib-connection-down-age {
      xr:xr-xml-map "bgp:LastRIBConnectionDownAge";
      type uint32;
      units "second";
      description
        "Time since last RIB connection Down event (in
        seconds)";
    }
  }

  grouping BGP-POSTIT-COUNT-INFO {
    description "BGP POSTIT COUNT INFO";

    container neighbor-address {
      description "Neighbor Address";
      uses BGP-ADDRTYPE;
    }
    leaf postit-count {
      xr:xr-xml-map "bgp:PostitCount";
      type uint32;
      description "Count of the number of postits for this nbr";
    }
    leaf vrf-name {
      xr:xr-xml-map "bgp:VRFName";
      type string;
      description "Name of the VRF";
    }
  }

  grouping BGP-PERF-PROCESS-GBL {
    description "BGP PERF PROCESS GBL";

    container ipv4rib-server {
      description "IPv4 RIB server global info";
      uses BGP-PERF-RIB-GBL-INFO-BAG;
    }

    container ipv6rib-server {
      description "IPv6 RIB server global info";
      uses BGP-PERF-RIB-GBL-INFO-BAG;
    }

    container te-connection {
      description "MPLS TE server connection info";
      uses BGP-PERF-SERVER-CONN-STAT-BAG;
    }

    container lsd-connection {
      description "MPLS LSD server connection info";
      uses BGP-PERF-SERVER-CONN-STAT-BAG;
    }

    container ds-npl {
      description "NSR related DS and NPL information";
      uses BGP-PERF-DS-NPL-INFO-BAG;
    }
    leaf configuration-items-processed {
      xr:xr-xml-map "bgp:ConfigurationItemsProcessed";
      type uint32;
      description "Number of config items processed";
    }
    leaf configuration-processing-time {
      xr:xr-xml-map "bgp:ConfigurationProcessingTime";
      type uint32;
      units "millisecond";
      description "Time spent processing config (milliseconds)";
    }
    leaf edm-requests-count {
      xr:xr-xml-map "bgp:EDMRequestsCount";
      type uint32;
      description "Number of EDM requests processed";
    }
    leaf edm-processing-time {
      xr:xr-xml-map "bgp:EDMProcessingTime";
      type uint32;
      description "Time spent processing EDM requests (ms)";
    }
    leaf brib-api-output-messages-sent {
      xr:xr-xml-map "bgp:BribAPIOutputMessagesSent";
      type uint32;
      description "bRIB API output messages sent";
    }
    leaf brib-api-output-bytes-sent {
      xr:xr-xml-map "bgp:BribAPIOutputBytesSent";
      type uint32;
      units "byte";
      description "bRIB API output bytes sent";
    }
    leaf brib-api-output-bytes-generated {
      xr:xr-xml-map "bgp:BribAPIOutputBytesGenerated";
      type uint32;
      units "byte";
      description "bRIB API output bytes generated";
    }
    leaf brib-api-output-prefixes-advertised {
      xr:xr-xml-map "bgp:BribAPIOutputPrefixesAdvertised";
      type uint32;
      description "bRIB API output prefixes advertised";
    }
    leaf brib-api-output-prefixes-withdrawn {
      xr:xr-xml-map "bgp:BribAPIOutputPrefixesWithdrawn";
      type uint32;
      description "bRIB API output prefixes withdrawn";
    }
    leaf brib-api-output-sending-time {
      xr:xr-xml-map "bgp:BribAPIOutputSendingTime";
      type uint32;
      description "Time spent sending output to bRIB API (ms)";
    }
    leaf brib-api-output-generation-time {
      xr:xr-xml-map "bgp:BribAPIOutputGenerationTime";
      type uint32;
      units "millisecond";
      description
        "Time spent generating output for bRIB API
        (milliseconds)";
    }
    leaf brib-api-output-calls {
      xr:xr-xml-map "bgp:BribAPIOutputCalls";
      type uint32;
      description "bRIB API calls to generate output";
    }
    leaf brib-api-input-messages {
      xr:xr-xml-map "bgp:BribAPIInputMessages";
      type uint32;
      description "bRIB API input messages";
    }
    leaf brib-api-input-bytes {
      xr:xr-xml-map "bgp:BribAPIInputBytes";
      type uint32;
      units "byte";
      description "bRIB API input bytes";
    }
    leaf brib-api-input-prefixes-received {
      xr:xr-xml-map "bgp:BribAPIInputPrefixesReceived";
      type uint32;
      description "bRIB API input advertised prefixes received";
    }
    leaf brib-api-input-withdrawn-prefixes {
      xr:xr-xml-map "bgp:BribAPIInputWithdrawnPrefixes";
      type uint32;
      description "bRIB API input withdrawn prefixes received";
    }
    leaf brib-api-input-processing-time {
      xr:xr-xml-map "bgp:BribAPIInputProcessingTime";
      type uint32;
      units "millisecond";
      description
        "Time spent processing input from bRIB API
        (milliseconds)";
    }
    leaf instance-node-role {
      xr:xr-xml-map "bgp:InstanceNodeRole";
      type boolean;
      description "Node role - active/passive";
    }
    leaf active-nsrtcp-phase-two-enter-time {
      xr:xr-xml-map "bgp:ActiveNSRTCPPhaseTwoEnterTime";
      type uint32;
      units "second";
      description
        "Time that NSR TCP Init Sync Phase Two entered on
        active (seconds since Jan 1 1970)";
    }
    leaf sec-active-nsrtcp-phase-two-enter-time {
      xr:xr-xml-map "bgp:SecActiveNSRTCPPhaseTwoEnterTime";
      type uint32;
      units "second";
      description
        "Time that NSR TCP Init Sync Phase Two entered on
        active (seconds since Jan 1 1970)";
    }
    leaf proc-scoped-sync-state {
      xr:xr-xml-map "bgp:ProcScopedSyncState";
      type Bgp-scoped-sync-state;
      description "BGP scoped sync state";
    }
    leaf initial-sync-sessions-added {
      xr:xr-xml-map "bgp:InitialSyncSessionsAdded";
      type boolean;
      description
        "If true, BGP has at least one established
        session when NSR initial synchronization is
        started";
    }
    leaf in-event-attach-calls {
      xr:xr-xml-map "bgp:InEventAttachCalls";
      type uint32;
      description "event_file_attach  calls for input";
    }
    leaf out-event-attach-calls {
      xr:xr-xml-map "bgp:OutEventAttachCalls";
      type uint32;
      description "event_file_attach  calls for output";
    }
    leaf in-out-event-attach-calls {
      xr:xr-xml-map "bgp:InOutEventAttachCalls";
      type uint32;
      description "event_file_attach calls for input";
    }
    leaf updgen-timer-id {
      xr:xr-xml-map "bgp:UpdgenTimerId";
      type uint32;
      description "Updgen master timer ID";
    }
    leaf updgen-tree-timer-left {
      xr:xr-xml-map "bgp:UpdgenTreeTimerLeft";
      type uint64;
      description "Time left before the QNX timer would expire";
    }
    leaf updgen-tree-timer-expiry {
      xr:xr-xml-map "bgp:UpdgenTreeTimerExpiry";
      type uint64;
      description "Time as per tree->mtexptime";
    }
    leaf current-clock-time {
      xr:xr-xml-map "bgp:CurrentClockTime";
      type uint64;
      description "Current time";
    }
    leaf updgen-handler-tm {
      xr:xr-xml-map "bgp:UpdgenHandlerTm";
      type uint64;
      description "Timestamp when updgen timer handler got called";
    }
    leaf io-timer-id {
      xr:xr-xml-map "bgp:IOTimerId";
      type uint32;
      description "IO master timer ID";
    }
    leaf io-tree-timer-left {
      xr:xr-xml-map "bgp:IOTreeTimerLeft";
      type uint64;
      description "Time left before the QNX timer would expire";
    }
    leaf io-tree-timer-expiry {
      xr:xr-xml-map "bgp:IOTreeTimerExpiry";
      type uint64;
      description "Time as per tree->mtexptime";
    }
    leaf io-handler-tm {
      xr:xr-xml-map "bgp:IOHandlerTm";
      type uint64;
      description "Timestamp when IO timer handler got called";
    }
    leaf qad-messages-sent {
      xr:xr-xml-map "bgp:QADMessagesSent";
      type uint32;
      description "Messages sent on QAD ";
    }
    leaf qadack-sent {
      xr:xr-xml-map "bgp:QADACKSent";
      type uint32;
      description "Acks sent on QAD ";
    }
    leaf qad-send-failure {
      xr:xr-xml-map "bgp:QADSendFailure";
      type uint32;
      description "Send failure on QAD ";
    }
    leaf qad-ac-ks-failure {
      xr:xr-xml-map "bgp:QAD_ACKsFailure";
      type uint32;
      description "Ack failure on QAD ";
    }
    leaf qad-suspends {
      xr:xr-xml-map "bgp:QADSuspends";
      type uint32;
      description "QAD send suspend";
    }
    leaf qad-resumes {
      xr:xr-xml-map "bgp:QADResumes";
      type uint32;
      description "QAD send resume ";
    }
    leaf qad-send-drops {
      xr:xr-xml-map "bgp:QADSendDrops";
      type uint32;
      description "Send packets dropped due to null peer ";
    }
    leaf qad-messages-received {
      xr:xr-xml-map "bgp:QADMessagesReceived";
      type uint32;
      description "Messages received on QAD ";
    }
    leaf qad-processed {
      xr:xr-xml-map "bgp:QADProcessed";
      type uint32;
      description "Messages processed";
    }
    leaf qad-ac-ks-received {
      xr:xr-xml-map "bgp:QAD_ACKsReceived";
      type uint32;
      description "Acks received on QAD ";
    }
    leaf qad-timeout-received {
      xr:xr-xml-map "bgp:QAD_TimeoutReceived";
      type uint32;
      description "Timeouts received on QAD ";
    }
    leaf qad-init-drops {
      xr:xr-xml-map "bgp:QADInitDrops";
      type uint32;
      description
        "Packets dropped on standby during initialization";
    }
    leaf qadoos-drops {
      xr:xr-xml-map "bgp:QADOOSDrops";
      type uint32;
      description
        "Packets dropped due to  out of sequence
        packetreceived";
    }
    leaf qad-recv-drops {
      xr:xr-xml-map "bgp:QADRecvDrops";
      type uint32;
      description "Received packet dropped due to null peer ";
    }
    leaf qad-timeout-recvd {
      xr:xr-xml-map "bgp:QADTimeoutRecvd";
      type uint32;
      description "Number of packet send timeouts ";
    }
    leaf nsr-last-reset-reason {
      xr:xr-xml-map "bgp:NSRLastResetReason";
      type uint8;
      description "Reason for last nsr state  machine reset";
    }
    leaf redcon-nsr-ready {
      xr:xr-xml-map "bgp:RedconNsrReady";
      type boolean;
      description
        "NSR state conveyed to Redcon  by bgp - nsr
        ready/unready";
    }
    leaf redcon-state-time {
      xr:xr-xml-map "bgp:RedconStateTime";
      type uint32;
      description "Time when nsr state wasconveyed to Redcon last";
    }
    leaf active-nsr-state {
      xr:xr-xml-map "bgp:ActiveNsrState";
      type uint32;
      description "Current Active BGP nsrstate";
    }
    leaf sec-active-nsr-state {
      xr:xr-xml-map "bgp:SecActiveNsrState";
      type uint32;
      description "Current Sec Active BGP nsrstate";
    }
    leaf total-outstanding-postits {
      xr:xr-xml-map "bgp:TotalOutstandingPostits";
      type uint32;
      description "Total outstanding postits across all neighbors";
    }
    leaf total-neighbors-with-pending-postits {
      xr:xr-xml-map "bgp:TotalNeighborsWithPendingPostits";
      type uint32;
      description "Total nbrs with pending postits";
    }
    leaf tep2p-auto-tunnel-enabled {
      xr:xr-xml-map "bgp:TEP2PAutoTunnelEnabled";
      type boolean;
      description "TE support for P2P auto tunnel";
    }
    leaf-list active-nsr-mode-enter-time {
      xr:xr-xml-map "bgp:ActiveNSRModeEnterTime";
      type uint32;
      units "second";
      max-elements "26";
      description
        "Time that each mode was entered (seconds since
        Jan 1 1970)";
    }
    leaf-list standby-nsr-mode-enter-time {
      xr:xr-xml-map "bgp:StandbyNSRModeEnterTime";
      type uint32;
      units "second";
      max-elements "7";
      description
        "Time that each mode was entered (seconds since
        Jan 1 1970)";
    }
    leaf-list active-nsrfo-time {
      xr:xr-xml-map "bgp:ActiveNSRFOTime";
      type uint32;
      units "second";
      max-elements "10";
      description
        "Time that each thread isdone with its
        go-activeprocessing (seconds since Jan 1 1970)";
    }

    list postit-count-info {
      description "List of neighbors and their postit counts";
      uses BGP-POSTIT-COUNT-INFO;
    }
  }

  grouping BGP-PERF-PROCESS {
    description "BGP PERF PROCESS";

    container global {
      description "Global information";
      uses BGP-PERF-PROCESS-GBL;
    }

    container vrf {
      description "VRF information";
      uses BGP-PERF-PROCESS-VRF;
    }
  }

  grouping BGP-PROCESS-INFO-VRF {
    description "BGP PROCESS INFO VRF";
    leaf neighbors-count {
      xr:xr-xml-map "bgp:NeighborsCount";
      type uint32;
      description "Number of neighbors";
    }
    leaf established-neighbors-count {
      xr:xr-xml-map "bgp:EstablishedNeighborsCount";
      type uint32;
      description "Number of established neighbors";
    }
    leaf update-messages-received {
      xr:xr-xml-map "bgp:UpdateMessagesReceived";
      type uint32;
      description "Number of update messages received";
    }
    leaf update-messages-sent {
      xr:xr-xml-map "bgp:UpdateMessagesSent";
      type uint32;
      description "No. of update messages sent";
    }
    leaf notifications-received {
      xr:xr-xml-map "bgp:NotificationsReceived";
      type uint32;
      description "No. of notifications received";
    }
    leaf notifications-sent {
      xr:xr-xml-map "bgp:NotificationsSent";
      type uint32;
      description "No. of notifications sent";
    }
    leaf network-count {
      xr:xr-xml-map "bgp:NetworkCount";
      type uint32;
      description "Number of networks";
    }
    leaf path-count {
      xr:xr-xml-map "bgp:PathCount";
      type uint32;
      description "Number of paths";
    }
  }

  grouping BGP-PROCESS-INFO-GBL {
    description "BGP PROCESS INFO GBL";
    leaf process-instance-node {
      xr:xr-xml-map "bgp:ProcessInstanceNode";
      type string;
      description "Node the process instance is on";
    }
    leaf restart-count {
      xr:xr-xml-map "bgp:RestartCount";
      type uint32;
      description "No. of times BGP has started";
    }
    leaf path-attributes-entry-count {
      xr:xr-xml-map "bgp:PathAttributesEntryCount";
      type uint32;
      description "No. of path attribute entries";
    }
    leaf path-attribute-memory {
      xr:xr-xml-map "bgp:PathAttributeMemory";
      type uint32;
      units "byte";
      description "Memory (bytes) used by path attribute entries";
    }
    leaf as-path-entry-count {
      xr:xr-xml-map "bgp:ASPathEntryCount";
      type uint32;
      description "Number of AS-path entries";
    }
    leaf as-path-entries-memory {
      xr:xr-xml-map "bgp:ASPathEntriesMemory";
      type uint32;
      units "byte";
      description "Memory (in bytes) used by AS-path entries";
    }
    leaf community-entry-count {
      xr:xr-xml-map "bgp:CommunityEntryCount";
      type uint32;
      description "Number of community entries";
    }
    leaf community-memory {
      xr:xr-xml-map "bgp:CommunityMemory";
      type uint32;
      units "byte";
      description "Memory (in bytes) used by community entries";
    }
    leaf extended-community-entry-count {
      xr:xr-xml-map "bgp:ExtendedCommunityEntryCount";
      type uint32;
      description "Number of extended community entries";
    }
    leaf extended-community-memory {
      xr:xr-xml-map "bgp:ExtendedCommunityMemory";
      type uint32;
      units "byte";
      description
        "Memory (in bytes) used by extended community
        entries";
    }
    leaf pe-distinguisher-label-entry-count {
      xr:xr-xml-map "bgp:PEDistinguisherLabelEntryCount";
      type uint32;
      description "Number of PE distinguisher label entries";
    }
    leaf pe-distinguisher-label-memory {
      xr:xr-xml-map "bgp:PEDistinguisherLabelMemory";
      type uint32;
      units "byte";
      description
        "Memory (in bytes) used by PE distinguisher
        labels entries";
    }
    leaf pta-entry-count {
      xr:xr-xml-map "bgp:PtaEntryCount";
      type uint32;
      description "Number of PTA entries";
    }
    leaf pta-memory {
      xr:xr-xml-map "bgp:PtaMemory";
      type uint32;
      units "byte";
      description "Memory (in bytes) used by PTA entries";
    }
    leaf ribrnh-entry-count {
      xr:xr-xml-map "bgp:RIBRNHEntryCount";
      type uint32;
      description "Number of RIBRNH entries";
    }
    leaf ribrnh-memory {
      xr:xr-xml-map "bgp:RIBRNHMemory";
      type uint32;
      units "byte";
      description "Memory (in bytes) used by RIBRNH entries";
    }
    leaf ppmp-entry-count {
      xr:xr-xml-map "bgp:PPMPEntryCount";
      type uint32;
      description "Number of PPMP entries";
    }
    leaf ppmp-memory {
      xr:xr-xml-map "bgp:PPMPMemory";
      type uint32;
      units "byte";
      description "Memory (in bytes) used by PPMP entries";
    }
    leaf route-reflectors {
      xr:xr-xml-map "bgp:RouteReflectors";
      type uint32;
      description "Number of route reflector info entries";
    }
    leaf route-reflector-memory {
      xr:xr-xml-map "bgp:RouteReflectorMemory";
      type uint32;
      units "byte";
      description
        "Memory (in bytes) used by route reflector info
        entries";
    }
    leaf nexthop-count {
      xr:xr-xml-map "bgp:NexthopCount";
      type uint32;
      description "Number of nexthop attribute info entries";
    }
    leaf nexthop-memory {
      xr:xr-xml-map "bgp:NexthopMemory";
      type uint32;
      units "byte";
      description
        "Memory (in bytes) used by nexthop attribute info
        entries";
    }
    leaf local-as {
      xr:xr-xml-map "bgp:LocalAS";
      type uint32;
      description "Local autonomous system number";
    }
    leaf total-vrf-count {
      xr:xr-xml-map "bgp:TotalVRFCount";
      type uint32;
      description "total vrf count";
    }
    leaf neighbors-count-total {
      xr:xr-xml-map "bgp:NeighborsCountTotal";
      type uint32;
      description "Total number of neighbors";
    }
    leaf established-neighbors-count-total {
      xr:xr-xml-map "bgp:EstablishedNeighborsCountTotal";
      type uint32;
      description "Total umber of established neighbors";
    }
    leaf sn-num-non-dflt-vrf-nbrs {
      xr:xr-xml-map "bgp:sn_num_non_dflt_vrf_nbrs";
      type uint32;
      description "sn num non dflt vrf nbrs";
    }
    leaf sn-num-non-dflt-vrf-nbrs-estab {
      xr:xr-xml-map "bgp:sn_num_non_dflt_vrf_nbrs_estab";
      type uint32;
      description "sn num non dflt vrf nbrs estab";
    }
    leaf-list pool-size {
      xr:xr-xml-map "bgp:PoolSize";
      type uint32;
      max-elements "15";
      description "pool size";
    }
    leaf-list pool-alloc-count {
      xr:xr-xml-map "bgp:PoolAllocCount";
      type uint32;
      max-elements "15";
      description "pool alloc count";
    }
    leaf-list pool-free-count {
      xr:xr-xml-map "bgp:PoolFreeCount";
      type uint32;
      max-elements "15";
      description "pool free count";
    }
    leaf-list msg-log-pool-size {
      xr:xr-xml-map "bgp:MsgLogPoolSize";
      type uint32;
      max-elements "5";
      description "msg log pool size";
    }
    leaf-list msg-log-pool-alloc-count {
      xr:xr-xml-map "bgp:MsgLogPoolAllocCount";
      type uint32;
      max-elements "5";
      description "msg log pool alloc count";
    }
    leaf-list msg-log-pool-free-count {
      xr:xr-xml-map "bgp:MsgLogPoolFreeCount";
      type uint32;
      max-elements "5";
      description "msg log pool free count";
    }
  }

  grouping BGP-PROCESS-INFO-BAG {
    description "BGP Process information";

    container global {
      description "Global information";
      uses BGP-PROCESS-INFO-GBL;
    }

    container vrf {
      description "VRF information";
      uses BGP-PROCESS-INFO-VRF;
    }

    container performance-statistics {
      description "Performance statistics";
      uses BGP-PERF-PROCESS;
    }
    leaf process-instance {
      xr:xr-xml-map "bgp:ProcessInstance";
      type uint8;
      description "ID for the BGP process instance";
    }
    leaf vrf-name {
      xr:xr-xml-map "bgp:VRFName";
      type string;
      description "Name of the VRF";
    }
    leaf vrf-totals {
      xr:xr-xml-map "bgp:VRFTotals";
      type boolean;
      description "per VRF counts aggregated across all VRFs";
    }
  }

  grouping BGP-BMP-NBR-BAG {
    description "BMP per Neighbor Details";

    container bmp-neighbor-address {
      description "Address of Nbr that logs to BMP server";
      uses BGP-ADDRTYPE;
    }
    leaf bmp-neighbor-msg-pending {
      xr:xr-xml-map "bgp:BMPNeighborMsgPending";
      type uint32;
      description
        "Number of messages pending to be sent to BMP
        Server from this Neighbor";
    }
    leaf bmp-neighbor-msg-dropped {
      xr:xr-xml-map "bgp:BMPNeighborMsgDropped";
      type uint32;
      description
        "Number of messages dropped sent from this
        neighbor";
    }
    leaf bmp-neighbor-peer-up-sent {
      xr:xr-xml-map "bgp:BMPNeighborPeerUpSent";
      type uint32;
      description
        "Number of Peer UP Messages sent from this
        neighbor";
    }
    leaf bmp-neighbor-peer-down-sent {
      xr:xr-xml-map "bgp:BMPNeighborPeerDownSent";
      type uint32;
      description
        "Number of Peer DOWN Messages sent from this
        neighbor";
    }
    leaf bmp-neighbor-route-monitor-sent {
      xr:xr-xml-map "bgp:BMPNeighborRouteMonitorSent";
      type uint32;
      description "Number of Route Monitor Messages sent";
    }
  }

  grouping BGP-BMP-SRVR-BAG {
    description "BMP Server Details";

    container bmp-server-state-age {
      description "Age of current state of BMP Server";
      uses BGP-TIMESPEC;
    }

    container bmp-server-state-time-spec {
      description "Timespec of current state of BMP Server";
      uses BGP-TIMESPEC;
    }

    container bmp-server-last-discon-time {
      description
        "Timespec of Last Disconnect event received from
        BMP server";
      uses BGP-TIMESPEC;
    }

    container update-source-address {
      description
        "Address of Interface configured as Update Source";
      uses BGP-ADDRTYPE;
    }
    leaf bmp-server-id {
      xr:xr-xml-map "bgp:BMPServerID";
      type uint8;
      description "BMP Server ID";
    }
    leaf bmp-server-host-name {
      xr:xr-xml-map "bgp:BMPServerHostname";
      type string;
      description "BMP Server Hostname";
    }
    leaf bmp-server-port {
      xr:xr-xml-map "bgp:BMPServerPort";
      type uint32;
      description "BMP Server Port Number";
    }
    leaf bmp-server-state {
      xr:xr-xml-map "bgp:BMPServerState";
      type Bgp-bmp-state;
      description "Connection state of the BMP server";
    }
    leaf bmp-server-is-flapping {
      xr:xr-xml-map "bgp:BMPServerIsFlapping";
      type boolean;
      description "Connection to the BMP server Flapping";
    }
    leaf bmp-server-nbr-count {
      xr:xr-xml-map "bgp:BMPServerNbrCount";
      type uint32;
      description "Neighbor count for the BMP Server";
    }
    leaf bmp-init-msg-count {
      xr:xr-xml-map "bgp:BMPInitMsgCount";
      type uint32;
      description
        "Number of Initiation Msgs sent by this BMP
        Server";
    }
    leaf bmp-termination-msg-count {
      xr:xr-xml-map "bgp:BMPTerminationMsgCount";
      type uint32;
      description
        "Number of Termination Messages sent by this BMP
        Server";
    }
    leaf bmp-status-report-count {
      xr:xr-xml-map "bgp:BMPStatusReportCount";
      type uint32;
      description
        "Number of Status ReportMessages sent by this BMP
        Server";
    }
    leaf bmp-per-peer-msg-count {
      xr:xr-xml-map "bgp:BMPPerPeerMsgCount";
      type uint32;
      description "Total number of per peer messages sent";
    }
    leaf bmp-peer-msg-drop-count {
      xr:xr-xml-map "bgp:BMPPeerMsgDropCount";
      type uint32;
      description "Total number of messages dropped";
    }
    leaf tos-type {
      xr:xr-xml-map "bgp:TOSType";
      type uint8;
      description "Precedence (0) or DSCP (1) type";
    }
    leaf tos-value {
      xr:xr-xml-map "bgp:TOSValue";
      type uint8;
      description "Precedence or DSCP value";
    }
    leaf update-source-interface-name {
      xr:xr-xml-map "bgp:UpdateSourceInterfaceName";
      type string;
      description "Interface configured as Update Source";
    }
    leaf update-source-vrf-id {
      xr:xr-xml-map "bgp:UpdateSourceVRF_ID";
      type uint32;
      description "VRF ID of interface configured as Update Source";
    }
    leaf bmp-vrf-name {
      xr:xr-xml-map "bgp:BMP_VRFName";
      type string;
      description "VRF Name configured";
    }
    leaf bmp-vrf-id {
      xr:xr-xml-map "bgp:BMP_VRF_ID";
      type uint32;
      description "VRF ID for the vrf name configured";
    }
  }

  grouping BGP-UPDFILTER-ELEM-BAG {
    description "BGP Update filtering element information";
    leaf update-attribute-flags {
      xr:xr-xml-map "bgp:UpdateAttributeFlags";
      type uint8;
      description "Attribute Flags [RFC4271: BGP4]";
    }
    leaf update-attribute-code {
      xr:xr-xml-map "bgp:UpdateAttributeCode";
      type uint8;
      description "Attribute code [RFC4271: BGP4]";
    }
    leaf update-filter-action {
      xr:xr-xml-map "bgp:UpdateFilterAction";
      type Bgp-bag-upd-filter-action;
      description "Filtering action";
    }
  }

  grouping BGP-UPDFILTER-MSG-BAG {
    description "BGP Update filter message information";

    container update-filter-message-timestamp {
      description
        "Message timestamp: time elapsed since 00:00:00
        UTC, January 1, 1970";
      uses BGP-TIMESPEC;
    }
    leaf update-filtered-attribute-count {
      xr:xr-xml-map "bgp:UpdateFilteredAttributeCount";
      type uint32;
      description "Filtered attributes count";
    }
    leaf update-filter-final-action {
      xr:xr-xml-map "bgp:UpdateFilterFinalAction";
      type Bgp-bag-upd-filter-action;
      description "Filtering final action";
    }
    leaf update-filter-nlri-address-family {
      xr:xr-xml-map "bgp:UpdateFilterNLRIAddressFamily";
      type Bgp-afi;
      description "NLRI address-family";
    }
    leaf update-filter-nlri-string {
      xr:xr-xml-map "bgp:UpdateFilterNLRIString";
      type string;
      description "List of NLRIs in string format";
    }
    leaf update-filter-nlri-string-truncated {
      xr:xr-xml-map "bgp:UpdateFilterNLRIStringTruncated";
      type boolean;
      description
        "Indicates whether NLRI string was truncated due
        to lack of space";
    }
    leaf-list update-filter-message-data {
      xr:xr-xml-map "bgp:UpdateFilterMessageData";
      type uint8;
      description "Raw Message data in binary format";
    }

    list update-filter-element {
      max-elements "3";
      description "Filtering element list";
      uses BGP-UPDFILTER-ELEM-BAG;
    }
  }

  grouping BGP-UPDFILTER-ATTRF-ATTR-BAG {
    description "BGP Update filtering attributes information";

    container last-update-filter-match-timestamp {
      description
        "Last attribute filtered time: time elapsed since
        00:00:00 UTC, January 1, 1970";
      uses BGP-TIMESPEC;
    }
    leaf update-internal-attribute-code {
      xr:xr-xml-map "bgp:UpdateInternalAttributeCode";
      type uint32;
      description "Internal attribute code [RFC4271: BGP4]";
    }
    leaf update-filter-action {
      xr:xr-xml-map "bgp:UpdateFilterAction";
      type Bgp-bag-upd-filter-action;
      description "Filtering action";
    }
    leaf update-filter-match-count {
      xr:xr-xml-map "bgp:UpdateFilterMatchCount";
      type uint32;
      description "Filter match counter";
    }
    leaf establishment-update-filter-match-count {
      xr:xr-xml-map "bgp:EstablishmentUpdateFilterMatchCount";
      type uint32;
      description
        "Filter match counter since last session
        establishment";
    }
    leaf last-update-filter-match-age {
      xr:xr-xml-map "bgp:LastUpdateFilterMatchAge";
      type uint32;
      units "second";
      description
        "Time since this attribute was last filtered (in
        seconds)";
    }
  }

  grouping BGP-UPDFILTER-NBR-BAG {
    description "BGP Update filtering Neighbor information";

    container update-neighbor-address {
      description "Neighbor address";
      uses BGP-ADDRTYPE;
    }

    container first-update-filtered-timestamp {
      description
        "First filtered message received time: time
        elapsed since 00:00:00 UTC, January 1, 1970";
      uses BGP-TIMESPEC;
    }

    container last-update-filtered-timestamp {
      description
        "Last filtered message received time: time
        elapsed since 00:00:00 UTC, January 1, 1970";
      uses BGP-TIMESPEC;
    }
    leaf update-vrf-name {
      xr:xr-xml-map "bgp:UpdateVRFName";
      type string;
      description "VRF Name";
    }
    leaf update-filter-logging-enabled {
      xr:xr-xml-map "bgp:UpdateFilterLoggingEnabled";
      type boolean;
      description "Logging is enabled";
    }
    leaf configured-update-filter-message-buffer-count {
      xr:xr-xml-map "bgp:ConfiguredUpdateFilterMessageBufferCount";
      type uint32;
      description "Configured Filtered message buffer count";
    }
    leaf operational-update-filter-message-buffer-count {
      xr:xr-xml-map "bgp:OperationalUpdateFilterMessageBufferCount";
      type uint32;
      description "Operational Filtered messages buffer count";
    }
    leaf update-filter-message-buffer-circular {
      xr:xr-xml-map "bgp:UpdateFilterMessageBufferCircular";
      type boolean;
      description "Indicates if the message buffers are circular";
    }
    leaf update-attribute-filter-group-name {
      xr:xr-xml-map "bgp:UpdateAttributeFilterGroupName";
      type string;
      description "Update attribute-filter group name";
    }
    leaf operational-update-attribute-filtering-enabled {
      xr:xr-xml-map "bgp:OperationalUpdateAttributeFilteringEnabled";
      type boolean;
      description "Attribute filtering is enabled";
    }
    leaf message-update-attribute-filtering-enabled {
      xr:xr-xml-map "bgp:MessageUpdateAttributeFilteringEnabled";
      type boolean;
      description
        "Attribute filtering is enabled for the current
        message being parsed";
    }
    leaf total-filter-update-message-count {
      xr:xr-xml-map "bgp:TotalFilterUpdateMessageCount";
      type uint32;
      description "Total update messages count";
    }
    leaf establishment-total-filter-update-message-count {
      xr:xr-xml-map "bgp:EstablishmentTotalFilterUpdateMessageCount";
      type uint32;
      description
        "Total update messages count since session
        establishment";
    }
    leaf update-filtered-message-count {
      xr:xr-xml-map "bgp:UpdateFilteredMessageCount";
      type uint32;
      description "Filtered messages count";
    }
    leaf establishment-update-filtered-message-count {
      xr:xr-xml-map "bgp:EstablishmentUpdateFilteredMessageCount";
      type uint32;
      description
        "Filtered messages count since session
        establishment";
    }
    leaf last-update-filtered-age {
      xr:xr-xml-map "bgp:LastUpdateFilteredAge";
      type uint32;
      units "second";
      description
        "Time since last filtered message received event
        (in seconds)";
    }
    leaf update-filter-message-list-count {
      xr:xr-xml-map "bgp:UpdateFilterMessageListCount";
      type uint32;
      description "Filtered messages list count";
    }

    list update-attribute-filter-attributes {
      description "List of attributes that can be filtered";
      uses BGP-UPDFILTER-ATTRF-ATTR-BAG;
    }

    list update-filter-message {
      description "List of filtered messages";
      uses BGP-UPDFILTER-MSG-BAG;
    }
  }

  grouping BGP-UPDERR-ELEM-BAG {
    description "BGP Update error-handling element information";
    leaf update-attribute-flags {
      xr:xr-xml-map "bgp:UpdateAttributeFlags";
      type uint8;
      description "Attribute Flags [RFC4271: BGP4]";
    }
    leaf update-attribute-code {
      xr:xr-xml-map "bgp:UpdateAttributeCode";
      type uint8;
      description "Attribute code [RFC4271: BGP4]";
    }
    leaf update-attribute-length {
      xr:xr-xml-map "bgp:UpdateAttributeLength";
      type uint16;
      description "Attribute Length [RFC4271: BGP4]";
    }
    leaf update-error-data {
      xr:xr-xml-map "bgp:UpdateErrorData";
      type yang:hex-string;
      description "Error data";
    }
    leaf update-error-data-length {
      xr:xr-xml-map "bgp:UpdateErrorDataLength";
      type uint16;
      description "Error data length";
    }
    leaf update-error-action {
      xr:xr-xml-map "bgp:UpdateErrorAction";
      type Bgp-bag-upd-err-action;
      description "Error action";
    }
  }

  grouping BGP-UPDERR-RESET-DATA-BAG {
    description
      "BGP Update error-handling session reset
      information";
    leaf update-error-reset-reason {
      xr:xr-xml-map "bgp:UpdateErrorResetReason";
      type Bgp-reset-reason-index;
      description "Reset Reason";
    }
    leaf update-error-reset-notification-code {
      xr:xr-xml-map "bgp:UpdateErrorResetNotificationCode";
      type uint8;
      description "Notification code";
    }
    leaf update-error-reset-notification-sub-code {
      xr:xr-xml-map "bgp:UpdateErrorResetNotificationSubCode";
      type uint16;
      description "Notification sub code";
    }
    leaf update-error-reset-notification-data {
      xr:xr-xml-map "bgp:UpdateErrorResetNotificationData";
      type yang:hex-string;
      description "Notification data";
    }
    leaf update-error-reset-notification-data-length {
      xr:xr-xml-map "bgp:UpdateErrorResetNotificationDataLength";
      type uint16;
      description "Notification data length";
    }
  }

  grouping BGP-UPDERR-MSG-BAG {
    description "BGP Update error message information";

    container update-message-timestamp {
      description
        "Message timestamp: time elapsed since 00:00:00
        UTC, January 1, 1970";
      uses BGP-TIMESPEC;
    }

    container update-message-reset-data {
      description "Reset data";
      uses BGP-UPDERR-RESET-DATA-BAG;
    }
    leaf update-error-final-action {
      xr:xr-xml-map "bgp:UpdateErrorFinalAction";
      type Bgp-bag-upd-err-action;
      description "Error final action";
    }
    leaf update-attribute-discard-count {
      xr:xr-xml-map "bgp:UpdateAttributeDiscardCount";
      type uint32;
      description "Discarded attribute count";
    }
    leaf update-error-nlri-address-family {
      xr:xr-xml-map "bgp:UpdateErrorNLRIAddressFamily";
      type Bgp-afi;
      description "NLRI address-family";
    }
    leaf update-error-nlri-string {
      xr:xr-xml-map "bgp:UpdateErrorNLRIString";
      type string;
      description "List of NLRIs in string format";
    }
    leaf update-error-nlri-string-truncated {
      xr:xr-xml-map "bgp:UpdateErrorNLRIStringTruncated";
      type boolean;
      description
        "Indicates whether NLRI string was truncated due
        to lack of space";
    }
    leaf-list update-message-data {
      xr:xr-xml-map "bgp:UpdateMessageData";
      type uint8;
      description "Raw Message data in binary format";
    }

    list update-error-element {
      max-elements "3";
      description "Error element list";
      uses BGP-UPDERR-ELEM-BAG;
    }
  }

  grouping BGP-UPDERR-NBR-BAG {
    description "BGP Update error-handling Neighbor information";

    container update-neighbor-address {
      description "Neighbor address";
      uses BGP-ADDRTYPE;
    }

    container first-update-malformed-timestamp {
      description
        "First malformed message received time: time
        elapsed since 00:00:00 UTC, January 1, 1970";
      uses BGP-TIMESPEC;
    }

    container last-update-malformed-timestamp {
      description
        "Last malformed message received time: time
        elapsed since 00:00:00 UTC, January 1, 1970";
      uses BGP-TIMESPEC;
    }

    container first-update-memory-allocation-fail-timestamp {
      description
        "First memory allocation failure time: time
        elapsed since 00:00:00 UTC, January 1, 1970";
      uses BGP-TIMESPEC;
    }

    container last-update-memory-allocation-fail-timestamp {
      description
        "Last memory allocation failure time: time
        elapsed since 00:00:00 UTC, January 1, 1970";
      uses BGP-TIMESPEC;
    }

    container first-update-error-handling-reset-timestamp {
      description
        "First error-handling reset time: time elapsed
        since 00:00:00 UTC, January 1, 1970";
      uses BGP-TIMESPEC;
    }

    container last-error-handling-reset-timestamp {
      description
        "Last error-handling reset time: time elapsed
        since 00:00:00 UTC, January 1, 1970";
      uses BGP-TIMESPEC;
    }
    leaf update-vrf-name {
      xr:xr-xml-map "bgp:UpdateVRFName";
      type string;
      description "VRF Name";
    }
    leaf update-error-handling-avoid-reset {
      xr:xr-xml-map "bgp:UpdateErrorHandlingAvoidReset";
      type boolean;
      description "Configure error-handling to avoid resets";
    }
    leaf total-update-message-count {
      xr:xr-xml-map "bgp:TotalUpdateMessageCount";
      type uint32;
      description "Total update messages count";
    }
    leaf update-malformed-message-count {
      xr:xr-xml-map "bgp:UpdateMalformedMessageCount";
      type uint32;
      description "Malformed messages count";
    }
    leaf last-update-malformed-age {
      xr:xr-xml-map "bgp:LastUpdateMalformedAge";
      type uint32;
      units "second";
      description
        "Time since last malformed message received event
        (in seconds)";
    }
    leaf update-memory-allocation-fail-count {
      xr:xr-xml-map "bgp:UpdateMemoryAllocationFailCount";
      type uint32;
      description "Memory allocation failure count";
    }
    leaf last-update-memory-allocation-fail-age {
      xr:xr-xml-map "bgp:LastUpdateMemoryAllocationFailAge";
      type uint32;
      units "second";
      description
        "Time since last memory allocation failure event
        (in seconds)";
    }
    leaf update-error-handling-reset-count {
      xr:xr-xml-map "bgp:UpdateErrorHandlingResetCount";
      type uint32;
      description "Error-handling reset count";
    }
    leaf last-error-handling-reset-age {
      xr:xr-xml-map "bgp:LastErrorHandlingResetAge";
      type uint32;
      units "second";
      description
        "Time since last error-handling reset event (in
        seconds)";
    }
    leaf update-error-message-list-count {
      xr:xr-xml-map "bgp:UpdateErrorMessageListCount";
      type uint32;
      description "Malformed messages list count";
    }
    leaf update-attribute-discard-count {
      xr:xr-xml-map "bgp:UpdateAttributeDiscardCount";
      type uint32;
      description "Discarded attribute count";
    }
    leaf establishment-total-update-message-count {
      xr:xr-xml-map "bgp:EstablishmentTotalUpdateMessageCount";
      type uint32;
      description
        "Total update messages count since session
        establishment";
    }
    leaf-list establishment-action-count {
      xr:xr-xml-map "bgp:EstablishmentActionCount";
      type uint32;
      max-elements "7";
      description
        "Number of occurence of each action type since
        session establishment";
    }

    list update-error-message {
      description "List of malformed messages";
      uses BGP-UPDERR-MSG-BAG;
    }
  }

  grouping BGP-GLOBAL-PROCESS-INFO-VRF {
    description "BGP GLOBAL PROCESS INFO VRF";
    leaf vrf-is-active {
      xr:xr-xml-map "bgp:VRFIsActive";
      type boolean;
      description "VRF state";
    }
    leaf route-distinguisher {
      xr:xr-xml-map "bgp:RouteDistinguisher";
      type yang:hex-string;
      description "Route Distinguisher";
    }
    leaf router-id {
      xr:xr-xml-map "bgp:RouterID";
      type inet:ipv4-address;
      description "Router ID for the VRF";
    }
    leaf configured-router-id {
      xr:xr-xml-map "bgp:ConfiguredRouterID";
      type inet:ipv4-address;
      description "Configured router ID";
    }
    leaf is-redistribute-ibgp-to-ig-ps-enabled {
      xr:xr-xml-map "bgp:ISRedistributeIBGPToIGPsEnabled";
      type boolean;
      description "Redistribute iBGP into IGPs enabled";
    }
    leaf is-fast-external-fallover-enabled {
      xr:xr-xml-map "bgp:IsFastExternalFalloverEnabled";
      type boolean;
      description "Fast external fallover enabled";
    }
    leaf is-bestpath-missing-med-is-worst-enabled {
      xr:xr-xml-map "bgp:IsBestpathMissingMEDIsWorstEnabled";
      type boolean;
      description "Bestpath: Treat missing MED as worst";
    }
    leaf is-bestpath-always-compare-med-enabled {
      xr:xr-xml-map "bgp:IsBestpathAlwaysCompareMEDEnabled";
      type boolean;
      description "Bestpath: Always compare MED";
    }
    leaf is-bestpath-ignore-as-path-enabled {
      xr:xr-xml-map "bgp:IsBestpathIgnoreASPathEnabled";
      type boolean;
      description "Bestpath: Ignore AS path";
    }
    leaf is-bestpath-as-path-mpath-relax-enabled {
      xr:xr-xml-map "bgp:IsBestpathASPathMpathRelaxEnabled";
      type boolean;
      description "Bestpath: Relax AS path for mpath";
    }
    leaf is-bestpath-compare-med-from-confed-peer-enabled {
      xr:xr-xml-map "bgp:IsBestpathCompareMEDFromConfedPeerEnabled";
      type boolean;
      description "Bestpath: Compare MED from confed peer";
    }
    leaf is-bestpath-compare-router-id-for-ebgp-peers-enabled {
      xr:xr-xml-map "bgp:IsBestpathCompareRouterIDForEBGPPeersEnabl"+
        "ed";
      type boolean;
      description "Bestpath: Compare routerID for eBGP peers";
    }
    leaf is-bestpath-aigp-ignore-enabled {
      xr:xr-xml-map "bgp:IsBestpathAIGPIgnoreEnabled";
      type boolean;
      description
        "Bestpath: Ignore AIGP unless both paths have
        AIGP attribute";
    }
    leaf is-multipath-as-path-ignore-onwards-enabled {
      xr:xr-xml-map "bgp:IsMultipathASPathIgnoreOnwardsEnabled";
      type boolean;
      description
        "Multipath: Ignore everything AS path onwards for
        mpath";
    }
    leaf is-enforce-first-as-enabled {
      xr:xr-xml-map "bgp:IsEnforceFirstASEnabled";
      type boolean;
      description "Enforce first AS";
    }
    leaf default-local-preference {
      xr:xr-xml-map "bgp:DefaultLocalPreference";
      type uint32;
      description "Default local preference";
    }
    leaf keep-alive-time {
      xr:xr-xml-map "bgp:KeepAliveTime";
      type uint16;
      units "second";
      description "Default keepalive timer (seconds)";
    }
    leaf hold-time {
      xr:xr-xml-map "bgp:HoldTime";
      type uint16;
      units "second";
      description "Default hold timer (seconds)";
    }
    leaf min-acceptable-hold-time {
      xr:xr-xml-map "bgp:MinAcceptableHoldTime";
      type uint16;
      units "second";
      description
        "Default min acceptable hold time from
        neighbor(seconds)";
    }
    leaf is-neighbor-logging {
      xr:xr-xml-map "bgp:IsNeighborLogging";
      type boolean;
      description "Neighbor logging enabled";
    }
    leaf is-default-metric-configured {
      xr:xr-xml-map "bgp:IsDefaultMetricConfigured";
      type boolean;
      description "Default metric configured";
    }
    leaf default-metric {
      xr:xr-xml-map "bgp:DefaultMetric";
      type uint32;
      description "Default metric";
    }
    leaf is-default-originate-configured {
      xr:xr-xml-map "bgp:IsDefaultOriginateConfigured";
      type boolean;
      description "Default route originate configured";
    }
    leaf is-graceful-restart {
      xr:xr-xml-map "bgp:IsGracefulRestart";
      type boolean;
      description "Graceful restart enabled";
    }
    leaf is-nsr {
      xr:xr-xml-map "bgp:IsNsr";
      type boolean;
      description "Non-stop routing enabled";
    }
    leaf restart-time {
      xr:xr-xml-map "bgp:RestartTime";
      type uint32;
      units "second";
      description "Restart time (in seconds)";
    }
    leaf stale-path-time {
      xr:xr-xml-map "bgp:StalePathTime";
      type uint32;
      units "second";
      description "Stale path timeout time (in seconds)";
    }
    leaf rib-purge-timeout {
      xr:xr-xml-map "bgp:RIBPurgeTimeout";
      type uint32;
      units "second";
      description "RIB purge timeout time (in seconds)";
    }
  }

  grouping CLUSTER-ID-BAG {
    description "CLUSTER ID BAG";
    leaf cluster-id-val {
      xr:xr-xml-map "bgp:ClusterIDVal";
      type uint32;
      description "Cluster ID ";
    }
    leaf cluster-id-type {
      xr:xr-xml-map "bgp:ClusterIDType";
      type uint8;
      description "Cluster ID type: number or IPv4 address";
    }
  }

  grouping BGP-GLOBAL-PROCESS-INFO-GBL {
    description "BGP GLOBAL PROCESS INFO GBL";
    leaf in-standalone-mode {
      xr:xr-xml-map "bgp:InStandaloneMode";
      type boolean;
      description "Standalone or Distributed mode";
    }
    leaf local-as {
      xr:xr-xml-map "bgp:LocalAS";
      type uint32;
      description "Local autonomous system number";
    }
    leaf instance-name {
      xr:xr-xml-map "bgp:InstanceName";
      type string;
      description "Name of BGP instance";
    }
    leaf restart-count {
      xr:xr-xml-map "bgp:RestartCount";
      type uint32;
      description "No of times BGP has started";
    }
    leaf update-delay {
      xr:xr-xml-map "bgp:UpdateDelay";
      type uint32;
      units "second";
      description "Update delay timeout time (in seconds)";
    }
    leaf generic-scan-period {
      xr:xr-xml-map "bgp:GenericScanPeriod";
      type uint16;
      units "second";
      description "Period (in seconds) of generic scanner runs";
    }
    leaf confederation-id {
      xr:xr-xml-map "bgp:ConfederationID";
      type uint32;
      description "Confederation ID";
    }
    leaf cluster-id {
      xr:xr-xml-map "bgp:ClusterID";
      type uint32;
      description "Cluster ID";
    }
    leaf configured-cluster-id {
      xr:xr-xml-map "bgp:ConfiguredClusterID";
      type uint32;
      description "Configured cluster ID";
    }
    leaf is-cluster-id-specified-as-ip {
      xr:xr-xml-map "bgp:IsClusterIDSpecifiedAsIP";
      type boolean;
      description "Cluster ID specified as an IP address";
    }
    leaf asn-format {
      xr:xr-xml-map "bgp:ASNFormat";
      type uint32;
      description "BGP AS Number Format";
    }
    leaf srgb-start-configured {
      xr:xr-xml-map "bgp:SRGBStartConfigured";
      type uint32;
      description
        "Configured segment-routing Global Block start
        value";
    }
    leaf srgb-end-configured {
      xr:xr-xml-map "bgp:SRGBEndConfigured";
      type uint32;
      description
        "Configured segment-routing Global Block end
        value";
    }
    leaf srgb-start {
      xr:xr-xml-map "bgp:SRGBStart";
      type uint32;
      description "In use segment-routing Global Block start value";
    }
    leaf srgb-end {
      xr:xr-xml-map "bgp:SRGBEnd";
      type uint32;
      description "In use Segment-routing Global Block end value";
    }
    leaf graceful-maintenance {
      xr:xr-xml-map "bgp:GracefulMaintenance";
      type boolean;
      description "Graceful Maintenance";
    }
    leaf graceful-maint-all-nbrs {
      xr:xr-xml-map "bgp:GracefulMaintAllNbrs";
      type boolean;
      description
        "Graceful Maintenance also for neighbors without
        GM configuration";
    }
    leaf graceful-maint-retain-routes {
      xr:xr-xml-map "bgp:GracefulMaintRetainRoutes";
      type boolean;
      description
        "Retaining routes in RIB when BGP process stops
        while in Graceful Maintenance";
    }
    leaf process-rlimit {
      xr:xr-xml-map "bgp:ProcessRlimit";
      type uint64;
      description "Platform RLIMIT max for the process";
    }
    leaf bmp-maximum-buffer-size {
      xr:xr-xml-map "bgp:BMPMaximumBufferSize";
      type uint64;
      description
        "Maximum limit user can configure for
        max-buffer-size command under bmp-server";
    }
    leaf bmp-default-buffer-size {
      xr:xr-xml-map "bgp:BMPDefaultBufferSize";
      type uint64;
      description
        "Default value for BMP buffer limit when a value
        is not configured";
    }

    list cluster-id-entry {
      description "All configured Cluster IDs";
      uses CLUSTER-ID-BAG;
    }
  }

  grouping BGP-GLOBAL-PROCESS-INFO-BAG {
    description
      "BGP process information common to all BGP
      processes";

    container global {
      description "Global information";
      uses BGP-GLOBAL-PROCESS-INFO-GBL;
    }

    container vrf {
      description "VRF information";
      uses BGP-GLOBAL-PROCESS-INFO-VRF;
    }
    leaf vrf-name {
      xr:xr-xml-map "bgp:VRFName";
      type string;
      description "Name of the VRF";
    }
    leaf vrfid {
      xr:xr-xml-map "bgp:VRFID";
      type uint32;
      description "VRF ID";
    }
  }

  grouping BGP-POSTIT-INFO {
    description "BGP POSTIT INFO";

    container postit-notification {
      description "Postit notification";
      uses BGP-NOTFNTYPE;
    }
    leaf postit-type {
      xr:xr-xml-map "bgp:PostitType";
      type uint32;
      description "Postit Type";
    }
    leaf postit-subtype {
      xr:xr-xml-map "bgp:PostitSubtype";
      type uint32;
      description "Postit Subtype";
    }
    leaf postit-flags {
      xr:xr-xml-map "bgp:PostitFlags";
      type uint8;
      description "Postit Flags";
    }
    leaf postit-af-name {
      xr:xr-xml-map "bgp:PostitAFName";
      type Bgp-afi;
      description "Postit Afi";
    }
    leaf postit-ts {
      xr:xr-xml-map "bgp:PostitTS";
      type uint64;
      description "Postit TS";
    }
    leaf postit-direction {
      xr:xr-xml-map "bgp:PostitDirection";
      type uint8;
      description "Postit Direction";
    }
    leaf postit-id {
      xr:xr-xml-map "bgp:PostitID";
      type uint32;
      description "Postit ID";
    }
    leaf peer-id {
      xr:xr-xml-map "bgp:PeerID";
      type uint32;
      description "Peer ID";
    }
    leaf postit-policy {
      xr:xr-xml-map "bgp:PostitPolicy";
      type string;
      description "Policy";
    }
    leaf postit-reset {
      xr:xr-xml-map "bgp:PostitReset";
      type Bgp-reset-reason-index;
      description "Reset";
    }
  }

  grouping BGP-NEIGHBOR-NSR-BAG {
    description "BGP neighbor nsr bag";

    container neighbors-address {
      description "Neighbor Addr";
      uses BGP-ADDRTYPE;
    }
    leaf vrf-name {
      xr:xr-xml-map "bgp:VRFName";
      type string;
      description "VRF Name";
    }
    leaf connect-state {
      xr:xr-xml-map "bgp:ConnectState";
      type uint32;
      description "State";
    }
    leaf start-time {
      xr:xr-xml-map "bgp:StartTime";
      type uint32;
      description "StartTime";
    }
    leaf nsr-state {
      xr:xr-xml-map "bgp:NSRState";
      type Bgp-sync-nbr-nsr-state;
      description "NSR state";
    }

    list neighbor-af {
      min-elements "23";
      max-elements "23";
      description "Neighbor Afi";
      leaf entry {
        type boolean;
        description "Array entry.";
      }
    }

    list postit-info {
      description "Postit Info";
      uses BGP-POSTIT-INFO;
    }
  }

  grouping BGP-UPDFILTER-VRF-BAG {
    description "BGP Update filtering VRF information";

    container last-update-filtered-timestamp {
      description
        "Last Filtered messages received time: time
        elapsed since 00:00:00 UTC, January 1, 1970";
      uses BGP-TIMESPEC;
    }
    leaf update-vrf-name {
      xr:xr-xml-map "bgp:UpdateVRFName";
      type string;
      description "VRF Name";
    }
    leaf update-filtered-message-count {
      xr:xr-xml-map "bgp:UpdateFilteredMessageCount";
      type uint32;
      description "Filtered messages count";
    }
    leaf update-filtered-neighbor-count {
      xr:xr-xml-map "bgp:UpdateFilteredNeighborCount";
      type uint32;
      description
        "Count of neighbors that received filtered
        messages";
    }
    leaf last-update-filtered-age {
      xr:xr-xml-map "bgp:LastUpdateFilteredAge";
      type uint32;
      units "second";
      description
        "Time since last filtered messages received event
        (in seconds)";
    }
  }

  grouping BGP-VRF-INFO-BAG {
    description "BGP VRF information bag";
    leaf route-distinguisher {
      xr:xr-xml-map "bgp:RouteDistinguisher";
      type xr:Route-dist;
      description "Route Distinguisher";
    }
  }

  grouping BGP-PFXLST {
    description "Prefix list entry";

    list bgp-pfxlst {
      description "bgp pfxlst";

      container bgp-prefix {
        description "BGP prefix";
        uses BGP-PREFIXTYPE;
      }
      leaf sequence-number {
        type uint32;
        description "Sequence number";
      }
      leaf is-prefix-grant {
        type boolean;
        description "TRUE = permit, FALSE = deny";
      }
      leaf min-prefix-length {
        type uint8;
        description "Minimum prefix length";
      }
      leaf max-prefix-length {
        type uint8;
        description "Maximum prefix length";
      }
    }
  }

  grouping BGP-RCV-PFXLST-BAG {
    description "Received prefix filter";

    container neighbor-address-xr {
      description "Neighbor Address";
      uses BGP-ADDRTYPE;
    }

    container prefix-list-info {
      description "Prefix list";
      uses BGP-PFXLST;
    }
    leaf af-name {
      xr:xr-xml-map "bgp:AFName";
      type Bgp-afi;
      description "Address family identfier";
    }
  }

  grouping BGP-UPDGEN-AF-BAG {
    description "BGP Update generation address-family information";

    container update-statistics {
      description "Upate statistics";
      uses BGP-UPDGEN-STATS-BAG;
    }
    leaf update-group-af-name {
      xr:xr-xml-map "bgp:UpdateGroupAFName";
      type Bgp-afi;
      description "Address family identifier";
    }
    leaf update-main-table-version {
      xr:xr-xml-map "bgp:UpdateMainTableVersion";
      type uint32;
      description "Main table version";
    }
    leaf update-rib-version {
      xr:xr-xml-map "bgp:UpdateRIBVersion";
      type uint32;
      description "RIB version";
    }
    leaf update-min-neighbor-version {
      xr:xr-xml-map "bgp:UpdateMinNeighborVersion";
      type uint32;
      description "Minimum Neighbor version";
    }
    leaf current-update-limit-af {
      xr:xr-xml-map "bgp:CurrentUpdateLimitAF";
      type uint32;
      description "Current AF update limit";
    }
    leaf configured-update-limit-af {
      xr:xr-xml-map "bgp:ConfiguredUpdateLimitAF";
      type uint32;
      description "Configured AF update limit";
    }
    leaf current-update-limit-subgrp-ebgp {
      xr:xr-xml-map "bgp:CurrentUpdateLimitSubgrpEBGP";
      type uint32;
      description "Current EBGP sub-group update limit";
    }
    leaf configured-update-limit-subgrp-ebgp {
      xr:xr-xml-map "bgp:ConfiguredUpdateLimitSubgrpEBGP";
      type uint32;
      description "Configured EBGP sub-group update limit";
    }
    leaf current-update-limit-sub-group-ibgp {
      xr:xr-xml-map "bgp:CurrentUpdateLimitSubGroupIBGP";
      type uint32;
      description "Current IBGP sub-group update limit";
    }
    leaf configured-update-limit-sub-group-ibgp {
      xr:xr-xml-map "bgp:ConfiguredUpdateLimitSubGroupIBGP";
      type uint32;
      description "Configured IBGP sub-group update limit";
    }
    leaf update-out-queue-messages {
      xr:xr-xml-map "bgp:UpdateOutQueueMessages";
      type uint32;
      description "OutQueue messsages";
    }
    leaf update-out-queue-size {
      xr:xr-xml-map "bgp:UpdateOutQueueSize";
      type uint32;
      description "OutQueue size";
    }
    leaf update-throttled {
      xr:xr-xml-map "bgp:UpdateThrottled";
      type boolean;
      description "Is Update throttled";
    }
    leaf update-update-group-count {
      xr:xr-xml-map "bgp:UpdateUpdateGroupCount";
      type uint32;
      description "Update-group count";
    }
    leaf update-sub-group-count {
      xr:xr-xml-map "bgp:UpdateSubGroupCount";
      type uint32;
      description "Sub-group count";
    }
    leaf sub-group-throttled-count {
      xr:xr-xml-map "bgp:SubGroupThrottledCount";
      type uint32;
      description "Throttled sub-group count";
    }
    leaf refresh-sub-group-count {
      xr:xr-xml-map "bgp:RefreshSubGroupCount";
      type uint32;
      description "Refresh sub-group count";
    }
    leaf refresh-sub-group-throttled-count {
      xr:xr-xml-map "bgp:RefreshSubGroupThrottledCount";
      type uint32;
      description "Throttled refresh sub-group count";
    }
    leaf filter-group-count {
      xr:xr-xml-map "bgp:FilterGroupCount";
      type uint32;
      description "Filter-group count";
    }
    leaf neighbor-count {
      xr:xr-xml-map "bgp:NeighborCount";
      type uint32;
      description "Neighbor count";
    }
    leaf update-table-vrf-name {
      xr:xr-xml-map "bgp:UpdateTableVRFName";
      type string;
      description "VRF Name";
    }
    leaf update-vrfaf-name {
      xr:xr-xml-map "bgp:UpdateVRFAFName";
      type uint32;
      description "Address family identifier";
    }
    leaf update-vrf-rd-version {
      xr:xr-xml-map "bgp:UpdateVRF_RDVersion";
      type uint32;
      description "RD Version";
    }
    leaf update-vrf-table-rib-version {
      xr:xr-xml-map "bgp:UpdateVRFTableRIBVersion";
      type uint32;
      description "VRF Table RIB version";
    }
    leaf table-update-group-count {
      xr:xr-xml-map "bgp:TableUpdateGroupCount";
      type uint32;
      description "VRF Table update-group count";
    }
    leaf update-table-sub-group-count {
      xr:xr-xml-map "bgp:UpdateTableSubGroupCount";
      type uint32;
      description "VRF Table sub-group count";
    }
    leaf table-sub-group-throttled-count {
      xr:xr-xml-map "bgp:TableSubGroupThrottledCount";
      type uint32;
      description "VRF Table throttled sub-group count";
    }
    leaf table-refresh-sub-group-count {
      xr:xr-xml-map "bgp:TableRefreshSubGroupCount";
      type uint32;
      description "VRF Table refresh sub-group count";
    }
    leaf table-refresh-sub-group-throttled-count {
      xr:xr-xml-map "bgp:TableRefreshSubGroupThrottledCount";
      type uint32;
      description "VRF Table throttled refresh sub-group count";
    }
    leaf update-table-filter-group-count {
      xr:xr-xml-map "bgp:UpdateTableFilterGroupCount";
      type uint32;
      description "VRF Table filter-group count";
    }
    leaf table-neighbor-count {
      xr:xr-xml-map "bgp:TableNeighborCount";
      type uint32;
      description "VRF Table neighbor count";
    }
  }

  grouping BGP-UPDGEN-NBR-BAG {
    description "BGP Update generation Neighbor information";

    container update-neighbor-address {
      description "Neighbor address";
      uses BGP-ADDRTYPE;
    }

    container last-sub-group-add-timestamp {
      description "Last added time";
      uses BGP-TIMESPEC;
    }

    container last-sub-group-remove-timestamp {
      description "Last removed time";
      uses BGP-TIMESPEC;
    }

    container last-filter-group-add-timestamp {
      description "Last added time";
      uses BGP-TIMESPEC;
    }

    container last-filter-group-remove-timestamp {
      description "Last removed time";
      uses BGP-TIMESPEC;
    }

    container first-default-originate-timestamp {
      description "First default-origination time";
      uses BGP-TIMESPEC;
    }

    container last-default-originate-timestamp {
      description "Last default-origination time";
      uses BGP-TIMESPEC;
    }

    container last-update-group-start-timestamp {
      description "Last update-group timer start";
      uses BGP-TIMESPEC;
    }

    container last-update-group-expiry-timestamp {
      description "Last update-group timer expiry";
      uses BGP-TIMESPEC;
    }

    container first-update-queued-timestamp {
      description "First update queued time";
      uses BGP-TIMESPEC;
    }

    container last-update-queued-timestamp {
      description "Last update queued time";
      uses BGP-TIMESPEC;
    }

    container last-refresh-update-queued-timestamp {
      description "Last refresh update queued time";
      uses BGP-TIMESPEC;
    }

    container first-update-write-timestamp {
      description "First update write time";
      uses BGP-TIMESPEC;
    }

    container last-update-write-timestamp {
      description "Last update write time";
      uses BGP-TIMESPEC;
    }

    container last-refresh-update-write-timestamp {
      description "Last refresh update write time";
      uses BGP-TIMESPEC;
    }

    container update-statistics {
      description "Update statistics";
      uses BGP-UPDGEN-STATS-BAG;
    }
    leaf process-id {
      xr:xr-xml-map "bgp:ProcessID";
      type uint32;
      description "ProcessID";
    }
    leaf update-vrf-name {
      xr:xr-xml-map "bgp:UpdateVRFName";
      type string;
      description "VRF Name";
    }
    leaf update-group-af-name {
      xr:xr-xml-map "bgp:UpdateGroupAFName";
      type Bgp-afi;
      description "Address family identifier";
    }
    leaf update-filter-group-index {
      xr:xr-xml-map "bgp:UpdateFilterGroupIndex";
      type uint32;
      description "Filter-group index";
    }
    leaf refresh-filter-group-index {
      xr:xr-xml-map "bgp:RefreshFilterGroupIndex";
      type uint32;
      description "Refresh Filter-group index";
    }
    leaf sub-group-index-xr {
      xr:xr-xml-map "bgp:sub-group-index-xr";
      type uint32;
      description "Sub-group index";
    }
    leaf refresh-sub-group-index {
      xr:xr-xml-map "bgp:RefreshSubGroupIndex";
      type uint32;
      description "Refresh Sub-group index";
    }
    leaf refresh-sub-group-id {
      xr:xr-xml-map "bgp:RefreshSubGroupID";
      type uint32;
      description "Refresh sub-group ID";
    }
    leaf update-group-index-xr {
      xr:xr-xml-map "bgp:update-group-index-xr";
      type uint32;
      description "Update-group index";
    }
    leaf update-main-table-version {
      xr:xr-xml-map "bgp:UpdateMainTableVersion";
      type uint32;
      description "Main table version";
    }
    leaf update-vrf-table-rib-version {
      xr:xr-xml-map "bgp:UpdateVRFTableRIBVersion";
      type uint32;
      description "VRF Table RIB version";
    }
    leaf update-out-queue-messages {
      xr:xr-xml-map "bgp:UpdateOutQueueMessages";
      type uint32;
      description "OutQueue messages";
    }
    leaf update-out-queue-size {
      xr:xr-xml-map "bgp:UpdateOutQueueSize";
      type uint32;
      description "OutQueue size";
    }
    leaf refresh-update-out-queue-messages {
      xr:xr-xml-map "bgp:RefreshUpdateOutQueueMessages";
      type uint32;
      description "Refresh OutQueue messages";
    }
    leaf refresh-update-out-queue-size {
      xr:xr-xml-map "bgp:RefreshUpdateOutQueueSize";
      type uint32;
      description "Refresh OutQueue size";
    }
    leaf update-filter-group-messages {
      xr:xr-xml-map "bgp:UpdateFilterGroupMessages";
      type uint32;
      description "Filter-group messages";
    }
    leaf version {
      xr:xr-xml-map "bgp:Version";
      type uint32;
      description "Version";
    }
    leaf pending-target-version {
      xr:xr-xml-map "bgp:PendingTargetVersion";
      type uint32;
      description "Pending target version";
    }
    leaf next-resume-version {
      xr:xr-xml-map "bgp:NextResumeVersion";
      type uint32;
      description "Resume version";
    }
    leaf ack-version {
      xr:xr-xml-map "bgp:AckVersion";
      type uint32;
      description "Ack version";
    }
    leaf synced-ack-version {
      xr:xr-xml-map "bgp:SyncedAckVersion";
      type uint32;
      description "Synced ack version";
    }
    leaf outstanding-version-count {
      xr:xr-xml-map "bgp:OutstandingVersionCount";
      type uint32;
      description "Outstanding version count";
    }
    leaf update-refresh-version {
      xr:xr-xml-map "bgp:UpdateRefreshVersion";
      type uint32;
      description "Refresh version";
    }
    leaf refresh-requested-target-version {
      xr:xr-xml-map "bgp:RefreshRequestedTargetVersion";
      type uint32;
      description "Requested refresh target version";
    }
    leaf update-refresh-target-version {
      xr:xr-xml-map "bgp:UpdateRefreshTargetVersion";
      type uint32;
      description "Refresh target version";
    }
    leaf refresh-pending-target-version {
      xr:xr-xml-map "bgp:RefreshPendingTargetVersion";
      type uint32;
      description "Pending refresh target version";
    }
    leaf refresh-next-resume-version {
      xr:xr-xml-map "bgp:RefreshNextResumeVersion";
      type uint32;
      description "Refresh resume version";
    }
    leaf refresh-ack-version {
      xr:xr-xml-map "bgp:RefreshAckVersion";
      type uint32;
      description "Refresh Ack version";
    }
    leaf last-default-originate-age {
      xr:xr-xml-map "bgp:LastDefaultOriginateAge";
      type uint32;
      units "second";
      description
        "Time since last default-origination event (in
        seconds)";
    }
    leaf default-originate-state {
      xr:xr-xml-map "bgp:DefaultOriginateState";
      type int32;
      description "Default-origination state";
    }
    leaf default-originate-internal-context {
      xr:xr-xml-map "bgp:DefaultOriginateInternalContext";
      type int32;
      description "Default-origination context";
    }
    leaf is-eor-outstanding {
      xr:xr-xml-map "bgp:IsEOROutstanding";
      type boolean;
      description "Number of EORs outstanding";
    }
    leaf outbound-refresh-count {
      xr:xr-xml-map "bgp:OutboundRefreshCount";
      type uint32;
      description "Refresh Outbound count";
    }
    leaf inbound-refresh-count {
      xr:xr-xml-map "bgp:InboundRefreshCount";
      type uint32;
      description "Refresh Inbound count";
    }
    leaf is-update-group-timer-running {
      xr:xr-xml-map "bgp:IsUpdateGroupTimerRunning";
      type boolean;
      description "Is update-group timer running";
    }
    leaf current-update-group-af-name {
      xr:xr-xml-map "bgp:CurrentUpdateGroupAFName";
      type Bgp-afi;
      description "Current Update-group address-family identifier";
    }
    leaf last-update-group-af-name {
      xr:xr-xml-map "bgp:LastUpdateGroupAFName";
      type Bgp-afi;
      description "Last Update-group address-family identifier";
    }
    leaf last-update-queued-age {
      xr:xr-xml-map "bgp:LastUpdateQueuedAge";
      type uint32;
      units "second";
      description
        "Time since last update queued event (in seconds)";
    }
    leaf last-refresh-update-queued-age {
      xr:xr-xml-map "bgp:LastRefreshUpdateQueuedAge";
      type uint32;
      units "second";
      description
        "Time since last refresh update queued event (in
        seconds)";
    }
    leaf last-update-write-age {
      xr:xr-xml-map "bgp:LastUpdateWriteAge";
      type uint32;
      units "second";
      description "Time since last update write event (in seconds)";
    }
    leaf last-refresh-update-write-age {
      xr:xr-xml-map "bgp:LastRefreshUpdateWriteAge";
      type uint32;
      units "second";
      description
        "Time since last refresh update write event (in
        seconds)";
    }
  }

  grouping BGP-NBR-GSHUT {
    description "BGP NBR GSHUT";
    leaf gshut-exists {
      xr:xr-xml-map "bgp:GshutExists";
      type boolean;
      description "Graceful Maintenance enabled";
    }
    leaf gshut-local-active {
      xr:xr-xml-map "bgp:GshutLocalActive";
      type boolean;
      description "Graceful Maintenance locally activated";
    }
    leaf gshut-active {
      xr:xr-xml-map "bgp:GshutActive";
      type boolean;
      description "Graceful Maintenance activated";
    }
    leaf gshut-locpref-set {
      xr:xr-xml-map "bgp:GshutLocprefSet";
      type boolean;
      description "Graceful Maintenance Local Preference set";
    }
    leaf gshut-locpref {
      xr:xr-xml-map "bgp:GshutLocpref";
      type uint32;
      description "Graceful Maintenance Local Preference";
    }
    leaf gshut-prepends {
      xr:xr-xml-map "bgp:GshutPrepends";
      type uint8;
      description "Graceful Maintenance number of AS prepends";
    }
  }

  grouping BGP-NBR-MSG-STATS-UNIT {
    description "BGP NBR MSG STATS UNIT";

    container last-time-spec {
      description "Last timespec";
      uses BGP-TIMESPEC;
    }
    leaf count {
      xr:xr-xml-map "bgp:Count";
      type uint32;
      description "Count";
    }
  }

  grouping BGP-NBR-MSG-STATS-OP {
    description "BGP NBR MSG STATS OP";

    container tx {
      description "Transmit";
      uses BGP-NBR-MSG-STATS-UNIT;
    }

    container rx {
      description "Receive";
      uses BGP-NBR-MSG-STATS-UNIT;
    }
  }

  grouping BGP-NBR-MSG-STATS {
    description "BGP NBR MSG STATS";

    container open {
      description "Open";
      uses BGP-NBR-MSG-STATS-OP;
    }

    container notification {
      description "Notification";
      uses BGP-NBR-MSG-STATS-OP;
    }

    container update {
      description "Update";
      uses BGP-NBR-MSG-STATS-OP;
    }

    container keepalive {
      description "Keepalive";
      uses BGP-NBR-MSG-STATS-OP;
    }

    container route-refresh {
      description "Route refresh";
      uses BGP-NBR-MSG-STATS-OP;
    }

    container total {
      description "Total";
      uses BGP-NBR-MSG-STATS-OP;
    }
  }

  grouping BGP-PERF-NBR-AF {
    description "BGP PERF NBR AF";
    leaf sub-group-pending-message-count {
      xr:xr-xml-map "bgp:SubGroupPendingMessageCount";
      type uint32;
      description
        "No. of sub-group messages waiting to be sent out
        on this neighbor -- DEPRECATED -- ";
    }
    leaf processed-messages {
      xr:xr-xml-map "bgp:ProcessedMessages";
      type uint32;
      description
        "Number of messages processed from the neighbor's
        write queue";
    }
    leaf sent-messages {
      xr:xr-xml-map "bgp:SentMessages";
      type uint32;
      description
        "Number of messages sent from the neighbor's
        write queue";
    }
    leaf split-horizon-update-transmit {
      xr:xr-xml-map "bgp:SplitHorizonUpdateTransmit";
      type uint32;
      description
        "No. of update messages with split-horizon flag
        that were sent out";
    }
    leaf split-horizon-update-blocked {
      xr:xr-xml-map "bgp:SplitHorizonUpdateBlocked";
      type uint32;
      description
        "No. of update messages with split-horizon flag
        that were blocked";
    }
    leaf split-horizon-withdraw-transmit {
      xr:xr-xml-map "bgp:SplitHorizonWithdrawTransmit";
      type uint32;
      description
        "No. of withdraw messages with split-horizon flag
        that were sent out";
    }
    leaf split-horizon-withdraw-blocked {
      xr:xr-xml-map "bgp:SplitHorizonWithdrawBlocked";
      type uint32;
      description
        "No. of withdraw messages with split-horizon flag
        that were blocked";
    }
  }

  grouping BGP-NBR-AF {
    description "BGP neighbor address family specific information";

    container neighbor-af-performance-statistics {
      description "Neighbor AF statistics";
      uses BGP-PERF-NBR-AF;
    }
    leaf af-name {
      xr:xr-xml-map "bgp:AFName";
      type Bgp-afi;
      description "Address family identifier";
    }
    leaf is-neighbor-route-reflector-client {
      xr:xr-xml-map "bgp:IsNeighborRouteReflectorClient";
      type boolean;
      description "Nbr is a route reflector client";
    }
    leaf is-legacy-pe-rt {
      xr:xr-xml-map "bgp:IsLegacyPE_RT";
      type boolean;
      description
        "Nbr accepts route from legacy PE for
        RT-Constraint AF ";
    }
    leaf is-neighbor-af-capable {
      xr:xr-xml-map "bgp:IsNeighborAFCapable";
      type boolean;
      description
        "Address family capability received from neighbor";
    }
    leaf is-soft-reconfiguration-inbound-allowed {
      xr:xr-xml-map "bgp:IsSoftReconfigurationInboundAllowed";
      type boolean;
      description "Inbound soft reconfiguration allowed";
    }
    leaf is-use-soft-reconfiguration-always-on {
      xr:xr-xml-map "bgp:IsUseSoftReconfigurationAlwaysOn";
      type boolean;
      description "Soft reconf overrides route refresh";
    }
    leaf remove-private-as-from-updates {
      xr:xr-xml-map "bgp:RemovePrivateASFromUpdates";
      type boolean;
      description
        "Private AS numbers removed from updates to this
        nbr";
    }
    leaf remove-private-as-entire-aspath-from-updates {
      xr:xr-xml-map "bgp:RemovePrivateASEntireAspathFromUpdates";
      type boolean;
      description
        "Private AS numbers removed from updates to
        thisnbr only if the aspath hasonly private ASes";
    }
    leaf remove-private-as-from-inbound-updates {
      xr:xr-xml-map "bgp:RemovePrivateASFromInboundUpdates";
      type boolean;
      description
        "Private AS numbers removed from updates from
        this nbr";
    }
    leaf remove-private-as-entire-aspath-from-inbound-updates {
      xr:xr-xml-map "bgp:RemovePrivateASEntireAspathFromInboundUpda"+
        "tes";
      type boolean;
      description
        "Private AS numbers removed from updates from
        this nbr only if the aspath has only private
        ASes";
    }
    leaf flowspec-validation-d-isable {
      xr:xr-xml-map "bgp:FlowspecValidationDIsable";
      type boolean;
      description "Flowspec Validation Disabled";
    }
    leaf flowspec-redirect-validation-d-isable {
      xr:xr-xml-map "bgp:FlowspecRedirectValidationDIsable";
      type boolean;
      description "Flowspec Redirect Validation Disabled";
    }
    leaf orr-group-name {
      xr:xr-xml-map "bgp:OrrGroupName";
      type string;
      description "ORR Group Name";
    }
    leaf orr-group-index {
      xr:xr-xml-map "bgp:OrrGroupIndex";
      type uint32;
      description "ORR Group Index";
    }
    leaf is-orr-root-address-configured {
      xr:xr-xml-map "bgp:IsOrrRootAddressConfigured";
      type boolean;
      description
        "ORR Root address configuredfor the neighbor
        connection";
    }
    leaf advertise-afi {
      xr:xr-xml-map "bgp:AdvertiseAFI";
      type boolean;
      description "Encode in Advertise AFI";
    }
    leaf advertise-afi-reorg {
      xr:xr-xml-map "bgp:AdvertiseAFIReorg";
      type boolean;
      description "Encode in Advertise AFI";
    }
    leaf advertise-afi-disable {
      xr:xr-xml-map "bgp:AdvertiseAFIDisable";
      type boolean;
      description "Encode in Advertise AFI";
    }
    leaf encapsulation-type {
      xr:xr-xml-map "bgp:EncapsulationType";
      type uint32;
      description "Encapsulation type";
    }
    leaf advertise-rt-type {
      xr:xr-xml-map "bgp:AdvertiseRTType";
      type uint8;
      description "Advertise RT type";
    }
    leaf advertise-afi-def-vrf-imp-disable {
      xr:xr-xml-map "bgp:AdvertiseAFIDefVrfImpDisable";
      type boolean;
      description "Advertise of default VRF import disable";
    }
    leaf advertise-evp-nv4afi-def-vrf-imp-disable {
      xr:xr-xml-map "bgp:AdvertiseEVPNv4AFIDefVrfImpDisable";
      type boolean;
      description "Advertise of v4 default VRF import disable";
    }
    leaf advertise-evp-nv6afi-def-vrf-imp-disable {
      xr:xr-xml-map "bgp:AdvertiseEVPNv6AFIDefVrfImpDisable";
      type boolean;
      description "Advertise of v6 default VRF import disable";
    }
    leaf advertise-afi-eo-r-ready {
      xr:xr-xml-map "bgp:AdvertiseAFIEoRReady";
      type boolean;
      description "EoR Can be sent for Advertise AFI";
    }
    leaf always-use-next-hop-local {
      xr:xr-xml-map "bgp:AlwaysUseNextHopLocal";
      type boolean;
      description "Local router always used for next-hop";
    }
    leaf sent-community-to-neighbor {
      xr:xr-xml-map "bgp:SentCommunityToNeighbor";
      type boolean;
      description "Community attribute sent to neighbor";
    }
    leaf sent-gshut-community-to-neighbor {
      xr:xr-xml-map "bgp:SentGshutCommunityToNeighbor";
      type boolean;
      description "GSHUT Community attribute sent to neighbor";
    }
    leaf sent-extended-community-to-neighbor {
      xr:xr-xml-map "bgp:SentExtendedCommunityToNeighbor";
      type boolean;
      description "Extended community attribute sent to neighbor";
    }
    leaf neighbor-default-originate {
      xr:xr-xml-map "bgp:NeighborDefaultOriginate";
      type boolean;
      description "Neighbor originates default";
    }
    leaf is-orf-sent {
      xr:xr-xml-map "bgp:IsORFSent";
      type boolean;
      description "Outbound route filter sent to neighbor";
    }
    leaf is-update-deferred {
      xr:xr-xml-map "bgp:IsUpdateDeferred";
      type boolean;
      description
        "Update deferred until ORF/route refresh received";
    }
    leaf is-orf-send-scheduled {
      xr:xr-xml-map "bgp:IsORFSendScheduled";
      type boolean;
      description "Scheduled to send prefix based ORF";
    }
    leaf update-group-number {
      xr:xr-xml-map "bgp:UpdateGroupNumber";
      type uint32;
      description "Update group index";
    }
    leaf filter-group-index {
      xr:xr-xml-map "bgp:FilterGroupIndex";
      type uint32;
      description "Filter group index";
    }
    leaf is-update-throttled {
      xr:xr-xml-map "bgp:IsUpdateThrottled";
      type boolean;
      description "Updates Throttled becausewrite limit is reached";
    }
    leaf is-update-leaving {
      xr:xr-xml-map "bgp:IsUpdateLeaving";
      type boolean;
      description "Nbr leaving update-groupto another";
    }
    leaf vpn-update-gen-enabled {
      xr:xr-xml-map "bgp:VPNUpdateGenEnabled";
      type boolean;
      description "RT Nbr enabled for updategento another";
    }
    leaf vpn-update-gen-trigger-enabled {
      xr:xr-xml-map "bgp:VPNUpdateGenTriggerEnabled";
      type boolean;
      description "RT Nbr enabled for updategento another";
    }
    leaf is-addpath-send-operational {
      xr:xr-xml-map "bgp:IsAddpathSendOperational";
      type boolean;
      description "Addpath is operational on send-side";
    }
    leaf is-addpath-receive-operational {
      xr:xr-xml-map "bgp:IsAddpathReceiveOperational";
      type boolean;
      description "Addpath is operational on receive-side";
    }
    leaf neighbor-version {
      xr:xr-xml-map "bgp:NeighborVersion";
      type uint32;
      description "Neighbor version";
    }
    leaf weight {
      xr:xr-xml-map "bgp:Weight";
      type uint32;
      description "Weight for this AF";
    }
    leaf max-prefix-limit {
      xr:xr-xml-map "bgp:MaxPrefixLimit";
      type uint32;
      description "Max limit for # of prefixes";
    }
    leaf use-max-prefix-warning-only {
      xr:xr-xml-map "bgp:UseMaxPrefixWarningOnly";
      type boolean;
      description "Warning only when maximum prefix limit reached";
    }
    leaf max-prefix-discard-extra-paths {
      xr:xr-xml-map "bgp:MaxPrefixDiscardExtraPaths";
      type boolean;
      description "Discard extra paths when prefix limit reached";
    }
    leaf max-prefix-exceed-discard-paths {
      xr:xr-xml-map "bgp:MaxPrefixExceedDiscardPaths";
      type boolean;
      description
        "Did we discard extra paths when prefix limit
        reached";
    }
    leaf max-prefix-threshold-percent {
      xr:xr-xml-map "bgp:MaxPrefixThresholdPercent";
      type uint8;
      units "percentage";
      description
        "Percentage of maximum no. of prefixes at which
        to generate warning";
    }
    leaf max-prefix-restart-time {
      xr:xr-xml-map "bgp:MaxPrefixRestartTime";
      type uint16;
      units "minute";
      description
        "Time interval (in minutes) after which peering
        session will be reestablished";
    }
    leaf prefixes-accepted {
      xr:xr-xml-map "bgp:PrefixesAccepted";
      type uint32;
      description "No. of prefixes accepted";
    }
    leaf prefixes-synced {
      xr:xr-xml-map "bgp:PrefixesSynced";
      type uint32;
      description "Number of prefixes synced to standby";
    }
    leaf prefixes-withdrawn-not-found {
      xr:xr-xml-map "bgp:PrefixesWithdrawnNotFound";
      type uint32;
      description "No. of prefixes withdrawn but not found";
    }
    leaf prefixes-denied {
      xr:xr-xml-map "bgp:PrefixesDenied";
      type uint32;
      description "No. of prefixes denied";
    }
    leaf prefixes-denied-no-policy {
      xr:xr-xml-map "bgp:PrefixesDeniedNoPolicy";
      type uint32;
      description
        "No. of prefixes denied because there was no
        inbound policy";
    }
    leaf prefixes-denied-rt-permit {
      xr:xr-xml-map "bgp:PrefixesDeniedRTPermit";
      type uint32;
      description
        "No. of prefixes denied because RT extended
        community is not imported";
    }
    leaf prefixes-denied-orf-policy {
      xr:xr-xml-map "bgp:PrefixesDeniedORFPolicy";
      type uint32;
      description
        "No. of prefixes denied by prefix based ORF
        policy";
    }
    leaf prefixes-denied-policy {
      xr:xr-xml-map "bgp:PrefixesDeniedPolicy";
      type uint32;
      description "No. of prefixes denied by inbound policy";
    }
    leaf number-of-bestpaths {
      xr:xr-xml-map "bgp:NumberOfBestpaths";
      type uint32;
      description "No. of bestpaths from this neighbor";
    }
    leaf number-of-best-externalpaths {
      xr:xr-xml-map "bgp:NumberOfBestExternalpaths";
      type uint32;
      description "No. of best-external paths from this neighbor";
    }
    leaf prefixes-advertised {
      xr:xr-xml-map "bgp:PrefixesAdvertised";
      type uint32;
      description "No. of prefixes advertised";
    }
    leaf prefixes-be-advertised {
      xr:xr-xml-map "bgp:PrefixesBEAdvertised";
      type uint32;
      description "No BE prefixes advertised";
    }
    leaf prefixes-suppressed {
      xr:xr-xml-map "bgp:PrefixesSuppressed";
      type uint32;
      description "No. of prefixes suppressed";
    }
    leaf prefixes-withdrawn {
      xr:xr-xml-map "bgp:PrefixesWithdrawn";
      type uint32;
      description "No. of prefixes withdrawn";
    }
    leaf is-peer-orf-capable {
      xr:xr-xml-map "bgp:IsPeerORFCapable";
      type boolean;
      description "Peer has outbound route filter capability";
    }
    leaf is-advertised-orf-send {
      xr:xr-xml-map "bgp:IsAdvertisedORFSend";
      type boolean;
      description
        "Prefix based ORF send mode capability advertised";
    }
    leaf is-received-orf-send-capable {
      xr:xr-xml-map "bgp:IsReceivedORFSendCapable";
      type boolean;
      description "Prefix based ORF send mode capability received";
    }
    leaf is-advertised-orf-receive {
      xr:xr-xml-map "bgp:IsAdvertisedORFReceive";
      type boolean;
      description
        "Prefix based ORF receive mode capability
        advertised";
    }
    leaf is-received-orf-receive-capable {
      xr:xr-xml-map "bgp:IsReceivedORFReceiveCapable";
      type boolean;
      description
        "Prefix based ORF receive mode capability
        received";
    }
    leaf is-advertised-graceful-restart {
      xr:xr-xml-map "bgp:IsAdvertisedGracefulRestart";
      type boolean;
      description "Graceful Restart Capability advertised";
    }
    leaf is-graceful-restart-state-flag {
      xr:xr-xml-map "bgp:IsGracefulRestartStateFlag";
      type boolean;
      description "Restart state flag enabled";
    }
    leaf is-received-graceful-restart-capable {
      xr:xr-xml-map "bgp:IsReceivedGracefulRestartCapable";
      type boolean;
      description "Graceful Restart Capability received";
    }
    leaf is-add-path-send-capability-advertised {
      xr:xr-xml-map "bgp:IsAddPathSendCapabilityAdvertised";
      type boolean;
      description "Addpath Send capability advertised";
    }
    leaf is-add-path-send-capability-received {
      xr:xr-xml-map "bgp:IsAddPathSendCapabilityReceived";
      type boolean;
      description "Addpath Send capability received";
    }
    leaf is-add-path-receive-capability-advertised {
      xr:xr-xml-map "bgp:IsAddPathReceiveCapabilityAdvertised";
      type boolean;
      description "Addpath Receive capability advertised";
    }
    leaf is-add-path-receive-capability-received {
      xr:xr-xml-map "bgp:IsAddPathReceiveCapabilityReceived";
      type boolean;
      description "Addpath Receive capability received";
    }
    leaf restart-time {
      xr:xr-xml-map "bgp:RestartTime";
      type uint32;
      units "second";
      description "Restart time advertised (seconds)";
    }
    leaf local-restart-time {
      xr:xr-xml-map "bgp:LocalRestartTime";
      type uint32;
      units "second";
      description "Local Restart time (seconds)";
    }
    leaf stale-path-timeout {
      xr:xr-xml-map "bgp:StalePathTimeout";
      type uint32;
      units "second";
      description "Stale path timeout time (in seconds)";
    }
    leaf rib-purge-timeout-value {
      xr:xr-xml-map "bgp:RIBPurgeTimeoutValue";
      type uint32;
      units "second";
      description "RIB purge timeout time (in seconds)";
    }
    leaf neighbor-preserved-forwarding-state {
      xr:xr-xml-map "bgp:NeighborPreservedForwardingState";
      type boolean;
      description "Neighbor preserved forwarding state";
    }
    leaf long-lived-graceful-restart-stale-time-configured {
      xr:xr-xml-map "bgp:LongLivedGracefulRestartStaleTimeConfigure"+
        "d";
      type boolean;
      description
        "Long-lived graceful-restart stale time is
        configured";
    }
    leaf long-lived-graceful-restart-stale-time-sent {
      xr:xr-xml-map "bgp:LongLivedGracefulRestartStaleTimeSent";
      type uint32;
      units "second";
      description
        "Stale time sent in long-lived graceful-restart
        capability (seconds)";
    }
    leaf long-lived-graceful-restart-stale-time-accept {
      xr:xr-xml-map "bgp:LongLivedGracefulRestartStaleTimeAccept";
      type uint32;
      units "second";
      description
        "Maximum long-lived graceful-restart stale time
        acceptable from the neighbor (seconds)";
    }
    leaf long-lived-graceful-restart-capability-received {
      xr:xr-xml-map "bgp:LongLivedGracefulRestartCapabilityReceived";
      type boolean;
      description
        "Long-lived graceful-restart capability received
        from the neighbor";
    }
    leaf long-lived-graceful-restart-stale-time-received {
      xr:xr-xml-map "bgp:LongLivedGracefulRestartStaleTimeReceived";
      type uint32;
      units "second";
      description
        "Long-lived graceful-restart stale time received
        from the neighbor (seconds)";
    }
    leaf neighbor-preserved-long-lived-forwarding-state {
      xr:xr-xml-map "bgp:NeighborPreservedLongLivedForwardingState";
      type boolean;
      description "Neighbor preserved long-lived forwarding state";
    }
    leaf neighbor-long-lived-graceful-restart-capable {
      xr:xr-xml-map "bgp:NeighborLongLivedGracefulRestartCapable";
      type boolean;
      description
        "Treat neighbor as long-lived graceful-restart
        capable";
    }
    leaf neighbor-long-lived-graceful-restart-time-remaining {
      xr:xr-xml-map "bgp:NeighborLongLivedGracefulRestartTimeRemain"+
        "ing";
      type uint32;
      description "Remaining long-lived graceful-restart time";
    }
    leaf route-refreshes-received {
      xr:xr-xml-map "bgp:RouteRefreshesReceived";
      type uint32;
      description "Number of route refresh requests received";
    }
    leaf route-refreshes-sent {
      xr:xr-xml-map "bgp:RouteRefreshesSent";
      type uint32;
      description "Number of route refresh requests sent";
    }
    leaf refresh-target-version {
      xr:xr-xml-map "bgp:RefreshTargetVersion";
      type uint32;
      description "Target version for refresh update generation";
    }
    leaf refresh-version {
      xr:xr-xml-map "bgp:RefreshVersion";
      type uint32;
      description
        "Version till which refresh updates have been
        generated";
    }
    leaf refresh-acked-version {
      xr:xr-xml-map "bgp:RefreshAckedVersion";
      type uint32;
      description
        "Version acked by the peer for refresh updates
        sent";
    }
    leaf is-prefix-orf-present {
      xr:xr-xml-map "bgp:IsPrefixORFPresent";
      type boolean;
      description "Outbound route filter prefix ORF present";
    }
    leaf orf-entries-received {
      xr:xr-xml-map "bgp:ORFEntriesReceived";
      type uint32;
      description
        "Number of outbound route filter entries received";
    }
    leaf is-default-originate-sent {
      xr:xr-xml-map "bgp:IsDefaultOriginateSent";
      type boolean;
      description "Default origination update sent";
    }
    leaf route-policy-prefix-orf {
      xr:xr-xml-map "bgp:RoutePolicyPrefixORF";
      type string;
      description "Prefix based ORF for incoming updates";
    }
    leaf route-policy-in {
      xr:xr-xml-map "bgp:RoutePolicyIn";
      type string;
      description "Incoming route policy name";
    }
    leaf route-policy-out {
      xr:xr-xml-map "bgp:RoutePolicyOut";
      type string;
      description "Outgoing route policy name";
    }
    leaf route-policy-default-originate {
      xr:xr-xml-map "bgp:RoutePolicyDefaultOriginate";
      type string;
      description "Default-originate route policy name";
    }
    leaf is-neighbor-ebgp-without-inbound-policy {
      xr:xr-xml-map "bgp:IsNeighborEBGPWithoutInboundPolicy";
      type boolean;
      description "eBGP neighbor with no configured inbound policy";
    }
    leaf is-neighbor-ebgp-without-outbound-policy {
      xr:xr-xml-map "bgp:IsNeighborEBGPWithoutOutboundPolicy";
      type boolean;
      description
        "eBGP neighbor with no configured outbound policy";
    }
    leaf is-as-override-set {
      xr:xr-xml-map "bgp:IsAsOverrideSet";
      type boolean;
      description "As override set ";
    }
    leaf is-allow-as-in-set {
      xr:xr-xml-map "bgp:IsAllowAsInSet";
      type boolean;
      description "Allowas-in set ";
    }
    leaf allow-as-in-count {
      xr:xr-xml-map "bgp:AllowAsInCount";
      type uint32;
      description "Allowas-in count config";
    }
    leaf address-family-long-lived-time {
      xr:xr-xml-map "bgp:AddressFamilyLongLivedTime";
      type uint32;
      description "AF specific Long-lived-time config";
    }
    leaf eo-r-received-in-read-only {
      xr:xr-xml-map "bgp:EoRReceivedInReadOnly";
      type boolean;
      description "An EoR was received while in read-only mode";
    }
    leaf acked-version {
      xr:xr-xml-map "bgp:AckedVersion";
      type uint32;
      description "Version mapped from acked seqNo";
    }
    leaf synced-acked-version {
      xr:xr-xml-map "bgp:SyncedAckedVersion";
      type uint32;
      description
        "Version mapped from acked seqNo that was synced
        last";
    }
    leaf outstanding-version {
      xr:xr-xml-map "bgp:OutstandingVersion";
      type uint32;
      description
        "Version mapped from acked seqNo that was synced
        last";
    }
    leaf outstanding-version-max {
      xr:xr-xml-map "bgp:OutstandingVersionMax";
      type uint32;
      description
        "Version mapped from acked seqNo that was synced
        last";
    }
    leaf is-aigp-set {
      xr:xr-xml-map "bgp:IsAIGPSet";
      type boolean;
      description "AIGP set ";
    }
    leaf is-rt-present {
      xr:xr-xml-map "bgp:IsRTPresent";
      type boolean;
      description "RT attribute list present";
    }
    leaf is-rt-present-standby {
      xr:xr-xml-map "bgp:IsRTPresentStandby";
      type boolean;
      description "RT attribute list present";
    }
    leaf accept-own-enabled {
      xr:xr-xml-map "bgp:AcceptOwnEnabled";
      type boolean;
      description "Accept-Own enabled";
    }
    leaf selective-multipath-eligible {
      xr:xr-xml-map "bgp:SelectiveMultipathEligible";
      type boolean;
      description "Selective multipath eligible";
    }
    leaf afrpki-disable {
      xr:xr-xml-map "bgp:AFRPKIDisable";
      type boolean;
      description "Prefix validation disabled";
    }
    leaf afrpki-use-validity {
      xr:xr-xml-map "bgp:AFRPKIUseValidity";
      type boolean;
      description "Prefix v. use validity";
    }
    leaf afrpki-allow-invalid {
      xr:xr-xml-map "bgp:AFRPKIAllowInvalid";
      type boolean;
      description "Prefix v. allow invalid";
    }
    leaf afrpki-signal-ibgp {
      xr:xr-xml-map "bgp:AFRPKISignalIBGP";
      type boolean;
      description "Prefix v. signal ibgp";
    }
    leaf is-advertise-permanent-network {
      xr:xr-xml-map "bgp:IsAdvertisePermanentNetwork";
      type boolean;
      description "Advertise Permanent Network";
    }
    leaf is-send-mcast-attr {
      xr:xr-xml-map "bgp:IsSendMcastAttr";
      type boolean;
      description "Send Mcast Attr";
    }
    leaf import-stitching {
      xr:xr-xml-map "bgp:ImportStitching";
      type boolean;
      description "Import Stitching enabled";
    }
    leaf import-reoriginate {
      xr:xr-xml-map "bgp:ImportReoriginate";
      type boolean;
      description "Import Reoriginate enabled";
    }
    leaf import-reoriginate-stitching {
      xr:xr-xml-map "bgp:ImportReoriginateStitching";
      type boolean;
      description "Import Reoriginate Stitching enabled";
    }
    leaf advertise-v4-flags {
      xr:xr-xml-map "bgp:AdvertiseV4Flags";
      type uint32;
      description "Advertise options for VPNV4";
    }
    leaf advertise-v6-flags {
      xr:xr-xml-map "bgp:AdvertiseV6Flags";
      type uint32;
      description "Advertise options for VPNV6";
    }
    leaf-list extended-community {
      xr:xr-xml-map "bgp:ExtendedCommunity";
      type uint8;
      description "Extended community attribute";
    }
    leaf-list extended-community-standby {
      xr:xr-xml-map "bgp:ExtendedCommunityStandby";
      type uint8;
      description "Extended community attribute";
    }
  }

  grouping BGP-PERF-NBR {
    description "BGP PERF NBR";
    leaf read-throttles {
      xr:xr-xml-map "bgp:ReadThrottles";
      type uint32;
      description "Number of partial read throttles";
    }
    leaf low-throttled-read {
      xr:xr-xml-map "bgp:LowThrottledRead";
      type uint32;
      description
        "Num socket reads after nbrs crossed low
        threshold";
    }
    leaf high-throttled-read {
      xr:xr-xml-map "bgp:HighThrottledRead";
      type uint32;
      description
        "Num of socket reads after nbr crossed high
        threshold";
    }
    leaf time-since-last-throttled-read {
      xr:xr-xml-map "bgp:TimeSinceLastThrottledRead";
      type uint32;
      units "second";
      description
        "Time (in secs) since last read after being
        throttled";
    }
    leaf read-calls-count {
      xr:xr-xml-map "bgp:ReadCallsCount";
      type uint32;
      description "No. of calls to function to read inbound data";
    }
    leaf read-messages-count {
      xr:xr-xml-map "bgp:ReadMessagesCount";
      type uint32;
      description "Number of BGP messages read";
    }
    leaf data-bytes-read {
      xr:xr-xml-map "bgp:DataBytesRead";
      type uint32;
      units "byte";
      description "No. of bytes of data read";
    }
    leaf io-read-time {
      xr:xr-xml-map "bgp:IOReadTime";
      type uint32;
      units "millisecond";
      description "Time spent reading inbound data (milliseconds)";
    }
    leaf write-calls-count {
      xr:xr-xml-map "bgp:WriteCallsCount";
      type uint32;
      description "No. of calls to function to write outbound data";
    }
    leaf data-bytes-written {
      xr:xr-xml-map "bgp:DataBytesWritten";
      type uint32;
      units "byte";
      description "No. of data bytes written";
    }
    leaf io-write-time {
      xr:xr-xml-map "bgp:IOWriteTime";
      type uint32;
      units "millisecond";
      description "Time spent writing outbound data (milliseconds)";
    }
    leaf last-sent-seq-no {
      xr:xr-xml-map "bgp:LastSentSeqNo";
      type uint32;
      description "Seq No of the last sent byte";
    }
    leaf write-subgroup-calls-count {
      xr:xr-xml-map "bgp:WriteSubgroupCallsCount";
      type uint32;
      description
        "No. of calls to function to process sub-group
        message list";
    }
    leaf write-subgroup-messages-count {
      xr:xr-xml-map "bgp:WriteSubgroupMessagesCount";
      type uint32;
      description "Number of sub-group msgs processed";
    }
    leaf subgroup-list-time {
      xr:xr-xml-map "bgp:SubgroupListTime";
      type uint32;
      units "millisecond";
      description
        "Time spent processing sub-group message list 
        (milliseconds)";
    }
    leaf write-queue-calls-count {
      xr:xr-xml-map "bgp:WriteQueueCallsCount";
      type uint32;
      description "No. of calls to function to process write queue";
    }
    leaf write-queue-messages-count {
      xr:xr-xml-map "bgp:WriteQueueMessagesCount";
      type uint32;
      description "Number of write queue messages processed";
    }
    leaf write-queue-time {
      xr:xr-xml-map "bgp:WriteQueueTime";
      type uint32;
      units "millisecond";
      description
        "Time spent processing write queue (milliseconds)";
    }
    leaf inbound-update-messages {
      xr:xr-xml-map "bgp:InboundUpdateMessages";
      type uint32;
      description "Number of inbound update messages processed";
    }
    leaf inbound-update-messages-time {
      xr:xr-xml-map "bgp:InboundUpdateMessagesTime";
      type uint32;
      units "millisecond";
      description
        "Time spent processing inbound update messages
        (milliseconds)";
    }
    leaf maximum-read-size {
      xr:xr-xml-map "bgp:MaximumReadSize";
      type uint32;
      units "millisecond";
      description "Size of largest socket (milliseconds)";
    }
    leaf actives {
      xr:xr-xml-map "bgp:Actives";
      type uint32;
      description
        "Number of retried Active opens for this neighbor";
    }
    leaf failed-post-actives {
      xr:xr-xml-map "bgp:FailedPostActives";
      type uint32;
      description
        "Number of Active Opens that failed in the Post
        Active State for this neighbor";
    }
    leaf passives {
      xr:xr-xml-map "bgp:Passives";
      type uint32;
      description
        "Number of retried Passive opens for this
        neighbor";
    }
    leaf rejected-passives {
      xr:xr-xml-map "bgp:RejectedPassives";
      type uint32;
      description
        "Number of rejected Passive opens for this
        neighbor";
    }
    leaf active-collision {
      xr:xr-xml-map "bgp:ActiveCollision";
      type uint32;
      description
        "Number of Closed Active connections for this
        neighbor due to collision ";
    }
    leaf passive-collision {
      xr:xr-xml-map "bgp:PassiveCollision";
      type uint32;
      description
        "Number of Closed Remote opens for this
        neighborneighbor due to collision ";
    }
    leaf control-to-read-thread-trigger {
      xr:xr-xml-map "bgp:ControlToReadThreadTrigger";
      type uint32;
      description
        "Number of times io-control thread trigger read
        thread";
    }
    leaf control-to-write-thread-trigger {
      xr:xr-xml-map "bgp:ControlToWriteThreadTrigger";
      type uint32;
      description
        "Number of times io-control thread trigger write
        thread";
    }
    leaf network-status {
      xr:xr-xml-map "bgp:NetworkStatus";
      type uint32;
      description "Socket status, TRUE if socket closed";
    }
    leaf reset-flags {
      xr:xr-xml-map "bgp:ResetFlags";
      type uint32;
      description "Reset flags, per thread";
    }
    leaf nbr-flags {
      xr:xr-xml-map "bgp:NbrFlags";
      type uint32;
      description "Nbr flags, per thread";
    }
    leaf nbr-fd {
      xr:xr-xml-map "bgp:NbrFd";
      type int32;
      description "Primary FD, per nbr";
    }
    leaf reset-retries {
      xr:xr-xml-map "bgp:ResetRetries";
      type uint8;
      description "Reset Retries, per nbr";
    }
    leaf sync-flags {
      xr:xr-xml-map "bgp:SyncFlags";
      type uint32;
      description "Sync flags, per nbr";
    }
    leaf nsr-oper-down-count {
      xr:xr-xml-map "bgp:NSROperDownCount";
      type uint32;
      description "Number of times NSR scoped sync has been done";
    }
    leaf last-nsr-scoped-sync {
      xr:xr-xml-map "bgp:LastNSRScopedSync";
      type uint32;
      description
        "Last time NSR scoped syncwas done for the
        neighbor";
    }
  }

  grouping BGP-NOTFNTYPE {
    description "BGP NOTFNTYPE";
    leaf time-since-last-notification {
      xr:xr-xml-map "bgp:TimeSinceLastNotification";
      type uint32;
      units "second";
      description
        "Time since the last notification was sent or
        received (seconds)";
    }
    leaf notification-error-code {
      xr:xr-xml-map "bgp:NotificationErrorCode";
      type uint8;
      description "Error code in last notification";
    }
    leaf notification-error-subcode {
      xr:xr-xml-map "bgp:NotificationErrorSubcode";
      type uint8;
      description "Error subcode in last notification";
    }
    leaf-list last-notification-data {
      xr:xr-xml-map "bgp:LastNotificationData";
      type uint8;
      description "Message data in last notification";
    }
  }

  grouping BGP-NBR-BAG {
    description "BGP Neighbor Information";

    container connection-local-address {
      description "Local address for the connection";
      uses BGP-ADDRTYPE;
    }

    container connection-remote-address {
      description "Remote address for the connection";
      uses BGP-ADDRTYPE;
    }

    container send-notification-info {
      description "Information on the last notification sent";
      uses BGP-NOTFNTYPE;
    }

    container received-notification-info {
      description "Information on the last notification received";
      uses BGP-NOTFNTYPE;
    }

    container performance-statistics {
      description "Performance statistics";
      uses BGP-PERF-NBR;
    }

    container message-statistics {
      description "Message statistics";
      uses BGP-NBR-MSG-STATS;
    }

    container tcp-init-sync-time-spec {
      description "Time When neighbor entered TCP Init Sync";
      uses BGP-TIMESPEC;
    }

    container tcp-init-sync-phase-two-time-spec {
      description
        "Time when neighbor entered TCP Init Sync Phase
        Two";
      uses BGP-TIMESPEC;
    }

    container tcp-init-sync-done-time-spec {
      description "Time when neighbor entered TCP Init Sync Done";
      uses BGP-TIMESPEC;
    }

    container graceful-maintenance {
      description "Graceful Maintenance";
      uses BGP-NBR-GSHUT;
    }
    leaf speaker-id {
      xr:xr-xml-map "bgp:SpeakerID";
      type uint8;
      description "Speaker this neighbor is allocated to";
    }
    leaf description {
      xr:xr-xml-map "bgp:Description";
      type string;
      description "Description";
    }
    leaf local-as {
      xr:xr-xml-map "bgp:LocalAS";
      type uint32;
      description "Local AS number";
    }
    leaf remote-as {
      xr:xr-xml-map "bgp:RemoteAS";
      type uint32;
      description "Remote AS number";
    }
    leaf has-internal-link {
      xr:xr-xml-map "bgp:HasInternalLink";
      type boolean;
      description "Internal link to neighbor";
    }
    leaf is-external-neighbor-not-directly-connected {
      xr:xr-xml-map "bgp:IsExternalNeighborNotDirectlyConnected";
      type boolean;
      description "External neighbor not directly connected";
    }
    leaf messages-received {
      xr:xr-xml-map "bgp:MessagesReceived";
      type uint32;
      description "Number of messages received";
    }
    leaf messages-sent {
      xr:xr-xml-map "bgp:MessagesSent";
      type uint32;
      description "Number of messages sent";
    }
    leaf update-messages-in {
      xr:xr-xml-map "bgp:UpdateMessagesIn";
      type uint32;
      description "No. of update msgs received";
    }
    leaf update-messages-out {
      xr:xr-xml-map "bgp:UpdateMessagesOut";
      type uint32;
      description "No. of update messages sent";
    }
    leaf messages-queued-in {
      xr:xr-xml-map "bgp:MessagesQueuedIn";
      type uint32;
      description "No. of msgs on receive queue";
    }
    leaf messages-queued-out {
      xr:xr-xml-map "bgp:MessagesQueuedOut";
      type uint32;
      description "No. of messages on send queue";
    }
    leaf connection-established-time {
      xr:xr-xml-map "bgp:ConnectionEstablishedTime";
      type uint32;
      units "second";
      description
        "Time (in secs) that the connection has been
        established";
    }
    leaf connection-state {
      xr:xr-xml-map "bgp:ConnectionState";
      type Bgp-conn-state;
      description "State of connection";
    }
    leaf previous-connection-state {
      xr:xr-xml-map "bgp:PreviousConnectionState";
      type uint32;
      description "Previous state of connection";
    }
    leaf connection-admin-status {
      xr:xr-xml-map "bgp:ConnectionAdminStatus";
      type uint32;
      description "Administrative status of connection";
    }
    leaf open-check-error-code {
      xr:xr-xml-map "bgp:OpenCheckErrorCode";
      type Bgp-open-check-err;
      description "Open check error code";
    }
    leaf is-local-address-configured {
      xr:xr-xml-map "bgp:IsLocalAddressConfigured";
      type boolean;
      description
        "Local address configured for the neighbor
        connection";
    }
    leaf connection-local-port {
      xr:xr-xml-map "bgp:ConnectionLocalPort";
      type uint32;
      description "Local port for the connection";
    }
    leaf connection-remote-port {
      xr:xr-xml-map "bgp:ConnectionRemotePort";
      type uint32;
      description "Remote port for the connection";
    }
    leaf neighbor-interface-handle {
      xr:xr-xml-map "bgp:NeighborInterfaceHandle";
      type uint32;
      description "Interface Handle of Neighbor";
    }
    leaf reset-notification-sent {
      xr:xr-xml-map "bgp:ResetNotificationSent";
      type boolean;
      description "Notification was sent during last reset";
    }
    leaf is-administratively-shut-down {
      xr:xr-xml-map "bgp:IsAdministrativelyShutDown";
      type boolean;
      description "Neighbor is administratively shut down";
    }
    leaf is-neighbor-max-prefix-shutdown {
      xr:xr-xml-map "bgp:IsNeighborMaxPrefixShutdown";
      type boolean;
      description
        "Neighbor shut down because it exceeded max prfx
        count";
    }
    leaf is-out-of-memory-shutdown {
      xr:xr-xml-map "bgp:IsOutOfMemoryShutdown";
      type boolean;
      description
        "Neighbor shut down during a SEVERE low memory
        condition";
    }
    leaf is-out-of-memory-forced-up {
      xr:xr-xml-map "bgp:IsOutOfMemoryForcedUp";
      type boolean;
      description
        "Neighbor forced up during a low memory condition";
    }
    leaf is-ebgp-peer-as-league {
      xr:xr-xml-map "bgp:IsEBGPPeerASLeague";
      type boolean;
      description "EBGP peer belongs to AS League";
    }
    leaf is-ebgp-peer-common-admin {
      xr:xr-xml-map "bgp:IsEBGPPeerCommonAdmin";
      type boolean;
      description "EBGP peer with common administation";
    }
    leaf ttl-security-enabled {
      xr:xr-xml-map "bgp:TTLSecurityEnabled";
      type boolean;
      description "TTL Security enabled";
    }
    leaf suppress4-byte-as {
      xr:xr-xml-map "bgp:Suppress4ByteAs";
      type boolean;
      description "Suppress 4byteas capability";
    }
    leaf bfd-session-state {
      xr:xr-xml-map "bgp:BFDSessionState";
      type Bgp-bfd-state;
      description "BFD state for this peer";
    }
    leaf bfd-session-created-state {
      xr:xr-xml-map "bgp:BFDSessionCreatedState";
      type Bgp-bfd-state;
      description "BFD state for this peer";
    }
    leaf bfd-session-enable-mode {
      xr:xr-xml-map "bgp:BFDSessionEnableMode";
      type Bgp-bfd-enable-mode;
      description "BFD enable mode for this peer";
    }
    leaf bfd-minintervalval {
      xr:xr-xml-map "bgp:BFDMinintervalval";
      type uint32;
      description "BFD Mininterval for this peer";
    }
    leaf bfd-multiplierval {
      xr:xr-xml-map "bgp:BFDMultiplierval";
      type uint32;
      description "BFD Multiplier for this peer";
    }
    leaf bfd-state-ts {
      xr:xr-xml-map "bgp:BfdStateTs";
      type uint64;
      description "Timestamp since when nbr is in this bfd state";
    }
    leaf router-id {
      xr:xr-xml-map "bgp:RouterID";
      type inet:ipv4-address;
      description "Router ID for the neighbor";
    }
    leaf negotiated-protocol-version {
      xr:xr-xml-map "bgp:NegotiatedProtocolVersion";
      type uint16;
      description "Negotiated protocol version";
    }
    leaf ebgp-time-to-live {
      xr:xr-xml-map "bgp:EBGPTimeToLive";
      type uint32;
      description
        "Maximum number of hops for external BGP neighbor";
    }
    leaf is-ebgp-multihop-bgpmpls-forwarding-disabled {
      xr:xr-xml-map "bgp:IsEBGPMultihopBGPMPLSForwardingDisabled";
      type boolean;
      description
        "If true, MPLS and NULL rewrite is disabled; if
        false, it is enabled";
    }
    leaf tcpmss {
      xr:xr-xml-map "bgp:TCPMSS";
      type uint32;
      description
        "Neighbor TCP Maximum Segment                    
        size";
    }
    leaf msg-log-in {
      xr:xr-xml-map "bgp:MsgLogIn";
      type uint32;
      description "Message in log count";
    }
    leaf msg-log-out {
      xr:xr-xml-map "bgp:MsgLogOut";
      type uint32;
      description "Message out log count";
    }
    leaf neighbor-local-as {
      xr:xr-xml-map "bgp:NeighborLocalAS";
      type uint32;
      description "Local AS configured on the neighbor";
    }
    leaf local-as-no-prepend {
      xr:xr-xml-map "bgp:LocalASNoPrepend";
      type boolean;
      description
        "Option to not prepend the Local AS to
        announcements";
    }
    leaf is-capability-negotiation-suppressed {
      xr:xr-xml-map "bgp:IsCapabilityNegotiationSuppressed";
      type boolean;
      description "Capability negotiation suppressed";
    }
    leaf is-capability-negotiation-performed {
      xr:xr-xml-map "bgp:IsCapabilityNegotiationPerformed";
      type boolean;
      description "Capability negotiation performed";
    }
    leaf is-route-refresh-capability-received {
      xr:xr-xml-map "bgp:IsRouteRefreshCapabilityReceived";
      type boolean;
      description "Route refresh capability received";
    }
    leaf is-route-refresh-old-capability-received {
      xr:xr-xml-map "bgp:IsRouteRefreshOldCapabilityReceived";
      type boolean;
      description "Route refresh old capability received";
    }
    leaf is-gr-aware {
      xr:xr-xml-map "bgp:IsGRAware";
      type boolean;
      description "GR awareness received";
    }
    leaf is4-byte-as-capability-received {
      xr:xr-xml-map "bgp:Is4ByteASCapabilityReceived";
      type boolean;
      description "4-byte AScapability received";
    }
    leaf is4-byte-as-capability-sent {
      xr:xr-xml-map "bgp:Is4ByteASCapabilitySent";
      type boolean;
      description "4-byte AScapability Snt";
    }
    leaf multi-protocol-capability-received {
      xr:xr-xml-map "bgp:MultiProtocolCapabilityReceived";
      type boolean;
      description "Multi-protocol capability has been received";
    }
    leaf hold-time {
      xr:xr-xml-map "bgp:HoldTime";
      type uint16;
      units "second";
      description
        "Hold time (in secs) negotiated for this
        connection";
    }
    leaf keep-alive-time {
      xr:xr-xml-map "bgp:KeepAliveTime";
      type uint16;
      units "second";
      description
        "Keepalive time (in secs) negotiated for this
        connection";
    }
    leaf configured-hold-time {
      xr:xr-xml-map "bgp:ConfiguredHoldTime";
      type uint16;
      units "second";
      description
        "Hold time (in secs) configured for this
        connection";
    }
    leaf configured-keepalive {
      xr:xr-xml-map "bgp:ConfiguredKeepalive";
      type uint16;
      units "second";
      description
        "Keepalive time (in secs) configured for this
        connection";
    }
    leaf configured-min-acc-hold-time {
      xr:xr-xml-map "bgp:ConfiguredMinAccHoldTime";
      type uint16;
      units "second";
      description
        "Minimum acceptable hold time from neighbor (in
        secs) configured for this connection";
    }
    leaf min-advertise-interval {
      xr:xr-xml-map "bgp:MinAdvertiseInterval";
      type uint32;
      units "second";
      description "Minimum advertisement interval, secs part";
    }
    leaf min-advertise-interval-msecs {
      xr:xr-xml-map "bgp:MinAdvertiseIntervalMsecs";
      type uint32;
      units "millisecond";
      description "Minimum advertisement interval, msecs part";
    }
    leaf min-origination-interval {
      xr:xr-xml-map "bgp:MinOriginationInterval";
      type uint16;
      units "second";
      description "Minimum origination interval (in secs)";
    }
    leaf connect-retry-interval {
      xr:xr-xml-map "bgp:ConnectRetryInterval";
      type uint16;
      units "second";
      description "Time (in secs) for connect retry timer";
    }
    leaf time-since-last-update {
      xr:xr-xml-map "bgp:TimeSinceLastUpdate";
      type uint32;
      units "second";
      description
        "Time (in secs) since last update message was
        received";
    }
    leaf time-since-last-read {
      xr:xr-xml-map "bgp:TimeSinceLastRead";
      type uint32;
      units "second";
      description "Time (in secs) since last read";
    }
    leaf time-since-last-read-reset {
      xr:xr-xml-map "bgp:TimeSinceLastReadReset";
      type uint32;
      units "second";
      description
        "Time (in secs) since last read before last reset";
    }
    leaf time-last-cb {
      xr:xr-xml-map "bgp:TimeLastCB";
      type uint64;
      description "CB";
    }
    leaf time-last-cb-reset {
      xr:xr-xml-map "bgp:TimeLastCBReset";
      type uint32;
      description "Last CB before reset";
    }
    leaf time-last-fb {
      xr:xr-xml-map "bgp:TimeLastFB";
      type uint64;
      description "FB";
    }
    leaf count-last-write {
      xr:xr-xml-map "bgp:CountLastWrite";
      type uint32;
      description "Count";
    }
    leaf time-since-last-write {
      xr:xr-xml-map "bgp:TimeSinceLastWrite";
      type uint32;
      units "second";
      description "Time (in secs) since last write";
    }
    leaf attempted-last-write-bytes {
      xr:xr-xml-map "bgp:AttemptedLastWriteBytes";
      type uint32;
      description "Attempted size of last write";
    }
    leaf actual-last-write-bytes {
      xr:xr-xml-map "bgp:ActualLastWriteBytes";
      type uint32;
      description "Actual size of last write";
    }
    leaf time-since-second-last-write {
      xr:xr-xml-map "bgp:TimeSinceSecondLastWrite";
      type uint32;
      units "second";
      description "Time (in secs) since second  last write";
    }
    leaf attempted-second-last-write-bytes {
      xr:xr-xml-map "bgp:AttemptedSecondLastWriteBytes";
      type uint32;
      description "Attempted size of second last write";
    }
    leaf actual-second-last-write-bytes {
      xr:xr-xml-map "bgp:ActualSecondLastWriteBytes";
      type uint32;
      description "Actual size of second last write";
    }
    leaf time-since-last-write-reset {
      xr:xr-xml-map "bgp:TimeSinceLastWriteReset";
      type uint32;
      units "second";
      description
        "Time (in secs) since last write before last
        reset";
    }
    leaf attempted-last-write-reset-bytes {
      xr:xr-xml-map "bgp:AttemptedLastWriteResetBytes";
      type uint32;
      description "Attempted size of last write before reset";
    }
    leaf actual-last-write-reset-bytes {
      xr:xr-xml-map "bgp:ActualLastWriteResetBytes";
      type uint32;
      description "Actual size of last write before reset";
    }
    leaf time-since-second-last-write-reset {
      xr:xr-xml-map "bgp:TimeSinceSecondLastWriteReset";
      type uint32;
      units "second";
      description
        "Time (in secs) since last write before last
        reset";
    }
    leaf attempted-second-last-write-reset-bytes {
      xr:xr-xml-map "bgp:AttemptedSecondLastWriteResetBytes";
      type uint32;
      description
        "Attempted size of second last write before reset";
    }
    leaf actual-second-last-write-reset-bytes {
      xr:xr-xml-map "bgp:ActualSecondLastWriteResetBytes";
      type uint32;
      description "Actual size of second last write before reset";
    }
    leaf last-write-event {
      xr:xr-xml-map "bgp:LastWriteEvent";
      type uint32;
      units "second";
      description "Time (in secs) since last write thread event";
    }
    leaf second-last-write-event {
      xr:xr-xml-map "bgp:SecondLastWriteEvent";
      type uint32;
      units "second";
      description
        "Time (in secs) since second last write thread
        event";
    }
    leaf last-k-aexpiry-reset {
      xr:xr-xml-map "bgp:LastKAexpiryReset";
      type uint32;
      units "second";
      description
        "Time (in secs) since last KA timer expiry before
        reset";
    }
    leaf second-last-k-aexpiry-reset {
      xr:xr-xml-map "bgp:SecondLastKAexpiryReset";
      type uint32;
      units "second";
      description
        "Time (in secs) since second last KA timer expiry
        before reset";
    }
    leaf last-k-anotsent-reset {
      xr:xr-xml-map "bgp:LastKAnotsentReset";
      type uint32;
      units "second";
      description
        "Duration (in secs) since last time that KA was
        not sent before reset";
    }
    leaf last-k-aerror-reset {
      xr:xr-xml-map "bgp:LastKAerrorReset";
      type uint32;
      units "second";
      description
        "Duration (in secs) since last time that an error
        was encountered after KA expiry";
    }
    leaf last-k-astart-reset {
      xr:xr-xml-map "bgp:LastKAstartReset";
      type uint32;
      units "second";
      description
        "Time (in secs) since the last KA timer start
        before reset";
    }
    leaf second-last-k-astart-reset {
      xr:xr-xml-map "bgp:SecondLastKAstartReset";
      type uint32;
      units "second";
      description
        "Time (in secs) since the second last KA timer
        start before reset";
    }
    leaf connection-up-count {
      xr:xr-xml-map "bgp:ConnectionUpCount";
      type uint32;
      description "Number of times the connection was established";
    }
    leaf connection-down-count {
      xr:xr-xml-map "bgp:ConnectionDownCount";
      type uint32;
      description "Number of times connection was dropped";
    }
    leaf time-since-connection-last-dropped {
      xr:xr-xml-map "bgp:TimeSinceConnectionLastDropped";
      type uint32;
      units "second";
      description
        "Time since the connection last went down
        (seconds)";
    }
    leaf reset-reason {
      xr:xr-xml-map "bgp:ResetReason";
      type Bgp-reset-reason-index;
      description "Reason for last connection reset";
    }
    leaf peer-reset-reason {
      xr:xr-xml-map "bgp:PeerResetReason";
      type Bgp-peer-reset-reason-index;
      description "Reason for last peer close event";
    }
    leaf peer-error-code {
      xr:xr-xml-map "bgp:PeerErrorCode";
      type uint32;
      description "If peer closed, error received from transport";
    }
    leaf last-notify-error-code {
      xr:xr-xml-map "bgp:LastNotifyErrorCode";
      type uint8;
      description
        "Code for the last error notification seen on the
        connection";
    }
    leaf last-notify-error-subcode {
      xr:xr-xml-map "bgp:LastNotifyErrorSubcode";
      type uint8;
      description
        "Error subcode of the last error notification
        seen on the connection";
    }
    leaf error-notifies-received {
      xr:xr-xml-map "bgp:ErrorNotifiesReceived";
      type uint32;
      description
        "Number of error notifications received on the
        connection";
    }
    leaf error-notifies-sent {
      xr:xr-xml-map "bgp:ErrorNotifiesSent";
      type uint32;
      description
        "Number of error notifications sent on the
        connection";
    }
    leaf remote-as-number {
      xr:xr-xml-map "bgp:RemoteASNumber";
      type uint32;
      description "Remote AS number";
    }
    leaf dmz-link-bandwidth {
      xr:xr-xml-map "bgp:DMZLinkBandwidth";
      type uint32;
      description "Bandwidth of link to single-hop eBGP peer";
    }
    leaf ebgp-recv-dmz {
      xr:xr-xml-map "bgp:EBGPRecvDmz";
      type boolean;
      description
        "Receive Bandwidth of link to single-hop eBGP
        peer";
    }
    leaf ebgp-send-dmz-mode {
      xr:xr-xml-map "bgp:EBGPSendDmzMode";
      type Bgp-ebgp-send-dmz-enable-mode;
      description "Ebgp send dmz link bw mode";
    }
    leaf tos-type {
      xr:xr-xml-map "bgp:TOSType";
      type uint8;
      description "Precedence or DSCP type";
    }
    leaf tos-value {
      xr:xr-xml-map "bgp:TOSValue";
      type uint8;
      description "Precedence or DSCP value";
    }
    leaf tcp-session-open-mode {
      xr:xr-xml-map "bgp:TCPSessionOpenMode";
      type Bgp-tcp-mode;
      description
        "The TCP mode to be used to set up BGP session
        with the neighbor";
    }
    leaf vrf-name {
      xr:xr-xml-map "bgp:VRFName";
      type string;
      description "Name of the VRF";
    }
    leaf standby-rp {
      xr:xr-xml-map "bgp:StandbyRP";
      type boolean;
      description "Standby RP socket inited for Active Open";
    }
    leaf nsr-enabled {
      xr:xr-xml-map "bgp:NSREnabled";
      type boolean;
      description "Neighbor supports NSR";
    }
    leaf graceful-restart-enabled-nbr {
      xr:xr-xml-map "bgp:GracefulRestartEnabledNbr";
      type boolean;
      description "Neighbor supports graceful-restart";
    }
    leaf gr-restart-time {
      xr:xr-xml-map "bgp:GrRestartTime";
      type uint32;
      units "second";
      description "Neighbor restart time (in seconds)";
    }
    leaf gr-stale-path-time {
      xr:xr-xml-map "bgp:GrStalePathTime";
      type uint32;
      units "second";
      description "Neighbor stale-path time (in seconds)";
    }
    leaf fssn-offset {
      xr:xr-xml-map "bgp:FssnOffset";
      type uint32;
      description "First standby SeqNo offset";
    }
    leaf fpbsn-offset {
      xr:xr-xml-map "bgp:FpbsnOffset";
      type uint32;
      description "First standby PDU boundary SeqNo offset";
    }
    leaf last-ackd-seq-no {
      xr:xr-xml-map "bgp:LastAckdSeqNo";
      type uint32;
      description "SeqNo of the last Ackd byte";
    }
    leaf bytes-written {
      xr:xr-xml-map "bgp:BytesWritten";
      type uint32;
      units "byte";
      description "Total bytes written by write thread";
    }
    leaf bytes-read {
      xr:xr-xml-map "bgp:BytesRead";
      type uint32;
      units "byte";
      description "Total bytes read";
    }
    leaf socket-read-bytes {
      xr:xr-xml-map "bgp:SocketReadBytes";
      type uint32;
      units "byte";
      description "Total read bytes value insocket-lib";
    }
    leaf is-read-disabled {
      xr:xr-xml-map "bgp:IsReadDisabled";
      type boolean;
      description "If true, socket read isdisabled";
    }
    leaf update-bytes-read {
      xr:xr-xml-map "bgp:UpdateBytesRead";
      type uint32;
      units "byte";
      description "Total update bytes read";
    }
    leaf nsr-state {
      xr:xr-xml-map "bgp:NSRState";
      type Bgp-sync-nbr-nsr-state;
      description "NSR state";
    }
    leaf is-passive-close {
      xr:xr-xml-map "bgp:IsPassiveClose";
      type boolean;
      description
        "If true, active socket canbe closed if passive
        openis received for a GRcapable neighbor";
    }
    leaf nbr-enforce-first-as {
      xr:xr-xml-map "bgp:NbrEnforceFirstAS";
      type boolean;
      description "Neighbor enforce first AS";
    }
    leaf active-bmp-servers {
      xr:xr-xml-map "bgp:ActiveBMPServers";
      type uint8;
      description "BMP Servers to which the neighbor sends logs";
    }
    leaf nbr-cluster-id {
      xr:xr-xml-map "bgp:NbrClusterID";
      type uint32;
      description "Cluster id";
    }
    leaf nbr-in-cluster {
      xr:xr-xml-map "bgp:NbrInCluster";
      type uint8;
      description "Type of cluster_id:undefined/number/Ip address";
    }
    leaf ignore-connected {
      xr:xr-xml-map "bgp:IgnoreConnected";
      type boolean;
      description "If true, the VPN client isan IBGP CE peer";
    }
    leaf internal-vpn-client {
      xr:xr-xml-map "bgp:InternalVPNClient";
      type boolean;
      description "If true, don't do NHconnected check for nbr";
    }
    leaf io-armed {
      xr:xr-xml-map "bgp:IoArmed";
      type boolean;
      description
        "If true, socket has beenauto-armed for io
        control";
    }
    leaf read-armed {
      xr:xr-xml-map "bgp:ReadArmed";
      type boolean;
      description "If true, socket has beenauto-armed for read";
    }
    leaf write-armed {
      xr:xr-xml-map "bgp:WriteArmed";
      type boolean;
      description "If true, socket has beenauto-armed for write";
    }
    leaf discard-data-bytes {
      xr:xr-xml-map "bgp:DiscardDataBytes";
      type uint32;
      units "byte";
      description "Remaining discard data (bytes) on Standby";
    }
    leaf local-as-replace-as {
      xr:xr-xml-map "bgp:LocalASReplaceAS";
      type boolean;
      description "Local AS Replace-AS option";
    }
    leaf local-as-dual-as {
      xr:xr-xml-map "bgp:LocalASDualAS";
      type boolean;
      description "Local AS Dual-AS option";
    }
    leaf local-as-dual-as-mode-native {
      xr:xr-xml-map "bgp:LocalASDualASModeNative";
      type boolean;
      description
        "Applies only if Local AS Dual-AS option is
        enabled. Indicates if Dual-AS mode is native.";
    }
    leaf egress-peer-engineering-enabled {
      xr:xr-xml-map "bgp:EgressPeerEngineeringEnabled";
      type boolean;
      description "Indicates if Egress Peer Engineering is enabled";
    }
    leaf discard-as4-path {
      xr:xr-xml-map "bgp:DiscardAS4Path";
      type uint32;
      description
        "Discard AS4_PATH in case there is a discrepancy
        in merging AS_PATH and AS4_PATH,retain ASPATH";
    }
    leaf rpki-disable {
      xr:xr-xml-map "bgp:RPKIDisable";
      type boolean;
      description "Prefix validation disabled";
    }
    leaf rpki-use-validity {
      xr:xr-xml-map "bgp:RPKIUseValidity";
      type boolean;
      description "Prefix v. use validity";
    }
    leaf rpki-allow-invalid {
      xr:xr-xml-map "bgp:RPKIAllowInvalid";
      type boolean;
      description "Prefix v. allow invalid";
    }
    leaf rpki-signal-ibgp {
      xr:xr-xml-map "bgp:RPKISignalIBGP";
      type boolean;
      description "Prefix v. signal ibgp";
    }

    list af-data {
      max-elements "23";
      description "Address family specific neighbor data";
      uses BGP-NBR-AF;
    }
  }

  grouping BGP-PATH-MULTI {
    description "BGP path set";

    list paths {
      description "paths";
      uses BGP-PATH-BAG;
    }

    list adv-path-info {
      description "Net Advertized Paths";
      uses BGP-PATH-ADV-BAG;
    }
  }

  grouping BGP-NBR-ADV-CNT-BAG {
    description "BGP Neighbor adv cnt bag";
    leaf max-prefix-advertisedcount {
      xr:xr-xml-map "bgp:MaxPrefixAdvertisedcount";
      type uint32;
      description "Number of prefixes advertsied to neighbor";
    }
  }

  grouping BGP-EPE-SET-BAG {
    description "BGP EPE SET BAG";

    container epe-local-address {
      description "Local address";
      uses BGP-ADDRTYPE;
    }

    container epe-next-hop {
      description "Nexthop address";
      uses BGP-ADDRTYPE;
    }
    leaf epe-key-length-xr {
      xr:xr-xml-map "bgp:epe-key-length-xr";
      type uint8;
      description "EPE key length in bits";
    }
    leaf epe-version {
      xr:xr-xml-map "bgp:EPEVersion";
      type uint32;
      description "EPE object's version";
    }
    leaf epe-flags {
      xr:xr-xml-map "bgp:EPEFlags";
      type uint8;
      description "EPE object's flags";
    }
    leaf epe-local-asn {
      xr:xr-xml-map "bgp:EPELocalASN";
      type uint32;
      description "Local AS Number";
    }
    leaf epe-remote-asn {
      xr:xr-xml-map "bgp:EPERemoteASN";
      type uint32;
      description "Remote AS Number";
    }
    leaf epe-remote-router-id {
      xr:xr-xml-map "bgp:EPERemoteRouterID";
      type uint32;
      description "Remote router id";
    }
    leaf epe-local-router-id {
      xr:xr-xml-map "bgp:EPELocalRouterID";
      type uint32;
      description "Local router id";
    }
    leaf label {
      xr:xr-xml-map "bgp:Label";
      type uint32;
      description "Label assigned to the RPCnext-hop set";
    }
    leaf ref-count {
      xr:xr-xml-map "bgp:RefCount";
      type uint32;
      description "Refcount";
    }
    leaf-list epe-key {
      xr:xr-xml-map "bgp:EPEKey";
      type uint8;
      description "Key of EPE object";
    }
    leaf-list nexthop-id {
      xr:xr-xml-map "bgp:NexthopIDList";
      type uint32;
      description "List of nexthop ID of EPE";
    }

    list first-hop {
      description "List of firsthops of EPE";
      uses BGP-ADDRTYPE;
    }
  }

  grouping BGP-UPDGEN-FILTERGRP-BAG {
    description "BGP Update generation Filter-group information";
    leaf process-id {
      xr:xr-xml-map "bgp:ProcessID";
      type uint32;
      description "ProcessID";
    }
    leaf update-vrf-name {
      xr:xr-xml-map "bgp:UpdateVRFName";
      type string;
      description "VRF Name";
    }
    leaf update-group-af-name {
      xr:xr-xml-map "bgp:UpdateGroupAFName";
      type Bgp-afi;
      description "Address family identifier";
    }
    leaf update-filter-group-index {
      xr:xr-xml-map "bgp:UpdateFilterGroupIndex";
      type uint32;
      description "Filter-group index";
    }
    leaf parent-filter-group-index {
      xr:xr-xml-map "bgp:ParentFilterGroupIndex";
      type uint32;
      description "Parent Filter-group index";
    }
    leaf sub-group-index-xr {
      xr:xr-xml-map "bgp:sub-group-index-xr";
      type uint32;
      description "Sub-group index";
    }
    leaf sub-group-id-xr {
      xr:xr-xml-map "bgp:sub-group-id-xr";
      type uint32;
      description "Sub-group identifier";
    }
    leaf parent-sub-group-index {
      xr:xr-xml-map "bgp:ParentSubGroupIndex";
      type uint32;
      description "Parent Sub-group index";
    }
    leaf parent-sub-group-id {
      xr:xr-xml-map "bgp:ParentSubGroupID";
      type uint32;
      description "Parent Sub-group identifier";
    }
    leaf update-group-index-xr {
      xr:xr-xml-map "bgp:update-group-index-xr";
      type uint32;
      description "Update-group index";
    }
    leaf neighbor-count {
      xr:xr-xml-map "bgp:NeighborCount";
      type uint32;
      description "Neighbor count";
    }
  }

  grouping BGP-UPDGEN-UPDGRP-BAG {
    description "BGP Update generation Update-group information";

    container last-update-timer-start-timestamp {
      description "Last update timer start time";
      uses BGP-TIMESPEC;
    }

    container last-update-timer-stop-timestamp {
      description "Last update timer stop time";
      uses BGP-TIMESPEC;
    }

    container last-update-timer-expiry-timestamp {
      description "Last update timer expiry time";
      uses BGP-TIMESPEC;
    }

    container last-update-timer-remaining-value {
      description "Update timer remaining time";
      uses BGP-TIMESPEC;
    }

    container last-update-timer-delay-value {
      description "Last update timer delay value";
      uses BGP-TIMESPEC;
    }

    container update-statistics {
      description "Update statistics";
      uses BGP-UPDGEN-STATS-BAG;
    }
    leaf process-id {
      xr:xr-xml-map "bgp:ProcessID";
      type uint32;
      description "ProcessID";
    }
    leaf update-vrf-name {
      xr:xr-xml-map "bgp:UpdateVRFName";
      type string;
      description "VRF Name";
    }
    leaf update-group-af-name {
      xr:xr-xml-map "bgp:UpdateGroupAFName";
      type Bgp-afi;
      description "Address family identifier";
    }
    leaf neighbor-session-af-name {
      xr:xr-xml-map "bgp:NeighborSessionAFName";
      type uint8;
      description "Neighbor session address family";
    }
    leaf update-group-index-xr {
      xr:xr-xml-map "bgp:update-group-index-xr";
      type uint32;
      description "Update-group index";
    }
    leaf update-group-flags2 {
      xr:xr-xml-map "bgp:UpdateGroupFlags2";
      type uint32;
      description "Update-group internal flags2";
    }
    leaf update-out-queue-messages {
      xr:xr-xml-map "bgp:UpdateOutQueueMessages";
      type uint32;
      description "OutQueue Messages";
    }
    leaf update-out-queue-size {
      xr:xr-xml-map "bgp:UpdateOutQueueSize";
      type uint32;
      description "OutQueue Size";
    }
    leaf update-sub-group-count {
      xr:xr-xml-map "bgp:UpdateSubGroupCount";
      type uint32;
      description "Sub-group count";
    }
    leaf sub-group-throttled-count {
      xr:xr-xml-map "bgp:SubGroupThrottledCount";
      type uint32;
      description "Throttled sub-group count";
    }
    leaf refresh-sub-group-count {
      xr:xr-xml-map "bgp:RefreshSubGroupCount";
      type uint32;
      description "Refresh sub-group count";
    }
    leaf refresh-sub-group-throttled-count {
      xr:xr-xml-map "bgp:RefreshSubGroupThrottledCount";
      type uint32;
      description "Throttled refresh sub-group count";
    }
    leaf filter-group-count {
      xr:xr-xml-map "bgp:FilterGroupCount";
      type uint32;
      description "Filter-group count";
    }
    leaf neighbor-count {
      xr:xr-xml-map "bgp:NeighborCount";
      type uint32;
      description "Neighbor count";
    }
    leaf neighbor-leaving-count {
      xr:xr-xml-map "bgp:NeighborLeavingCount";
      type uint32;
      description "Count of neighbors leaving the update-group";
    }
    leaf update-generation-recovery-pending {
      xr:xr-xml-map "bgp:UpdateGenerationRecoveryPending";
      type boolean;
      description "Is update generation recovery pending";
    }
    leaf last-update-timer-expiry-age {
      xr:xr-xml-map "bgp:LastUpdateTimerExpiryAge";
      type uint32;
      description "Time since last update timer expiry event";
    }
    leaf is-update-timer-running {
      xr:xr-xml-map "bgp:IsUpdateTimerRunning";
      type boolean;
      description "Is update timer running";
    }
    leaf perm-pelem-encountered {
      xr:xr-xml-map "bgp:PermPelemEncountered";
      type uint32;
      description "Count of Perm Pelems seen by updgen";
    }
    leaf perm-pelem-allowed {
      xr:xr-xml-map "bgp:PermPelemAllowed";
      type uint32;
      description "Count of Perm Pelems allowed by updgen";
    }
    leaf perm-pelem-not-allowed {
      xr:xr-xml-map "bgp:PermPelemNotAllowed";
      type uint32;
      description "Count of Perm Pelems not allowed by updgen";
    }
    leaf perm-pelem-exp-wdr {
      xr:xr-xml-map "bgp:PermPelemExpWdr";
      type uint32;
      description "Count of Perm Pelems explicitly wdrn by updgen";
    }
    leaf perm-pelem-spur-wdr {
      xr:xr-xml-map "bgp:PermPelemSpurWdr";
      type uint32;
      description
        "Count of Perm Pelems Spurious withdraws by
        updgen";
    }
    leaf is-permanent {
      xr:xr-xml-map "bgp:IsPermanent";
      type boolean;
      description "Permanent UG check";
    }
  }

  grouping BGP-RTSET {
    description "BGP RT-set";
    leaf rt-set-len {
      xr:xr-xml-map "bgp:RTSetLen";
      type uint8;
      units "byte";
      description "Length in bytes of set of route targets";
    }
    leaf rt-set-id {
      xr:xr-xml-map "bgp:RTSetID";
      type uint32;
      description "Identifier of the rtset";
    }
    leaf rt-set-net-count {
      xr:xr-xml-map "bgp:RTSetNetCount";
      type uint32;
      description "Count of nets with paths with the rtset";
    }
    leaf-list rt-set {
      xr:xr-xml-map "bgp:RTSet";
      type uint8;
      description "Set of route targets";
    }
  }

  grouping BGP-RTSET-BAG {
    description "BGP RT-set information";

    container route-target-set {
      description "Route Target set";
      uses BGP-RTSET;
    }
  }

  grouping BGP-INT-NH-GW {
    description "BGP Internal Nexthop Gateway Information";
    leaf gateway-flags {
      xr:xr-xml-map "bgp:GatewayFlags";
      type uint32;
      description "Gateway flags";
    }
    leaf registration-type {
      xr:xr-xml-map "bgp:RegistrationType";
      type Bgp-nh-validate;
      description "Nexthop registration type";
    }
    leaf registration-since {
      xr:xr-xml-map "bgp:RegistrationSince";
      type uint32;
      description "Time since registration";
    }
  }

  grouping BGP-INT-NH {
    description "BGP Internal Nexthop information";

    container nexthop-address {
      description "Nexthop address";
      uses BGP-ADDRTYPE;
    }
    leaf nexthop-id {
      xr:xr-xml-map "bgp:NexthopId";
      type uint32;
      description "Comm librray ID";
    }
    leaf nexthop-version {
      xr:xr-xml-map "bgp:NexthopVersion";
      type uint32;
      description "Table version";
    }
    leaf nexthop-flags {
      xr:xr-xml-map "bgp:NexthopFlags";
      type uint32;
      description "Nexthop flags";
    }
    leaf nexthop-if-handle {
      xr:xr-xml-map "bgp:NexthopIFHandle";
      type uint32;
      description "Nexthop ifhandle";
    }
    leaf nexthop-af-user-bits {
      xr:xr-xml-map "bgp:NexthopAFUserBits";
      type uint32;
      description
        "Bitmask indicating the AFs which share the
        nexthop";
    }
    leaf nexthop-label {
      xr:xr-xml-map "bgp:NexthopLabel";
      type uint32;
      description "Nexthop label";
    }
    leaf gateway-flags {
      xr:xr-xml-map "bgp:GatewayFlags";
      type uint32;
      description "Gateway flags";
    }
    leaf-list nexthop-metrice {
      xr:xr-xml-map "bgp:NexthopMetrices";
      type uint32;
      description "Nexthop metrices";
    }
    leaf-list nexthop-refcount {
      xr:xr-xml-map "bgp:NexthopRefcounts";
      type uint32;
      description "Nexthop refcounts";
    }

    list nexthop-gateway-internal-info {
      description "Internal nexthop Gateway info";
      uses BGP-INT-NH-GW;
    }
  }

  grouping BGP-NEXTHOP-GW-INFO {
    description "BGP Nexthop GW info";

    container nexthop-route {
      description "Route resolving the nethop";
      uses BGP-ADDRTYPE;
    }
    leaf nexthop-route-prefix-length {
      xr:xr-xml-map "bgp:NexthopRoutePrefixLength";
      type uint8;
      description
        "Prefix length of the route resolving the nexthop";
    }
    leaf nexthop-route-protocol {
      xr:xr-xml-map "bgp:NexthopRouteProtocol";
      type string;
      description "Protocol that resolves the route to the nexthop";
    }
    leaf nexthop-route-path-count {
      xr:xr-xml-map "bgp:NexthopRoutePathCount";
      type uint32;
      description "Number of paths in the resolving route";
    }
    leaf nexthop-af-invalid-bits {
      xr:xr-xml-map "bgp:NexthopAFInvalidBits";
      type uint16;
      description
        "Bitmask indicating the AFs which have been
        invalidated for the nexthop";
    }
    leaf nexthop-status {
      xr:xr-xml-map "bgp:NexthopStatus";
      type uint8;
      description "Nexthop status";
    }
    leaf nexthop-tableid {
      xr:xr-xml-map "bgp:NexthopTableid";
      type uint64;
      description "Nexthop Table id";
    }
    leaf nexthop-metric {
      xr:xr-xml-map "bgp:NexthopMetric";
      type uint32;
      description "IGP metric for nexthop";
    }
    leaf last-event-type {
      xr:xr-xml-map "bgp:LastEventType";
      type Bgp-nh-event;
      description "Last nexthop event type";
    }
    leaf last-update-type {
      xr:xr-xml-map "bgp:LastUpdateType";
      type Bgp-nh-update;
      description "Last nexthop update type";
    }
    leaf critical-events {
      xr:xr-xml-map "bgp:CriticalEvents";
      type uint32;
      description "Number of critical events received from RIB";
    }
    leaf non-critical-events {
      xr:xr-xml-map "bgp:NonCriticalEvents";
      type uint32;
      description "Number of non-critical events received from RIB";
    }
    leaf last-event-since {
      xr:xr-xml-map "bgp:LastEventSince";
      type uint32;
      description
        "Time since the last event sent to or received
        from RIB";
    }
    leaf last-rib-update {
      xr:xr-xml-map "bgp:LastRibUpdate";
      type uint32;
      description "Time since the last rib update happened";
    }
    leaf nexthop-mpls-enabled {
      xr:xr-xml-map "bgp:NexthopMPLSEnabled";
      type boolean;
      description
        "TRUE if MPLS is configured for IAS/CsC
        application";
    }
    leaf nexthop-mpls-interfaces {
      xr:xr-xml-map "bgp:NexthopMPLSInterfaces";
      type uint32;
      description "Number of interfaces on which MPLS is enabled";
    }
    leaf nexthop-mpls-label {
      xr:xr-xml-map "bgp:NexthopMPLSLabel";
      type uint32;
      description "Local label allocated for IAS/CsC application";
    }

    list nexthop-route-path {
      description "Nexthops of the resolving route";
      uses BGP-ADDRTYPE;
    }
  }

  grouping BGP-NEXTHOP-BAG {
    description "BGP Nexthop info";

    container nexthop-address {
      description "Nexthop address";
      uses BGP-ADDRTYPE;
    }

    container nhte-tunnel {
      description "NH TE tunnel information";
      uses BGP-TE-TUNNEL;
    }

    container nexthop-internal-info {
      description "Internal nexthop info";
      uses BGP-INT-NH;
    }
    leaf af-name {
      xr:xr-xml-map "bgp:AFName";
      type Bgp-afi;
      description "Address family identifier";
    }
    leaf rib-nexthop-id {
      xr:xr-xml-map "bgp:RIBNexthopId";
      type uint32;
      description "RIB Nexthop Id";
    }
    leaf nexthop-pending-registration {
      xr:xr-xml-map "bgp:NexthopPendingRegistration";
      type uint8;
      description "Nexthop registration is pending";
    }
    leaf nexthop-reference-count {
      xr:xr-xml-map "bgp:NexthopReferenceCount";
      type uint32;
      description
        "Number of neighbors/prefixes referencing this
        nexthop";
    }
    leaf nh-reference-count-total {
      xr:xr-xml-map "bgp:NHReferenceCountTotal";
      type uint32;
      description
        "Number of neighbors/prefixes referencing this
        nexthop (AFs)";
    }
    leaf nh-first-hop-if-handle {
      xr:xr-xml-map "bgp:NHFirstHopIfHandle";
      type xr:Interface-name;
      description "First-hop interface handle";
    }
    leaf nexthop-aigp-metric {
      xr:xr-xml-map "bgp:NexthopAIGPMetric";
      type uint32;
      description "AIGP metrice of nexthop";
    }
    leaf nexthop-gateway-reachable {
      xr:xr-xml-map "bgp:NexthopGatewayReachable";
      type boolean;
      description "Is Gateway reachable ?";
    }
    leaf nexthop-gateway-prefix-connected {
      xr:xr-xml-map "bgp:NexthopGatewayPrefixConnected";
      type boolean;
      description "Is Gateway resolved through Connected route ?";
    }
    leaf nexthop-gateway-prefix-length {
      xr:xr-xml-map "bgp:NexthopGatewayPrefixLength";
      type uint32;
      description "Gateway prefix length";
    }

    list nexthop-gateway-info {
      description
        "Gateway related info, includingOptimal Route
        Reflector Gateways";
      uses BGP-NEXTHOP-GW-INFO;
    }

    list neighbor-address {
      description "Neighbor Address List";
      uses BGP-ADDRTYPE;
    }
  }

  grouping BGP-NEXTHOP-PERF-VRF-AF-BAG {
    description "BGP nexthop statistics for a VRF AF";
    leaf critical-notf-count {
      xr:xr-xml-map "bgp:CriticalNotfCount";
      type uint32;
      description "Number of critical event notifications from RIB";
    }
    leaf noncritical-notf-count {
      xr:xr-xml-map "bgp:NoncriticalNotfCount";
      type uint32;
      description
        "Number of non-critical event notifications from
        RIB";
    }
    leaf last-notf-bestpath-deletes {
      xr:xr-xml-map "bgp:LastNotfBestpathDeletes";
      type uint32;
      description
        "Number of bestpath deletes due to last
        notification";
    }
    leaf last-notf-bestpath-changes {
      xr:xr-xml-map "bgp:LastNotfBestpathChanges";
      type uint32;
      description
        "Number of bestpath changes due to last
        notification";
    }
    leaf nh-sync-reg-calls {
      xr:xr-xml-map "bgp:NHSyncRegCalls";
      type uint32;
      description "NH sync register calls";
    }
    leaf nha-sync-reg-calls {
      xr:xr-xml-map "bgp:NHASyncRegCalls";
      type uint32;
      description "NH async register calls";
    }
    leaf nha-sync-un-reg-calls {
      xr:xr-xml-map "bgp:NHASyncUnRegCalls";
      type uint32;
      description "NH async unregister calls";
    }
    leaf nh-pending-registrations {
      xr:xr-xml-map "bgp:NHPendingRegistrations";
      type uint32;
      description "NH Registration List Count";
    }
    leaf nh-peak-registrations {
      xr:xr-xml-map "bgp:NHPeakRegistrations";
      type uint32;
      description "NH Registration List Count Peak";
    }
    leaf nh-batch-finish-calls {
      xr:xr-xml-map "bgp:NHBatchFinishCalls";
      type uint32;
      description "NH batch finish calls";
    }
    leaf nh-flush-timer-calls {
      xr:xr-xml-map "bgp:NHFlushTimerCalls";
      type uint32;
      description "NH flush timer calls";
    }
    leaf nh-last-sync-reg-ts {
      xr:xr-xml-map "bgp:NHLastSyncRegTs";
      type uint32;
      description "NH Last sync Register TS";
    }
    leaf nh-last-a-sync-reg-ts {
      xr:xr-xml-map "bgp:NHLastASyncRegTs";
      type uint32;
      description "NH Last async Register TS";
    }
    leaf nh-last-a-sync-un-reg-ts {
      xr:xr-xml-map "bgp:NHLastASyncUnRegTs";
      type uint32;
      description "NH Last async UnRegister TS";
    }
    leaf nh-last-batch-finish-ts {
      xr:xr-xml-map "bgp:NHLastBatchFinishTs";
      type uint32;
      description "NH Last batch finish TS";
    }
    leaf nh-last-flush-timer-ts {
      xr:xr-xml-map "bgp:NHLastFlushTimerTs";
      type uint32;
      description "NH Last flush timer TS";
    }
    leaf nhrib-update-calls {
      xr:xr-xml-map "bgp:NHRIBUpdateCalls";
      type uint32;
      description "No. of calls to RIB update function";
    }
    leaf nhrib-update-time {
      xr:xr-xml-map "bgp:NHRIBUpdateTime";
      type uint32;
      units "millisecond";
      description "Time spent sending RIB updates (milliseconds)";
    }
    leaf nexthops-sent-to-rib {
      xr:xr-xml-map "bgp:NexthopsSentToRIB";
      type uint32;
      description "No. of nexthops sent to RIB";
    }
    leaf nexthops-resent-to-rib {
      xr:xr-xml-map "bgp:NexthopsResentToRIB";
      type uint32;
      description "No. of nexthops re-sent to RIB";
    }
    leaf nexthops-removed-from-rib {
      xr:xr-xml-map "bgp:NexthopsRemovedFromRIB";
      type uint32;
      description "No. of nexthops withdrawn from RIB";
    }
    leaf rib-sync-registers-failed {
      xr:xr-xml-map "bgp:RIBSyncRegistersFailed";
      type uint32;
      description "No. of sync registers with RIB that failed";
    }
    leaf riba-sync-registers-failed {
      xr:xr-xml-map "bgp:RIBASyncRegistersFailed";
      type uint32;
      description "No. of async registers with RIB that failed";
    }
    leaf ribnh-reg-failed-for-no-tbl-id {
      xr:xr-xml-map "bgp:RIBNHRegFailedForNoTblId";
      type uint32;
      description "No. of nh registers failed because of no tbl-id";
    }
    leaf ribnh-reg-failed-for-no-rib-conn {
      xr:xr-xml-map "bgp:RIBNHRegFailedForNoRibConn";
      type uint32;
      description
        "No. of nh registers failed because of no rib
        conn";
    }
    leaf tunnel-walk-nh-not-found {
      xr:xr-xml-map "bgp:TunnelWalkNHNotFound";
      type uint32;
      description
        "No. of times nexthop was not found during tunnel
        walk";
    }
    leaf tunnel-walk-gw-not-found {
      xr:xr-xml-map "bgp:TunnelWalkGWNotFound";
      type uint32;
      description
        "No. of times gw was not found during tunnel walk";
    }
    leaf tunnel-walk-backup-creates {
      xr:xr-xml-map "bgp:TunnelWalkBackupCreates";
      type uint32;
      description
        "No. of times backup tid created during tunnel
        walk";
    }
  }

  grouping BGP-NEXTHOP-VRF-AF-BAG {
    description "BGP nexthop processing information for a VRF AF";

    container performance-statistics {
      description "Performance statistics";
      uses BGP-NEXTHOP-PERF-VRF-AF-BAG;
    }
    leaf af-name {
      xr:xr-xml-map "bgp:AFName";
      type Bgp-afi;
      description "Address family identifier";
    }
    leaf gwaf-name {
      xr:xr-xml-map "bgp:GWAFName";
      type Bgp-afi;
      description "GW Address family identifier";
    }
    leaf total-nexthops {
      xr:xr-xml-map "bgp:TotalNexthops";
      type uint32;
      description "Total number of nexthops";
    }
    leaf critical-trigger-delay {
      xr:xr-xml-map "bgp:CriticalTriggerDelay";
      type uint32;
      description "Trigger delay for critical event processing";
    }
    leaf non-critical-trigger-delay {
      xr:xr-xml-map "bgp:NonCriticalTriggerDelay";
      type uint32;
      description "Trigger delay for non-critical event processing";
    }
    leaf table-active {
      xr:xr-xml-map "bgp:TableActive";
      type boolean;
      description "Whether the VRF is active";
    }
    leaf nh-rib-up {
      xr:xr-xml-map "bgp:NHRibUp";
      type boolean;
      description "Whether the VRF is active";
    }
    leaf nh-rib-version {
      xr:xr-xml-map "bgp:NHRibVersion";
      type uint32;
      description "RIB version for gw_ctx";
    }
    leaf nh-nexthop-version {
      xr:xr-xml-map "bgp:NHNexthopVersion";
      type uint32;
      description "NH version for gw_ctx";
    }
    leaf nh-table-id {
      xr:xr-xml-map "bgp:NHTableId";
      type uint32;
      description "Gateway context table id";
    }
    leaf epe-table-version {
      xr:xr-xml-map "bgp:EPETableVersion";
      type uint32;
      description "Version of the EPE table";
    }
    leaf epe-label-version {
      xr:xr-xml-map "bgp:EPELabelVersion";
      type uint32;
      description "Version of the EPE label walk";
    }
    leaf epe-downloaded-version {
      xr:xr-xml-map "bgp:EPEDownloadedVersion";
      type uint32;
      description "Version of the EPE table downloaded";
    }
    leaf epe-standby-version {
      xr:xr-xml-map "bgp:EPEStandbyVersion";
      type uint32;
      description
        "Version of the EPE table processed by sync
        thread";
    }
  }

  grouping BGP-UPDGEN-SUBGRP-BAG {
    description "BGP Update generation Sub-group information";

    container creation-timestamp {
      description "Creation time";
      uses BGP-TIMESPEC;
    }

    container last-merge-timestamp {
      description "Last merge time";
      uses BGP-TIMESPEC;
    }

    container first-update-walk-start-timestamp {
      description "First update walk start time";
      uses BGP-TIMESPEC;
    }

    container first-update-walk-end-timestamp {
      description "First update walk end time";
      uses BGP-TIMESPEC;
    }

    container last-update-walk-start-timestamp {
      description "Last update walk start time";
      uses BGP-TIMESPEC;
    }

    container last-update-walk-end-timestamp {
      description "Last update walk end time";
      uses BGP-TIMESPEC;
    }

    container last-update-queued-timestamp {
      description "Last update queued time";
      uses BGP-TIMESPEC;
    }

    container update-statistics {
      description "Update statistics";
      uses BGP-UPDGEN-STATS-BAG;
    }
    leaf process-id {
      xr:xr-xml-map "bgp:ProcessID";
      type uint32;
      description "ProcessID";
    }
    leaf update-vrf-name {
      xr:xr-xml-map "bgp:UpdateVRFName";
      type string;
      description "VRF Name";
    }
    leaf update-group-af-name {
      xr:xr-xml-map "bgp:UpdateGroupAFName";
      type Bgp-afi;
      description "Address family identifier";
    }
    leaf sub-group-index-xr {
      xr:xr-xml-map "bgp:sub-group-index-xr";
      type uint32;
      description "Sub-group index";
    }
    leaf sub-group-id-xr {
      xr:xr-xml-map "bgp:sub-group-id-xr";
      type uint32;
      description "Sub-group ID";
    }
    leaf parent-sub-group-index {
      xr:xr-xml-map "bgp:ParentSubGroupIndex";
      type uint32;
      description "Parent Sub-group index";
    }
    leaf parent-sub-group-id {
      xr:xr-xml-map "bgp:ParentSubGroupID";
      type uint32;
      description "Parent Sub-group identifier";
    }
    leaf update-group-index-xr {
      xr:xr-xml-map "bgp:update-group-index-xr";
      type uint32;
      description "Update-group index";
    }
    leaf update-main-table-version {
      xr:xr-xml-map "bgp:UpdateMainTableVersion";
      type uint32;
      description "Main table version";
    }
    leaf update-vrf-table-rib-version {
      xr:xr-xml-map "bgp:UpdateVRFTableRIBVersion";
      type uint32;
      description "VRF Table RIB version";
    }
    leaf current-update-limit-sub-group {
      xr:xr-xml-map "bgp:CurrentUpdateLimitSubGroup";
      type uint32;
      description "Current update limit";
    }
    leaf configured-update-limit-sub-group {
      xr:xr-xml-map "bgp:ConfiguredUpdateLimitSubGroup";
      type uint32;
      description "Configured update limit";
    }
    leaf update-out-queue-messages {
      xr:xr-xml-map "bgp:UpdateOutQueueMessages";
      type uint32;
      description "OutQueue messages";
    }
    leaf update-out-queue-size {
      xr:xr-xml-map "bgp:UpdateOutQueueSize";
      type uint32;
      description "OutQueue size";
    }
    leaf update-throttled {
      xr:xr-xml-map "bgp:UpdateThrottled";
      type boolean;
      description "Is update throttled";
    }
    leaf refresh-sub-group-count {
      xr:xr-xml-map "bgp:RefreshSubGroupCount";
      type uint32;
      description "Refresh sub-group count";
    }
    leaf filter-group-count {
      xr:xr-xml-map "bgp:FilterGroupCount";
      type uint32;
      description "Filter-group count";
    }
    leaf neighbor-count {
      xr:xr-xml-map "bgp:NeighborCount";
      type uint32;
      description "Neighbor count";
    }
    leaf version {
      xr:xr-xml-map "bgp:Version";
      type uint32;
      description "Version";
    }
    leaf nsr-version {
      xr:xr-xml-map "bgp:NSRVersion";
      type uint32;
      description "NSR version";
    }
    leaf pending-target-version {
      xr:xr-xml-map "bgp:PendingTargetVersion";
      type uint32;
      description "Pending target version";
    }
    leaf next-resume-version {
      xr:xr-xml-map "bgp:NextResumeVersion";
      type uint32;
      description "Next resume version";
    }
    leaf update-refresh-target-version {
      xr:xr-xml-map "bgp:UpdateRefreshTargetVersion";
      type uint32;
      description "Refresh target version";
    }
    leaf io-write-event-pending {
      xr:xr-xml-map "bgp:IOWriteEventPending";
      type boolean;
      description "Is IO write event pending";
    }
    leaf update-default-route-sent {
      xr:xr-xml-map "bgp:UpdateDefaultRouteSent";
      type boolean;
      description "Is default route sent";
    }
    leaf merge-count {
      xr:xr-xml-map "bgp:MergeCount";
      type uint32;
      description "Merge count";
    }
    leaf last-merged-sub-group-index {
      xr:xr-xml-map "bgp:LastMergedSubGroupIndex";
      type uint32;
      description "Last merged sub-group index";
    }
    leaf eo-r-attempted {
      xr:xr-xml-map "bgp:EoRAttempted";
      type boolean;
      description "Sending EoR has been attempted";
    }
    leaf last-update-walk-end-age {
      xr:xr-xml-map "bgp:LastUpdateWalkEndAge";
      type uint32;
      description "Time since last update walk end event";
    }
    leaf last-update-queued-age {
      xr:xr-xml-map "bgp:LastUpdateQueuedAge";
      type uint32;
      units "second";
      description
        "Time since last update queued event (in seconds)";
    }
  }

  grouping BGP-ATTR-BAG {
    description "BGP attribute information";

    container attribute-info {
      description "Attributes";
      uses BGP-ATTR;
    }
    leaf process-instance-id {
      xr:xr-xml-map "bgp:ProcessInstanceID";
      type uint8;
      description "Process instance ID";
    }
    leaf attribute-instance-id {
      xr:xr-xml-map "bgp:AttributeInstanceID";
      type uint8;
      description "Attribute Instance ID";
    }
    leaf attribute-structure-id {
      xr:xr-xml-map "bgp:AttributeStructureID";
      type uint32;
      description "ID of attribute structure";
    }
    leaf attribute-structure-hash-value {
      xr:xr-xml-map "bgp:AttributeStructureHashValue";
      type uint32;
      description "Hash value for attribute structure";
    }
    leaf reference-count {
      xr:xr-xml-map "bgp:ReferenceCount";
      type uint32;
      description
        "Number of paths which use this attribute
        structure";
    }
  }

  grouping BGP-UPD-FILTERGRP {
    description "Update filter-group entry";
    leaf update-filter-group-number {
      xr:xr-xml-map "bgp:UpdateFilterGroupNumber";
      type uint32;
      description "Update sub-group index";
    }
    leaf rts {
      xr:xr-xml-map "bgp:RTs";
      type uint32;
      description "RT count per filter group";
    }
    leaf fgroup-flags {
      xr:xr-xml-map "bgp:FGroupFlags";
      type uint8;
      description "Flags per filter group";
    }
    leaf fgroup-neighbors {
      xr:xr-xml-map "bgp:FGroupNeighbors";
      type uint16;
      description "Nbrs per filter group";
    }
    leaf fgroup-created-message-elements {
      xr:xr-xml-map "bgp:FGroupCreatedMessageElements";
      type uint32;
      description "Number of message elems created for filtergroup";
    }
    leaf fgroup-deleted-message-elements {
      xr:xr-xml-map "bgp:FGroupDeletedMessageElements";
      type uint32;
      description "Number of message elems deleted";
    }
    leaf fgroup-queued-message-elements {
      xr:xr-xml-map "bgp:FGroupQueuedMessageElements";
      type uint32;
      description "Number of message elems queued";
    }
    leaf fgroup-advertised-prefixes {
      xr:xr-xml-map "bgp:FGroupAdvertisedPrefixes";
      type uint32;
      description
        "Number of prefixes advertised to filtergroup in
        last update walk";
    }
    leaf fgroup-total-advertised-prefixes {
      xr:xr-xml-map "bgp:FGroupTotalAdvertisedPrefixes";
      type uint32;
      description
        "Number of prefixes advertised to filtergroup in
        all update walk";
    }
    leaf fgroup-withdrawn-prefixes {
      xr:xr-xml-map "bgp:FGroupWithdrawnPrefixes";
      type uint32;
      description
        "Number of prefixes withdrawn f`rom filtergroupin
        last update walk";
    }
    leaf fgroup-total-withdrawn-prefixes {
      xr:xr-xml-map "bgp:FGroupTotalWithdrawnPrefixes";
      type uint32;
      description
        "Number of prefixes withdrawn f`rom filtergroupin
        all update walk";
    }
    leaf fgroup-total-non-optimised-prefixes {
      xr:xr-xml-map "bgp:FGroupTotalNonOptimisedPrefixes";
      type uint32;
      description
        "Number of prefixes  non-optm from filtergroupin
        all update walk";
    }
    leaf fgroup-skipped-prefixes {
      xr:xr-xml-map "bgp:FGroupSkippedPrefixes";
      type uint32;
      description
        "Number of prefixes skipped for filtergroup in
        last update walk";
    }
    leaf fgroup-suppressed-prefixes {
      xr:xr-xml-map "bgp:FGroupSuppressedPrefixes";
      type uint32;
      description
        "Number of prefixes suppressed for filtergroup in
        last update walk";
    }
    leaf is-rt-present {
      xr:xr-xml-map "bgp:IsRTPresent";
      type boolean;
      description "RT attribute list present";
    }
    leaf-list extended-community {
      xr:xr-xml-map "bgp:ExtendedCommunity";
      type uint8;
      description "Extended community attribute";
    }

    list neighbor {
      description "Neighbors in this update sub-group";
      uses BGP-ADDRTYPE;
    }
  }

  grouping BGP-UPD-SUBGRP {
    description "Update sub-group entry";
    leaf update-sub-group-number {
      xr:xr-xml-map "bgp:UpdateSubGroupNumber";
      type uint32;
      description "Update sub-group index";
    }
    leaf filter-group {
      xr:xr-xml-map "bgp:FilterGroup";
      type uint16;
      description "Update sub-group fgrp-num";
    }
    leaf wait-for-eo-rs {
      xr:xr-xml-map "bgp:WaitForEoRs";
      type boolean;
      description "Wait for  RT Nbr EoRs";
    }

    list update-filter-group {
      description "Update f-group list";
      uses BGP-UPD-FILTERGRP;
    }

    list neighbor {
      description "Neighbors in this subgrp not in any filtergrp";
      uses BGP-ADDRTYPE;
    }
  }

  grouping BGP-PERF-UPDGRP {
    description "BGP PERF UPDGRP";
    leaf update-generation-calls {
      xr:xr-xml-map "bgp:UpdateGenerationCalls";
      type uint32;
      description "No. of calls to update generation function";
    }
    leaf update-generation-prefixes-count {
      xr:xr-xml-map "bgp:UpdateGenerationPrefixesCount";
      type uint32;
      description "No. of prefixes updates generated for";
    }
    leaf update-generation-be-prefixes-count {
      xr:xr-xml-map "bgp:UpdateGenerationBePrefixesCount";
      type uint32;
      description "No. of be prefixes updates generated for";
    }
    leaf update-generation-messages-count {
      xr:xr-xml-map "bgp:UpdateGenerationMessagesCount";
      type uint32;
      description "No. of update messages generated";
    }
    leaf update-generation-time {
      xr:xr-xml-map "bgp:UpdateGenerationTime";
      type uint32;
      units "millisecond";
      description "Time spent generating updates (milliseconds)";
    }
    leaf updgen-timer-start-time {
      xr:xr-xml-map "bgp:UpdgenTimerStartTime";
      type uint64;
      description "Timestamp when update timer started for updgrp";
    }
    leaf updgen-timer-stop-time {
      xr:xr-xml-map "bgp:UpdgenTimerStopTime";
      type uint64;
      description "Timestamp when update timer stopped for updgrp";
    }
    leaf updgen-timer-process-time {
      xr:xr-xml-map "bgp:UpdgenTimerProcessTime";
      type uint64;
      description
        "Timestamp when update timer processed for updgrp";
    }
  }

  grouping BGP-UPDGRP-BAG {
    description "BGP Update Group information";

    container performance-statistics {
      description "Performance statistics";
      uses BGP-PERF-UPDGRP;
    }
    leaf process-instance-id {
      xr:xr-xml-map "bgp:ProcessInstanceID";
      type uint8;
      description "Process instance ID";
    }
    leaf session-af-name {
      xr:xr-xml-map "bgp:SessionAFName";
      type uint8;
      description "Neighbor session Address family";
    }
    leaf update-group-number {
      xr:xr-xml-map "bgp:UpdateGroupNumber";
      type uint32;
      description "Update group index";
    }
    leaf update-group-af-name {
      xr:xr-xml-map "bgp:UpdateGroupAFName";
      type Bgp-afi;
      description "Address family for update group";
    }
    leaf should-send-communities {
      xr:xr-xml-map "bgp:ShouldSendCommunities";
      type boolean;
      description "Send communities";
    }
    leaf should-send-ext-communities {
      xr:xr-xml-map "bgp:ShouldSendExtCommunities";
      type boolean;
      description "Send Extended communities";
    }
    leaf should-send-stitching-rt {
      xr:xr-xml-map "bgp:ShouldSendStitchingRT";
      type boolean;
      description "Send Stitching RT";
    }
    leaf has-orf-receive-capability {
      xr:xr-xml-map "bgp:HasORFReceiveCapability";
      type boolean;
      description "ORF receive capability";
    }
    leaf is-route-reflector-client {
      xr:xr-xml-map "bgp:IsRouteReflectorClient";
      type boolean;
      description "Route-reflector client";
    }
    leaf is-client-reflection-disabled {
      xr:xr-xml-map "bgp:IsClientReflectionDisabled";
      type boolean;
      description
        "True if client-to-client reflection is disabled ";
    }
    leaf accepts-legacy-pe-rt-route {
      xr:xr-xml-map "bgp:AcceptsLegacyPE_RTRoute";
      type boolean;
      description "accept-legacy-pe-RT route";
    }
    leaf updgrp-cluster-id {
      xr:xr-xml-map "bgp:UpdgrpClusterID";
      type uint32;
      description
        "Cluster ID (populated ifclient-to-client
        reflectionis disabled)";
    }
    leaf updgrp-cluster-type {
      xr:xr-xml-map "bgp:UpdgrpClusterType";
      type uint8;
      description "Cluster ID type:undefined/number/Ip address";
    }
    leaf orr-group-name {
      xr:xr-xml-map "bgp:OrrGroupName";
      type string;
      description "ORR Group Name";
    }
    leaf orr-group-index {
      xr:xr-xml-map "bgp:OrrGroupIndex";
      type uint32;
      description "ORR Group Index";
    }
    leaf is-orr-root-address-configured {
      xr:xr-xml-map "bgp:IsOrrRootAddressConfigured";
      type boolean;
      description
        "ORR Root address configuredfor the neighbor
        connection";
    }
    leaf should-remove-private-a-ss {
      xr:xr-xml-map "bgp:ShouldRemovePrivateASs";
      type boolean;
      description "Remove private AS numbers";
    }
    leaf should-remove-private-as-ent-path {
      xr:xr-xml-map "bgp:ShouldRemovePrivateASEntPath";
      type boolean;
      description
        "Remove private AS numbersif the entire path
        consistsof private ASes";
    }
    leaf use-next-hop-self {
      xr:xr-xml-map "bgp:UseNextHopSelf";
      type boolean;
      description "Next hop self";
    }
    leaf use-next-hop-unchanged-mpath {
      xr:xr-xml-map "bgp:UseNextHopUnchangedMpath";
      type boolean;
      description "Next-hop-unchanged multipath";
    }
    leaf is-internal-peers {
      xr:xr-xml-map "bgp:IsInternalPeers";
      type boolean;
      description "Internal peers";
    }
    leaf is-common-admin-peers {
      xr:xr-xml-map "bgp:IsCommonAdminPeers";
      type boolean;
      description "Common admin peers";
    }
    leaf is4-byte-as-peer {
      xr:xr-xml-map "bgp:Is4ByteASPeer";
      type boolean;
      description "4-byte AS capable peers";
    }
    leaf is-addpath-capable {
      xr:xr-xml-map "bgp:IsAddpathCapable";
      type boolean;
      description "Add-path capable peers";
    }
    leaf is-send-mcast-attr-enabled {
      xr:xr-xml-map "bgp:IsSendMcastAttrEnabled";
      type boolean;
      description "Send mcast attribute enabled";
    }
    leaf is-aigp-capable {
      xr:xr-xml-map "bgp:IsAIGPCapable";
      type boolean;
      description "AIGP capable peers";
    }
    leaf is-aigp-cost-community-capable {
      xr:xr-xml-map "bgp:IsAIGPCostCommunityCapable";
      type boolean;
      description "Send AIGP cost community to peers";
    }
    leaf is-aigp-med-capable {
      xr:xr-xml-map "bgp:IsAIGP_MEDCapable";
      type boolean;
      description "Send AIGP cost in MED";
    }
    leaf is-llgr-capable {
      xr:xr-xml-map "bgp:IsLLGRCapable";
      type boolean;
      description "Send Long-lived Stale paths";
    }
    leaf is-adv-capable {
      xr:xr-xml-map "bgp:IsAdvCapable";
      type boolean;
      description "Send tranlsated paths";
    }
    leaf is-adv-reorg-capable {
      xr:xr-xml-map "bgp:IsAdvReorgCapable";
      type boolean;
      description "Send Re-orig paths";
    }
    leaf disable-native-advertisement {
      xr:xr-xml-map "bgp:DisableNativeAdvertisement";
      type boolean;
      description "Disable advertising native routes";
    }
    leaf disable-def-vrf-imp-advertisement {
      xr:xr-xml-map "bgp:DisableDefVrfImpAdvertisement";
      type boolean;
      description
        "Disable advertising default VRF  imported routes";
    }
    leaf encapsulation-type {
      xr:xr-xml-map "bgp:EncapsulationType";
      type uint32;
      description "Encapsulation type";
    }
    leaf advertise-rt-type {
      xr:xr-xml-map "bgp:AdvertiseRTType";
      type uint8;
      description "Advertise RT type";
    }
    leaf is-directly-connected-ebgp-v6-peers {
      xr:xr-xml-map "bgp:IsDirectlyConnectedEBGP_V6Peers";
      type boolean;
      description "Directly connected EBGP v6 peers";
    }
    leaf minimum-advertisement-interval {
      xr:xr-xml-map "bgp:MinimumAdvertisementInterval";
      type uint32;
      units "second";
      description "Minimum advertisement interval, secs part";
    }
    leaf minimum-advertisement-interval-msecs {
      xr:xr-xml-map "bgp:MinimumAdvertisementIntervalMsecs";
      type uint32;
      units "millisecond";
      description "Minimum advertisement interval, msecs part";
    }
    leaf local-as {
      xr:xr-xml-map "bgp:LocalAS";
      type uint32;
      description "Local AS number";
    }
    leaf route-policy-out {
      xr:xr-xml-map "bgp:RoutePolicyOut";
      type string;
      description "Outbound route policy name";
    }
    leaf desync-count {
      xr:xr-xml-map "bgp:DesyncCount";
      type uint32;
      description
        "Number of times the update has been
        desynchronized";
    }
    leaf subgrp-merge-count {
      xr:xr-xml-map "bgp:SubgrpMergeCount";
      type uint32;
      description "Number of times sub-groups have been merged";
    }
    leaf refresh-subgrp-count {
      xr:xr-xml-map "bgp:RefreshSubgrpCount";
      type uint32;
      description "Current count of refresh subgroups";
    }
    leaf updates-formatted {
      xr:xr-xml-map "bgp:UpdatesFormatted";
      type uint32;
      description "Number of updates formatted";
    }
    leaf updates-replicated {
      xr:xr-xml-map "bgp:UpdatesReplicated";
      type uint32;
      description "No. of updates replicated";
    }
    leaf local-as-replace-as {
      xr:xr-xml-map "bgp:LocalASReplaceAS";
      type boolean;
      description "Local AS Replace-AS option";
    }
    leaf as-override {
      xr:xr-xml-map "bgp:ASOverride";
      type boolean;
      description "AS Override option";
    }
    leaf soo {
      xr:xr-xml-map "bgp:SOO";
      type boolean;
      description "Site-of-origin option";
    }
    leaf soo-value {
      xr:xr-xml-map "bgp:SOOValue";
      type yang:hex-string;
      description "Site-of-origin value";
    }
    leaf split-horizon {
      xr:xr-xml-map "bgp:SplitHorizon";
      type boolean;
      description "Split horizon check";
    }
    leaf is-labeled-afi-enabled {
      xr:xr-xml-map "bgp:IsLabeledAFIEnabled";
      type boolean;
      description "Update group has labeled AFI enabled";
    }
    leaf is-unlabeled-afi-enabled {
      xr:xr-xml-map "bgp:IsUnlabeledAFIEnabled";
      type boolean;
      description "Update group has unlabeled AFI enabled";
    }
    leaf remote-as {
      xr:xr-xml-map "bgp:RemoteAS";
      type uint32;
      description "Remote AS number";
    }
    leaf is-adv-perm-net-capable {
      xr:xr-xml-map "bgp:IsAdvPermNetCapable";
      type boolean;
      description "Advertise Permanent-Net capable peers";
    }
    leaf should-send-gshut-community {
      xr:xr-xml-map "bgp:ShouldSendGshutCommunity";
      type boolean;
      description "Send GSHUT community";
    }
    leaf gshut-active {
      xr:xr-xml-map "bgp:GshutActive";
      type boolean;
      description "GSHUT active";
    }
    leaf gshut-locpref-set {
      xr:xr-xml-map "bgp:GshutLocprefSet";
      type boolean;
      description "GSHUT local preference set";
    }
    leaf gshut-locpref {
      xr:xr-xml-map "bgp:GshutLocpref";
      type uint32;
      description "GSHUT local preference";
    }
    leaf gshut-prepends {
      xr:xr-xml-map "bgp:GshutPrepends";
      type uint8;
      description "GSHUT AS prepends";
    }

    list neighbor {
      description
        "Neighbors in this update group which are not in
        any sub-group";
      uses BGP-ADDRTYPE;
    }

    list update-sub-group {
      description "Update sub-group list";
      uses BGP-UPD-SUBGRP;
    }
  }

  grouping BGP-STATIC-ROUTES-BAG {
    description "BGP static routes information";

    container sourced-prefix {
      description "Prefix length";
      uses BGP-PREFIXTYPE;
    }
    leaf af-name {
      xr:xr-xml-map "bgp:AFName";
      type Bgp-afi;
      description "Address family identifier";
    }
    leaf is-backdoor {
      xr:xr-xml-map "bgp:IsBackdoor";
      type boolean;
      description "TRUE if net is a backdoor route";
    }
  }

  grouping BGP-GLOBAL-PROCESS-INFO-AF-VRF {
    description "BGP GLOBAL PROCESS INFO AF VRF";
    leaf table-is-active {
      xr:xr-xml-map "bgp:TableIsActive";
      type boolean;
      description "Table state is active";
    }
    leaf table-id {
      xr:xr-xml-map "bgp:TableId";
      type uint32;
      description "Table ID";
    }
    leaf table-version {
      xr:xr-xml-map "bgp:TableVersion";
      type uint32;
      description "Table version";
    }
    leaf rd-version {
      xr:xr-xml-map "bgp:RDVersion";
      type uint32;
      description "RD version";
    }
    leaf rib-version {
      xr:xr-xml-map "bgp:RIBVersion";
      type uint32;
      description "Table version synced to RIB";
    }
    leaf nsr-conv-version {
      xr:xr-xml-map "bgp:NsrConvVersion";
      type uint32;
      description "NSR conv version";
    }
    leaf nsr-is-conv {
      xr:xr-xml-map "bgp:NsrIsConv";
      type boolean;
      description "NSR is converged";
    }
    leaf client-reflection-enabled {
      xr:xr-xml-map "bgp:ClientReflectionEnabled";
      type boolean;
      description "Client reflection enabled";
    }
    leaf dampening-enabled {
      xr:xr-xml-map "bgp:DampeningEnabled";
      type boolean;
      description "Dampening enabled";
    }
    leaf ebgp-distance {
      xr:xr-xml-map "bgp:EBGPDistance";
      type uint16;
      description "Distance for eBGP routes (external)";
    }
    leaf ibgp-distance {
      xr:xr-xml-map "bgp:IBGPDistance";
      type uint16;
      description "Distance for iBGP routes (internal)";
    }
    leaf aggregates-distance {
      xr:xr-xml-map "bgp:AggregatesDistance";
      type uint16;
      description "Dist for aggregate routes (local)";
    }
    leaf dynamic-med-enabled {
      xr:xr-xml-map "bgp:DynamicMEDEnabled";
      type boolean;
      description "Update generation enabled for MED change";
    }
    leaf dynamic-med-interval {
      xr:xr-xml-map "bgp:DynamicMEDInterval";
      type uint16;
      units "minute";
      description
        "Delay in update generation after a MED change
        (in minutes)";
    }
    leaf dynamic-med-timer-running {
      xr:xr-xml-map "bgp:DynamicMEDTimerRunning";
      type boolean;
      description "Dynamic MED timer running";
    }
    leaf dynamic-med-timer-value {
      xr:xr-xml-map "bgp:DynamicMEDTimerValue";
      type uint16;
      units "second";
      description
        "Dynamic MED timer value (in seconds) left on the
        timer";
    }
    leaf dynamic-med-periodic-timer-running {
      xr:xr-xml-map "bgp:DynamicMEDPeriodicTimerRunning";
      type boolean;
      description "Dynamic MED periodic timer running";
    }
    leaf dynamic-med-periodic-timer-value {
      xr:xr-xml-map "bgp:DynamicMEDPeriodicTimerValue";
      type uint16;
      units "second";
      description
        "Dynamic MED periodic timer value (in seconds)
        left on the timer";
    }
    leaf rib-has-converged {
      xr:xr-xml-map "bgp:RIBHasConverged";
      type boolean;
      description "Received convergence notification from RIB";
    }
    leaf rib-convergence-version {
      xr:xr-xml-map "bgp:RIBConvergenceVersion";
      type uint32;
      description "Last convergence version received from RIB";
    }
    leaf is-rib-table-full {
      xr:xr-xml-map "bgp:IsRIBTableFull";
      type boolean;
      description "Indicates if RIB table is in prefix-limit state";
    }
    leaf rib-table-full-version {
      xr:xr-xml-map "bgp:RIBTableFullVersion";
      type uint32;
      description
        "Version when RIB table became full (from
        non-full)";
    }
    leaf nexthop-resolution-minimum-prefix-length-configured {
      xr:xr-xml-map "bgp:NexthopResolutionMinimumPrefixLengthConfig"+
        "ured";
      type boolean;
      description
        "Is nexthop resoultion minimum prefix-length
        configured ?";
    }
    leaf nexthop-resolution-minimum-prefix-length {
      xr:xr-xml-map "bgp:NexthopResolutionMinimumPrefixLength";
      type uint32;
      description "Nexthop resoultion minimum prefix-length";
    }
    leaf selective-ebgp-multipath-enabled {
      xr:xr-xml-map "bgp:SelectiveEBGPMultipathEnabled";
      type boolean;
      description "Selective eBGP multipath isenabled";
    }
    leaf selective-ibgp-multipath-enabled {
      xr:xr-xml-map "bgp:SelectiveIBGPMultipathEnabled";
      type boolean;
      description "Selective iBGP multipath isenabled";
    }
    leaf selective-eibgp-multipath-enabled {
      xr:xr-xml-map "bgp:SelectiveEIBGPMultipathEnabled";
      type boolean;
      description "Selective eiBGP multipath isenabled";
    }
    leaf rib-acked-table-version {
      xr:xr-xml-map "bgp:RIBAckedTableVersion";
      type uint32;
      description "Table version acked by RIB";
    }
  }

  grouping BGP-GLOBAL-PROCESS-INFO-AF-GBL {
    description "BGP GLOBAL PROCESS INFO AF GBL";

    container rib-install {
      description "RIB install info";
      uses BGP-RIB-INSTALL-TIME-INFO;
    }
    leaf scanner-period {
      xr:xr-xml-map "bgp:ScannerPeriod";
      type uint16;
      units "second";
      description
        "Period (in seconds) of address-family scanner
        runs";
    }
    leaf nh-tunnel-version {
      xr:xr-xml-map "bgp:NHTunnelVersion";
      type uint32;
      description "NH Tunnel Version";
    }
    leaf scan-prefixes {
      xr:xr-xml-map "bgp:ScanPrefixes";
      type uint32;
      description "Total prefixes of address-family scanned";
    }
    leaf scan-segment-prefixes {
      xr:xr-xml-map "bgp:ScanSegmentPrefixes";
      type uint32;
      description
        "Number of prefixes scanned in a segment of
        address-family";
    }
    leaf scan-segments {
      xr:xr-xml-map "bgp:ScanSegments";
      type uint8;
      description
        "Number of segments to scan all prefixes of
        address-family";
    }
    leaf inter-as-install-enabled {
      xr:xr-xml-map "bgp:InterASInstallEnabled";
      type boolean;
      description "Is inter-AS install to pim on ASBR enabled";
    }
    leaf global-mcast-enabled {
      xr:xr-xml-map "bgp:GlobalMcastEnabled";
      type boolean;
      description "Is global table mcast enabled";
    }
    leaf segmented-mcast-enabled {
      xr:xr-xml-map "bgp:SegmentedMcastEnabled";
      type boolean;
      description "Is segmented mcast enabled";
    }
    leaf gblafrpki-disable {
      xr:xr-xml-map "bgp:GBLAFRPKIDisable";
      type boolean;
      description "Prefix validation disabled";
    }
    leaf gblafrpki-use-validity {
      xr:xr-xml-map "bgp:GBLAFRPKIUseValidity";
      type boolean;
      description "Prefix v. use validity";
    }
    leaf gblafrpki-allow-invalid {
      xr:xr-xml-map "bgp:GBLAFRPKIAllowInvalid";
      type boolean;
      description "Prefix v. allow invalid";
    }
    leaf gblafrpki-signal-ibgp {
      xr:xr-xml-map "bgp:GBLAFRPKISignalIBGP";
      type boolean;
      description "Prefix v. signal ibgp";
    }
    leaf update-wait-install-enabled {
      xr:xr-xml-map "bgp:UpdateWaitInstallEnabled";
      type boolean;
      description "Update wait-install enabled";
    }
    leaf rib-ack-requests {
      xr:xr-xml-map "bgp:RIBAckRequests";
      type uint32;
      description "Counter for RIB ack requests";
    }
    leaf rib-acks-received {
      xr:xr-xml-map "bgp:RIBAcksReceived";
      type uint32;
      description "Counter for RIB ack received";
    }
    leaf rib-slow-acks {
      xr:xr-xml-map "bgp:RIBSlowAcks";
      type uint32;
      description "Counter for slow RIB acks";
    }
    leaf is-perm-net-cfg {
      xr:xr-xml-map "bgp:IsPermNetCfg";
      type boolean;
      description "Permanent Network Enabled";
    }
    leaf perm-net-del-count {
      xr:xr-xml-map "bgp:PermNetDelCount";
      type uint16;
      description "Count of removed perm paths";
    }
    leaf perm-net-stale-del-count {
      xr:xr-xml-map "bgp:PermNetStaleDelCount";
      type uint16;
      description "Count of stale perm paths";
    }
    leaf perm-net-stale-mark-count {
      xr:xr-xml-map "bgp:PermNetStaleMarkCount";
      type uint16;
      description "Count of stale marked perm paths";
    }
    leaf perm-net-insert-count {
      xr:xr-xml-map "bgp:PermNetInsertCount";
      type uint16;
      description "Count of inserted perm paths";
    }
    leaf perm-net-existing-count {
      xr:xr-xml-map "bgp:PermNetExistingCount";
      type uint16;
      description "Count of existing perm paths";
    }
    leaf perm-net-rpl-query-count {
      xr:xr-xml-map "bgp:PermNetRplQueryCount";
      type uint16;
      description "Count of perm nets given by RPL";
    }
    leaf perm-net-rpl-process-count {
      xr:xr-xml-map "bgp:PermNetRplProcessCount";
      type uint16;
      description "Count of perm nets processed in RPL";
    }
    leaf perm-nbr-count {
      xr:xr-xml-map "bgp:PermNbrCount";
      type uint16;
      description "Count of neighbors configured with perm net";
    }
    leaf rib-perm-pelem-not-found-count {
      xr:xr-xml-map "bgp:RibPermPelemNotFoundCount";
      type uint16;
      description "";
    }
    leaf rib-perm-path-not-found-count {
      xr:xr-xml-map "bgp:RibPermPathNotFoundCount";
      type uint16;
      description "";
    }
    leaf rib-perm-pelem-found-count {
      xr:xr-xml-map "bgp:RibPermPelemFoundCount";
      type uint16;
      description "";
    }
    leaf rib-reg-path-found-count {
      xr:xr-xml-map "bgp:RibRegPathFoundCount";
      type uint16;
      description "";
    }
    leaf rib-perm-path-found-count {
      xr:xr-xml-map "bgp:RibPermPathFoundCount";
      type uint16;
      description "";
    }
    leaf perm-pelem-free-count {
      xr:xr-xml-map "bgp:PermPelemFreeCount";
      type uint16;
      description "Count of freed perm pelems";
    }
    leaf perm-path-refresh-count {
      xr:xr-xml-map "bgp:PermPathRefreshCount";
      type uint16;
      description "Count of perm paths refreshed";
    }
    leaf perm-pelem-bump-count {
      xr:xr-xml-map "bgp:PermPelemBumpCount";
      type uint16;
      description "Count of bumped perm pelems";
    }
    leaf perm-pelem-all-bump-count {
      xr:xr-xml-map "bgp:PermPelemAllBumpCount";
      type uint16;
      description "Count of bumped perm pelems";
    }
    leaf-list syncgrp-version {
      xr:xr-xml-map "bgp:SyncgrpVersion";
      type uint32;
      max-elements "2";
      description "Sync-group Version";
    }
  }

  grouping BGP-GLOBAL-PROCESS-INFO-AF-BAG {
    description
      "BGP address family specific information common to
      all BGP processes";

    container global {
      description "Global information";
      uses BGP-GLOBAL-PROCESS-INFO-AF-GBL;
    }

    container vrf {
      description "VRF information";
      uses BGP-GLOBAL-PROCESS-INFO-AF-VRF;
    }
    leaf vrf-name {
      xr:xr-xml-map "bgp:VRFName";
      type string;
      description "Name of the VRF";
    }
    leaf af-name {
      xr:xr-xml-map "bgp:AFName";
      type Bgp-afi;
      description "Address family id";
    }
    leaf is-nsr-enabled {
      xr:xr-xml-map "bgp:IsNsrEnabled";
      type boolean;
      description "Non-stop routing enabled";
    }
  }

  grouping BGP-RPC-SET-BAG {
    description "BGP RPC SET BAG";
    leaf next-hop-xr {
      xr:xr-xml-map "bgp:next-hop-xr";
      type uint32;
      description "Number of multipath next-hops";
    }
    leaf label {
      xr:xr-xml-map "bgp:Label";
      type uint32;
      description "Label assigned to the RPCnext-hop set";
    }
    leaf ref-count {
      xr:xr-xml-map "bgp:RefCount";
      type uint32;
      description "Refcount";
    }

    list next-hop {
      description "List of multipath next-hops";
      uses BGP-ADDRTYPE;
    }
  }

  grouping BGP-PERF-PROCESS-AF-VRF {
    description "BGP PERF PROCESS AF VRF";

    container time-rib-coverged {
      description "Time last RIB ack was sent ";
      uses BGP-TIMESPEC;
    }

    container time-rib-down {
      description
        "Time last RIB down wassent. This field is
        deprecated";
      uses BGP-TIMESPEC;
    }

    container first-rib-table-full-timestamp {
      description
        "Timestamp when RIB table was full for the first
        time";
      uses BGP-TIMESPEC;
    }

    container last-rib-table-full-timestamp {
      description
        "Timestamp when RIB table was full for the last
        time";
      uses BGP-TIMESPEC;
    }

    container first-rib-table-has-space-timestamp {
      description
        "Timestamp when RIB table had space for the first
        time";
      uses BGP-TIMESPEC;
    }

    container last-rib-table-has-space-timestamp {
      description
        "Timestamp when RIB table had space for the last
        time";
      uses BGP-TIMESPEC;
    }

    container time-label-retain {
      description "Time last label retentiontriggered ";
      uses BGP-TIMESPEC;
    }
    leaf update-generation-calls {
      xr:xr-xml-map "bgp:UpdateGenerationCalls";
      type uint32;
      description "No. of calls to update generation function";
    }
    leaf update-generation-prefixes-count {
      xr:xr-xml-map "bgp:UpdateGenerationPrefixesCount";
      type uint32;
      description "No. of prefixes updates generated for";
    }
    leaf update-generation-be-prefixes-count {
      xr:xr-xml-map "bgp:UpdateGenerationBePrefixesCount";
      type uint32;
      description "No. of be prefixes updates generated for";
    }
    leaf update-generation-messages-count {
      xr:xr-xml-map "bgp:UpdateGenerationMessagesCount";
      type uint32;
      description "No. of update messages generated";
    }
    leaf update-generation-time {
      xr:xr-xml-map "bgp:UpdateGenerationTime";
      type uint32;
      units "millisecond";
      description "Time spent generating updates (milliseconds)";
    }
    leaf rib-update-calls {
      xr:xr-xml-map "bgp:RIBUpdateCalls";
      type uint32;
      description "No. of calls to RIB update function";
    }
    leaf rib-update-time {
      xr:xr-xml-map "bgp:RIBUpdateTime";
      type uint32;
      units "millisecond";
      description "Time spent sending RIB updates (milliseconds)";
    }
    leaf prefixes-sent-to-rib {
      xr:xr-xml-map "bgp:PrefixesSentToRIB";
      type uint32;
      description "No. of prefixes sent to RIB";
    }
    leaf prefixes-resent-to-rib {
      xr:xr-xml-map "bgp:PrefixesResentToRIB";
      type uint32;
      description "No. of prefixes re-sent to RIB";
    }
    leaf prefixes-removed-from-rib {
      xr:xr-xml-map "bgp:PrefixesRemovedFromRIB";
      type uint32;
      description "No. of prefixes withdrawn from RIB";
    }
    leaf attributes-sent-to-rib {
      xr:xr-xml-map "bgp:AttributesSentToRIB";
      type uint32;
      description "No. of attributes sent to RIB";
    }
    leaf attributes-removed-from-rib {
      xr:xr-xml-map "bgp:AttributesRemovedFromRIB";
      type uint32;
      description "No. of attributes withdrawn from RIB";
    }
    leaf attributes-recover-from-rib {
      xr:xr-xml-map "bgp:AttributesRecoverFromRIB";
      type uint32;
      description "No. of attributes recovered from RIB";
    }
    leaf scanner-runs {
      xr:xr-xml-map "bgp:ScannerRuns";
      type uint32;
      description "# of times scanner has run";
    }
    leaf scanner-time {
      xr:xr-xml-map "bgp:ScannerTime";
      type uint32;
      units "millisecond";
      description "Time spent running scanner (milliseconds)";
    }
    leaf rib-tbl-del-calls {
      xr:xr-xml-map "bgp:RibTblDelCalls";
      type uint32;
      description
        "No. of rib update skipped on account of table
        delete";
    }
    leaf rib-tbl-invalid-calls {
      xr:xr-xml-map "bgp:RibTblInvalidCalls";
      type uint32;
      description "No. of  rib update skipped due to table invalid";
    }
    leaf rib-tbl-skip-calls {
      xr:xr-xml-map "bgp:RibTblSkipCalls";
      type uint32;
      description "No. of rib update skipped";
    }
    leaf rib-tbl-local-label {
      xr:xr-xml-map "bgp:RibTblLocalLabel";
      type uint32;
      description
        "No. of rib update skipped. due to no local label";
    }
    leaf rib-tbl-retry {
      xr:xr-xml-map "bgp:RibTblRetry";
      type uint32;
      description "No. of table rib retires.";
    }
    leaf time-last-update-sent {
      xr:xr-xml-map "bgp:TimeLastUpdateSent";
      type uint32;
      units "second";
      description
        "Time last update was sent (seconds since Jan 1
        1970)";
    }
    leaf is-rib-table-full {
      xr:xr-xml-map "bgp:IsRIBTableFull";
      type boolean;
      description "Indicates if RIB table is in prefix-limit state";
    }
    leaf rib-table-full-version {
      xr:xr-xml-map "bgp:RIBTableFullVersion";
      type uint32;
      description
        "Version when RIB table became full (from
        non-full)";
    }
    leaf first-rib-table-full-version {
      xr:xr-xml-map "bgp:FirstRIBTableFullVersion";
      type uint32;
      description
        "Version when RIB table was full for the first
        time";
    }
    leaf last-rib-table-full-version {
      xr:xr-xml-map "bgp:LastRIBTableFullVersion";
      type uint32;
      description
        "Version when RIB table was full for the last
        time";
    }
    leaf last-rib-table-full-age {
      xr:xr-xml-map "bgp:LastRIBTableFullAge";
      type uint32;
      units "second";
      description
        "Time since RIB table was full for the last time
        (in seconds)";
    }
    leaf first-rib-table-has-space-version {
      xr:xr-xml-map "bgp:FirstRIBTableHasSpaceVersion";
      type uint32;
      description
        "Version when RIB table had space for the first
        time";
    }
    leaf last-rib-table-has-space-version {
      xr:xr-xml-map "bgp:LastRIBTableHasSpaceVersion";
      type uint32;
      description
        "Version when RIB table had space for the last
        time";
    }
    leaf last-rib-table-has-space-age {
      xr:xr-xml-map "bgp:LastRIBTableHasSpaceAge";
      type uint32;
      units "second";
      description
        "Times since RIB table had space for the last
        time (in seconds)";
    }
    leaf rib-trigger {
      xr:xr-xml-map "bgp:RibTrigger";
      type boolean;
      description "Rib trigger enabled";
    }
    leaf vrf-flags {
      xr:xr-xml-map "bgp:VrfFlags";
      type uint32;
      description "VRF flags for debug display";
    }
    leaf label-calls {
      xr:xr-xml-map "bgp:LabelCalls";
      type uint32;
      description
        "No. of calls to label allocation processing
        function";
    }
    leaf label-time {
      xr:xr-xml-map "bgp:LabelTime";
      type uint32;
      units "millisecond";
      description
        "Time spent running label processing
        (milliseconds)";
    }
    leaf label-rewrite-count {
      xr:xr-xml-map "bgp:LabelRewriteCount";
      type uint32;
      description "Number of label rewrites created";
    }
    leaf label-release-count {
      xr:xr-xml-map "bgp:LabelReleaseCount";
      type uint32;
      description "Number of labels released";
    }
    leaf label-added-count {
      xr:xr-xml-map "bgp:LabelAddedCount";
      type uint32;
      description "Number of labels requested";
    }
    leaf import-calls {
      xr:xr-xml-map "bgp:ImportCalls";
      type uint32;
      description "Number of calls to import processing function";
    }
    leaf import-time {
      xr:xr-xml-map "bgp:ImportTime";
      type uint32;
      units "millisecond";
      description
        "Time spent in import processing (milliseconds)
        Note time accounted against source nets.";
    }
    leaf import-src-net-processed-count {
      xr:xr-xml-map "bgp:ImportSrcNetProcessedCount";
      type uint32;
      description "Number of source nets processed";
    }
    leaf import-dest-net-processed-count {
      xr:xr-xml-map "bgp:ImportDestNetProcessedCount";
      type uint32;
      description "Number of destination nets processed";
    }
    leaf import-added-path-count {
      xr:xr-xml-map "bgp:ImportAddedPathCount";
      type uint32;
      description "Number of imported paths added";
    }
    leaf import-removed-path-count {
      xr:xr-xml-map "bgp:ImportRemovedPathCount";
      type uint32;
      description "Number of imported paths removed";
    }
    leaf import-replaced-path-count {
      xr:xr-xml-map "bgp:ImportReplacedPathCount";
      type uint32;
      description "Number of imported paths ";
    }
    leaf update-group-count {
      xr:xr-xml-map "bgp:UpdateGroupCount";
      type uint32;
      description "No. of update group";
    }
    leaf subgroup-count {
      xr:xr-xml-map "bgp:SubgroupCount";
      type uint32;
      description "No. of update subgroup";
    }
  }

  grouping BGP-PERF-PROCESS-AF-GBL {
    description "BGP PERF PROCESS AF GBL";
    leaf has-converged {
      xr:xr-xml-map "bgp:HasConverged";
      type boolean;
      description "TRUE if process has converged";
    }
    leaf total-pim-install {
      xr:xr-xml-map "bgp:TotalPimInstall";
      type uint32;
      description "Total number of install to PIM";
    }
    leaf total-pim-callbacks {
      xr:xr-xml-map "bgp:TotalPimCallbacks";
      type uint32;
      description "Total number of PIM callbacks";
    }
    leaf total-pim-callback-batch {
      xr:xr-xml-map "bgp:TotalPimCallbackBatch";
      type uint32;
      description "Total number of Pim callback batches";
    }
    leaf-list mode-enter-time {
      xr:xr-xml-map "bgp:ModeEnterTime";
      type uint32;
      units "second";
      max-elements "7";
      description
        "Time that each mode was entered (seconds since
        Jan 1 1970)";
    }
    leaf-list total-pim-install-add {
      xr:xr-xml-map "bgp:TotalPimInstallAdd";
      type uint32;
      max-elements "7";
      description "Total number of install to PIM for add";
    }
    leaf-list total-pim-install-del {
      xr:xr-xml-map "bgp:TotalPimInstallDel";
      type uint32;
      max-elements "7";
      description "Total number of install to PIM for del";
    }
    leaf-list total-pim-callback-add {
      xr:xr-xml-map "bgp:TotalPimCallbackAdd";
      type uint32;
      max-elements "7";
      description "Total number of Pim callbacks for add";
    }
    leaf-list total-pim-callback-del {
      xr:xr-xml-map "bgp:TotalPimCallbackDel";
      type uint32;
      max-elements "7";
      description "Total number of Pim callbacks for del";
    }
    leaf-list total-pim-callback-add-local {
      xr:xr-xml-map "bgp:TotalPimCallbackAddLocal";
      type uint32;
      max-elements "7";
      description "Total number of Pim callbacks for local add";
    }
    leaf-list total-pim-callback-del-local {
      xr:xr-xml-map "bgp:TotalPimCallbackDelLocal";
      type uint32;
      max-elements "7";
      description "Total number of Pim callbacks for Local del";
    }
  }

  grouping BGP-PERF-PROCESS-AF {
    description "BGP PERF PROCESS AF";

    container global {
      description "Global information";
      uses BGP-PERF-PROCESS-AF-GBL;
    }

    container vrf {
      description "VRF information";
      uses BGP-PERF-PROCESS-AF-VRF;
    }
  }

  grouping BGP-PROCESS-INFO-AF-VRF {
    description "BGP PROCESS INFO AF VRF";
    leaf network-entry-count {
      xr:xr-xml-map "bgp:NetworkEntryCount";
      type uint32;
      description "Number of network entries";
    }
    leaf paths-count {
      xr:xr-xml-map "bgp:PathsCount";
      type uint32;
      description "Number of paths";
    }
    leaf imported-paths {
      xr:xr-xml-map "bgp:ImportedPaths";
      type uint32;
      description "Number of imported paths";
    }
    leaf local-paths {
      xr:xr-xml-map "bgp:LocalPaths";
      type uint32;
      description "Number of local paths";
    }
    leaf path-elems-count {
      xr:xr-xml-map "bgp:PathElemsCount";
      type uint32;
      description "Number of path elems";
    }
    leaf path-memory {
      xr:xr-xml-map "bgp:PathMemory";
      type uint32;
      units "byte";
      description "Memory (in bytes) used by path data";
    }
    leaf imported-path-memory {
      xr:xr-xml-map "bgp:ImportedPathMemory";
      type uint32;
      units "byte";
      description "Memory (in bytes) used by imported paths";
    }
    leaf local-path-memory {
      xr:xr-xml-map "bgp:LocalPathMemory";
      type uint32;
      units "byte";
      description "Memory (in bytes) used by local paths";
    }
    leaf prefix-memory {
      xr:xr-xml-map "bgp:PrefixMemory";
      type uint32;
      units "byte";
      description "Memory (in bytes) used by prefix data";
    }
    leaf path-elem-memory {
      xr:xr-xml-map "bgp:PathElemMemory";
      type uint32;
      units "byte";
      description "Memory (in bytes) used by pathelem data";
    }
    leaf received-path-count {
      xr:xr-xml-map "bgp:ReceivedPathCount";
      type uint32;
      description
        "Number of (unused) received paths for inbound
        soft reconfiguration";
    }
    leaf history-path-count {
      xr:xr-xml-map "bgp:HistoryPathCount";
      type uint32;
      description "Number of history paths (for dampening)";
    }
    leaf damped-path-count {
      xr:xr-xml-map "bgp:DampedPathCount";
      type uint32;
      description "Number of dampened paths";
    }
    leaf malloced-prefix-count {
      xr:xr-xml-map "bgp:MallocedPrefixCount";
      type uint32;
      description "Activity: Number of prefixes malloced";
    }
    leaf freed-prefix-count {
      xr:xr-xml-map "bgp:FreedPrefixCount";
      type uint32;
      description "Activity: Number of prefixes freed";
    }
    leaf malloced-path-count {
      xr:xr-xml-map "bgp:MallocedPathCount";
      type uint32;
      description "Activity: Number of paths malloced";
    }
    leaf freed-path-count {
      xr:xr-xml-map "bgp:FreedPathCount";
      type uint32;
      description "Activity: Number of paths freed";
    }
    leaf malloced-path-elem-count {
      xr:xr-xml-map "bgp:MallocedPathElemCount";
      type uint32;
      description "Activity: Number of path elems malloced";
    }
    leaf freed-path-elem-count {
      xr:xr-xml-map "bgp:FreedPathElemCount";
      type uint32;
      description "Activity: Number of pathelems freed";
    }
    leaf any-ebgp-neighbor-missing-policy {
      xr:xr-xml-map "bgp:AnyEBGPNeighborMissingPolicy";
      type boolean;
      description
        "Is there any neighbor which is missing either
        inbound or outbound or both routing policy for
        this address family?";
    }
    leaf attribute-download {
      xr:xr-xml-map "bgp:AttributeDownload";
      type boolean;
      description "Attribute download is ";
    }
    leaf route-target-download {
      xr:xr-xml-map "bgp:RouteTargetDownload";
      type boolean;
      description "Route Target download is enabled";
    }
    leaf add-path-install-enable {
      xr:xr-xml-map "bgp:AddPathInstallEnable";
      type boolean;
      description "Additional paths installation is enabled";
    }
    leaf add-path-install-disable {
      xr:xr-xml-map "bgp:AddPathInstallDisable";
      type boolean;
      description "Additional paths installation is disabled";
    }
    leaf best-external {
      xr:xr-xml-map "bgp:BestExternal";
      type boolean;
      description "Best External is enabled";
    }
    leaf best-external-disable {
      xr:xr-xml-map "bgp:BestExternalDisable";
      type boolean;
      description "Best External is enabled";
    }
    leaf label-retain {
      xr:xr-xml-map "bgp:LabelRetain";
      type boolean;
      description "Label retention is enabled";
    }
    leaf label-retainvalue {
      xr:xr-xml-map "bgp:LabelRetainValue";
      type uint32;
      description "Label retention value enabled";
    }
    leaf tbl-bitf-size {
      xr:xr-xml-map "bgp:TblBitfSize";
      type uint16;
      description "Bitfield size on table";
    }
    leaf tbl-chunk-bitf-size {
      xr:xr-xml-map "bgp:TblChunkBitfSize";
      type uint16;
      description "Chunk Bitfield size on table";
    }
    leaf is-route-reflector {
      xr:xr-xml-map "bgp:IsRouteReflector";
      type boolean;
      description "Router is an RR for this AF";
    }
    leaf asbr {
      xr:xr-xml-map "bgp:ASBR";
      type boolean;
      description "Router is an ASBR for this AF";
    }
    leaf retain-rt-all {
      xr:xr-xml-map "bgp:RetainRTAll";
      type boolean;
      description "Retain-RT-All enabled";
    }
    leaf ibgp-nexthop-self-count {
      xr:xr-xml-map "bgp:IBGPNexthopSelfCount";
      type uint32;
      description "Number of iBGP sessions configured with nh-self";
    }
  }

  grouping BGP-RIB-INSTALL-TIME-INFO {
    description "BGP RIB INSTALL TIME INFO";

    container update-time {
      description "RIB update time";
      uses BGP-TIMESPEC;
    }

    container install-time {
      description "RIB install time";
      uses BGP-TIMESPEC;
    }
    leaf installed-count {
      xr:xr-xml-map "bgp:InstalledCount";
      type uint32;
      description "Installed routes";
    }
    leaf modified-count {
      xr:xr-xml-map "bgp:ModifiedCount";
      type uint32;
      description "Modified routes";
    }
    leaf withdrawn-count {
      xr:xr-xml-map "bgp:WithdrawnCount";
      type uint32;
      description "Withdrawn routes";
    }
    leaf start-version {
      xr:xr-xml-map "bgp:StartVersion";
      type uint32;
      description "Start version";
    }
    leaf target-version {
      xr:xr-xml-map "bgp:TargetVersion";
      type uint32;
      description "Target version";
    }
  }

  grouping BGP-THREAD-TRIGGER-INFO-STAT {
    description "BGP THREAD TRIGGER INFO STAT";

    container trigger-time-spec {
      description "trigger time spec";
      uses BGP-TIMESPEC;
    }
    leaf trigger-version {
      xr:xr-xml-map "bgp:TriggerVersion";
      type uint32;
      description "TriggerVersion";
    }
    leaf trigger-table-version {
      xr:xr-xml-map "bgp:TriggerTableVersion";
      type uint32;
      description "TriggerTableVersion";
    }
  }

  grouping BGP-THREAD-TRIGGER-INFO {
    description "BGP THREAD TRIGGER INFO";
    leaf triggers {
      xr:xr-xml-map "bgp:Triggers";
      type uint32;
      description "Triggers";
    }

    list statistic {
      description "statistic";
      uses BGP-THREAD-TRIGGER-INFO-STAT;
    }
  }

  grouping BGP-PROCESS-INFO-AF-GBL {
    description "BGP PROCESS INFO AF GBL";

    container version-wrap-time-spec {
      description "Version Wrap timestamp";
      uses BGP-TIMESPEC;
    }

    container version-wrap-start-time-spec {
      description "Version Wrap handle start timestamp";
      uses BGP-TIMESPEC;
    }

    container version-wrap-done-time-spec {
      description "Version Wrap handle Done timestamp";
      uses BGP-TIMESPEC;
    }

    container trigger-rib {
      description "Trigger RIB";
      uses BGP-THREAD-TRIGGER-INFO;
    }

    container trigger-import {
      description "Trigger import";
      uses BGP-THREAD-TRIGGER-INFO;
    }

    container trigger-update {
      description "Trigger update";
      uses BGP-THREAD-TRIGGER-INFO;
    }

    container trigger-label {
      description "Trigger label";
      uses BGP-THREAD-TRIGGER-INFO;
    }

    container rib-install {
      description "RIB install info";
      uses BGP-RIB-INSTALL-TIME-INFO;
    }
    leaf router-state {
      xr:xr-xml-map "bgp:RouterState";
      type Bgp-rtr-state;
      description "Router state";
    }
    leaf table-version {
      xr:xr-xml-map "bgp:TableVersion";
      type uint32;
      description "BGP table version";
    }
    leaf version-wrapped {
      xr:xr-xml-map "bgp:VersionWrapped";
      type uint32;
      description "Number of times Version Wrap happened";
    }
    leaf version-wrapped-tid {
      xr:xr-xml-map "bgp:VersionWrappedTid";
      type uint32;
      description "Version Wrapped trigger tid";
    }
    leaf max-active-pelem-version {
      xr:xr-xml-map "bgp:MaxActivePelemVersion";
      type uint32;
      description "Maximum Active Pelem Version";
    }
    leaf merged-table-version {
      xr:xr-xml-map "bgp:MergedTableVersion";
      type uint32;
      description "Merged Table Version";
    }
    leaf route-download-go-active-done-pending {
      xr:xr-xml-map "bgp:RouteDownloadGoActiveDonePending";
      type uint32;
      description "Route Download Go Active Done Pending";
    }
    leaf rib-brib-received-version {
      xr:xr-xml-map "bgp:RibBribReceivedVersion";
      type uint32;
      description "Version received from ";
    }
    leaf table-brib-version {
      xr:xr-xml-map "bgp:TableBRIBVersion";
      type uint32;
      description "Version sent to RIB/bRIB";
    }
    leaf label-version {
      xr:xr-xml-map "bgp:LabelVersion";
      type uint32;
      description "Version updated by label thread";
    }
    leaf import-version {
      xr:xr-xml-map "bgp:ImportVersion";
      type uint32;
      description "Version updated by import thread";
    }
    leaf standby-version {
      xr:xr-xml-map "bgp:StandbyVersion";
      type uint32;
      description "Version updated by sync thread";
    }
    leaf send-version {
      xr:xr-xml-map "bgp:SendVersion";
      type uint32;
      description "Version for sending updates to peers";
    }
    leaf num-init-sync-pfx {
      xr:xr-xml-map "bgp:NumInitSyncPfx";
      type uint32;
      description "Num of prefix synced during Initsync";
    }
    leaf local-networks-num {
      xr:xr-xml-map "bgp:LocalNetworksNum";
      type uint32;
      description "Total local networks";
    }
    leaf local-networks-memory {
      xr:xr-xml-map "bgp:LocalNetworksMemory";
      type uint32;
      description "Total local networks memory";
    }
    leaf local-networks-malloced-num {
      xr:xr-xml-map "bgp:LocalNetworksMallocedNum";
      type uint32;
      description "Total local networks malloced";
    }
    leaf local-networks-freed-num {
      xr:xr-xml-map "bgp:LocalNetworksFreedNum";
      type uint32;
      description "Total local networks freed";
    }
    leaf local-paths-num {
      xr:xr-xml-map "bgp:LocalPathsNum";
      type uint32;
      description "Total local paths";
    }
    leaf local-paths-memory {
      xr:xr-xml-map "bgp:LocalPathsMemory";
      type uint32;
      description "Total local paths memory";
    }
    leaf local-paths-malloced-num {
      xr:xr-xml-map "bgp:LocalPathsMallocedNum";
      type uint32;
      description "Total local paths malloced";
    }
    leaf local-paths-freed-num {
      xr:xr-xml-map "bgp:LocalPathsFreedNum";
      type uint32;
      description "Total local paths freed";
    }
    leaf imported-paths-num {
      xr:xr-xml-map "bgp:ImportedPathsNum";
      type uint32;
      description "Total impoorted paths ";
    }
    leaf imported-paths-memory {
      xr:xr-xml-map "bgp:ImportedPathsMemory";
      type uint32;
      description "Total imported paths memory";
    }
    leaf networks-num {
      xr:xr-xml-map "bgp:NetworksNum";
      type uint32;
      description "Total Num of networks";
    }
    leaf networks-memory {
      xr:xr-xml-map "bgp:NetworksMemory";
      type uint32;
      description "Total networks memory";
    }
    leaf networks-malloced-num {
      xr:xr-xml-map "bgp:NetworksMallocedNum";
      type uint32;
      description "Total networks malloced";
    }
    leaf networks-freed-num {
      xr:xr-xml-map "bgp:NetworksFreedNum";
      type uint32;
      description "Total networks freed";
    }
    leaf paths-num {
      xr:xr-xml-map "bgp:PathsNum";
      type uint32;
      description "Total Num of paths";
    }
    leaf paths-memory {
      xr:xr-xml-map "bgp:PathsMemory";
      type uint32;
      description "Total paths memory";
    }
    leaf paths-malloced-num {
      xr:xr-xml-map "bgp:PathsMallocedNum";
      type uint32;
      description "Total paths malloced";
    }
    leaf paths-freed-num {
      xr:xr-xml-map "bgp:PathsFreedNum";
      type uint32;
      description "Total paths freed";
    }
    leaf path-elems-num {
      xr:xr-xml-map "bgp:PathElemsNum";
      type uint32;
      description "Total Num of path-elems";
    }
    leaf path-elems-memory {
      xr:xr-xml-map "bgp:PathElemsMemory";
      type uint32;
      description "Total path-elems memory";
    }
    leaf path-elems-malloced-num {
      xr:xr-xml-map "bgp:PathElemsMallocedNum";
      type uint32;
      description "Total path-elems malloced";
    }
    leaf path-elems-freed-num {
      xr:xr-xml-map "bgp:PathElemsFreedNum";
      type uint32;
      description "Total path-elems freed";
    }
    leaf label-last-trigger {
      xr:xr-xml-map "bgp:LabelLastTrigger";
      type uint64;
      description "Timestamp when Label thread is last triggered";
    }
    leaf last-label-version {
      xr:xr-xml-map "bgp:LastLabelVersion";
      type uint32;
      description "Label thread version when last triggered";
    }
    leaf label-bgp-version {
      xr:xr-xml-map "bgp:LabelBGPVersion";
      type uint32;
      description "BGP version when label thread is last triggered";
    }
    leaf label-triggers {
      xr:xr-xml-map "bgp:LabelTriggers";
      type uint32;
      description "Label thread triggers";
    }
    leaf rib-last-trigger {
      xr:xr-xml-map "bgp:RIBLastTrigger";
      type uint64;
      description "Timestamp when RIB thread is last triggered";
    }
    leaf last-rib-version {
      xr:xr-xml-map "bgp:LastRIBVersion";
      type uint32;
      description "RIB thread version when last triggered";
    }
    leaf ribbgp-version {
      xr:xr-xml-map "bgp:RIBBGPVersion";
      type uint32;
      description "BGP version when RIB thread is last triggered";
    }
    leaf rib-triggers {
      xr:xr-xml-map "bgp:RIBTriggers";
      type uint32;
      description "RIB thread triggers";
    }
    leaf import-last-trigger {
      xr:xr-xml-map "bgp:ImportLastTrigger";
      type uint64;
      description "Timestamp when Import thread is last triggered";
    }
    leaf last-import-version {
      xr:xr-xml-map "bgp:LastImportVersion";
      type uint32;
      description "Import thread version when last triggered";
    }
    leaf import-bgp-version {
      xr:xr-xml-map "bgp:ImportBGPVersion";
      type uint32;
      description
        "BGP version when Import thread is last triggered";
    }
    leaf import-triggers {
      xr:xr-xml-map "bgp:ImportTriggers";
      type uint32;
      description "Import thread triggers";
    }
    leaf update-gen-last-trigger {
      xr:xr-xml-map "bgp:UpdateGenLastTrigger";
      type uint64;
      description
        "Timestamp when Update generation thread is last
        triggered";
    }
    leaf update-gen-bgp-version {
      xr:xr-xml-map "bgp:UpdateGenBGPVersion";
      type uint32;
      description
        "BGP version when Update generation thread is
        last triggered";
    }
    leaf update-triggers {
      xr:xr-xml-map "bgp:UpdateTriggers";
      type uint32;
      description "Update thread triggers";
    }
    leaf total-r-ds-num {
      xr:xr-xml-map "bgp:TotalRDsNum";
      type uint32;
      description "Total Num of RDs";
    }
    leaf total-remote-r-ds-num {
      xr:xr-xml-map "bgp:TotalRemoteRDsNum";
      type uint32;
      description "Total Num of remote RDs";
    }
    leaf total-same-r-ds-num {
      xr:xr-xml-map "bgp:TotalSameRDsNum";
      type uint32;
      description "Total Num of same RDs";
    }
    leaf malloced-rd-count {
      xr:xr-xml-map "bgp:MallocedRDCount";
      type uint32;
      description "Activity: Number of RDs malloced";
    }
    leaf freed-rd-count {
      xr:xr-xml-map "bgp:FreedRDCount";
      type uint32;
      description "Activity: Number of RDs freed";
    }
    leaf rd-memory {
      xr:xr-xml-map "bgp:RDMemory";
      type uint32;
      units "byte";
      description "Memory (in bytes) used by RD data";
    }
    leaf multipath-network-entry-count {
      xr:xr-xml-map "bgp:MultipathNetworkEntryCount";
      type uint32;
      description "Number of multipath network entries";
    }
    leaf multipath-network-entry-memory {
      xr:xr-xml-map "bgp:MultipathNetworkEntryMemory";
      type uint32;
      units "byte";
      description
        "Memory (in bytes) used bymultipath network
        entries";
    }
    leaf multipath-paths-count {
      xr:xr-xml-map "bgp:MultipathPathsCount";
      type uint32;
      description "Number of multipath paths";
    }
    leaf multipath-paths-memory {
      xr:xr-xml-map "bgp:MultipathPathsMemory";
      type uint32;
      units "byte";
      description "Memory (in bytes) used bymultimpath paths";
    }
    leaf update-wait-install-enabled {
      xr:xr-xml-map "bgp:UpdateWaitInstallEnabled";
      type uint32;
      description "Update wait-install enabled";
    }
    leaf rib-acked-table-version {
      xr:xr-xml-map "bgp:RIBAckedTableVersion";
      type uint32;
      description "Table version acked by RIB";
    }
    leaf rib-ack-requests {
      xr:xr-xml-map "bgp:RIBAckRequests";
      type uint32;
      description "Counter for RIB ack requests";
    }
    leaf rib-acks-received {
      xr:xr-xml-map "bgp:RIBAcksReceived";
      type uint32;
      description "Counter for RIB ack received";
    }
    leaf rib-slow-acks {
      xr:xr-xml-map "bgp:RIBSlowAcks";
      type uint32;
      description "Counter for slow RIB acks";
    }
  }

  grouping BGP-PROCESS-INFO-AF-BAG {
    description "BGP address family specific process information";

    container global {
      description "Global information";
      uses BGP-PROCESS-INFO-AF-GBL;
    }

    container vrf {
      description "VRF information";
      uses BGP-PROCESS-INFO-AF-VRF;
    }

    container performance-statistics {
      description "Performance statistics";
      uses BGP-PERF-PROCESS-AF;
    }
    leaf af-name {
      xr:xr-xml-map "bgp:AFName";
      type Bgp-afi;
      description "Address family id";
    }
    leaf process-instance {
      xr:xr-xml-map "bgp:ProcessInstance";
      type uint8;
      description "ID for the BGP process instance";
    }
    leaf vrf-name {
      xr:xr-xml-map "bgp:VRFName";
      type string;
      description "Name of the VRF";
    }
    leaf vrf-totals {
      xr:xr-xml-map "bgp:VRFTotals";
      type boolean;
      description "per VRF information aggregated across all VRFs";
    }
  }

  grouping BGP-CONVERGENCE-BAG {
    description "BGP Convergence";
    leaf af-name {
      xr:xr-xml-map "bgp:AFName";
      type Bgp-afi;
      description "Address family identifier";
    }
    leaf has-converged {
      xr:xr-xml-map "bgp:HasConverged";
      type boolean;
      description "Convergence has been reached";
    }
    leaf are-write-queues-empty {
      xr:xr-xml-map "bgp:AreWriteQueuesEmpty";
      type boolean;
      description "All neighbor write queues are empty";
    }
  }

  grouping BGP-PATH-ADV-BAG {
    description "BGP path with advertised attributes information";

    container neighbor-address-xr {
      description "Neighbor Address";
      uses BGP-ADDRTYPE;
    }

    container path-info-after-policy-in {
      description "Path information after inbound policy";
      uses BGP-PATH;
    }

    container path-info-after-policy-out {
      description "Path information after outbound policy";
      uses BGP-PATH;
    }

    container attributes-after-policy-in {
      description "Attributes after inbound policy";
      uses BGP-ATTR;
    }

    container attributes-after-policy-out {
      description "Attributes after outbound policy";
      uses BGP-ATTR;
    }
    leaf no-path {
      xr:xr-xml-map "bgp:NoPath";
      type boolean;
      description
        "No path exists All 'sp_path_in' fields except
        'sp_path_in->bag_prefix' are invalid.  All
        'sp_path_out' fields are invalid.";
    }
    leaf af-name {
      xr:xr-xml-map "bgp:AFName";
      type Bgp-afi;
      description "Address family identifier";
    }
    leaf route-distinguisher {
      xr:xr-xml-map "bgp:RouteDistinguisher";
      type xr:Route-dist;
      description "Route Distinguisher";
    }
    leaf source-route-distinguisher {
      xr:xr-xml-map "bgp:SourceRouteDistinguisher";
      type xr:Route-dist;
      description "Source Route Distinguisher";
    }
    leaf vrf-name {
      xr:xr-xml-map "bgp:VRFName";
      type string;
      description "Name of the VRF";
    }
  }

  grouping BGP-PATH-ELEM-BAG {
    description "BGP path element";

    container pelem-path-nexthop {
      description "Path nexthop address";
      uses BGP-ADDRTYPE;
    }

    container nhte-tunnel {
      description "NH TE tunnel information";
      uses BGP-TE-TUNNEL;
    }

    container pelem-path-neighbor-addr {
      description "Path neighbor address";
      uses BGP-ADDRTYPE;
    }
    leaf pelem-path-id {
      xr:xr-xml-map "bgp:PelemPathID";
      type uint32;
      description "Local Path ID";
    }
    leaf pelem-version {
      xr:xr-xml-map "bgp:PelemVersion";
      type uint32;
      description "Version";
    }
    leaf pelem-flags {
      xr:xr-xml-map "bgp:PelemFlags";
      type uint32;
      description "Flags";
    }
    leaf pelem-gw-metric {
      xr:xr-xml-map "bgp:PelemGwMetric";
      type uint32;
      description "Gateway metric";
    }
    leaf pelem-path-flags {
      xr:xr-xml-map "bgp:PelemPathFlags";
      type uint64;
      description "Path flags";
    }
    leaf pelem-path-peer-path-id {
      xr:xr-xml-map "bgp:PelemPathPeerPathID";
      type uint32;
      description "Path peer path ID";
    }
    leaf pelem-table-attr-version {
      xr:xr-xml-map "bgp:PelemTableAttrVersion";
      type uint32;
      description "Table Attr version";
    }
    leaf pelem-path-table-attr-version {
      xr:xr-xml-map "bgp:PelemPathTableAttrVersion";
      type uint32;
      description "Path Table Attr version";
    }
    leaf pelem-no-bestpath-table-attr-version {
      xr:xr-xml-map "bgp:PelemNoBestpathTableAttrVersion";
      type uint32;
      description "No-bestpath Table Attr version";
    }
    leaf pelem-no-addpath-table-attr-version {
      xr:xr-xml-map "bgp:PelemNoAddpathTableAttrVersion";
      type uint32;
      description "No-addpath Table Attr version";
    }
    leaf is-perm-path-pelem {
      xr:xr-xml-map "bgp:IsPermPathPelem";
      type boolean;
      description "Pelem for permanent path";
    }
  }

  grouping BGP-ATTR-RNH-ADDR {
    description "BGP ATTR RNH ADDR";
    leaf len {
      xr:xr-xml-map "bgp:len";
      type Bgp-rnh-addr-len;
      description "len";
    }
    leaf ipv4-address {
      xr:xr-xml-map "bgp:IPV4Address";
      when "../len = 'v4'" {
        description "../len = 'v4'";
      }
      type inet:ipv4-address;
      description "IPv4 Addr";
    }
    leaf ipv6-address {
      xr:xr-xml-map "bgp:IPV6Address";
      when "../len = 'v6'" {
        description "../len = 'v6'";
      }
      type Ipv6-address;
      description "IPv6 Addr";
    }
    leaf mac-address {
      xr:xr-xml-map "bgp:MACAddress";
      when "../len = 'mac'" {
        description "../len = 'Mac'";
      }
      type Mac-address;
      description "MAC Addr";
    }
  }

  grouping BGP-PEDISTLBL-ENTRY {
    description "PE distinguisher Label entry";
    leaf pe-address {
      xr:xr-xml-map "bgp:PEAddress";
      type inet:ipv4-address;
      description " PE address";
    }
    leaf label {
      xr:xr-xml-map "bgp:Label";
      type uint32;
      description "Label";
    }
  }

  grouping BGP-COMMON-ATTR-ENTRY {
    description "Common Set of attribute entry";
    leaf is-metric-present {
      xr:xr-xml-map "bgp:IsMetricPresent";
      type boolean;
      description "Metric attribute present";
    }
    leaf is-local-pref-present {
      xr:xr-xml-map "bgp:IsLocalPrefPresent";
      type boolean;
      description "Local Preference attribute present";
    }
    leaf is-atomic-aggregate-present {
      xr:xr-xml-map "bgp:IsAtomicAggregatePresent";
      type boolean;
      description "Atomic aggregate attribute present";
    }
    leaf is-aggregator-present {
      xr:xr-xml-map "bgp:IsAggregatorPresent";
      type boolean;
      description "Aggregator attribute present";
    }
    leaf is-origin-present {
      xr:xr-xml-map "bgp:IsOriginPresent";
      type boolean;
      description "Origin attribute present";
    }
    leaf is-as-path-present {
      xr:xr-xml-map "bgp:IsASPathPresent";
      type boolean;
      description "AS path attribute present";
    }
    leaf is-community-present {
      xr:xr-xml-map "bgp:IsCommunityPresent";
      type boolean;
      description "Community attribute present";
    }
    leaf is-extended-community-present {
      xr:xr-xml-map "bgp:IsExtendedCommunityPresent";
      type boolean;
      description "Extended community attribute present";
    }
    leaf is-ssa-present {
      xr:xr-xml-map "bgp:IsSsaPresent";
      type boolean;
      description "SSA attribute present";
    }
    leaf is-connector-present {
      xr:xr-xml-map "bgp:IsConnectorPresent";
      type boolean;
      description "Connector present";
    }
    leaf is-pmsi-present {
      xr:xr-xml-map "bgp:IsPMSIPresent";
      type boolean;
      description "PMSI Attribute  present";
    }
    leaf is-pppmp-present {
      xr:xr-xml-map "bgp:IsPPPMPPresent";
      type boolean;
      description "PPMP Attribute  present";
    }
    leaf is-aigp-present {
      xr:xr-xml-map "bgp:IsAIGPPresent";
      type boolean;
      description "AIGP Present";
    }
    leaf is-pe-distinguisher-label-present {
      xr:xr-xml-map "bgp:IsPEDistinguisherLabelPresent";
      type boolean;
      description "PE distinguisher label  attribute present";
    }
    leaf is-ls-attribute-present {
      xr:xr-xml-map "bgp:IsLSAttributePresent";
      type boolean;
      description "BGP LS attribute present";
    }
    leaf is-label-index-present {
      xr:xr-xml-map "bgp:IsLabelIndexPresent";
      type boolean;
      description "Label Index attribute present";
    }
    leaf neighbor-as {
      xr:xr-xml-map "bgp:NeighborAS";
      type uint32;
      description "Neighbor AS number";
    }
    leaf aggregator-as {
      xr:xr-xml-map "bgp:AggregatorAS";
      type uint32;
      description "AS where aggregation was last performed";
    }
    leaf aggregator-address {
      xr:xr-xml-map "bgp:AggregatorAddress";
      type inet:ipv4-address;
      description "Address where aggregation was performed";
    }
    leaf metric {
      xr:xr-xml-map "bgp:Metric";
      type uint32;
      description "Metric";
    }
    leaf local-preference {
      xr:xr-xml-map "bgp:LocalPreference";
      type uint32;
      description "Local preference";
    }
    leaf origin {
      xr:xr-xml-map "bgp:Origin";
      type uint16;
      description "Origin";
    }
    leaf extended-community-flags {
      xr:xr-xml-map "bgp:ExtendedCommunityFlags";
      type uint8;
      description "Extended community Flags";
    }
    leaf originator {
      xr:xr-xml-map "bgp:Originator";
      type inet:ipv4-address;
      description "Originator attribute";
    }
    leaf l2tpv3-session-id {
      xr:xr-xml-map "bgp:L2TPv3SessionID";
      type uint32;
      description "L2TPv3 session id";
    }
    leaf connector-type {
      xr:xr-xml-map "bgp:ConnectorType";
      type uint16;
      description "Connector Type";
    }
    leaf aigp-metric-value {
      xr:xr-xml-map "bgp:AIGPMetricValue";
      type uint64;
      description "AIGP metric value";
    }
    leaf pmsi-type {
      xr:xr-xml-map "bgp:PMSIType";
      type uint16;
      description "PMSI Type";
    }
    leaf pmsi-flags {
      xr:xr-xml-map "bgp:PMSIFlags";
      type uint8;
      description "PMSI Value";
    }
    leaf pmsi-label {
      xr:xr-xml-map "bgp:PMSILabel";
      type uint32;
      description "PMSI label";
    }
    leaf ppm-pvalue {
      xr:xr-xml-map "bgp:PPMPvalue";
      type uint32;
      description "PPMP Value";
    }
    leaf-list as-path {
      xr:xr-xml-map "bgp:ASPath";
      type uint8;
      description "AS path attribute";
    }
    leaf-list community {
      xr:xr-xml-map "bgp:Community";
      type uint32;
      description "Community attribute";
    }
    leaf-list extended-community {
      xr:xr-xml-map "bgp:ExtendedCommunity";
      type uint8;
      description "Extended community attribute";
    }
    leaf-list unknown-attribute {
      xr:xr-xml-map "bgp:UnknownAttributes";
      type uint8;
      description "Unknown attributes";
    }
    leaf-list cluster {
      xr:xr-xml-map "bgp:ClusterList";
      type uint32;
      description "Cluster list attribute";
    }
    leaf-list l2tpv3-cookie {
      xr:xr-xml-map "bgp:L2TPv3Cookie";
      type uint8;
      description "L2TPv3 Cookie";
    }
    leaf-list connector-value {
      xr:xr-xml-map "bgp:ConnectorValue";
      type uint8;
      description "Connector Value";
    }
    leaf-list pmsi-value {
      xr:xr-xml-map "bgp:PMSIValue";
      type uint8;
      description "PMSI Value";
    }
    leaf-list ls-attr {
      xr:xr-xml-map "bgp:LSAttr";
      type uint8;
      description "BGP LS attribute";
    }
    leaf-list label-index-attr {
      xr:xr-xml-map "bgp:LabelIndexAttr";
      type uint8;
      description "Label Index attribute";
    }

    list pe-distinguisher-label {
      description "PE distinguisher label attribute";
      uses BGP-PEDISTLBL-ENTRY;
    }
  }

  grouping BGP-ATTR {
    description "BGP Attributes";

    container common-attributes {
      description "Common attributes";
      uses BGP-COMMON-ATTR-ENTRY;
    }

    container attr-set {
      description "ATTR_SET attribute";
      uses BGP-COMMON-ATTR-ENTRY;
    }

    container rnh-addr {
      description "RNH Address";
      uses BGP-ATTR-RNH-ADDR;
    }

    container ribrnh-ip {
      description "RIB RNH IP Address";
      uses BGP-ADDRTYPE;
    }
    leaf is-as-path2-byte {
      xr:xr-xml-map "bgp:IsASPath2Byte";
      type boolean;
      description "AS path encoded as 2-byte";
    }
    leaf is-application-gateway-present {
      xr:xr-xml-map "bgp:IsApplicationGatewayPresent";
      type boolean;
      description "Application gateway present";
    }
    leaf is-attr-set-present {
      xr:xr-xml-map "bgp:IsAttrSetPresent";
      type boolean;
      description "BGP ATTR_SET attribute present";
    }
    leaf set-aigp-inbound-igp {
      xr:xr-xml-map "bgp:SetAIGPInboundIGP";
      type boolean;
      description "AIGP set by policy inbound IGP ";
    }
    leaf set-aigp-inbound-metric {
      xr:xr-xml-map "bgp:SetAIGPInboundMetric";
      type boolean;
      description "AIGP set by policy inbound metric";
    }
    leaf is-rnh-present {
      xr:xr-xml-map "bgp:IsRNHPresent";
      type boolean;
      description "RNH Attribute  present";
    }
    leaf is-ribrnh-present {
      xr:xr-xml-map "bgp:IsRIBRNHPresent";
      type boolean;
      description "RIB RNH Attribute  present";
    }
    leaf attribute-key-number {
      xr:xr-xml-map "bgp:AttributeKeyNumber";
      type uint32;
      description "Attribute key number";
    }
    leaf attribute-reuse-id-config {
      xr:xr-xml-map "bgp:AttributeReuseIDConfig";
      type boolean;
      description "Attribute reuse ID Configured";
    }
    leaf attribute-reuse-id-max-id {
      xr:xr-xml-map "bgp:AttributeReuseIDMaxID";
      type uint32;
      description "Attribute reuse ID maximum ID";
    }
    leaf attribute-reuse-id-node {
      xr:xr-xml-map "bgp:AttributeReuseIDNode";
      type uint32;
      description "Attribute reuse ID nodes";
    }
    leaf attribute-reuse-id-current {
      xr:xr-xml-map "bgp:AttributeReuseIDCurrent";
      type uint32;
      description "Attribute reuse ID current ID";
    }
    leaf attribute-reuse-id-keys {
      xr:xr-xml-map "bgp:AttributeReuseIDKeys";
      type uint32;
      description "Attribute reuse ID allocated keys";
    }
    leaf attribute-reuse-id-recover-sec {
      xr:xr-xml-map "bgp:AttributeReuseIDRecoverSec";
      type uint32;
      units "second";
      description "Attribute reuse ID timer in seconds";
    }
    leaf vpn-distinguisher {
      xr:xr-xml-map "bgp:VPNDistinguisher";
      type uint32;
      description "VPN Distinguisher";
    }
    leaf rnh-type {
      xr:xr-xml-map "bgp:RNHType";
      type uint16;
      description "RNH Type";
    }
    leaf rnh-len {
      xr:xr-xml-map "bgp:RNHLen";
      type uint8;
      description "RNH Length";
    }
    leaf rnh-addr-len {
      xr:xr-xml-map "bgp:RNHAddrLen";
      type uint32;
      description "RNH Address Length";
    }
    leaf ribrnh-table {
      xr:xr-xml-map "bgp:RIBRNHTable";
      type uint32;
      description "RIB RNH Table";
    }
    leaf ribrnh-mac {
      xr:xr-xml-map "bgp:RIBRNHMac";
      type Mac-address;
      description "RIB RNH MAC Address";
    }
    leaf ribrnhip-table {
      xr:xr-xml-map "bgp:RIBRNHIPTable";
      type uint32;
      description "RIB RNH IP Table";
    }
    leaf ribrnh-vni {
      xr:xr-xml-map "bgp:RIBRNHVni";
      type uint32;
      description "RIB RNH Vni";
    }
    leaf ribrnh-encap {
      xr:xr-xml-map "bgp:RIBRNHEncap";
      type uint8;
      description "RIB RNH Encapsulation Type";
    }
  }

  grouping BGP-EVPN-GW-ADDR {
    description "BGP EVPN GW ADDR";
    leaf len {
      xr:xr-xml-map "bgp:len";
      type Bgp-gw-addr-len;
      description "len";
    }
    leaf ipv4-address {
      xr:xr-xml-map "bgp:IPV4Address";
      when "../len = 'gwipv4'" {
        description "../len = 'gwipv4'";
      }
      type inet:ipv4-address;
      description "IPv4 Addr";
    }
    leaf ipv6-address {
      xr:xr-xml-map "bgp:IPV6Address";
      when "../len = 'gwipv6'" {
        description "../len = 'gwipv6'";
      }
      type Ipv6-address;
      description "IPv6 Addr";
    }
  }

  grouping BGP-L2VPN-EVPN-ESI {
    description "BGP L2VPN EVPN ESI";
    leaf esi {
      xr:xr-xml-map "bgp:esi";
      type yang:hex-string;
      description "esi";
    }
  }

  grouping BGP-TE-TUNNEL {
    description "BGP TE TUNNEL";
    leaf tunnel-name {
      xr:xr-xml-map "bgp:tunnel_name";
      type yang:hex-string;
      description "tunnel name";
    }
    leaf has-te-tunnel {
      xr:xr-xml-map "bgp:HasTETunnel";
      type boolean;
      description "NH TE Tunnel info is present";
    }
    leaf is-tunnel-up {
      xr:xr-xml-map "bgp:IsTunnelUp";
      type boolean;
      description "Tunnel Up flag";
    }
    leaf is-tunnel-info-stale {
      xr:xr-xml-map "bgp:IsTunnelInfoStale";
      type boolean;
      description "Tunnel is stale";
    }
    leaf is-tunnel-registered {
      xr:xr-xml-map "bgp:IsTunnelRegistered";
      type boolean;
      description "Tunnel registered flag";
    }
    leaf tunnel-v6-required {
      xr:xr-xml-map "bgp:TunnelV6Required";
      type boolean;
      description "Tunnel need IPv6";
    }
    leaf tunnel-v6-enabled {
      xr:xr-xml-map "bgp:TunnelV6Enabled";
      type boolean;
      description "IPv6 enabled";
    }
    leaf binding-label {
      xr:xr-xml-map "bgp:BindingLabel";
      type uint32;
      description "Binding label for the tunnel";
    }
    leaf tunnel-if-handle {
      xr:xr-xml-map "bgp:TunnelIFHandle";
      type uint32;
      description "Interface handle for the tunnel";
    }
    leaf last-tunnel-update {
      xr:xr-xml-map "bgp:LastTunnelUpdate";
      type uint32;
      description "Time since the last rib update happened";
    }
  }

  grouping BGP-PATH {
    description "BGP Path";

    container bgp-prefix {
      description "BGP prefix";
      uses BGP-PREFIXTYPE;
    }

    container neighbor-address {
      description "Neighbor address";
      uses BGP-ADDRTYPE;
    }

    container next-hop {
      description "Next hop";
      uses BGP-ADDRTYPE;
    }

    container nhte-tunnel {
      description "NH TE tunnel information";
      uses BGP-TE-TUNNEL;
    }

    container mdt-group-addr {
      description "IPv4 MDT Group Address for the path";
      uses BGP-ADDRTYPE;
    }

    container l2vpn-evpn-esi {
      description "L2VPN EVPN ESI";
      uses BGP-L2VPN-EVPN-ESI;
    }

    container gw-addr {
      description "Path GW Address";
      uses BGP-EVPN-GW-ADDR;
    }

    container best-path-comp-winner {
      description
        "Neighbor address of the path which won best path
        comparison";
      uses BGP-ADDRTYPE;
    }

    container mvpn-nbr-addr {
      description "Mvpn nbr Address for the path";
      uses BGP-ADDRTYPE;
    }

    container mvpn-nexthop-addr {
      description "Mvpn nexthop Address for the path";
      uses BGP-ADDRTYPE;
    }
    leaf route-type {
      xr:xr-xml-map "bgp:RouteType";
      type Bgp-route1;
      description "Route Type of path";
    }
    leaf is-path-valid {
      xr:xr-xml-map "bgp:IsPathValid";
      type boolean;
      description "Path attributes are usable";
    }
    leaf is-path-damped {
      xr:xr-xml-map "bgp:IsPathDamped";
      type boolean;
      description "Path suppressed due to dampening";
    }
    leaf is-path-history-held {
      xr:xr-xml-map "bgp:IsPathHistoryHeld";
      type boolean;
      description "Path entry held to remember history";
    }
    leaf is-internal-path {
      xr:xr-xml-map "bgp:IsInternalPath";
      type boolean;
      description "Received over an internal link";
    }
    leaf is-best-path {
      xr:xr-xml-map "bgp:IsBestPath";
      type boolean;
      description "Best available path";
    }
    leaf is-as-best {
      xr:xr-xml-map "bgp:IsASBest";
      type boolean;
      description "Best available path within AS";
    }
    leaf is-spkr-as-best {
      xr:xr-xml-map "bgp:IsSpkrASBest";
      type boolean;
      description "Best available path within AS in speaker";
    }
    leaf is-partial-best {
      xr:xr-xml-map "bgp:IsPartialBest";
      type boolean;
      description "Partial best path within distributed speaker";
    }
    leaf is-aggregation-suppressed {
      xr:xr-xml-map "bgp:IsAggregationSuppressed";
      type boolean;
      description "Path suppressed due to aggregation";
    }
    leaf is-import-dampened {
      xr:xr-xml-map "bgp:IsImportDampened";
      type boolean;
      description "net import dampened";
    }
    leaf is-import-suspect {
      xr:xr-xml-map "bgp:IsImportSuspect";
      type boolean;
      description "net import suspect";
    }
    leaf is-path-not-advertised {
      xr:xr-xml-map "bgp:IsPathNotAdvertised";
      type boolean;
      description "Not advertised to any peer";
    }
    leaf is-path-not-advertised-to-ebg-ps {
      xr:xr-xml-map "bgp:IsPathNotAdvertisedToEBGPs";
      type boolean;
      description "Not advertised to EBGPs";
    }
    leaf is-path-advertised-local-as-only {
      xr:xr-xml-map "bgp:IsPathAdvertisedLocalASOnly";
      type boolean;
      description "Not advertised outside local AS";
    }
    leaf is-path-from-route-reflector {
      xr:xr-xml-map "bgp:IsPathFromRouteReflector";
      type boolean;
      description "Path received from route reflector";
    }
    leaf is-path-received-only {
      xr:xr-xml-map "bgp:IsPathReceivedOnly";
      type boolean;
      description "Path is received only";
    }
    leaf is-received-path-not-modified {
      xr:xr-xml-map "bgp:IsReceivedPathNotModified";
      type boolean;
      description "Received path used without modification";
    }
    leaf is-path-locally-sourced {
      xr:xr-xml-map "bgp:IsPathLocallySourced";
      type boolean;
      description "Path sourced locally";
    }
    leaf is-path-local-aggregate {
      xr:xr-xml-map "bgp:IsPathLocalAggregate";
      type boolean;
      description "Path is a locally created aggregate";
    }
    leaf is-path-from-network-command {
      xr:xr-xml-map "bgp:IsPathFromNetworkCommand";
      type boolean;
      description "Path sourced by network command";
    }
    leaf is-path-from-redistribute-command {
      xr:xr-xml-map "bgp:IsPathFromRedistributeCommand";
      type boolean;
      description "Path sourced by redistribute command";
    }
    leaf is-path-imported {
      xr:xr-xml-map "bgp:IsPathImported";
      type boolean;
      description "Path is imported";
    }
    leaf is-path-reoriginated {
      xr:xr-xml-map "bgp:IsPathReoriginated";
      type boolean;
      description "Path is reoriginated";
    }
    leaf is-path-reoriginated-stitching {
      xr:xr-xml-map "bgp:IsPathReoriginatedStitching";
      type boolean;
      description "Path is reoriginated with stitching RTs";
    }
    leaf is-path-vpn-only {
      xr:xr-xml-map "bgp:IsPathVPNOnly";
      type boolean;
      description "Path is not in the vrf";
    }
    leaf is-path-from-confederation-peer {
      xr:xr-xml-map "bgp:IsPathFromConfederationPeer";
      type boolean;
      description "Path received from confederation peer";
    }
    leaf is-path-synced-with-igp {
      xr:xr-xml-map "bgp:IsPathSyncedWithIGP";
      type boolean;
      description "Path synchronized with IGP";
    }
    leaf is-path-multipath {
      xr:xr-xml-map "bgp:IsPathMultipath";
      type boolean;
      description "Path is one of multipath best routes";
    }
    leaf is-path-imp-candidate {
      xr:xr-xml-map "bgp:IsPathImpCandidate";
      type boolean;
      description "Path is a candidate for multipath import";
    }
    leaf is-path-stale {
      xr:xr-xml-map "bgp:IsPathStale";
      type boolean;
      description "Stale routes learnt before neighbor restarts";
    }
    leaf is-path-long-lived-stale {
      xr:xr-xml-map "bgp:IsPathLongLivedStale";
      type boolean;
      description
        "Long lived stale routes learnt before neighbor
        restarts";
    }
    leaf is-path-backup {
      xr:xr-xml-map "bgp:IsPathBackup";
      type boolean;
      description "Path is a backup path ";
    }
    leaf is-path-backup-protect-multipath {
      xr:xr-xml-map "bgp:IsPathBackupProtectMultipath";
      type boolean;
      description "Path is a backup path to protect multipaths";
    }
    leaf is-path-best-external {
      xr:xr-xml-map "bgp:IsPathBestExternal";
      type boolean;
      description "Path is a best external path";
    }
    leaf is-path-additional-path {
      xr:xr-xml-map "bgp:IsPathAdditionalPath";
      type boolean;
      description "Path is an additional-path";
    }
    leaf is-path-nexthop-discarded {
      xr:xr-xml-map "bgp:IsPathNexthopDiscarded";
      type boolean;
      description "Path is redirected to Null0";
    }
    leaf has-rcvd-label {
      xr:xr-xml-map "bgp:HasRcvdLabel";
      type boolean;
      description "Path has received label";
    }
    leaf rcvd-label {
      xr:xr-xml-map "bgp:RcvdLabel";
      type uint32;
      description "Path received label";
    }
    leaf has-local-net-label {
      xr:xr-xml-map "bgp:HasLocalNetLabel";
      type boolean;
      description "Path has local label";
    }
    leaf local-label {
      xr:xr-xml-map "bgp:LocalLabel";
      type uint32;
      description "Path local label";
    }
    leaf igp-metric {
      xr:xr-xml-map "bgp:IGPMetric";
      type uint32;
      description "IGP metric to the gateway";
    }
    leaf path-weight {
      xr:xr-xml-map "bgp:PathWeight";
      type uint16;
      description "Weight for the path";
    }
    leaf neighbor-router-id {
      xr:xr-xml-map "bgp:NeighborRouterID";
      type inet:ipv4-address;
      description "Router ID of the neighbor for the path";
    }
    leaf has-mdt-group-addr {
      xr:xr-xml-map "bgp:HasMDTGroupAddr";
      type boolean;
      description "Path has MDT Group Address";
    }
    leaf l2vpn-size {
      xr:xr-xml-map "bgp:L2VPNSize";
      type uint32;
      description "Path block size";
    }
    leaf has-esi {
      xr:xr-xml-map "bgp:HasEsi";
      type boolean;
      description "Path has EVPN ESI";
    }
    leaf has-gw-addr {
      xr:xr-xml-map "bgp:HasGwAddr";
      type boolean;
      description "Path has GW Address";
    }
    leaf has-second-label {
      xr:xr-xml-map "bgp:HasSecondLabel";
      type boolean;
      description "Path has second received label";
    }
    leaf second-label {
      xr:xr-xml-map "bgp:SecondLabel";
      type uint32;
      description "Path second received label";
    }
    leaf path-flap-count {
      xr:xr-xml-map "bgp:PathFlapCount";
      type uint32;
      description "Number of times this route has flapped";
    }
    leaf seconds-since-first-flap {
      xr:xr-xml-map "bgp:SecondsSinceFirstFlap";
      type uint32;
      units "second";
      description "Seconds since route first flapped";
    }
    leaf time-to-unsuppress {
      xr:xr-xml-map "bgp:TimeToUnsuppress";
      type uint32;
      units "second";
      description "Seconds until route is unsuppressed";
    }
    leaf dampen-penalty {
      xr:xr-xml-map "bgp:DampenPenalty";
      type uint32;
      description "Dampening penalty";
    }
    leaf halflife-time {
      xr:xr-xml-map "bgp:HalflifeTime";
      type uint32;
      description "Half-life time for the penalty";
    }
    leaf suppress-penalty {
      xr:xr-xml-map "bgp:SuppressPenalty";
      type uint32;
      description "Value to start suppressing a route";
    }
    leaf reuse-value {
      xr:xr-xml-map "bgp:ReuseValue";
      type uint32;
      description "Value to start reusing a route";
    }
    leaf maximum-suppress-time {
      xr:xr-xml-map "bgp:MaximumSuppressTime";
      type uint32;
      description "Maximum duration to suppress a stable route";
    }
    leaf best-path-comp-stage {
      xr:xr-xml-map "bgp:BestPathCompStage";
      type Bgp-bp-stage;
      description
        "Stage where the path lost to the best path or
        group best";
    }
    leaf best-path-id-comp-winner {
      xr:xr-xml-map "bgp:BestPathIDCompWinner";
      type uint32;
      description
        "Path ID of the path which won best path
        comparison";
    }
    leaf path-flags {
      xr:xr-xml-map "bgp:PathFlags";
      type uint64;
      description "Flags associated with path";
    }
    leaf path-import-flags {
      xr:xr-xml-map "bgp:PathImportFlags";
      type uint32;
      description "Path import flags";
    }
    leaf best-path-id {
      xr:xr-xml-map "bgp:BestPathId";
      type uint32;
      description "Best path ID; DEPRECATED BYLocalPathId";
    }
    leaf local-path-id {
      xr:xr-xml-map "bgp:LocalPathId";
      type uint32;
      description "Local path ID";
    }
    leaf rcvd-path-id {
      xr:xr-xml-map "bgp:RcvdPathId";
      type uint32;
      description "Received path ID";
    }
    leaf path-table-version {
      xr:xr-xml-map "bgp:PathTableVersion";
      type uint32;
      description "Table version # for pelem";
    }
    leaf advertisedto-pe {
      xr:xr-xml-map "bgp:AdvertisedtoPE";
      type boolean;
      description
        "Net could be advertised                         
        to PE peers";
    }
    leaf rib-failed {
      xr:xr-xml-map "bgp:RIBFailed";
      type boolean;
      description
        "Is net failed installed                         
        in RIB";
    }
    leaf sn-rpki-origin-as-validity {
      xr:xr-xml-map "bgp:sn_rpki_origin_as_validity";
      type uint8;
      description "RPKI origin validation state";
    }
    leaf show-rpki-origin-as-validity {
      xr:xr-xml-map "bgp:show_rpki_origin_as_validity";
      type boolean;
      description "Display validity state ?";
    }
    leaf ibgp-signaled-validity {
      xr:xr-xml-map "bgp:IBGPSignaledValidity";
      type boolean;
      description "IBGP signalled validation";
    }
    leaf rpki-origin-as-validation-disabled {
      xr:xr-xml-map "bgp:RPKIOriginASValidationDisabled";
      type boolean;
      description "RPKI originAS V. Disabled";
    }
    leaf accept-own-path {
      xr:xr-xml-map "bgp:AcceptOwnPath";
      type boolean;
      description "Accept Own";
    }
    leaf accept-own-self-originated-p-ath {
      xr:xr-xml-map "bgp:AcceptOwnSelfOriginatedPAth";
      type boolean;
      description "Accept-Own self-originated";
    }
    leaf aigp-metric {
      xr:xr-xml-map "bgp:AIGPMetric";
      type uint64;
      description "Total AIGP metric";
    }
    leaf mvpn-sfs-path {
      xr:xr-xml-map "bgp:MVPN_SFSPath";
      type boolean;
      description "Is MVPN single forwarder PE path";
    }
    leaf fspec-invalid-path {
      xr:xr-xml-map "bgp:FSPEC_InvalidPath";
      type boolean;
      description "Is Fspec invalid path";
    }
    leaf has-mvpn-nbr-addr {
      xr:xr-xml-map "bgp:HasMvpnNbrAddr";
      type boolean;
      description "Path has Mvpn nbr Address";
    }
    leaf has-mvpn-nexthop-addr {
      xr:xr-xml-map "bgp:HasMvpnNexthopAddr";
      type boolean;
      description "Path has MVPN nexthop Address";
    }
    leaf has-mvpn-pmsi {
      xr:xr-xml-map "bgp:HasMvpnPmsi";
      type boolean;
      description "Path has MVPN PMSI feedback";
    }
    leaf mvpn-pmsi-type {
      xr:xr-xml-map "bgp:MvpnPMSIType";
      type uint16;
      description "Mvpn PMSI Type";
    }
    leaf mvpn-pmsi-flags {
      xr:xr-xml-map "bgp:MvpnPMSIFlags";
      type uint8;
      description "Mvpn PMSI Value";
    }
    leaf mvpn-pmsi-label {
      xr:xr-xml-map "bgp:MvpnPMSILabel";
      type uint32;
      description "Mvpn PMSI label";
    }
    leaf has-mvpn-extcomm {
      xr:xr-xml-map "bgp:HasMvpnExtcomm";
      type boolean;
      description "Path has MVPN EXTCOMM feedback";
    }
    leaf mvpn-path-flags {
      xr:xr-xml-map "bgp:MvpnPathFlags";
      type uint16;
      description "Mvpn path flags";
    }
    leaf local-nh {
      xr:xr-xml-map "bgp:LocalNH";
      type boolean;
      description "Path has local nexthop";
    }
    leaf rt-set-limit-enabled {
      xr:xr-xml-map "bgp:RTSetLimitEnabled";
      type boolean;
      description "Path subject to RT-set net limit";
    }
    leaf path-rt-set-id {
      xr:xr-xml-map "bgp:PathRTSetID";
      type uint32;
      description "RT-set id of the path";
    }
    leaf path-rt-set-route-count {
      xr:xr-xml-map "bgp:PathRTSetRouteCount";
      type uint32;
      description "Count in RT-set";
    }
    leaf is-path-af-install-eligible {
      xr:xr-xml-map "bgp:IsPathAFInstallEligible";
      type boolean;
      description "Path can be installed in AF RIB";
    }
    leaf is-permanent-path {
      xr:xr-xml-map "bgp:IsPermanentPath";
      type boolean;
      description "Path is of type Permanent path";
    }
    leaf graceful-shutdown {
      xr:xr-xml-map "bgp:GracefulShutdown";
      type boolean;
      description "Marked for graceful shutdown";
    }
    leaf-list l2vpn-circuit-status-value {
      xr:xr-xml-map "bgp:L2vpnCircuitStatusValue";
      type uint8;
      description "L2VPN Circuit Status Value";
    }
    leaf-list mvpn-pmsi-value {
      xr:xr-xml-map "bgp:MvpnPMSIValue";
      type uint8;
      description "Mvpn PMSI Value";
    }
    leaf-list extended-community {
      xr:xr-xml-map "bgp:ExtendedCommunity";
      type uint8;
      description "Mvpn Extended community attribute";
    }

    list local-peers-advertised-to {
      description
        "Local peers that this prefix has been advertised
        to";
      uses BGP-ADVINFO-TYPE;
    }

    list pe-peers-advertised-to {
      description
        "PE peers that this prefix has been advertised to";
      uses BGP-ADVINFO-TYPE;
    }

    list best-path-orr-bitfield {
      description "ORR Best path Bitfields";
      uses BGP-ADVINFO-TYPE;
    }

    list add-path-orr-bitfield {
      description "ORR Add path Bitfields";
      uses BGP-ADVINFO-TYPE;
    }
  }

  grouping BGP-PATH-BAG {
    description "BGP path";

    container neighbor-address-xr {
      description "Neighbor Address";
      uses BGP-ADDRTYPE;
    }

    container path-information {
      description "Path information";
      uses BGP-PATH;
    }

    container attributes-after-policy-in {
      description "Attributes after inbound policy applied";
      uses BGP-ATTR;
    }
    leaf no-path {
      xr:xr-xml-map "bgp:NoPath";
      type boolean;
      description
        "No path exists. All 'sp_path' fields except
        'sp_path->bag_prefix' are invalid";
    }
    leaf af-name {
      xr:xr-xml-map "bgp:AFName";
      type Bgp-afi;
      description "Address family identifier";
    }
    leaf process-instance-id {
      xr:xr-xml-map "bgp:ProcessInstanceID";
      type uint8;
      description "Process instance ID";
    }
    leaf label-oor {
      xr:xr-xml-map "bgp:LabelOOR";
      type boolean;
      description "LSD label space is exhausted";
    }
    leaf label-o-or-version {
      xr:xr-xml-map "bgp:LabelOOrVersion";
      type uint32;
      description "Label Version when OOR happens";
    }
    leaf label-fail {
      xr:xr-xml-map "bgp:LabelFail";
      type boolean;
      description "LSD label allocation failed ";
    }
    leaf route-distinguisher {
      xr:xr-xml-map "bgp:RouteDistinguisher";
      type xr:Route-dist;
      description "Route Distinguisher";
    }
    leaf source-route-distinguisher {
      xr:xr-xml-map "bgp:SourceRouteDistinguisher";
      type xr:Route-dist;
      description "Source Route Distinguisher";
    }
    leaf prefix-version {
      xr:xr-xml-map "bgp:PrefixVersion";
      type uint32;
      description "Version of BGP Prefix Table";
    }
    leaf vrf-name {
      xr:xr-xml-map "bgp:VRFName";
      type string;
      description "Name of the VRF";
    }
    leaf source-vrf-name {
      xr:xr-xml-map "bgp:SourceVRFName";
      type string;
      description "Name of the source VRF";
    }
    leaf srcaf-name {
      xr:xr-xml-map "bgp:SRCAFName";
      type Bgp-afi;
      description "Address family identifier";
    }
  }

  grouping BGP-ADVINFO-TYPE {
    description "Peers being advertised to";

    container neighbor-address {
      description "Neighbor Address";
      uses BGP-ADDRTYPE;
    }
    leaf is-neighbor {
      xr:xr-xml-map "bgp:IsNeighbor";
      type boolean;
      description "Entry is a neighbor (not an update group)";
    }
    leaf update-group-number {
      xr:xr-xml-map "bgp:UpdateGroupNumber";
      type uint32;
      description "Update group index";
    }
  }

  grouping BGP-PREFIXTYPE {
    description "BGP PREFIXTYPE";

    container prefix {
      description "Prefix";
      uses BGP-ADDRTYPE;
    }
    leaf prefix-length {
      xr:xr-xml-map "bgp:PrefixLength";
      type uint16;
      description "Prefix length";
    }
  }

  grouping BGP-NET-BAG {
    description "BGP network";

    container bgp-prefix {
      description "BGP prefix";
      uses BGP-PREFIXTYPE;
    }

    container version-timestamp {
      description "Version timestamp";
      uses BGP-TIMESPEC;
    }

    container version-age {
      description "Version age";
      uses BGP-TIMESPEC;
    }
    leaf af-name {
      xr:xr-xml-map "bgp:AFName";
      type Bgp-afi;
      description "Address family identifier";
    }
    leaf process-instance-id {
      xr:xr-xml-map "bgp:ProcessInstanceID";
      type uint8;
      description "Process instance ID";
    }
    leaf has-inconsistent-paths {
      xr:xr-xml-map "bgp:HasInconsistentPaths";
      type boolean;
      description "Net has inconsistent paths";
    }
    leaf is-net-aggregation-suppressed {
      xr:xr-xml-map "bgp:IsNetAggregationSuppressed";
      type boolean;
      description "Net suppressed due to aggregation";
    }
    leaf is-net-ldp-signaled {
      xr:xr-xml-map "bgp:IsNetLDPSignaled";
      type boolean;
      description "L2VPN Net LDP signaled  aggregation";
    }
    leaf table-version {
      xr:xr-xml-map "bgp:TableVersion";
      type uint32;
      description "Table version # for net";
    }
    leaf table-brib-version {
      xr:xr-xml-map "bgp:TableBRIBVersion";
      type uint32;
      description "Table version # for updates";
    }
    leaf advertisedto-pe {
      xr:xr-xml-map "bgp:AdvertisedtoPE";
      type boolean;
      description
        "Net could be advertised                         
        to PE peers";
    }
    leaf has-local-label {
      xr:xr-xml-map "bgp:HasLocalLabel";
      type boolean;
      description "Net has local label";
    }
    leaf net-local-label {
      xr:xr-xml-map "bgp:NetLocalLabel";
      type uint32;
      description "Local label";
    }
    leaf net-local-label-rewrite {
      xr:xr-xml-map "bgp:NetLocalLabelRewrite";
      type boolean;
      description "Net label has rewrite";
    }
    leaf net-local-label-srgb {
      xr:xr-xml-map "bgp:NetLocalLabelSRGB";
      type boolean;
      description
        "Net label allocated fromSegment routing global
        block";
    }
    leaf has-lbl-retained {
      xr:xr-xml-map "bgp:HasLblRetained";
      type boolean;
      description "Net has label retained";
    }
    leaf route-distinguisher {
      xr:xr-xml-map "bgp:RouteDistinguisher";
      type xr:Route-dist;
      description "Route Distinguisher";
    }
    leaf vrf-name {
      xr:xr-xml-map "bgp:VRFName";
      type string;
      description "Name of the VRF";
    }
    leaf net-flags {
      xr:xr-xml-map "bgp:NetFlags";
      type uint32;
      description
        "Flags associated with                           
        net";
    }
    leaf net-extended-flags {
      xr:xr-xml-map "bgp:NetExtendedFlags";
      type uint32;
      description "Net extended flags";
    }
    leaf net-multipath {
      xr:xr-xml-map "bgp:NetMultipath";
      type boolean;
      description "Net has multipaths";
    }
    leaf net-eibgp-multipath {
      xr:xr-xml-map "bgp:NetEIBGPMultipath";
      type boolean;
      description "Net has EIBGP multipaths";
    }
    leaf net-backup-available {
      xr:xr-xml-map "bgp:NetBackupAvailable";
      type boolean;
      description "Net has backup path";
    }
    leaf net-backup-label-rewrite-available {
      xr:xr-xml-map "bgp:NetBackupLabelRewriteAvailable";
      type boolean;
      description "Net has label rewrite for backup path";
    }
    leaf rib-failed {
      xr:xr-xml-map "bgp:RIBFailed";
      type boolean;
      description "RIB install failed";
    }
    leaf gateway-array {
      xr:xr-xml-map "bgp:GatewayArray";
      type uint32;
      description "Gateway array ID";
    }
    leaf resilient-nexthop-set {
      xr:xr-xml-map "bgp:ResilientNexthopSet";
      type uint32;
      description "Resilient nexthop set ID";
    }
    leaf is-permanent-network {
      xr:xr-xml-map "bgp:IsPermanentNetwork";
      type boolean;
      description "Permanent Network";
    }
    leaf num-of-path {
      xr:xr-xml-map "bgp:NumOfPath";
      type uint32;
      description "Number of path for this net";
    }

    list local-peers-advertised-to {
      description
        "Local peers that this prefix has been advertised
        to";
      uses BGP-ADVINFO-TYPE;
    }

    list pe-peers-advertised-to {
      description
        "PE peers that this prefix has been advertised to";
      uses BGP-ADVINFO-TYPE;
    }

    list best-path-orr-bitfield {
      description "ORR Best path Bitfields";
      uses BGP-ADVINFO-TYPE;
    }

    list add-path-orr-bitfield {
      description "ORR Add path Bitfields";
      uses BGP-ADVINFO-TYPE;
    }

    list local-process-instance-path {
      description "Local (to process instance) paths for this net ";
      uses BGP-PATH-BAG;
    }

    list active-process-instance-path {
      description "Active's paths for this net ";
      uses BGP-PATH-BAG;
    }

    list local-path-element {
      description "Local path element list";
      uses BGP-PATH-ELEM-BAG;
    }

    list active-path-element {
      description "Path element list received from Active inst";
      uses BGP-PATH-ELEM-BAG;
    }
  }

  grouping BGP-UPDERR-VRF-BAG {
    description "BGP Update error-handling VRF information";

    container last-update-malformed-timestamp {
      description
        "Last malformed messages received time: time
        elapsed since 00:00:00 UTC, January 1, 1970";
      uses BGP-TIMESPEC;
    }
    leaf update-vrf-name {
      xr:xr-xml-map "bgp:UpdateVRFName";
      type string;
      description "VRF Name";
    }
    leaf update-malformed-message-count {
      xr:xr-xml-map "bgp:UpdateMalformedMessageCount";
      type uint32;
      description "Malformed messages count";
    }
    leaf update-malformed-neighbor-count {
      xr:xr-xml-map "bgp:UpdateMalformedNeighborCount";
      type uint32;
      description
        "Count of neighbors that received malformed
        messages";
    }
    leaf last-update-malformed-age {
      xr:xr-xml-map "bgp:LastUpdateMalformedAge";
      type uint32;
      units "second";
      description
        "Time since last malformed messages received
        event (in seconds)";
    }
  }

  grouping BGP-EDM-RPKI-REFRESH-ENTRY {
    description "BGP EDM RPKI REFRESH ENTRY";
    leaf af-name {
      xr:xr-xml-map "bgp:AFName";
      type Bgp-rpki-af;
      description "Address Family";
    }
    leaf neighbor {
      xr:xr-xml-map "bgp:Neighbor";
      type string;
      description "BGP neighbor";
    }
    leaf policy {
      xr:xr-xml-map "bgp:Policy";
      type string;
      description "Route Policy";
    }
    leaf paths {
      xr:xr-xml-map "bgp:Paths";
      type uint32;
      description "Number of BGP paths modified or dropped";
    }
    leaf drop {
      xr:xr-xml-map "bgp:Drop";
      type boolean;
      description "BGP paths were dropped";
    }
  }

  grouping BGP-RPKI-REFRESH-LIST-BAG {
    description "BGP RPKI REFRESH LIST BAG";

    list refresh-entry {
      description "Array of refresh entries";
      uses BGP-EDM-RPKI-REFRESH-ENTRY;
    }
  }

  grouping BGP-TIMESPEC {
    description "BGP TIMESPEC";
    leaf seconds {
      xr:xr-xml-map "bgp:Seconds";
      type uint32;
      units "second";
      description "Seconds part of time value";
    }
    leaf nanoseconds {
      xr:xr-xml-map "bgp:Nanoseconds";
      type uint32;
      units "nanosecond";
      description "Nanoseconds part of time value";
    }
  }

  grouping BGP-UPDGEN-STATS-BAG {
    description
      "BGP Update generation common statistics
      information";

    container last-update-discard-timestamp {
      description "Last Discarded time";
      uses BGP-TIMESPEC;
    }

    container last-update-cleared-timestamp {
      description "Last Cleared time";
      uses BGP-TIMESPEC;
    }

    container last-update-throttle-timestamp {
      description "Last Throttled time";
      uses BGP-TIMESPEC;
    }

    container last-update-recovery-timestamp {
      description "Last Recovery time";
      uses BGP-TIMESPEC;
    }

    container last-update-memory-allocation-fail-timestamp {
      description "Memory allocation failure time";
      uses BGP-TIMESPEC;
    }
    leaf update-out-queue-messages-high {
      xr:xr-xml-map "bgp:UpdateOutQueueMessagesHigh";
      type uint32;
      description "OutQueue High Messages";
    }
    leaf update-out-queue-messages-cumulative {
      xr:xr-xml-map "bgp:UpdateOutQueueMessagesCumulative";
      type uint32;
      description "OutQueue Cumulative Messages";
    }
    leaf update-out-queue-messages-discarded {
      xr:xr-xml-map "bgp:UpdateOutQueueMessagesDiscarded";
      type uint32;
      description "OutQueue Discarded Messages";
    }
    leaf update-out-queue-messages-cleared {
      xr:xr-xml-map "bgp:UpdateOutQueueMessagesCleared";
      type uint32;
      description "OutQueue Cleared Messages";
    }
    leaf update-out-queue-size-high {
      xr:xr-xml-map "bgp:UpdateOutQueueSizeHigh";
      type uint32;
      description "OutQueue Hi Size";
    }
    leaf update-out-queue-size-cumulative {
      xr:xr-xml-map "bgp:UpdateOutQueueSizeCumulative";
      type uint64;
      description "OutQueue Cumulative Size";
    }
    leaf update-out-queue-size-discarded {
      xr:xr-xml-map "bgp:UpdateOutQueueSizeDiscarded";
      type uint64;
      description "OutQueue Discarded Size";
    }
    leaf update-out-queue-size-cleared {
      xr:xr-xml-map "bgp:UpdateOutQueueSizeCleared";
      type uint64;
      description "OutQueue Cleared Size";
    }
    leaf last-update-discard-age {
      xr:xr-xml-map "bgp:LastUpdateDiscardAge";
      type uint32;
      units "second";
      description "Time since last Discard event (in seconds)";
    }
    leaf last-update-cleard-age {
      xr:xr-xml-map "bgp:LastUpdateCleardAge";
      type uint32;
      units "second";
      description "Time since last Clear event (in seconds)";
    }
    leaf update-throttle-count {
      xr:xr-xml-map "bgp:UpdateThrottleCount";
      type uint32;
      description "Throttle Count";
    }
    leaf last-update-throttle-age {
      xr:xr-xml-map "bgp:LastUpdateThrottleAge";
      type uint32;
      units "second";
      description "Time since last Throttle event (in seconds)";
    }
    leaf update-recovery-count {
      xr:xr-xml-map "bgp:UpdateRecoveryCount";
      type uint32;
      description "Recovery Count";
    }
    leaf last-update-recovery-age {
      xr:xr-xml-map "bgp:LastUpdateRecoveryAge";
      type uint32;
      units "second";
      description "Time since last Recovery event (in seconds)";
    }
    leaf update-memory-allocation-fail-count {
      xr:xr-xml-map "bgp:UpdateMemoryAllocationFailCount";
      type uint32;
      description "Memory allocation failure count";
    }
    leaf last-update-memory-allocation-fail-age {
      xr:xr-xml-map "bgp:LastUpdateMemoryAllocationFailAge";
      type uint32;
      units "second";
      description
        "Time since last memory allocation failure event
        (in seconds)";
    }
  }

  grouping BGP-UPDGEN-AF-SUMMARY-BAG {
    description
      "BGP Update generation address-family summary
      information";
    leaf update-group-af-name {
      xr:xr-xml-map "bgp:UpdateGroupAFName";
      type Bgp-afi;
      description "Address family identifier";
    }
    leaf current-update-limit-af {
      xr:xr-xml-map "bgp:CurrentUpdateLimitAF";
      type uint32;
      description "Current AF update limit";
    }
    leaf update-out-queue-messages {
      xr:xr-xml-map "bgp:UpdateOutQueueMessages";
      type uint32;
      description "OutQueue messages";
    }
    leaf update-out-queue-size {
      xr:xr-xml-map "bgp:UpdateOutQueueSize";
      type uint32;
      description "OutQueue size";
    }
    leaf update-throttled {
      xr:xr-xml-map "bgp:UpdateThrottled";
      type boolean;
      description "Is update throttled";
    }
    leaf update-update-group-count {
      xr:xr-xml-map "bgp:UpdateUpdateGroupCount";
      type uint32;
      description "Update-group count";
    }
    leaf update-sub-group-count {
      xr:xr-xml-map "bgp:UpdateSubGroupCount";
      type uint32;
      description "Sub-group count";
    }
    leaf sub-group-throttled-count {
      xr:xr-xml-map "bgp:SubGroupThrottledCount";
      type uint32;
      description "Throttled sub-group count";
    }
    leaf refresh-sub-group-count {
      xr:xr-xml-map "bgp:RefreshSubGroupCount";
      type uint32;
      description "Refresh sub-group count";
    }
    leaf refresh-sub-group-throttled-count {
      xr:xr-xml-map "bgp:RefreshSubGroupThrottledCount";
      type uint32;
      description "Throttled refresh sub-group count";
    }
    leaf filter-group-count {
      xr:xr-xml-map "bgp:FilterGroupCount";
      type uint32;
      description "Filter-group count";
    }
    leaf neighbor-count {
      xr:xr-xml-map "bgp:NeighborCount";
      type uint32;
      description "Neighbor count";
    }
  }

  grouping BGP-UPDGEN-PROC-BAG {
    description "BGP Update generation Process information";

    container update-statistics {
      description "Update statistics";
      uses BGP-UPDGEN-STATS-BAG;
    }
    leaf update-out-logging {
      xr:xr-xml-map "bgp:UpdateOutLogging";
      type boolean;
      description
        "Enable syslog messages for update generation
        events";
    }
    leaf current-update-limit-process {
      xr:xr-xml-map "bgp:CurrentUpdateLimitProcess";
      type uint32;
      description "Current Process update limit";
    }
    leaf configured-update-limit-process {
      xr:xr-xml-map "bgp:ConfiguredUpdateLimitProcess";
      type uint32;
      description "Configured Process update limit";
    }
    leaf update-out-queue-messages {
      xr:xr-xml-map "bgp:UpdateOutQueueMessages";
      type uint32;
      description "OutQueue messages";
    }
    leaf update-out-queue-size {
      xr:xr-xml-map "bgp:UpdateOutQueueSize";
      type uint32;
      description "OutQueue size";
    }
    leaf update-throttled {
      xr:xr-xml-map "bgp:UpdateThrottled";
      type boolean;
      description "Is update throttled";
    }

    list update-address-family {
      description "List of address-families";
      uses BGP-UPDGEN-AF-SUMMARY-BAG;
    }
  }

  grouping BGP-CONFIG-RELATIVES-BAG {
    description "BGP config ancestors/children information";

    container neighbor-address-xr {
      description "Neighbor Address";
      uses BGP-ADDRTYPE;
    }

    container af-independent-relatives {
      description "AF-independent relatives";
      uses BGP-CONFIG-ENTID;
    }
    leaf group-name {
      xr:xr-xml-map "bgp:GroupName";
      type string;
      description "Entity/group name";
    }
    leaf configuration-type {
      xr:xr-xml-map "bgp:ConfigurationType";
      type Bgp-entities;
      description "Entity type";
    }
    leaf address-family-identifier {
      xr:xr-xml-map "bgp:AddressFamilyIdentifier";
      type uint8;
      description "AF identifier";
    }

    list af-dependent-relative {
      max-elements "23";
      description "AF-dependent relatives";
      uses BGP-CONFIG-ENTID;
    }
  }

  grouping BGP-AF-DEP {
    description "BGP AF-dependent configuration information";

    container orr-root-address {
      description "ORR Root Address";
      uses BGP-ADDRTYPE;
    }

    container orf-capability-info {
      description "ORF capability item info";
      uses BGP-CONFIG-INFO;
    }

    container default-originate-info {
      description "Default-originate item info";
      uses BGP-CONFIG-INFO;
    }

    container max-prefixes-info {
      description "Maximum prefixes to accept item info";
      uses BGP-CONFIG-INFO;
    }

    container orr-info {
      description "Orr item info";
      uses BGP-CONFIG-INFO;
    }

    container next-hop-self-info {
      description "Next hop self item info";
      uses BGP-CONFIG-INFO;
    }

    container next-hop-unchanged-info {
      description "Next hop unchanged info";
      uses BGP-CONFIG-INFO;
    }

    container route-policy-in-info {
      description "Inbound route policy item info";
      uses BGP-CONFIG-INFO;
    }

    container route-policy-out-info {
      description "Outbound route policy item info";
      uses BGP-CONFIG-INFO;
    }

    container prefix-filter-info {
      description "Inbound prefix based filter item info";
      uses BGP-CONFIG-INFO;
    }

    container remove-private-as-info {
      description "Outbound private-AS removal item info";
      uses BGP-CONFIG-INFO;
    }

    container remove-private-as-in-info {
      description "Inbound private-AS removal item info";
      uses BGP-CONFIG-INFO;
    }

    container route-reflector-info {
      description "Route-reflector client item info";
      uses BGP-CONFIG-INFO;
    }

    container legacy-pe-rt-info {
      description "Accept-legacy-pe-RT item info";
      uses BGP-CONFIG-INFO;
    }

    container af-enabled-info {
      description "Address family activate item info";
      uses BGP-CONFIG-INFO;
    }

    container send-community-info {
      description "Send community attribute item info";
      uses BGP-CONFIG-INFO;
    }

    container send-graceful-shutdown-community-info {
      description
        "Send Graceful shutdown related community
        attribute item info";
      uses BGP-CONFIG-INFO;
    }

    container send-extended-community-info {
      description "Send extended community  item info";
      uses BGP-CONFIG-INFO;
    }

    container soft-reconfig-info {
      description "Soft reconf item info";
      uses BGP-CONFIG-INFO;
    }

    container so-o-info {
      description "BGP Site-of-Origin info";
      uses BGP-CONFIG-INFO;
    }

    container weight-info {
      description "Default weight item info";
      uses BGP-CONFIG-INFO;
    }

    container allowas-in-info {
      description "Allowas-in item info";
      uses BGP-CONFIG-INFO;
    }

    container af-long-lived-graceful-start-stale-time-info {
      description "Long-lived-time item info";
      uses BGP-CONFIG-INFO;
    }

    container af-long-lived-graceful-start-capable-info {
      description "Long-lived-time item info";
      uses BGP-CONFIG-INFO;
    }

    container as-override-info {
      description "As-override info ";
      uses BGP-CONFIG-INFO;
    }

    container aigp-info {
      description "AIGP info ";
      uses BGP-CONFIG-INFO;
    }

    container aigp-cost-community-info {
      description "AIGP Cost Community info ";
      uses BGP-CONFIG-INFO;
    }

    container aigp-med {
      description "AIGP MED info ";
      uses BGP-CONFIG-INFO;
    }

    container accept-own-info {
      description "Accept-Own info";
      uses BGP-CONFIG-INFO;
    }

    container multipath-info {
      description "Multipath info";
      uses BGP-CONFIG-INFO;
    }

    container fspec-valid-info {
      description "FSPEC Valid info";
      uses BGP-CONFIG-INFO;
    }

    container next-hop-unchanged-mpath-info {
      description "Next hop unchanged mpath info";
      uses BGP-CONFIG-INFO;
    }

    container permanent-network-info {
      description "Permanent network Info ";
      uses BGP-CONFIG-INFO;
    }

    container send-mcast-attr-info {
      description "Send mcast attr info";
      uses BGP-CONFIG-INFO;
    }

    container advertise-v4-afi-info {
      description "Advertise Afi Info ";
      uses BGP-CONFIG-INFO;
    }

    container advertise-v6-afi-info {
      description "Advertise Afi Info ";
      uses BGP-CONFIG-INFO;
    }

    container advertise-l2vpnevpn-afi-info {
      description "Advertise Afi Info ";
      uses BGP-CONFIG-INFO;
    }

    container advertise-dis-info {
      description "Advertise Afi Info ";
      uses BGP-CONFIG-INFO;
    }

    container advertise-def-vrf-imp-disable-afi-v4-info {
      description "Advertise Afi Info ";
      uses BGP-CONFIG-INFO;
    }

    container advertise-def-vrf-imp-disable-afi-v6-info {
      description "Advertise Afi Info ";
      uses BGP-CONFIG-INFO;
    }

    container af-encapsulation-type-info {
      description "Encapsulation type Info ";
      uses BGP-CONFIG-INFO;
    }

    container import-afi-info {
      description "Import Afi Info ";
      uses BGP-CONFIG-INFO;
    }
    leaf has-orf-capability {
      xr:xr-xml-map "bgp:HasORFCapability";
      type uint32;
      description "ORF capability";
    }
    leaf is-default-originate-not-disabled {
      xr:xr-xml-map "bgp:IsDefaultOriginateNotDisabled";
      type boolean;
      description "TRUE if default-originate is not disabled";
    }
    leaf default-originate-route-policy {
      xr:xr-xml-map "bgp:DefaultOriginateRoutePolicy";
      type string;
      description "Default-originate route policy name";
    }
    leaf max-prefixes {
      xr:xr-xml-map "bgp:MaxPrefixes";
      type uint32;
      description "Maximum prefixes to accept";
    }
    leaf max-prefix-warn-threshold {
      xr:xr-xml-map "bgp:MaxPrefixWarnThreshold";
      type uint32;
      description "Warning message threshhold";
    }
    leaf is-max-prefix-warn-only {
      xr:xr-xml-map "bgp:IsMaxPrefixWarnOnly";
      type boolean;
      description "Warning messages only";
    }
    leaf max-prefix-restart-time {
      xr:xr-xml-map "bgp:MaxPrefixRestartTime";
      type uint32;
      description "Restart time Value";
    }
    leaf is-max-prefix-discard-extra-paths {
      xr:xr-xml-map "bgp:IsMaxPrefixDiscardExtraPaths";
      type boolean;
      description "Discard extra paths";
    }
    leaf is-next-hop-self-disabled {
      xr:xr-xml-map "bgp:IsNextHopSelfDisabled";
      type boolean;
      description "Disable next-hop calc";
    }
    leaf is-next-hop-unchanged {
      xr:xr-xml-map "bgp:IsNextHopUnchanged";
      type boolean;
      description "Don't change next-hop";
    }
    leaf permanent-network {
      xr:xr-xml-map "bgp:PermanentNetwork";
      type boolean;
      description "Permanent Network";
    }
    leaf route-policy-in {
      xr:xr-xml-map "bgp:RoutePolicyIn";
      type string;
      description "Inbound route policy name";
    }
    leaf route-policy-out {
      xr:xr-xml-map "bgp:RoutePolicyOut";
      type string;
      description "Outbound route policy name";
    }
    leaf prefix-orf-filter {
      xr:xr-xml-map "bgp:PrefixORFFilter";
      type string;
      description "Inbound prefix based filter";
    }
    leaf remove-private-as-out {
      xr:xr-xml-map "bgp:RemovePrivateASOut";
      type boolean;
      description "Outbound private-AS removal";
    }
    leaf entire-aspath-out {
      xr:xr-xml-map "bgp:EntireAspathOut";
      type boolean;
      description
        "Outbound private-AS removalif the entire AS Path
        hasprivate ASes";
    }
    leaf remove-private-asin {
      xr:xr-xml-map "bgp:RemovePrivateASIN";
      type boolean;
      description "Inbound private-AS removal";
    }
    leaf entire-aspath-in {
      xr:xr-xml-map "bgp:EntireAspathIn";
      type boolean;
      description
        "Inbound private-AS removal if the entire AS Path
        has private ASes";
    }
    leaf client-route-reflector {
      xr:xr-xml-map "bgp:ClientRouteReflector";
      type boolean;
      description "Route-reflector client";
    }
    leaf accept-route-legacy-pe-rt {
      xr:xr-xml-map "bgp:AcceptRouteLegacyPE_RT";
      type boolean;
      description "accept-legacy-pe RT route";
    }
    leaf is-af-enabled {
      xr:xr-xml-map "bgp:IsAFEnabled";
      type boolean;
      description "Entity is activated for this address family";
    }
    leaf send-community-attribute {
      xr:xr-xml-map "bgp:SendCommunityAttribute";
      type boolean;
      description "Send community attribute";
    }
    leaf send-graceful-shut-community-attributes {
      xr:xr-xml-map "bgp:SendGracefulShutCommunityAttributes";
      type boolean;
      description
        "Send Graceful shutdown related community
        attributes";
    }
    leaf send-extended-community-attribute {
      xr:xr-xml-map "bgp:SendExtendedCommunityAttribute";
      type boolean;
      description "Send extended community attribute";
    }
    leaf soft-reconfig-not-disabled {
      xr:xr-xml-map "bgp:SoftReconfigNotDisabled";
      type boolean;
      description "TRUE if soft reconf is not disabled";
    }
    leaf alway-use-soft-reconfig {
      xr:xr-xml-map "bgp:AlwayUseSoftReconfig";
      type boolean;
      description "Always use soft reconfig";
    }
    leaf site-of-origin {
      xr:xr-xml-map "bgp:SiteOfOrigin";
      type string;
      description "Site of Origin";
    }
    leaf default-weight {
      xr:xr-xml-map "bgp:DefaultWeight";
      type uint32;
      description "Default weight";
    }
    leaf default-allowas {
      xr:xr-xml-map "bgp:DefaultAllowas";
      type uint32;
      description "Default allowas_in count";
    }
    leaf af-long-lived-graceful-restart-stale-time-send {
      xr:xr-xml-map "bgp:AFLongLivedGracefulRestartStaleTimeSend";
      type uint32;
      description
        "Stale time to be sent in long-lived
        graceful-restart capability";
    }
    leaf af-long-lived-graceful-restart-stale-time-accept {
      xr:xr-xml-map "bgp:AFLongLivedGracefulRestartStaleTimeAccept";
      type uint32;
      description
        "Maxmimum acceptable long-lived stale time
        acceptable from neighbor";
    }
    leaf af-long-lived-graceful-restart-capable {
      xr:xr-xml-map "bgp:AFLongLivedGracefulRestartCapable";
      type uint32;
      description "Long-lived graceful-restart capable";
    }
    leaf is-as-override-disabled {
      xr:xr-xml-map "bgp:IsAsOverrideDisabled";
      type boolean;
      description "Disable as override";
    }
    leaf is-aigp-enabled {
      xr:xr-xml-map "bgp:IsAIGPEnabled";
      type boolean;
      description "AIGP enabled";
    }
    leaf is-aigp-cost-community-enabled {
      xr:xr-xml-map "bgp:IsAIGPCostCommunityEnabled";
      type boolean;
      description "AIGP cost community enabled";
    }
    leaf is-aigp-cost-community-id {
      xr:xr-xml-map "bgp:IsAIGPCostCommunityID";
      type uint32;
      description "AIGP cost community ID";
    }
    leaf is-aigp-cost-community-transitive {
      xr:xr-xml-map "bgp:IsAIGPCostCommunityTransitive";
      type uint32;
      description "AIGP cost community ID is transitive";
    }
    leaf aigp-cost-community-poi {
      xr:xr-xml-map "bgp:AIGPCostCommunityPOI";
      type uint32;
      description "Point of insertion for AIGP cost community";
    }
    leaf is-aigp-med-enabled {
      xr:xr-xml-map "bgp:IsAIGP_MEDEnabled";
      type boolean;
      description "AIGP to MED enabled";
    }
    leaf accept-own {
      xr:xr-xml-map "bgp:AcceptOwn";
      type boolean;
      description "Accept Own";
    }
    leaf multipath {
      xr:xr-xml-map "bgp:Multipath";
      type boolean;
      description "multipath";
    }
    leaf is-fspec-valid-enabled {
      xr:xr-xml-map "bgp:IsFspecValidEnabled";
      type boolean;
      description "FSPEC VALID enabled";
    }
    leaf is-next-hop-unchanged-mpath {
      xr:xr-xml-map "bgp:IsNextHopUnchangedMpath";
      type boolean;
      description "Don't change mpath next-hop";
    }
    leaf is-send-mcast-attr-enabled {
      xr:xr-xml-map "bgp:IsSendMcastAttrEnabled";
      type boolean;
      description "Send mcast attr enabled";
    }
    leaf advertise-v4 {
      xr:xr-xml-map "bgp:AdvertiseV4";
      type uint8;
      description "Advertise afi";
    }
    leaf advertise-v6 {
      xr:xr-xml-map "bgp:AdvertiseV6";
      type uint8;
      description "Advertise afi";
    }
    leaf advertise-l2vpnevpn {
      xr:xr-xml-map "bgp:AdvertiseL2VPNEVPN";
      type uint8;
      description "Advertise afi";
    }
    leaf advertise-disable {
      xr:xr-xml-map "bgp:AdvertiseDisable";
      type uint8;
      description "Advertise afi";
    }
    leaf advertise-def-vrf-imp-disable-v4 {
      xr:xr-xml-map "bgp:AdvertiseDefVrfImpDisableV4";
      type uint8;
      description "Advertise afi";
    }
    leaf advertise-def-vrf-imp-disable-v6 {
      xr:xr-xml-map "bgp:AdvertiseDefVrfImpDisableV6";
      type uint8;
      description "Advertise afi";
    }
    leaf encapsulation-type {
      xr:xr-xml-map "bgp:EncapsulationType";
      type uint32;
      description "Encapsulation type";
    }
    leaf import {
      xr:xr-xml-map "bgp:Import";
      type boolean;
      description "Import";
    }
    leaf import-stitching {
      xr:xr-xml-map "bgp:ImportStitching";
      type boolean;
      description "Import stitching RTs";
    }
    leaf import-reoriginate {
      xr:xr-xml-map "bgp:ImportReoriginate";
      type boolean;
      description "Import reoriginate";
    }
    leaf import-reoriginate-stitching {
      xr:xr-xml-map "bgp:ImportReoriginateStitching";
      type boolean;
      description "Import reoriginate stitching RTs";
    }
  }

  grouping BGP-CONFIG-ENTID {
    description "BGP config group entity identification";

    list bgp-config-entid {
      description "bgp config entid";

      container neighbor-address {
        description "Neighbor Address";
        uses BGP-ADDRTYPE;
      }
      leaf address-family-identifier {
        type uint8;
        description "Address family identfier";
      }
      leaf configuration-type {
        type Bgp-entities;
        description "Entity type";
      }
      leaf group-name {
        type string;
        description "Group name";
      }
    }
  }

  grouping BGP-CONFIG-INFO {
    description "BGP item config information";

    container inheritance-chain {
      description "Pointer to the inheritance chain";
      uses BGP-CONFIG-ENTID;
    }
    leaf is-item-configured {
      xr:xr-xml-map "bgp:IsItemConfigured";
      type boolean;
      description
        "TRUE if the item value is a configured value
        different from the default";
    }
  }

  grouping BGP-AF-INDEP {
    description "BGP AF-independent configuration information";

    container local-ip-address {
      description
        "Local ipv4 or ipv6 address for neighbor
        connection";
      uses BGP-ADDRTYPE;
    }

    container remote-as-info {
      description "Remote AS number item info";
      uses BGP-CONFIG-INFO;
    }

    container speaker-id-info {
      description "Configured speaker ID item info";
      uses BGP-CONFIG-INFO;
    }

    container min-advertisement-info {
      description "Minimum advertisement interval item info";
      uses BGP-CONFIG-INFO;
    }

    container description-info {
      description "Description item info";
      uses BGP-CONFIG-INFO;
    }

    container ebgp-hop-count-info {
      description "EBGP neighbors hop count item info";
      uses BGP-CONFIG-INFO;
    }

    container tcpmss-info {
      description "TCP Maximum Segment Size item info";
      uses BGP-CONFIG-INFO;
    }

    container bmp-servers-info {
      description "BMP Servers Configuredinfo";
      uses BGP-CONFIG-INFO;
    }

    container keychain-info {
      description "Neighbor Keychain item info";
      uses BGP-CONFIG-INFO;
    }

    container local-as-info {
      description "Local AS number item info";
      uses BGP-CONFIG-INFO;
    }

    container password-info {
      description "Neighbor password item info";
      uses BGP-CONFIG-INFO;
    }

    container receive-buffer-info {
      description "Receive buffer sizes item info";
      uses BGP-CONFIG-INFO;
    }

    container send-buffer-info {
      description "Send buffer sizes item info";
      uses BGP-CONFIG-INFO;
    }

    container shutdown-info {
      description "Shutdown item info";
      uses BGP-CONFIG-INFO;
    }

    container timers-info {
      description "Timers item info";
      uses BGP-CONFIG-INFO;
    }

    container local-address-info {
      description "Local address item info";
      uses BGP-CONFIG-INFO;
    }

    container msg-log-in-info {
      description "Message Log Inbound item info";
      uses BGP-CONFIG-INFO;
    }

    container msg-log-out-info {
      description "Message Log Outbound item info";
      uses BGP-CONFIG-INFO;
    }

    container update-source-info {
      description "Update source item info";
      uses BGP-CONFIG-INFO;
    }

    container dmz-link-bandwidth-info {
      description "DMZ link bandwidth item ";
      uses BGP-CONFIG-INFO;
    }

    container ebgp-recv-dmz-info {
      description "EBGP receive DMZ link bandwidth item info";
      uses BGP-CONFIG-INFO;
    }

    container ebgp-send-dmz-info {
      description "EBGP send DMZ link bandwidth item info";
      uses BGP-CONFIG-INFO;
    }

    container ttl-security-info {
      description "BGP TTL Security item info";
      uses BGP-CONFIG-INFO;
    }

    container suppress4-bbyte-as-info {
      description "BGP suppress 4byte-as item info";
      uses BGP-CONFIG-INFO;
    }

    container session-open-mode-info {
      description "TCP conn open mode info";
      uses BGP-CONFIG-INFO;
    }

    container bfd-info {
      description "BFD item info";
      uses BGP-CONFIG-INFO;
    }

    container bfd-mininterval-info {
      description "BFD Mininterval item info";
      uses BGP-CONFIG-INFO;
    }

    container bfd-multiplier-info {
      description "BFD Multiplier item info";
      uses BGP-CONFIG-INFO;
    }

    container tos-info {
      description "TOS item info";
      uses BGP-CONFIG-INFO;
    }

    container nsr-disabled-info {
      description "NSR item info";
      uses BGP-CONFIG-INFO;
    }

    container graceful-restart-disabled-info {
      description "Graceful-restart item info";
      uses BGP-CONFIG-INFO;
    }

    container nbr-restart-time-info {
      description "Restart time item info";
      uses BGP-CONFIG-INFO;
    }

    container nbr-stale-path-time-info {
      description "Stale-path time item info";
      uses BGP-CONFIG-INFO;
    }

    container nbr-enforce-first-as-info {
      description "Neighbor enforce first AS info";
      uses BGP-CONFIG-INFO;
    }

    container cluster-id-info {
      description "Cluster ID item info";
      uses BGP-CONFIG-INFO;
    }

    container ignore-connected-info {
      description "Ignore Connected Info";
      uses BGP-CONFIG-INFO;
    }

    container internal-vpn-client-info {
      description "Internal VPN Client Info";
      uses BGP-CONFIG-INFO;
    }

    container addpath-send-capability-info {
      description "Addpath send capability info";
      uses BGP-CONFIG-INFO;
    }

    container addpath-receive-capability-info {
      description "Addpath receive capability info";
      uses BGP-CONFIG-INFO;
    }

    container egress-peer-engineering-info {
      description "Egress Peer Engineering info";
      uses BGP-CONFIG-INFO;
    }

    container update-error-handling-no-reset-info {
      description "Error-handling avoid-reset config info";
      uses BGP-CONFIG-INFO;
    }

    container prefix-validation-disable-info {
      description "RPKI disable info";
      uses BGP-CONFIG-INFO;
    }

    container prefix-validation-use-validit-info {
      description "RPKI use validity";
      uses BGP-CONFIG-INFO;
    }

    container prefix-validation-allow-invalid-info {
      description "RPKI allow invalid info";
      uses BGP-CONFIG-INFO;
    }

    container prefix-validation-signal-ibgp-info {
      description "RPKI signal ibgp info";
      uses BGP-CONFIG-INFO;
    }

    container neighbor-update-filter-exists-info {
      description "Neighbor update filter configuration info";
      uses BGP-CONFIG-INFO;
    }

    container neighbor-update-filter-message-buffer-count-info {
      description
        "Neighbor update filter message buffer count info";
      uses BGP-CONFIG-INFO;
    }

    container neighbor-update-filter-syslog-disable-info {
      description "Neighbor update filter syslog disable info";
      uses BGP-CONFIG-INFO;
    }

    container neighbor-update-filter-attribute-info {
      description
        "Neighbor update filter attribute-filter group
        info";
      uses BGP-CONFIG-INFO;
    }

    container graceful-shutdown-info {
      description "GracefulShutdown info";
      uses BGP-CONFIG-INFO;
    }

    container graceful-shutdown-loc-pref-info {
      description "GracefulShutdownLocPref info";
      uses BGP-CONFIG-INFO;
    }

    container graceful-shutdown-as-prepends-info {
      description "GracefulShutdownASPrepends info";
      uses BGP-CONFIG-INFO;
    }

    container graceful-shutdown-activate-info {
      description "GracefulShutdownAcivate info";
      uses BGP-CONFIG-INFO;
    }

    container capability-negotiation-suppressed-info {
      description "Capability negotiation suppressed info";
      uses BGP-CONFIG-INFO;
    }
    leaf remote-as-number-xx {
      xr:xr-xml-map "bgp:RemoteASNumberXX";
      type uint32;
      description "First half of Remote ASN";
    }
    leaf remote-as-number-yy {
      xr:xr-xml-map "bgp:RemoteASNumberYY";
      type uint32;
      description "Second half of Remote ASN";
    }
    leaf configured-speaker-id {
      xr:xr-xml-map "bgp:ConfiguredSpeakerID";
      type uint32;
      description "Configured speaker ID";
    }
    leaf tcp-mss {
      xr:xr-xml-map "bgp:tcp_mss";
      type uint32;
      description "Maximum Segment Size";
    }
    leaf min-advertisement-interval {
      xr:xr-xml-map "bgp:MinAdvertisementInterval";
      type uint32;
      units "second";
      description "Minimum advertisement interval, secs part";
    }
    leaf min-advertisement-interval-msecs {
      xr:xr-xml-map "bgp:MinAdvertisementIntervalMsecs";
      type uint32;
      units "millisecond";
      description "Minimum advertisement interval, msecs part";
    }
    leaf description {
      xr:xr-xml-map "bgp:Description";
      type string;
      description "Description";
    }
    leaf ebgp-hop-count {
      xr:xr-xml-map "bgp:EBGPHopCount";
      type uint32;
      description "EBGP neighbors hop count";
    }
    leaf bmp-servers {
      xr:xr-xml-map "bgp:BMPServers";
      type uint32;
      description "BMP Servers activated";
    }
    leaf is-ebgp-multihop-bgpmpls-forwarding-disabled {
      xr:xr-xml-map "bgp:IsEBGPMultihopBGPMPLSForwardingDisabled";
      type boolean;
      description
        "If true, MPLS and NULL rewrite is disabled; if
        false, it is enabled";
    }
    leaf keychain {
      xr:xr-xml-map "bgp:Keychain";
      type string;
      description "Neighbor keychain Name";
    }
    leaf local-as-number-xx {
      xr:xr-xml-map "bgp:LocalASNumberXX";
      type uint32;
      description "First half of Local ASN";
    }
    leaf local-as-number-yy {
      xr:xr-xml-map "bgp:LocalASNumberYY";
      type uint32;
      description "Second half of Local ASN";
    }
    leaf local-as-no-prepend {
      xr:xr-xml-map "bgp:LocalASNoPrepend";
      type boolean;
      description "Local AS no-prepend option";
    }
    leaf password {
      xr:xr-xml-map "bgp:Password";
      type string;
      description "Neighbor password";
    }
    leaf socket-buffer-receive-size {
      xr:xr-xml-map "bgp:SocketBufferReceiveSize";
      type uint32;
      description "Socket receive buffer size";
    }
    leaf bgp-buffer-receive-size {
      xr:xr-xml-map "bgp:BGPBufferReceiveSize";
      type uint32;
      description "BGP receive buffer size";
    }
    leaf socket-buffer-send-size {
      xr:xr-xml-map "bgp:SocketBufferSendSize";
      type uint32;
      description "Socket send buffer size";
    }
    leaf bgp-buffer-send-size {
      xr:xr-xml-map "bgp:BGPBufferSendSize";
      type uint32;
      description "BGP send buffer size";
    }
    leaf adminstrative-shutdown {
      xr:xr-xml-map "bgp:AdminstrativeShutdown";
      type boolean;
      description "Administrative shutdown";
    }
    leaf keepalive-interval {
      xr:xr-xml-map "bgp:KeepaliveInterval";
      type uint32;
      description "Keepalive interval";
    }
    leaf hold-time-value {
      xr:xr-xml-map "bgp:HoldTimeValue";
      type uint32;
      description "Holdtime";
    }
    leaf min-acc-hold-time-value {
      xr:xr-xml-map "bgp:MinAccHoldTimeValue";
      type uint32;
      description "Min acceptable holdtimefrom neighbor";
    }
    leaf msg-log-in-buf-count {
      xr:xr-xml-map "bgp:MsgLogInBufCount";
      type uint32;
      description "Message Log Inbound buffer count";
    }
    leaf msg-log-out-buf-count {
      xr:xr-xml-map "bgp:MsgLogOutBufCount";
      type uint32;
      description "Message Log Outbound buffer count";
    }
    leaf route-updates-source {
      xr:xr-xml-map "bgp:RouteUpdatesSource";
      type string;
      description "Source of routing updates";
    }
    leaf dmz-link-bandwidth {
      xr:xr-xml-map "bgp:DMZLinkBandwidth";
      type uint32;
      description "Propagate the DMZ link bandwidth";
    }
    leaf ebgp-recv-dmz {
      xr:xr-xml-map "bgp:EBGPRecvDmz";
      type uint32;
      description
        "Receive Bandwidth of link to single-hop eBGP
        peer";
    }
    leaf ebgp-send-dmz-mode {
      xr:xr-xml-map "bgp:EBGPSendDmzMode";
      type Bgp-ebgp-send-dmz-enable-mode;
      description "Send DMZ link bandwidthto ebgp peer";
    }
    leaf ttl-security {
      xr:xr-xml-map "bgp:TTLSecurity";
      type uint32;
      description "Enable BGP TTL Security";
    }
    leaf suppress4-byte-as {
      xr:xr-xml-map "bgp:Suppress4ByteAS";
      type uint32;
      description "Suppress BGP 4byteas Cap";
    }
    leaf capability-negotiation-suppressed {
      xr:xr-xml-map "bgp:CapabilityNegotiationSuppressed";
      type uint32;
      description "Capability negotiation is suppressed";
    }
    leaf session-open-mode {
      xr:xr-xml-map "bgp:SessionOpenMode";
      type Bgp-tcp-mode;
      description "TCP open mode to be used ";
    }
    leaf bfd {
      xr:xr-xml-map "bgp:BFD";
      type uint32;
      description "Fast failure detection using BFD";
    }
    leaf bfd-mininterval {
      xr:xr-xml-map "bgp:BFDMininterval";
      type uint32;
      description "BFD Minimum Interval";
    }
    leaf bfd-multiplier {
      xr:xr-xml-map "bgp:BFDMultiplier";
      type uint32;
      description "BFD Multiplier";
    }
    leaf tos-type-info {
      xr:xr-xml-map "bgp:TOSTypeInfo";
      type uint8;
      description "Precedence or DSCP type";
    }
    leaf tos-value-info {
      xr:xr-xml-map "bgp:TOSValueInfo";
      type uint8;
      description "Precedence or DSCP value";
    }
    leaf nsr-disabled {
      xr:xr-xml-map "bgp:NSRDisabled";
      type uint32;
      description "Support for NSR";
    }
    leaf graceful-restart-disabled {
      xr:xr-xml-map "bgp:GracefulRestartDisabled";
      type uint32;
      description "Support for graceful-restart";
    }
    leaf nbr-restart-time {
      xr:xr-xml-map "bgp:NbrRestartTime";
      type uint32;
      units "second";
      description "Restart time (in seconds)";
    }
    leaf nbr-stale-path-time {
      xr:xr-xml-map "bgp:NbrStalePathTime";
      type uint32;
      units "second";
      description "Stale-path time(in seconds)";
    }
    leaf nbr-enforce-first-as-status {
      xr:xr-xml-map "bgp:NbrEnforceFirstASStatus";
      type boolean;
      description "Neighbor enforce first AS status";
    }
    leaf nbr-cluster-id-type-info {
      xr:xr-xml-map "bgp:NbrClusterIDTypeInfo";
      type uint8;
      description "Cluster ID Type";
    }
    leaf nbr-cluster-id-info {
      xr:xr-xml-map "bgp:NbrClusterIDInfo";
      type uint32;
      description "Cluster ID value";
    }
    leaf ignore-connected-check {
      xr:xr-xml-map "bgp:IgnoreConnectedCheck";
      type boolean;
      description "If true, don't do NHconnected check for nbr";
    }
    leaf internal-vpn-client {
      xr:xr-xml-map "bgp:InternalVPNClient";
      type boolean;
      description "If true, the VPN client isan iBGP CE peer";
    }
    leaf addpath-send-capability {
      xr:xr-xml-map "bgp:AddpathSendCapability";
      type uint32;
      description
        "Indicates if addpath send capability is enabled
        or disabled";
    }
    leaf update-error-handling-no-reset {
      xr:xr-xml-map "bgp:UpdateErrorHandlingNoReset";
      type uint32;
      description
        "Indicates if avoid-reset behavior is enabled
        during update error-handling";
    }
    leaf addpath-receive-capability {
      xr:xr-xml-map "bgp:AddpathReceiveCapability";
      type uint32;
      description
        "Indicates if addpath receive capability is
        enabled or disabled";
    }
    leaf egress-peer-engineering {
      xr:xr-xml-map "bgp:EgressPeerEngineering";
      type uint32;
      description "Indicates egress peer engineering is enabled";
    }
    leaf prefix-validation-disable {
      xr:xr-xml-map "bgp:PrefixValidationDisable";
      type uint32;
      description "Prefix validation disable";
    }
    leaf bestpath-use-origin-as-validity {
      xr:xr-xml-map "bgp:BestpathUseOriginASValidity";
      type uint32;
      description "Bestpath Use Origin-AS Va";
    }
    leaf prefix-validation-allow-invalid {
      xr:xr-xml-map "bgp:PrefixValidationAllowInvalid";
      type uint32;
      description "Prefix vallidation allow invalid";
    }
    leaf prefix-validation-signal-ibgp {
      xr:xr-xml-map "bgp:PrefixValidationSignalIBGP";
      type uint32;
      description "Prefix validation signal ibgp";
    }
    leaf neighbor-update-filter-exists {
      xr:xr-xml-map "bgp:NeighborUpdateFilterExists";
      type boolean;
      description
        "Indicates if neighbor filter configuration
        exists";
    }
    leaf neighbor-update-filter-message-buffer-count {
      xr:xr-xml-map "bgp:NeighborUpdateFilterMessageBufferCount";
      type uint32;
      description "Count of neighbor filter message buffers";
    }
    leaf neighbor-update-filter-message-buffer-is-non-circular {
      xr:xr-xml-map "bgp:NeighborUpdateFilterMessageBufferIsNonCirc"+
        "ular";
      type boolean;
      description
        "Indicates if neighbor update filter message
        buffer is circular or not";
    }
    leaf neighbor-update-filter-logging-disable {
      xr:xr-xml-map "bgp:NeighborUpdateFilterLoggingDisable";
      type boolean;
      description
        "Indicates if neighbor filter logging is disabled";
    }
    leaf neighbor-update-filter-attribute-filter-group-name {
      xr:xr-xml-map "bgp:NeighborUpdateFilterAttributeFilterGroupNa"+
        "me";
      type string;
      description "Neighbor filter attribute-filter group name";
    }
    leaf graceful-shutdown-exists {
      xr:xr-xml-map "bgp:GracefulShutdownExists";
      type uint32;
      description
        "re-advertise all routes to and from this
        neighbor with the GSHUT community during
        Shutdown or bring-up";
    }
    leaf graceful-shutdown-loc-pref {
      xr:xr-xml-map "bgp:GracefulShutdownLocPref";
      type uint32;
      description
        "Local Preference to advertise routes with during
        Graceful Shutdown to IBGP. Default=No Touch";
    }
    leaf graceful-shutdown-as-prepends {
      xr:xr-xml-map "bgp:GracefulShutdownASPrepends";
      type uint32;
      description
        "Prepend the local AS this many times to the AS
        path of routes advertised during Graceful
        Shutdown";
    }
    leaf graceful-shutdown-activate {
      xr:xr-xml-map "bgp:GracefulShutdownActivate";
      type uint32;
      description "Graceful Shutdown state is activated";
    }
    leaf local-as-replace-as {
      xr:xr-xml-map "bgp:LocalASReplaceAS";
      type boolean;
      description "Local AS Replace-AS option";
    }
    leaf local-as-dual-as {
      xr:xr-xml-map "bgp:LocalASDualAS";
      type boolean;
      description "Local AS Dual-AS option";
    }
  }

  grouping BGP-L2VPN-MSPW-ADDR {
    description "BGP L2VPN MSPW ADDR";
    leaf l2vpn-address {
      xr:xr-xml-map "bgp:l2vpn_address";
      type yang:hex-string;
      description "l2vpn address";
    }
  }

  grouping L2VPNMSPW-ADDRESS-TYPE {
    description "L2VPN MSPW Address type";
    uses BGP-L2VPN-MSPW-ADDR;
  }

  grouping BGP-L2VPN-ADDR {
    description "BGP L2VPN ADDR";
    leaf l2vpn-address {
      xr:xr-xml-map "bgp:l2vpn_address";
      type yang:hex-string;
      description "l2vpn address";
    }
  }

  grouping BGP-ADDRTYPE {
    description "BGP ADDRTYPE";

    container l2vpnvpls-address {
      when "../afi = 'l2vpn-vpls'" {
        description "../AFI = 'L2VPN_VPLS'";
      }
      description "L2VPN VPLS Addr";
      uses BGP-L2VPN-ADDR;
    }

    container l2vpn-mspw-address {
      when "../afi = 'l2vpn-mspw'" {
        description "../AFI = 'L2VPN_MSPW'";
      }
      description "L2VPN MSPW Addr";
      uses L2VPNMSPW-ADDRESS-TYPE;
    }
    leaf afi {
      xr:xr-xml-map "bgp:AFI";
      type Bgp-afi;
      description "AFI";
    }
    leaf ipv4-address {
      xr:xr-xml-map "bgp:IPV4Address";
      when "../afi = 'ipv4'" {
        description "../AFI = 'IPv4'";
      }
      type inet:ipv4-address;
      description "IPv4 Addr";
    }
    leaf ipv4-mcast-address {
      xr:xr-xml-map "bgp:IPV4McastAddress";
      when "../afi = 'ipv4-multicast'" {
        description "../AFI = 'IPv4Multicast'";
      }
      type inet:ipv4-address;
      description "IPv4 Mcast Addr";
    }
    leaf ipv4-label-address {
      xr:xr-xml-map "bgp:IPV4LabelAddress";
      when "../afi = 'ipv4-labeled'" {
        description "../AFI = 'IPv4Labeled'";
      }
      type inet:ipv4-address;
      description "IPv4 Label Addr";
    }
    leaf ipv4-tunnel-address {
      xr:xr-xml-map "bgp:IPV4TunnelAddress";
      when "../afi = 'ipv4-tunnel'" {
        description "../AFI = 'IPv4Tunnel'";
      }
      type Ipv4-tunnel-address;
      description "IPv4 Tunnel";
    }
    leaf ipv4mdt-address {
      xr:xr-xml-map "bgp:IPV4MDTAddress";
      when "../afi = 'ipv4mdt'" {
        description "../AFI = 'IPv4MDT'";
      }
      type Ipv4mdt-address;
      description "IPv4 MDT Addr";
    }
    leaf ipv4vpn-address {
      xr:xr-xml-map "bgp:IPV4VPNAddress";
      when "../afi = 'vp-nv4'" {
        description "../AFI = 'VPNv4'";
      }
      type inet:ipv4-address;
      description "IPv4 VPN Addr";
    }
    leaf ipv4vpna-mcastddress {
      xr:xr-xml-map "bgp:IPV4VPNAMcastddress";
      when "../afi = 'vp-nv4-multicast'" {
        description "../AFI = 'VPNv4Multicast'";
      }
      type inet:ipv4-address;
      description "IPv4 VPN Mcast Addr";
    }
    leaf ipv6-address {
      xr:xr-xml-map "bgp:IPV6Address";
      when "../afi = 'ipv6'" {
        description "../AFI = 'IPv6'";
      }
      type Ipv6-address;
      description "IPV6 Addr";
    }
    leaf ipv6-mcast-address {
      xr:xr-xml-map "bgp:IPV6McastAddress";
      when "../afi = 'ipv6-multicast'" {
        description "../AFI = 'IPv6Multicast'";
      }
      type Ipv6-address;
      description "IPV6 Mcast Addr";
    }
    leaf ipv6-label-address {
      xr:xr-xml-map "bgp:IPv6LabelAddress";
      when "../afi = 'ipv6-labeled'" {
        description "../AFI = 'IPv6Labeled'";
      }
      type Ipv6-address;
      description "IPv6 Label Addr";
    }
    leaf ipv6vpn-address {
      xr:xr-xml-map "bgp:IPV6VPNAddress";
      when "../afi = 'vp-nv6'" {
        description "../AFI = 'VPNv6'";
      }
      type Ipv6-address;
      description "IPv6 VPN Addr";
    }
    leaf ipv6vpn-mcast-address {
      xr:xr-xml-map "bgp:IPV6VPNMcastAddress";
      when "../afi = 'vp-nv6-multicast'" {
        description "../AFI = 'VPNv6Multicast'";
      }
      type Ipv6-address;
      description "IPv6 VPN Mcast Addr";
    }
    leaf rt-constraint-address {
      xr:xr-xml-map "bgp:RTConstraintAddress";
      when "../afi = 'rt-constraint'" {
        description "../AFI = 'RTConstraint'";
      }
      type Rt-constraint-address;
      description "RT Constrt Addr";
    }
    leaf ipv6mvpn-address {
      xr:xr-xml-map "bgp:IPV6MVPNAddress";
      when "../afi = 'ipv6mvpn'" {
        description "../AFI = 'IPv6MVPN'";
      }
      type Ipv6mvpn-address;
      description "MVPN addr";
    }
    leaf ipv4mvpn-address {
      xr:xr-xml-map "bgp:IPV4MVPNAddress";
      when "../afi = 'ipv4mvpn'" {
        description "../AFI = 'IPv4MVPN'";
      }
      type Ipv4mvpn-address;
      description "MVPN4 addr";
    }
    leaf l2vpn-evpn-address {
      xr:xr-xml-map "bgp:L2VPN_EVPNAddress";
      when "../afi = 'l2vpn-evpn'" {
        description "../AFI = 'L2VPN_EVPN'";
      }
      type L2vpnevpn-address;
      description "L2VPN EVPN Addr";
    }
    leaf ls-ls-address {
      xr:xr-xml-map "bgp:LS_LSAddress";
      when "../afi = 'ls-ls'" {
        description "../AFI = 'LS_LS'";
      }
      type Ls-ls-address;
      description "LINKSTATE LINKSTATE Addr";
    }
    leaf ipv4-flowspec-address {
      xr:xr-xml-map "bgp:IPV4FlowspecAddress";
      when "../afi = 'ipv4-flowspec'" {
        description "../AFI = 'IPv4Flowspec'";
      }
      type Ipv4-flowspec-address;
      description "IPV4 Flowspec Addr";
    }
    leaf ipv6-flowspec-address {
      xr:xr-xml-map "bgp:IPV6FlowspecAddress";
      when "../afi = 'ipv6-flowspec'" {
        description "../AFI = 'IPv6Flowspec'";
      }
      type Ipv6-flowspec-address;
      description "IPV6 Flowspec Addr";
    }
    leaf ipv4vpn-flowspec-address {
      xr:xr-xml-map "bgp:IPV4VPNFlowspecAddress";
      when "../afi = 'vp-nv4-flowspec'" {
        description "../AFI = 'VPNv4Flowspec'";
      }
      type Ipv4-flowspec-address;
      description "IPV4 VPN Flowspec Addr";
    }
    leaf ipv6vpn-flowspec-address {
      xr:xr-xml-map "bgp:IPV6VPNFlowspecAddress";
      when "../afi = 'vp-nv6-flowspec'" {
        description "../AFI = 'VPNv6Flowspec'";
      }
      type Ipv6-flowspec-address;
      description "IPV6 VPN Flowspec Addr";
    }
  }

  grouping BGP-CONFIG-ENTITY-BAG {
    description "BGP entity config information";

    container neighbor-address-xr {
      description "Neighbor Address";
      uses BGP-ADDRTYPE;
    }

    container af-independent-config {
      description "AF-independent config";
      uses BGP-AF-INDEP;
    }
    leaf group-name {
      xr:xr-xml-map "bgp:GroupName";
      type string;
      description "Entity/group name";
    }
    leaf configuration-type {
      xr:xr-xml-map "bgp:ConfigurationType";
      type Bgp-entities;
      description "Entity type";
    }
    leaf address-family-identifier {
      xr:xr-xml-map "bgp:AddressFamilyIdentifier";
      type uint8;
      description "AF identifier";
    }

    list af-dependent-config {
      max-elements "23";
      description "Af-dependent config";
      uses BGP-AF-DEP;
    }
  }
}
