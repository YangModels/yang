submodule Cisco-IOS-XR-aaa-tacacs-oper-sub1 {

  belongs-to Cisco-IOS-XR-aaa-tacacs-oper {
    prefix Cisco-IOS-XR-aaa-tacacs-oper;
  }

  /*** LINKAGE (IMPORTS / INCLUDES) ***/

  import ietf-inet-types { prefix "inet"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR aaa-tacacs package operational data.

     Copyright (c) 2013-2016 by Cisco Systems, Inc.
     All rights reserved.";

  revision "2015-11-09" {
    description
      "IOS XR 6.0 revision.";
  }


  grouping TACACS-SERVER-GROUP-BAG {
    description "TACACS SERVER GROUP BAG";
    leaf group-name {
      xr:xr-xml-map "show_tacacs:group_name";
      type string;
      description "name of the server group";
    }
    leaf sg-map-num {
      xr:xr-xml-map "show_tacacs:sg_map_num";
      type uint32;
      description "server group mapped number";
    }
    leaf vrf-name {
      xr:xr-xml-map "show_tacacs:vrf_name";
      type string {
        length "0..33";
      }
      description "vrf of the group";
    }

    list server {
      description "list of servers in this group";
      uses TACACS-SERVERBAG;
    }
  }

  grouping TACACS-SERVER-GROUPS {
    description "TACACS SERVER GROUPS";

    list server-group {
      description "server group";
      uses TACACS-SERVER-GROUP-BAG;
    }
  }

  grouping TACACS-SERVERBAG {
    description "TACACS SERVERBAG";
    leaf addr {
      xr:xr-xml-map "show_tacacs:addr";
      type inet:ipv4-address;
      description "internet address of T+ server";
    }
    leaf timeout {
      xr:xr-xml-map "show_tacacs:timeout";
      type uint32;
      description "per-server timeout";
    }
    leaf port {
      xr:xr-xml-map "show_tacacs:port";
      type uint32;
      description "per server port to use";
    }
    leaf bytes-in {
      xr:xr-xml-map "show_tacacs:bytes_in";
      type uint32;
      units "byte";
      description "# of bytes read";
    }
    leaf bytes-out {
      xr:xr-xml-map "show_tacacs:bytes_out";
      type uint32;
      units "byte";
      description "# of bytes out";
    }
    leaf closes {
      xr:xr-xml-map "show_tacacs:closes";
      type uint32;
      description "socket closes";
    }
    leaf opens {
      xr:xr-xml-map "show_tacacs:opens";
      type uint32;
      description "socket opens";
    }
    leaf errors {
      xr:xr-xml-map "show_tacacs:errors";
      type uint32;
      description "error count";
    }
    leaf aborts {
      xr:xr-xml-map "show_tacacs:aborts";
      type uint32;
      description "abort count";
    }
    leaf paks-in {
      xr:xr-xml-map "show_tacacs:paks_in";
      type uint32;
      description "# of incoming packets read";
    }
    leaf paks-out {
      xr:xr-xml-map "show_tacacs:paks_out";
      type uint32;
      description "# of outgoing packets sent";
    }
    leaf replies-expected {
      xr:xr-xml-map "show_tacacs:replies_expected";
      type uint32;
      description "# of replies expected to arrive";
    }
    leaf up {
      xr:xr-xml-map "show_tacacs:up";
      type boolean;
      description "is the server UP or down ?";
    }
    leaf conn-up {
      xr:xr-xml-map "show_tacacs:conn_up";
      type boolean;
      description "is the server connected ?";
    }
    leaf single-connect {
      xr:xr-xml-map "show_tacacs:single_connect";
      type boolean;
      description "is this a single connect server ?";
    }
    leaf is-private {
      xr:xr-xml-map "show_tacacs:is_private";
      type boolean;
      description "is this a private server ?";
    }
    leaf vrf-name {
      xr:xr-xml-map "show_tacacs:vrf_name";
      type string {
        length "0..33";
      }
      description "VRF in which server is reachable";
    }
    leaf addr-buf {
      xr:xr-xml-map "show_tacacs:addr_buf";
      type string {
        length "0..46";
      }
      description "IP address buffer";
    }
    leaf family {
      xr:xr-xml-map "show_tacacs:family";
      type string {
        length "0..5";
      }
      description "IP address Family";
    }
  }

  grouping TACACS-SERVERS {
    description "TACACS SERVERS";

    list server {
      description "server";
      uses TACACS-SERVERBAG;
    }
  }

  grouping TACACS-REQUESTBAG {
    description "TACACS REQUESTBAG";

    list tacacs-requestbag {
      description "tacacs requestbag";
      leaf time-remaining {
        type uint32;
        description "time remaining for this request";
      }
      leaf bytes-out {
        type uint32;
        units "byte";
        description "bytes written";
      }
      leaf out-pak-size {
        type uint32;
        description "size of the packet to be sent";
      }
      leaf bytes-in {
        type uint32;
        units "byte";
        description "bytes read from socket";
      }
      leaf in-pak-size {
        type uint32;
        description "size of the packet to be received";
      }
      leaf pak-type {
        type string;
        description "the type of packet";
      }
      leaf session-id {
        type int32;
        description "same as in pkt hdr";
      }
      leaf sock {
        type int32;
        description "socket number";
      }
    }
  }

  grouping TACACS-REQUESTS {
    description "TACACS REQUESTS";

    list request {
      description "request";
      uses TACACS-REQUESTBAG;
    }
  }
}
