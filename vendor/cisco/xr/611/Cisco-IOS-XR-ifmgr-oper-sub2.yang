submodule Cisco-IOS-XR-ifmgr-oper-sub2 {

  belongs-to Cisco-IOS-XR-ifmgr-oper {
    prefix Cisco-IOS-XR-ifmgr-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR ifmgr package operational data.

     Copyright (c) 2013-2016 by Cisco Systems, Inc.
     All rights reserved.";

  revision "2015-07-30" {
    description
      "IOS XR 5.3.2 revision.";
  }

  revision "2015-01-07" {
    description
      "IOS XR 5.3.1 revision.";
  }

  typedef Im-state-enum {
    type enumeration {
      enum im-state-not-ready {
        description "im state not ready";
      }
      enum im-state-admin-down {
        description "im state admin down";
      }
      enum im-state-down {
        description "im state down";
      }
      enum im-state-up {
        description "im state up";
      }
      enum im-state-shutdown {
        description "im state shutdown";
      }
      enum im-state-err-disable {
        description "im state err disable";
      }
      enum im-state-down-immediate {
        description "im state down immediate";
      }
      enum im-state-down-immediate-admin {
        description "im state down immediate admin";
      }
      enum im-state-down-graceful {
        description "im state down graceful";
      }
      enum im-state-begin-shutdown {
        description "im state begin shutdown";
      }
      enum im-state-end-shutdown {
        description "im state end shutdown";
      }
      enum im-state-begin-error-disable {
        description "im state begin error disable";
      }
      enum im-state-end-error-disable {
        description "im state end error disable";
      }
      enum im-state-begin-down-graceful {
        description "im state begin down graceful";
      }
      enum im-state-reset {
        description "im state reset";
      }
      enum im-state-operational {
        description "im state operational";
      }
      enum im-state-not-operational {
        description "im state not operational";
      }
      enum im-state-unknown {
        description "im state unknown";
      }
      enum im-state-last {
        description "im state last";
      }
    }
    description "Im state enum";
  }

  grouping IM-SHOW-DAMP-NODE {
    description "IM SHOW DAMP NODE";

    container capsulation-dampening {
      description "Capsulation dampening";
      uses IM-SHOW-DAMP-NODE-INFO;
    }
    leaf capsulation-number {
      xr:xr-xml-map "im_show_edm:CapsulationNumber";
      type string;
      description "Capsulation number";
    }
  }

  grouping IM-SHOW-DAMP-NODE-INFO {
    description "IM SHOW DAMP NODE INFO";
    leaf penalty {
      xr:xr-xml-map "im_show_edm:Penalty";
      type uint32;
      description "Dampening penalty of the interface";
    }
    leaf is-suppressed-enabled {
      xr:xr-xml-map "im_show_edm:IsSuppressedEnabled";
      type boolean;
      description "Flag showing if state is suppressed";
    }
    leaf seconds-remaining {
      xr:xr-xml-map "im_show_edm:SecondsRemaining";
      type uint32;
      units "second";
      description "Remaining period of suppression in secs";
    }
    leaf flaps {
      xr:xr-xml-map "im_show_edm:Flaps";
      type uint32;
      description "Number of underlying state flaps";
    }
    leaf state {
      xr:xr-xml-map "im_show_edm:State";
      type Im-state-enum;
      description "Underlying state of the node";
    }
  }

  grouping IM-SHOW-DAMP-INFO {
    description "IM show dampening bag";

    container interface-dampening {
      description "Interface dampening";
      uses IM-SHOW-DAMP-NODE-INFO;
    }
    leaf state-transition-count {
      xr:xr-xml-map "im_show_edm:StateTransitionCount";
      type uint32;
      description "The number of times the state has changed";
    }
    leaf last-state-transition-time {
      xr:xr-xml-map "im_show_edm:LastStateTransitionTime";
      type uint32;
      description
        "The time elasped after the last state transition";
    }
    leaf is-dampening-enabled {
      xr:xr-xml-map "im_show_edm:IsDampeningEnabled";
      type boolean;
      description "Flag showing if dampening is enabled";
    }
    leaf half-life {
      xr:xr-xml-map "im_show_edm:HalfLife";
      type uint32;
      units "minute";
      description "Configured decay half life in mins";
    }
    leaf reuse-threshold {
      xr:xr-xml-map "im_show_edm:ReuseThreshold";
      type uint32;
      description "Configured reuse threshold";
    }
    leaf suppress-threshold {
      xr:xr-xml-map "im_show_edm:SuppressThreshold";
      type uint32;
      description "Value of suppress threshold";
    }
    leaf maximum-suppress-time {
      xr:xr-xml-map "im_show_edm:MaximumSuppressTime";
      type uint32;
      units "minute";
      description "Maximum suppress time in mins";
    }
    leaf restart-penalty {
      xr:xr-xml-map "im_show_edm:RestartPenalty";
      type uint32;
      description "Configured restart penalty";
    }

    list capsulation {
      description "Dampening information for capsulations";
      uses IM-SHOW-DAMP-NODE;
    }
  }
}
