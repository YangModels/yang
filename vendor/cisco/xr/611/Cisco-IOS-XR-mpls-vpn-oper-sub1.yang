submodule Cisco-IOS-XR-mpls-vpn-oper-sub1 {

  belongs-to Cisco-IOS-XR-mpls-vpn-oper {
    prefix Cisco-IOS-XR-mpls-vpn-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR mpls-vpn package operational data.

     Copyright (c) 2013-2016 by Cisco Systems, Inc.
     All rights reserved.";

  revision "2015-11-09" {
    description
      "IOS XR 6.0 revision.";
  }

  typedef Mpls-vpn-rt {
    type enumeration {
      enum import {
        value 1;
        description "VRF Route Target Type Import";
      }
      enum export {
        value 2;
        description "VRF Route Target Type Export";
      }
      enum both {
        value 3;
        description "VRF Route Target Type Import and Export";
      }
    }
    description "Layer 3 VPN Route Target Type";
  }
  typedef Mpls-vpn-safi {
    type enumeration {
      enum unicast {
        value 1;
        description "VRF Unicast sub-address family";
      }
      enum multicast {
        value 2;
        description "VRF Multicast sub-address family";
      }
      enum flowspec {
        value 133;
        description "VRF Flowspec sub-address family";
      }
    }
    description "Layer 3 VPN Sub-Address Family Type";
  }
  typedef Mpls-vpn-afi {
    type enumeration {
      enum ipv4 {
        value 1;
        description "VRF IPv4 address family";
      }
      enum ipv6 {
        value 2;
        description "VRF IPv6 address family";
      }
    }
    description "Layer 3 VPN Address Family Type";
  }

  grouping MPLS-VPN-RT {
    description "Layer 3 VPN Route Target";
    leaf route-target-type {
      xr:xr-xml-map "mpls_vpn:RouteTargetType";
      type Mpls-vpn-rt;
      description "Route Target Type";
    }
    leaf route-target-value {
      xr:xr-xml-map "mpls_vpn:RouteTargetValue";
      type string;
      description "Route Target Value";
    }
    leaf af-name {
      xr:xr-xml-map "mpls_vpn:AFName";
      type Mpls-vpn-afi;
      description "AF name";
    }
    leaf saf-name {
      xr:xr-xml-map "mpls_vpn:SAFName";
      type Mpls-vpn-safi;
      description "SAF name";
    }
  }

  grouping MPLS-VPN-AFI-SAFI {
    description "Layer 3 VPN AFI/SAFI Info";
    leaf af-name {
      xr:xr-xml-map "mpls_vpn:AFName";
      type Mpls-vpn-afi;
      description "AF name";
    }
    leaf saf-name {
      xr:xr-xml-map "mpls_vpn:SAFName";
      type Mpls-vpn-safi;
      description "SAF name";
    }
    leaf import-route-policy {
      xr:xr-xml-map "mpls_vpn:ImportRoutePolicy";
      type string;
      description "Import Route Policy";
    }
    leaf export-route-policy {
      xr:xr-xml-map "mpls_vpn:ExportRoutePolicy";
      type string;
      description "Export Route Policy";
    }

    list route-target {
      description "Route Targets";
      uses MPLS-VPN-RT;
    }
  }

  grouping MPLS-VPN-INTERFACES {
    description "Layer 3 VPN Interface Names";
    leaf interface-name {
      xr:xr-xml-map "mpls_vpn:InterfaceName";
      type string;
      description "Interface Name";
    }
  }

  grouping MPLS-VPN-VRF {
    description "Layer 3 VPN VRF";
    leaf vrf-name-xr {
      xr:xr-xml-map "mpls_vpn:vrf-name-xr";
      type string;
      description "VRF Name";
    }
    leaf vrf-description {
      xr:xr-xml-map "mpls_vpn:VRFDescription";
      type string;
      description "VRF Description";
    }
    leaf route-distinguisher {
      xr:xr-xml-map "mpls_vpn:RouteDistinguisher";
      type string;
      description "Route Distinguisher";
    }
    leaf is-big-vrf {
      xr:xr-xml-map "mpls_vpn:isBigVrf";
      type boolean;
      description "VRF mode information";
    }

    list interface {
      description "Interfaces in VRF";
      uses MPLS-VPN-INTERFACES;
    }

    list af {
      description "AF/SAF information";
      uses MPLS-VPN-AFI-SAFI;
    }
  }
}
