module Cisco-IOS-XR-ncs1k-macsec-ea-oper {

  /*** NAMESPACE / PREFIX DEFINITION ***/

  namespace "http://cisco.com/ns/yang"+
    "/Cisco-IOS-XR-ncs1k-macsec-ea-oper";


  prefix "ncs1k-macsec-ea-oper";

  /*** LINKAGE (IMPORTS / INCLUDES) ***/

  import Cisco-IOS-XR-types { prefix "xr"; }

  include Cisco-IOS-XR-ncs1k-macsec-ea-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ncs1k-macsec-ea package operational data.

     This module contains definitions
     for the following management objects:
       ncs1k-macsec-oper: Macsec data

     Copyright (c) 2013-2016 by Cisco Systems, Inc.
     All rights reserved.";

  revision "2015-11-09" {
    description
      "IOS XR 6.0 revision.";
  }


  container ncs1k-macsec-oper {
    xr:xr-xml-map "ncs1k_macsec_ea_oper:Ncs1kMacsecOper";
    config false;
    description "Macsec data";

    container ncs1k-macsec-ctrlr-names {
      xr:xr-xml-map "ncs1k_macsec_ea_oper:Ncs1kMacsecPortTable";
      description "All Macsec operational data";

      list ncs1k-macsec-ctrlr-name {
        xr:xr-xml-map "ncs1k_macsec_ea_oper:Ncs1kMacsecCtrlrName";
        key "name";
        description "Interface name";

        container ncs1k-status-info {
          xr:xr-xml-map "ncs1k_macsec_ea_oper:Ncs1kStatusInfo";
          description "controller data";
          uses NCS1K-MACSEC-IF-STATUS;
        }
        leaf name {
          xr:xr-xml-map "ncs1k_macsec_ea_oper:Name";
          type xr:Interface-name;
          description "Port name";
        }
      }
    }
  }
}
