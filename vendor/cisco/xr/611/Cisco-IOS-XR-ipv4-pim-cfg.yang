module Cisco-IOS-XR-ipv4-pim-cfg {

  /*** NAMESPACE / PREFIX DEFINITION ***/

  namespace "http://cisco.com/ns/yang/Cisco-IOS-XR-ipv4-pim-cfg";


  prefix "ipv4-pim-cfg";

  /*** LINKAGE (IMPORTS / INCLUDES) ***/

  import ietf-inet-types { prefix "inet"; }

  import Cisco-IOS-XR-types { prefix "xr"; }

  import Cisco-IOS-XR-ipv4-autorp-datatypes { prefix "dt1"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ipv4-pim package configuration.

     This module contains definitions
     for the following management objects:
       pim: PIM configuration

     Copyright (c) 2013-2016 by Cisco Systems, Inc.
     All rights reserved.";

  revision "2016-06-01" {
    description
      "Migrated multipath and ssm commands to PIM";
  }

  revision "2015-11-09" {
    description
      "IOS XR 6.0 revision.";
  }

  typedef Auto-rp-announce-period {
    type uint32 {
      range "1..600";
    }
    description "Auto rp announce period";
  }
  typedef Pim-multipath {
    type enumeration {
      enum enable {
        value 0;
        description "Enable PIM multipath";
      }
      enum interface-hash {
        value 1;
        description
          "Enable PIM multipath with interface based
          hashing";
      }
      enum source-hash {
        value 2;
        description
          "Enable PIM multipath with source based hashing";
      }
      enum source-next-hop-hash {
        value 3;
        description
          "Enable PIM multipath with source next-hop
          hashing";
      }
      enum source-group-hash {
        value 4;
        description
          "Enable PIM multipath with source, group based
          hashing";
      }
    }
    description "Pim multipath";
  }
  typedef Protocol-mode {
    type uint32 {
      range "0..1";
    }
    description "Protocol mode";
  }
  typedef Auto-rp-ttl {
    type uint32 {
      range "1..255";
    }
    description "Auto rp ttl";
  }
  typedef Priority {
    type uint32 {
      range "1..255";
    }
    description "Priority";
  }

  grouping SUPPRESS-DATA-REGISTERS {
    description "Common node of ipv4, ipv6";
    leaf suppress-data-registers {
      xr:xr-xml-map "ipv4_pim_common_cfg:SuppressDataRegisters";
      type empty;
      description
        "Suppress data registers after initial state
        setup";
    }
  }

  grouping ROUTE-POLICY {
    description "Common node of rpf, rpf-redirect";
    leaf route-policy {
      xr:xr-xml-map "ipv4_pim_common_cfg:RoutePolicy";
      type string;
      description "Route policy to select RPF topology";
    }
  }

  grouping JOIN-PRUNE-MTU {
    description "Common node of inheritable-defaults, interface";
    leaf join-prune-mtu {
      xr:xr-xml-map "ipv4_pim_common_cfg:JoinPruneMTU";
      type uint32 {
        range "576..65535";
      }
      units "byte";
      description "Join-Prune MTU in Bytes";
    }
  }

  grouping NEIGHBOR-CHECK-ON-RECEIVE {
    description "Common node of ipv4, ipv6";
    leaf neighbor-check-on-receive {
      xr:xr-xml-map "ipv4_pim_common_cfg:NeighborCheckOnReceive";
      type empty;
      description
        "Enable PIM neighbor checking when receiving PIM
        messages";
    }
  }

  grouping RPF {
    description "Common node of ipv4, ipv6";

    container rpf {
      xr:xr-xml-map "ipv4_pim_common_cfg:RPF";
      description "Configure RPF options";
      uses ROUTE-POLICY;
    }
  }

  grouping NEIGHBOR-CHECK-ON-SEND {
    description "Common node of ipv4, ipv6";
    leaf neighbor-check-on-send {
      xr:xr-xml-map "ipv4_pim_common_cfg:NeighborCheckOnSend";
      type empty;
      description
        "Enable PIM neighbor checking when sending
        join-prunes";
    }
  }

  grouping BSR {
    description "Common node of ipv4, ipv6";

    container bsr {
      xr:xr-xml-map "ipv4_pim_common_cfg:BSR";
      description "PIM BSR configuration";

      container candidate-rps {
        description "PIM RP configuration";

        list candidate-rp {
          key "address";
          description "BSR Candidate RP Configuration";

          grouping PARAMS {
            description
              "Parameters of BSR Candidate RP Configuration";
            leaf access-list-name {
              xr:xr-xml-map "ipv4_pim_common_cfg:AccessListName";
              type string;
              description
                "Access-list specifying the group range for
                the Candidate-RP";
            }
            leaf priority {
              xr:xr-xml-map "ipv4_pim_common_cfg:Priority";
              type Priority;
              default "192";
              description "Priority of the CRP";
            }
            leaf protocol-mode {
              xr:xr-xml-map "ipv4_pim_common_cfg:ProtocolMode";
              type Protocol-mode;
              description "CRP Mode";
            }
            leaf interval {
              xr:xr-xml-map "ipv4_pim_common_cfg:Interval";
              type uint32 {
                range "30..600";
              }
              default "60";
              description "Advertisement interval";
            }
          }

          container sm {
            must "protocol-mode = 0" {
              description "Must specify SM";
            }
            description "Parameters of PIM SM BSR Candidate-RP";
            uses PARAMS;
          }

          container bidir {
            must "protocol-mode = 1" {
              description "Must specify Bidir";
            }
            description "Parameters of PIM Bidir BSR Candidate-RP";
            uses PARAMS;
          }
          leaf address {
            xr:xr-xml-map "ipv4_pim_common_cfg:Address";
            type inet:ip-address-no-zone;
            description "Address of Candidate-RP";
          }
        }
      }

      container candidate-bsr {
        xr:xr-xml-map "ipv4_pim_common_cfg:CandidateBSR";
        presence "Indicates a candidate-bsr node is configured.";
        description "PIM Candidate BSR configuration";
        leaf address {
          xr:xr-xml-map "ipv4_pim_common_cfg:Address";
          type inet:ip-address-no-zone;
          mandatory true;
          description "BSR Address configured";
        }
        leaf prefix-length {
          xr:xr-xml-map "ipv4_pim_common_cfg:PrefixLength";
          type int32;
          default "30";
          description "Hash Mask Length for this candidate BSR";
        }
        leaf priority {
          xr:xr-xml-map "ipv4_pim_common_cfg:Priority";
          type Priority;
          default "1";
          description "Priority of the Candidate BSR";
        }
      }
    }
  }

  grouping SPARSE-MODE-RP-ADDRESS-TABLE {
    description "Common node of ipv4, ipv6";

    container sparse-mode-rp-addresses {
      xr:xr-xml-map "ipv4_pim_common_cfg:SparseModeRPAddressTable";
      description "Configure Sparse-Mode Rendezvous Point";

      list sparse-mode-rp-address {
        xr:xr-xml-map "ipv4_pim_common_cfg:SparseModeRPAddress";
        key "rp-address";
        description "Address of the Rendezvous Point";
        leaf rp-address {
          xr:xr-xml-map "ipv4_pim_common_cfg:RPAddress";
          type inet:ip-address-no-zone;
          description "RP address of Rendezvous Point";
        }
        leaf access-list-name {
          xr:xr-xml-map "ipv4_pim_common_cfg:AccessListName";
          type string;
          description
            "Access list of groups that should map to a 
            given RP";
        }
        leaf auto-rp-override {
          xr:xr-xml-map "ipv4_pim_common_cfg:AutoRPOverride";
          type boolean;
          description
            "TRUE Indicates if static RP config overrides
            AutoRP and BSR";
        }
      }
    }
  }

  grouping INHERITABLE-DEFAULTS {
    description "Common node of ipv4, ipv6";

    container inheritable-defaults {
      xr:xr-xml-map "ipv4_pim_common_cfg:InheritableDefaults";
      description "Inheritable defaults";
      leaf convergency {
        xr:xr-xml-map "ipv4_pim_common_cfg:Convergency";
        type uint32 {
          range "1800..2400";
        }
        units "second";
        description "Convergency timeout in seconds";
      }
      uses HELLO-INTERVAL;
      uses PROPAGATION-DELAY;
      uses DR-PRIORITY;
      uses JOIN-PRUNE-MTU;
      uses JP-INTERVAL;
      uses OVERRIDE-INTERVAL;
    }
  }

  grouping RP-STATIC-DENY {
    description "Common node of ipv4, ipv6";
    leaf rp-static-deny {
      xr:xr-xml-map "ipv4_pim_common_cfg:RPStaticDeny";
      type string;
      description "Configure static RP deny range";
    }
  }

  grouping SSM {
    description "Common node of ipv4, ipv6";

    container ssm {
      xr:xr-xml-map "ipv4_pim_common_cfg:SSM";
      description "Configure IP Multicast SSM";
      leaf disable {
        xr:xr-xml-map "ipv4_pim_common_cfg:Disable";
        type boolean;
        default "false";
        description "TRUE if SSM is disabled on this router";
      }
      leaf range {
        xr:xr-xml-map "ipv4_pim_common_cfg:Range";
        type string;
        description "Access list of groups enabled with SSM";
      }
    }
  }

  grouping OVERRIDE-INTERVAL {
    description "Common node of inheritable-defaults, interface";
    leaf override-interval {
      xr:xr-xml-map "ipv4_pim_common_cfg:OverrideInterval";
      type uint32 {
        range "400..65535";
      }
      units "millisecond";
      description "Override interval in milliseconds";
    }
  }

  grouping CONVERGENCE {
    description "Common node of ipv4, ipv6";

    container convergence {
      xr:xr-xml-map "ipv4_pim_common_cfg:Convergence";
      description "Configure convergence parameters";
      leaf rpf-conflict-join-delay {
        xr:xr-xml-map "ipv4_pim_common_cfg:RPFConflictJoinDelay";
        type uint32 {
          range "0..15";
        }
        units "second";
        description
          "Dampen first join if RPF path is through one of
          the downstream neighbor";
      }
      leaf link-down-prune-delay {
        xr:xr-xml-map "ipv4_pim_common_cfg:LinkDownPruneDelay";
        type uint32 {
          range "0..60";
        }
        units "second";
        description
          "Delay prunes if route join state transitions to
          not-joined on link down";
      }
    }
  }

  grouping REGISTER-SOURCE {
    description "Common node of ipv4, ipv6";
    leaf register-source {
      xr:xr-xml-map "ipv4_pim_common_cfg:RegisterSource";
      type xr:Interface-name;
      description "Source address to use for register messages";
    }
  }

  grouping PROPAGATION-DELAY {
    description "Common node of inheritable-defaults, interface";
    leaf propagation-delay {
      xr:xr-xml-map "ipv4_pim_common_cfg:PropagationDelay";
      type uint32 {
        range "100..32767";
      }
      units "millisecond";
      description "Propagation delay in milli seconds";
    }
  }

  grouping SPT-THRESHOLD-INFINITY {
    description "Common node of ipv4, ipv6";
    leaf spt-threshold-infinity {
      xr:xr-xml-map "ipv4_pim_common_cfg:SPTThresholdInfinity";
      type string;
      description
        "Configure threshold of infinity for switching to
        SPT on last-hop";
    }
  }

  grouping NEIGHBOR-FILTER {
    description "Common node of ipv4, ipv6";
    leaf neighbor-filter {
      xr:xr-xml-map "ipv4_pim_common_cfg:NeighborFilter";
      type string;
      description "Access-list of neighbors to be filtered";
    }
  }

  grouping SSM-ALLOW-OVERRIDE {
    description "Common node of ipv4, ipv6";
    leaf ssm-allow-override {
      xr:xr-xml-map "ipv4_pim_common_cfg:SSMAllowOverride";
      type empty;
      description
        "Allow SSM ranges to be overridden by more
        specific ranges";
    }
  }

  grouping IPV4 {
    description "Common node of vrf, default-context";

    container ipv4 {
      xr:xr-xml-map "ipv4_pim_cfg:IPV4";
      description "IPV4 commands";

      container cs-multicast-only-frrs {
        xr:xr-xml-map "ipv4_pim_cfg:CloneSourceMulticastOnlyFRR";
        description "Clone Source Multicast Only FRR";

        list cs-multicast-only-frr {
          xr:xr-xml-map "ipv4_pim_cfg:CSMulticastOnlyFRR";
          key "source primary backup prefix-length";
          description "Clone Source Multicast Only FRR";
          leaf source {
            xr:xr-xml-map "ipv4_pim_cfg:Source";
            type inet:ip-address-no-zone;
            description "Original address";
          }
          leaf primary {
            xr:xr-xml-map "ipv4_pim_cfg:Primary";
            type inet:ip-address-no-zone;
            description "Primary address";
          }
          leaf backup {
            xr:xr-xml-map "ipv4_pim_cfg:Backup";
            type inet:ip-address-no-zone;
            description "Backup address";
          }
          leaf prefix-length {
            xr:xr-xml-map "ipv4_pim_cfg:PrefixLength";
            type int32;
            description "Masklen";
          }
        }
      }

      container multicast-only-frr {
        xr:xr-xml-map "ipv4_pim_common_cfg:MulticastOnlyFRR";
        description "Multicast Only FRR";
        leaf non-revertive-multicast-only-frr {
          xr:xr-xml-map "ipv4_pim_common_cfg:NonRevertiveMulticastO"+
            "nlyFRR";
          type empty;
          description "Non-revertive Multicast Only FRR";
        }
        leaf flow-multicast-only-frr {
          xr:xr-xml-map "ipv4_pim_common_cfg:FlowMulticastOnlyFRR";
          type string;
          description
            "Access-list specifying SG that should do FLOW
            MOFRR";
        }
        leaf enable {
          xr:xr-xml-map "ipv4_pim_common_cfg:Enable";
          type empty;
          description "Enable Multicast Only FRR";
        }
        leaf rib-multicast-only-frr {
          xr:xr-xml-map "ipv4_pim_common_cfg:RIBMulticastOnlyFRR";
          type string;
          description
            "Access-list specifying SG that should do RIB
            MOFRR";
        }
      }

      container rpf-redirect {
        xr:xr-xml-map "ipv4_pim_common_cfg:RPFRedirect";
        description "Configure RPF-redirect feature";
        uses ROUTE-POLICY;
      }

      container paths {
        xr:xr-xml-map "ipv4_pim_cfg:RPFVectorInject";
        description "Inject PIM RPF Vector Proxy's";

        list path {
          xr:xr-xml-map "ipv4_pim_cfg:Path";
          key "source-address prefix-length";
          description "Inject PIM RPF Vector Proxy's";
          leaf source-address {
            xr:xr-xml-map "ipv4_pim_cfg:SourceAddress";
            type inet:ip-address-no-zone;
            description "Source Address";
          }
          leaf prefix-length {
            xr:xr-xml-map "ipv4_pim_cfg:PrefixLength";
            type int32;
            description "Masklen";
          }
          leaf-list rpf-proxy-address {
            xr:xr-xml-map "ipv4_pim_cfg:RPFProxyAddress";
            type inet:ipv4-address-no-zone;
            min-elements "1";
            max-elements "22";
            description "RPF Proxy Address";
          }
        }
      }

      container cj-multicast-only-frrs {
        xr:xr-xml-map "ipv4_pim_cfg:CloneJoinMulticastOnlyFRR";
        description "Clone Join Multicast Only FRR";

        list cj-multicast-only-frr {
          xr:xr-xml-map "ipv4_pim_cfg:CJMulticastOnlyFRR";
          key "source primary backup prefix-length";
          description "Clone Join Multicast Only FRR";
          leaf source {
            xr:xr-xml-map "ipv4_pim_cfg:Source";
            type inet:ip-address-no-zone;
            description "Original address";
          }
          leaf primary {
            xr:xr-xml-map "ipv4_pim_cfg:Primary";
            type inet:ip-address-no-zone;
            description "Primary address";
          }
          leaf backup {
            xr:xr-xml-map "ipv4_pim_cfg:Backup";
            type inet:ip-address-no-zone;
            description "Backup address";
          }
          leaf prefix-length {
            xr:xr-xml-map "ipv4_pim_cfg:PrefixLength";
            type int32;
            description "Masklen";
          }
        }
      }

      container auto-rp {
        xr:xr-xml-map "ipv4_pim_common_cfg:AutoRP";
        description "PIM AutoRP configuration";
      }

      container auto-rp-mapping-agent {
        xr:xr-xml-map "ipv4_multicast_autorp_cfg:AutoRPMappingAgent";
        description "Configure AutoRP Mapping Agent";

        container parameters {
          xr:xr-xml-map "ipv4_multicast_autorp_cfg:Parameters";
          presence "Indicates a parameters node is configured.";
          description
            "Specifications for Mapping Agent configured on
            this box";
          leaf interface-name {
            xr:xr-xml-map "ipv4_multicast_autorp_cfg:InterfaceName";
            type xr:Interface-name;
            mandatory true;
            description
              "Interface from which mapping packets will be
              sourced ";
          }
          leaf ttl {
            xr:xr-xml-map "ipv4_multicast_autorp_cfg:TTL";
            type Auto-rp-ttl;
            mandatory true;
            description "TTL in Hops";
          }
          leaf announce-period {
            xr:xr-xml-map "ipv4_multicast_autorp_cfg:AnnouncePeriod";
            type Auto-rp-announce-period;
            units "second";
            default "60";
            description
              "Time between discovery messages <in seconds>";
          }
        }

        container cache-limit {
          xr:xr-xml-map "ipv4_multicast_autorp_cfg:CacheLimit";
          presence "Indicates a cache-limit node is configured.";
          description "Mapping Agent cache size limit";
          leaf maximum-cache-entry {
            xr:xr-xml-map "ipv4_multicast_autorp_cfg:MaximumCacheEn"+
              "try";
            type uint32 {
              range "1..1000";
            }
            mandatory true;
            description "Maximum number of mapping cache entries";
          }
          leaf threshold-cache-entry {
            xr:xr-xml-map "ipv4_multicast_autorp_cfg:ThresholdCache"+
              "Entry";
            type uint32 {
              range "1..1000";
            }
            default "450";
            description "Warning threshold number of cache entries";
          }
        }
      }

      container candidate-rps {
        xr:xr-xml-map "ipv4_multicast_autorp_cfg:CandidateRPTable";
        description "Configure Candidate-RPs";

        list candidate-rp {
          xr:xr-xml-map "ipv4_multicast_autorp_cfg:CandidateRP";
          key "interface-name protocol-mode";
          description "Specifications for a Candidate-RP";

          container candidate-rp-range {
            xr:xr-xml-map "ipv4_multicast_autorp_cfg:CandidateRPRan"+
              "ge";
            presence "Indicates a candidate-rp-range node is"+
              " configured.";
            description
              "Configure the group range for the
              Candidate-RP";
            leaf ttl {
              xr:xr-xml-map "ipv4_multicast_autorp_cfg:TTL";
              type Auto-rp-ttl;
              mandatory true;
              description "TTL in Hops";
            }
            leaf access-list-name {
              xr:xr-xml-map "ipv4_multicast_autorp_cfg:AccessListNa"+
                "me";
              type string;
              default "224-4";
              description
                "Access-list specifying the group range for
                the Candidate-RP";
            }
            leaf announce-period {
              xr:xr-xml-map "ipv4_multicast_autorp_cfg:AnnouncePeri"+
                "od";
              type Auto-rp-announce-period;
              units "second";
              default "60";
              description
                "Time between announcements <in seconds> ";
            }
          }
          leaf interface-name {
            xr:xr-xml-map "ipv4_multicast_autorp_cfg:InterfaceName";
            type xr:Interface-name;
            description
              "Interface from which Candidate-RP packets
              will be sourced";
          }
          leaf protocol-mode {
            xr:xr-xml-map "ipv4_multicast_autorp_cfg:ProtocolMode";
            type dt1:Auto-rp-protocol-mode;
            description "Protocol Mode";
          }
        }
      }

      container injects {
        xr:xr-xml-map "ipv4_pim_cfg:ExplicitRPFVector";
        description "Inject Explicit PIM RPF Vector Proxy's";

        list inject {
          xr:xr-xml-map "ipv4_pim_cfg:Inject";
          key "source-address prefix-length";
          description "Inject Explicit PIM RPF Vector Proxy's";
          leaf source-address {
            xr:xr-xml-map "ipv4_pim_cfg:SourceAddress";
            type inet:ip-address-no-zone;
            description "Source Address";
          }
          leaf prefix-length {
            xr:xr-xml-map "ipv4_pim_cfg:PrefixLength";
            type int32;
            description "Masklen";
          }
          leaf-list rpf-proxy-address {
            xr:xr-xml-map "ipv4_pim_cfg:RPFProxyAddress";
            type inet:ipv4-address-no-zone;
            min-elements "1";
            max-elements "22";
            description "RPF Proxy Address";
          }
        }
      }
      leaf auto-rp-disable {
        xr:xr-xml-map "ipv4_pim_cfg:AutoRPDisable";
        type empty;
        description
          "Disable Rendezvous Point discovery through the
          AutoRP protocol";
      }
      uses NEIGHBOR-CHECK-ON-RECEIVE;
      uses OLD-REGISTER-CHECKSUM;
      uses SPARSE-MODE-RP-ADDRESS-TABLE;
      uses NEIGHBOR-FILTER;
      uses INHERITABLE-DEFAULTS;
      uses SPT-THRESHOLD-INFINITY;
      uses LOG-NEIGHBOR-CHANGES;
      uses RPF;
      uses REGISTER-SOURCE;
      uses ACCEPT-REGISTER;
      uses SG-EXPIRY-TIMER;
      uses RPF-VECTOR-ENABLE;
      uses NSF;
      uses SUPPRESS-RPF-PRUNES;
      uses MAXIMUM;
      uses SSM;
      uses ASSERT-DISABLE;
      uses BIDIR-RP-ADDRESS-TABLE;
      uses SSM-ALLOW-OVERRIDE;
      uses BSR;
      uses MULTIPATH;
      uses INTERFACE-TABLE;
      uses RP-STATIC-DENY;
      uses ALLOW-RP;
      uses SUPPRESS-DATA-REGISTERS;
      uses NEIGHBOR-CHECK-ON-SEND;
      uses CONVERGENCE;
    }
  }

  grouping IPV6 {
    description "Common node of vrf, default-context";

    container ipv6 {
      xr:xr-xml-map "ipv6_pim_cfg:IPV6";
      description "IPV6 commands";

      container embedded-rp-addresses {
        xr:xr-xml-map "ipv6_pim_cfg:EmbeddedRP";
        description "Set Embedded RP processing support";

        list embedded-rp-address {
          xr:xr-xml-map "ipv6_pim_cfg:EmbeddedRPAddress";
          key "rp-address";
          description "Set Embedded RP processing support";
          leaf rp-address {
            xr:xr-xml-map "ipv6_pim_cfg:RPAddress";
            type inet:ip-address-no-zone;
            description "RP address of the Rendezvous Point";
          }
          leaf access-list-name {
            xr:xr-xml-map "ipv6_pim_cfg:AccessListName";
            type string;
            mandatory true;
            description
              "Access list of groups that should map to a
              given RP";
          }
        }
      }
      leaf embedded-rp-disable {
        xr:xr-xml-map "ipv6_pim_cfg:EmbeddedRPDisable";
        type empty;
        description "Set Embedded RP processing support";
      }
      uses NEIGHBOR-CHECK-ON-RECEIVE;
      uses OLD-REGISTER-CHECKSUM;
      uses SPARSE-MODE-RP-ADDRESS-TABLE;
      uses NEIGHBOR-FILTER;
      uses INHERITABLE-DEFAULTS;
      uses SPT-THRESHOLD-INFINITY;
      uses LOG-NEIGHBOR-CHANGES;
      uses RPF;
      uses REGISTER-SOURCE;
      uses ACCEPT-REGISTER;
      uses SG-EXPIRY-TIMER;
      uses RPF-VECTOR-ENABLE;
      uses NSF;
      uses SUPPRESS-RPF-PRUNES;
      uses MAXIMUM;
      uses SSM;
      uses ASSERT-DISABLE;
      uses BIDIR-RP-ADDRESS-TABLE;
      uses SSM-ALLOW-OVERRIDE;
      uses BSR;
      uses MULTIPATH;
      uses INTERFACE-TABLE;
      uses RP-STATIC-DENY;
      uses ALLOW-RP;
      uses SUPPRESS-DATA-REGISTERS;
      uses NEIGHBOR-CHECK-ON-SEND;
      uses CONVERGENCE;
    }
  }

  grouping LOG-NEIGHBOR-CHANGES {
    description "Common node of ipv4, ipv6";
    leaf log-neighbor-changes {
      xr:xr-xml-map "ipv4_pim_common_cfg:LogNeighborChanges";
      type empty;
      description
        "PIM neighbor state change logging is turned on
        if configured";
    }
  }

  grouping MAXIMUM {
    description "Common node of ipv4, ipv6";

    container maximum {
      xr:xr-xml-map "ipv4_pim_common_cfg:Maximum";
      description "Configure PIM State Limits";

      container group-mappings-auto-rp {
        xr:xr-xml-map "ipv4_pim_common_cfg:GroupMappingsAutoRP";
        description
          "Override default maximum for number of group
          mappings from autorp mapping agent";
        leaf maximum-group-ranges-auto-rp {
          xr:xr-xml-map "ipv4_pim_common_cfg:MaximumGroupRangesAuto"+
            "RP";
          type uint32 {
            range "1..10000";
          }
          default "500";
          description
            "Maximum number of PIM group mappings from
            autorp";
        }
        leaf threshold-group-ranges-auto-rp {
          xr:xr-xml-map "ipv4_pim_common_cfg:ThresholdGroupRangesAu"+
            "toRP";
          type uint32 {
            range "1..10000";
          }
          default "450";
          description
            "Warning threshold number of PIM group mappings
            from autorp";
        }
      }

      container bsr-global-group-mappings {
        xr:xr-xml-map "ipv4_pim_common_cfg:BSRGlobalGroupMappings";
        presence "Indicates a bsr-global-group-mappings node is"+
          " configured.";
        description
          "Override default global maximum and threshold
          for PIM group mapping ranges from BSR";
        leaf bsr-maximum-global-group-mappings {
          xr:xr-xml-map "ipv4_pim_common_cfg:BSRMaximumGlobalGroupM"+
            "appings";
          type uint32 {
            range "1..10000";
          }
          mandatory true;
          description
            "Global Maximum number of PIM group mapping
            ranges from BSR";
        }
        leaf warning-threshold {
          xr:xr-xml-map "ipv4_pim_common_cfg:WarningThreshold";
          type uint32 {
            range "1..10000";
          }
          default "500";
          description "Set threshold to print warning";
        }
      }

      container global-routes {
        xr:xr-xml-map "ipv4_pim_common_cfg:GlobalRoutes";
        description "Override default maximum for number of routes";
        leaf maximum-routes {
          xr:xr-xml-map "ipv4_pim_common_cfg:MaximumRoutes";
          type uint32 {
            range "1..200000";
          }
          default "100000";
          description "Maximum number of PIM routes";
        }
        leaf warning-threshold {
          xr:xr-xml-map "ipv4_pim_common_cfg:WarningThreshold";
          type uint32 {
            range "1..200000";
          }
          default "100000";
          description "Set threshold to print warning";
        }
      }

      container bsr-group-mappings {
        xr:xr-xml-map "ipv4_pim_common_cfg:BSRGroupMappings";
        description
          "Override default maximum and threshold for
          number of group mappings from BSR";
        leaf bsr-maximum-group-ranges {
          xr:xr-xml-map "ipv4_pim_common_cfg:BSRMaximumGroupRanges";
          type uint32 {
            range "1..10000";
          }
          default "500";
          description
            "Maximum number of PIM group mappings from BSR";
        }
        leaf warning-threshold {
          xr:xr-xml-map "ipv4_pim_common_cfg:WarningThreshold";
          type uint32 {
            range "1..10000";
          }
          default "500";
          description "Set threshold to print warning";
        }
      }

      container global-group-mappings-auto-rp {
        xr:xr-xml-map "ipv4_pim_common_cfg:GlobalGroupMappingsAutoR"+
          "P";
        description
          "Maximum for number of group mappings from
          autorp mapping agent";
        leaf maximum-global-group-ranges-auto-rp {
          xr:xr-xml-map "ipv4_pim_common_cfg:MaximumGlobalGroupRang"+
            "esAutoRP";
          type uint32 {
            range "1..10000";
          }
          default "500";
          description
            "Maximum number of PIM group mappings from
            autorp";
        }
        leaf threshold-global-group-ranges-auto-rp {
          xr:xr-xml-map "ipv4_pim_common_cfg:ThresholdGlobalGroupRa"+
            "ngesAutoRP";
          type uint32 {
            range "1..10000";
          }
          default "450";
          description
            "Warning threshold number of PIM group mappings
            from autorp";
        }
      }

      container register-states {
        xr:xr-xml-map "ipv4_pim_common_cfg:RegisterStates";
        description
          "Override default maximum for number of
          sparse-mode source registers";
        leaf maximum-register-states {
          xr:xr-xml-map "ipv4_pim_common_cfg:MaximumRegisterStates";
          type uint32 {
            range "0..75000";
          }
          default "20000";
          description
            "Maximum number of PIM Sparse-Mode register
            states";
        }
        leaf warning-threshold {
          xr:xr-xml-map "ipv4_pim_common_cfg:WarningThreshold";
          type uint32 {
            range "0..75000";
          }
          default "20000";
          description "Set threshold to print warning";
        }
      }

      container route-interfaces {
        xr:xr-xml-map "ipv4_pim_common_cfg:RouteInterfaces";
        description
          "Override default maximum for number of
          route-interfaces";
        leaf maximum-route-interfaces {
          xr:xr-xml-map "ipv4_pim_common_cfg:MaximumRouteInterfaces";
          type uint32 {
            range "1..1100000";
          }
          default "300000";
          description "Maximum number of PIM route-interfaces";
        }
        leaf warning-threshold {
          xr:xr-xml-map "ipv4_pim_common_cfg:WarningThreshold";
          type uint32 {
            range "1..1100000";
          }
          default "300000";
          description "Set threshold to print warning";
        }
      }

      container bsr-global-candidate-rp-cache {
        xr:xr-xml-map "ipv4_pim_common_cfg:BSRGlobalCandidateRPCach"+
          "e";
        presence "Indicates a bsr-global-candidate-rp-cache node is"+
          " configured.";
        description
          "Override default global maximum and threshold
          for C-RP set in BSR";
        leaf bsr-maximum-global-candidate-rp-cache {
          xr:xr-xml-map "ipv4_pim_common_cfg:BSRMaximumGlobalCandid"+
            "ateRPCache";
          type uint32 {
            range "1..10000";
          }
          mandatory true;
          description
            "Global Maximum number of PIM C-RP Sets from
            BSR";
        }
        leaf warning-threshold {
          xr:xr-xml-map "ipv4_pim_common_cfg:WarningThreshold";
          type uint32 {
            range "1..10000";
          }
          default "100";
          description "Set threshold to print warning";
        }
      }

      container bsr-candidate-rp-cache {
        xr:xr-xml-map "ipv4_pim_common_cfg:BSRCandidateRPCache";
        description
          "Override default maximum and threshold for BSR
          C-RP cache setting";
        leaf bsr-maximum-candidate-rp-cache {
          xr:xr-xml-map "ipv4_pim_common_cfg:BSRMaximumCandidateRPC"+
            "ache";
          type uint32 {
            range "1..10000";
          }
          default "100";
          description "Maximum number of BSR C-RP cache setting";
        }
        leaf warning-threshold {
          xr:xr-xml-map "ipv4_pim_common_cfg:WarningThreshold";
          type uint32 {
            range "1..10000";
          }
          default "100";
          description "Set threshold to print warning";
        }
      }

      container global-register-states {
        xr:xr-xml-map "ipv4_pim_common_cfg:GlobalRegisterStates";
        description
          "Override default maximum for number of
          sparse-mode source registers";
        leaf maximum-register-states {
          xr:xr-xml-map "ipv4_pim_common_cfg:MaximumRegisterStates";
          type uint32 {
            range "0..75000";
          }
          default "20000";
          description
            "Maximum number of PIM Sparse-Mode register
            states";
        }
        leaf warning-threshold {
          xr:xr-xml-map "ipv4_pim_common_cfg:WarningThreshold";
          type uint32 {
            range "0..75000";
          }
          default "20000";
          description "Set threshold to print warning";
        }
      }

      container global-route-interfaces {
        xr:xr-xml-map "ipv4_pim_common_cfg:GlobalRouteInterfaces";
        description
          "Override default maximum for number of
          route-interfaces";
        leaf maximum-route-interfaces {
          xr:xr-xml-map "ipv4_pim_common_cfg:MaximumRouteInterfaces";
          type uint32 {
            range "1..1100000";
          }
          default "300000";
          description "Maximum number of PIM route-interfaces";
        }
        leaf warning-threshold {
          xr:xr-xml-map "ipv4_pim_common_cfg:WarningThreshold";
          type uint32 {
            range "1..1100000";
          }
          default "300000";
          description "Set threshold to print warning";
        }
      }

      container routes {
        xr:xr-xml-map "ipv4_pim_common_cfg:Routes";
        description "Override default maximum for number of routes";
        leaf maximum-routes {
          xr:xr-xml-map "ipv4_pim_common_cfg:MaximumRoutes";
          type uint32 {
            range "1..200000";
          }
          default "100000";
          description "Maximum number of PIM routes";
        }
        leaf warning-threshold {
          xr:xr-xml-map "ipv4_pim_common_cfg:WarningThreshold";
          type uint32 {
            range "1..200000";
          }
          default "100000";
          description "Set threshold to print warning";
        }
      }
      leaf gloabal-high-priority-packet-queue {
        xr:xr-xml-map "ipv4_pim_common_cfg:GloabalHighPriorityPacke"+
          "tQueue";
        type uint32 {
          range "0..2147483648";
        }
        units "byte";
        description "Maximum packet queue size in bytes";
      }
      leaf gloabal-low-priority-packet-queue {
        xr:xr-xml-map "ipv4_pim_common_cfg:GloabalLowPriorityPacket"+
          "Queue";
        type uint32 {
          range "0..2147483648";
        }
        units "byte";
        description "Maximum packet queue size in bytes";
      }
    }
  }

  grouping SG-EXPIRY-TIMER {
    description "Common node of ipv4, ipv6";

    container sg-expiry-timer {
      xr:xr-xml-map "ipv4_pim_common_cfg:SGExpiryTimer";
      description "Configure expiry timer for S,G routes";
      leaf interval {
        xr:xr-xml-map "ipv4_pim_common_cfg:Interval";
        type uint32 {
          range "40..57600";
        }
        units "second";
        description "(S,G) expiry time in seconds";
      }
      leaf access-list-name {
        xr:xr-xml-map "ipv4_pim_common_cfg:AccessListName";
        type string;
        description "Access-list of applicable S,G routes";
      }
    }
  }

  grouping INTERFACE-TABLE {
    description "Common node of ipv4, ipv6";

    container interfaces {
      xr:xr-xml-map "ipv4_pim_common_cfg:InterfaceTable";
      description "Interface-level Configuration";

      list interface {
        xr:xr-xml-map "ipv4_pim_common_cfg:Interface";
        key "interface-name";
        description "The name of the interface";

        container redirect-bundle {
          xr:xr-xml-map "ipv4_pim_common_cfg:RedirectBundle";
          presence "Indicates a redirect-bundle node is configured.";
          description
            "Configure RPF-redirect bundle for interface.
            Applicable for IPv4 only";
          leaf bundle-name {
            xr:xr-xml-map "ipv4_pim_common_cfg:BundleName";
            type string;
            mandatory true;
            description "Bundle name";
          }
          leaf interface-bandwidth {
            xr:xr-xml-map "ipv4_pim_common_cfg:InterfaceBandwidth";
            type uint32 {
              range "0..100000000";
            }
            units "kbit/s";
            description "Interface bandwidth in Kbps";
          }
          leaf threshold-bandwidth {
            xr:xr-xml-map "ipv4_pim_common_cfg:ThresholdBandwidth";
            type uint32 {
              range "0..100000000";
            }
            units "kbit/s";
            description "Threshold bandwidth in Kbps";
          }
        }

        container bfd {
          xr:xr-xml-map "ipv4_pim_common_cfg:BFD";
          description "BFD configuration";
          leaf detection-multiplier {
            xr:xr-xml-map "ipv4_pim_common_cfg:DetectionMultiplier";
            type uint32 {
              range "2..50";
            }
            description
              "Detection multiplier for BFD sessions created
              by PIM";
          }
          leaf interval {
            xr:xr-xml-map "ipv4_pim_common_cfg:Interval";
            type uint32 {
              range "3..30000";
            }
            units "millisecond";
            description
              "Hello interval for BFD sessions created by
              PIM";
          }
          leaf enable {
            xr:xr-xml-map "ipv4_pim_common_cfg:Enable";
            type boolean;
            description
              "TRUE to enable BFD. FALSE to disable and to
              prevent inheritance from a parent";
          }
        }

        container oor {
          xr:xr-xml-map "ipv4_pim_common_cfg:OOR";
          description "Enable maximum routes per Interface";
          leaf maximum {
            xr:xr-xml-map "ipv4_pim_common_cfg:Maximum";
            type uint32 {
              range "1..1100000";
            }
            description "Maximum number of Routes per interface";
          }
          leaf warning-threshold {
            xr:xr-xml-map "ipv4_pim_common_cfg:WarningThreshold";
            type uint32 {
              range "1..1100000";
            }
            description "Set threshold to print warning";
          }
          leaf access-list-name {
            xr:xr-xml-map "ipv4_pim_common_cfg:AccessListName";
            type xr:Cisco-ios-xr-string {
              length "0..64";
            }
            description "Access-list to account for";
          }
        }
        leaf neighbor-filter {
          xr:xr-xml-map "ipv4_pim_common_cfg:NeighborFilter";
          type string;
          description "Access-list of neighbors to be filtered";
        }
        leaf bsr-border {
          xr:xr-xml-map "ipv4_pim_common_cfg:BSRBorder";
          type boolean;
          description "BSR Border configuration for Interface";
        }
        leaf enable {
          xr:xr-xml-map "ipv4_pim_common_cfg:Enable";
          type empty;
          description "Enter PIM Interface processing";
        }
        leaf interface-enable {
          xr:xr-xml-map "ipv4_pim_common_cfg:InterfaceEnable";
          type boolean;
          description "Enable PIM processing on the interface";
        }
        leaf interface-name {
          xr:xr-xml-map "ipv4_pim_common_cfg:InterfaceName";
          type xr:Interface-name;
          description "The name of interface";
        }
        uses HELLO-INTERVAL;
        uses PROPAGATION-DELAY;
        uses DR-PRIORITY;
        uses JOIN-PRUNE-MTU;
        uses JP-INTERVAL;
        uses OVERRIDE-INTERVAL;
      }
    }
  }

  grouping MULTIPATH {
    description "Common node of ipv4, ipv6";
    leaf multipath {
      xr:xr-xml-map "ipv4_pim_common_cfg:Multipath";
      type Pim-multipath;
      description "Enable equal-cost multipath routing";
    }
  }

  grouping HELLO-INTERVAL {
    description "Common node of inheritable-defaults, interface";
    leaf hello-interval {
      xr:xr-xml-map "ipv4_pim_common_cfg:HelloInterval";
      type uint32 {
        range "1..3600";
      }
      units "second";
      description "Hello interval in seconds";
    }
  }

  grouping BIDIR-RP-ADDRESS-TABLE {
    description "Common node of ipv4, ipv6";

    container bidir-rp-addresses {
      xr:xr-xml-map "ipv4_pim_common_cfg:BidirRPAddressTable";
      description "Configure Bidirectional PIM Rendezvous Point";

      list bidir-rp-address {
        xr:xr-xml-map "ipv4_pim_common_cfg:BidirRPAddress";
        key "rp-address";
        description "Address of the Rendezvous Point";
        leaf rp-address {
          xr:xr-xml-map "ipv4_pim_common_cfg:RPAddress";
          type inet:ip-address-no-zone;
          description "RP address of Rendezvous Point";
        }
        leaf access-list-name {
          xr:xr-xml-map "ipv4_pim_common_cfg:AccessListName";
          type string;
          description
            "Access list of groups that should map to a
            given RP";
        }
        leaf auto-rp-override {
          xr:xr-xml-map "ipv4_pim_common_cfg:AutoRPOverride";
          type boolean;
          description
            "TRUE Indicates if static RP config overrides
            AutoRP and BSR";
        }
      }
    }
  }

  grouping JP-INTERVAL {
    description "Common node of inheritable-defaults, interface";
    leaf jp-interval {
      xr:xr-xml-map "ipv4_pim_common_cfg:JPInterval";
      type uint32 {
        range "10..600";
      }
      units "second";
      description "Join-Prune interval in seconds";
    }
  }

  grouping NSF {
    description "Common node of ipv4, ipv6";

    container nsf {
      xr:xr-xml-map "ipv4_pim_common_cfg:NSF";
      description "Configure Non-stop forwarding (NSF) options";
      leaf lifetime {
        xr:xr-xml-map "ipv4_pim_common_cfg:Lifetime";
        type uint32 {
          range "10..600";
        }
        units "second";
        description
          "Override default maximum lifetime for PIM NSF
          mode";
      }
    }
  }

  grouping ASSERT-DISABLE {
    description "Common node of ipv4, ipv6";
    leaf assert-disable {
      xr:xr-xml-map "ipv4_pim_common_cfg:AssertDisable";
      type empty;
      description "Configuring batch asserts disable";
    }
  }

  grouping DR-PRIORITY {
    description "Common node of inheritable-defaults, interface";
    leaf dr-priority {
      xr:xr-xml-map "ipv4_pim_common_cfg:DRPriority";
      type uint32 {
        range "0..4294967295";
      }
      description
        "Hello DR priority, preference given to larger
        value";
    }
  }

  grouping ACCEPT-REGISTER {
    description "Common node of ipv4, ipv6";
    leaf accept-register {
      xr:xr-xml-map "ipv4_pim_common_cfg:AcceptRegister";
      type string;
      description
        "Access-list which specifies unauthorized sources";
    }
  }

  grouping OLD-REGISTER-CHECKSUM {
    description "Common node of ipv4, ipv6";
    leaf old-register-checksum {
      xr:xr-xml-map "ipv4_pim_common_cfg:OldRegisterChecksum";
      type empty;
      description
        "Generate registers compatible with older IOS
        versions";
    }
  }

  grouping ALLOW-RP {
    description "Common node of ipv4, ipv6";

    container allow-rp {
      xr:xr-xml-map "ipv4_pim_common_cfg:AllowRP";
      presence "enable allow-rp";
      description "Enable allow-rp filtering for SM joins";
      leaf rp-list-name {
        xr:xr-xml-map "ipv4_pim_common_cfg:RPListName";
        type string;
        description "Access-list specifiying applicable RPs";
      }
      leaf group-list-name {
        xr:xr-xml-map "ipv4_pim_common_cfg:GroupListName";
        type string;
        description "Access-list specifiying applicable groups";
      }
    }
  }

  grouping SUPPRESS-RPF-PRUNES {
    description "Common node of ipv4, ipv6";
    leaf suppress-rpf-prunes {
      xr:xr-xml-map "ipv4_pim_common_cfg:SuppressRPFPrunes";
      type empty;
      description
        "Suppress prunes triggered as a result of RPF
        changes";
    }
  }

  grouping RPF-VECTOR-ENABLE {
    description "Common node of ipv4, ipv6";

    container rpf-vector-enable {
      xr:xr-xml-map "ipv4_pim_common_cfg:RPFVectorEnable";
      presence "Indicates a rpf-vector-enable node is configured.";
      description "Enable PIM RPF Vector Proxy's";
      leaf enable {
        xr:xr-xml-map "ipv4_pim_common_cfg:Enable";
        type empty;
        mandatory true;
        description "RPF Vector is turned on if configured";
      }
      leaf allow-ebgp {
        xr:xr-xml-map "ipv4_pim_common_cfg:AllowEBGP";
        type boolean;
        description
          "Allow RPF Vector origination over eBGP sessions";
      }
      leaf disable-ibgp {
        xr:xr-xml-map "ipv4_pim_common_cfg:DisableIBGP";
        type boolean;
        description
          "Disable RPF Vector origination over iBGP
          sessions";
      }
    }
  }

  container pim {
    xr:xr-xml-map "ipv4_pim_cfg:PIM";
    presence "Indicates a pim node is configured.";
    description "PIM configuration";

    container vrfs {
      xr:xr-xml-map "ipv4_pim_cfg:VRFTable";
      description "VRF table";

      list vrf {
        xr:xr-xml-map "ipv4_pim_cfg:VRF";
        key "vrf-name";
        description "VRF name";
        leaf vrf-name {
          xr:xr-xml-map "ipv4_pim_cfg:VRFName";
          type xr:Cisco-ios-xr-string;
          description "VRF name";
        }
        uses IPV6;
        uses IPV4;
      }
    }

    container default-context {
      xr:xr-xml-map "ipv4_pim_cfg:DefaultContext";
      presence "Indicates a default-context node is configured.";
      description "Default Context";
      uses IPV6;
      uses IPV4;
    }
  }
}
