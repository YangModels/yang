submodule Cisco-IOS-XR-bundlemgr-oper-sub1 {

  belongs-to Cisco-IOS-XR-bundlemgr-oper {
    prefix Cisco-IOS-XR-bundlemgr-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR bundlemgr package operational data.

     Copyright (c) 2013-2016 by Cisco Systems, Inc.
     All rights reserved.";

  revision "2015-11-09" {
    description
      "IOS XR 6.0 revision.";
  }

  typedef Bundle-media1 {
    type enumeration {
      enum ethernet {
        value 0;
        description "Ethernet";
      }
      enum pos {
        value 1;
        description "POS";
      }
    }
    description "Bundle media1";
  }
  typedef Load-balance {
    type enumeration {
      enum default {
        value 0;
        description "Default";
      }
      enum auto {
        value 1;
        description "Auto";
      }
      enum value {
        value 2;
        description "Value";
      }
      enum source-ip {
        value 3;
        description "Source IP";
      }
      enum destination-ip {
        value 4;
        description "Destination IP";
      }
      enum unknown {
        value 5;
        description "Unknown";
      }
    }
    description "Load balance";
  }
  typedef Bundle-media {
    type enumeration {
      enum bundle-media-ethernet {
        value 0;
        description "bundle media ethernet";
      }
      enum bundle-media-pos {
        value 1;
        description "bundle media pos";
      }
      enum bundle-media-count {
        value 2;
        description "bundle media count";
      }
    }
    description "Bundle media";
  }
  typedef Bundle-mlacp-mode {
    type enumeration {
      enum bundle-mlacp-mode-standby {
        value 0;
        description "bundle mlacp mode standby";
      }
      enum bundle-mlacp-mode-active {
        value 1;
        description "bundle mlacp mode active";
      }
      enum bundle-mlacp-mode-count {
        value 2;
        description "bundle mlacp mode count";
      }
    }
    description "Bundle mlacp mode";
  }

  grouping BMA-MEMBER-ITEM {
    description "BMA MEMBER ITEM";
    leaf interface-name {
      xr:xr-xml-map "bundlemgr_adj:InterfaceName";
      type xr:Interface-name;
      description "Member interface";
    }
    leaf link-id {
      xr:xr-xml-map "bundlemgr_adj:LinkID";
      type uint8;
      description "Member's link ID in database";
    }
    leaf link-order-number {
      xr:xr-xml-map "bundlemgr_adj:LinkOrder_Number";
      type uint8;
      description "Member's link order number in database";
    }
    leaf bandwidth {
      xr:xr-xml-map "bundlemgr_adj:Bandwidth";
      type uint8;
      description "Member's relative bandwidth";
    }
  }

  grouping BMA-BUNDLE-DATA {
    description "Adjacency info for a single bundle";

    container brief {
      description "Brief bundle data";
      uses BMA-BRIEF-ITEM;
    }

    container load-balance-data {
      description "Load Balance data";
      uses BMA-LOAD-BALANCE-DATA;
    }
    leaf media {
      xr:xr-xml-map "bundlemgr_adj:Media";
      type Bundle-media1;
      description "Media type of bundle";
    }
    leaf max-member-count {
      xr:xr-xml-map "bundlemgr_adj:MaxMemberCount";
      type uint32;
      description "Maximum number of members for the bundle";
    }
    leaf avoid-rebalance {
      xr:xr-xml-map "bundlemgr_adj:AvoidRebalance";
      type boolean;
      description "Avoid rebalancing traffic flows";
    }

    list member {
      description "Members of the bundle";
      uses BMA-MEMBER-ITEM;
    }

    list sub-interface {
      description "Sub-interfaces of the bundle";
      uses BMA-SUBINTF-ITEM;
    }
  }

  grouping BMA-LOAD-BALANCE-DATA {
    description "Load balance settings on a bundle";
    leaf type {
      xr:xr-xml-map "bundlemgr_adj:type";
      type Load-balance;
      description "Type of load balancing to use";
    }
    leaf value {
      xr:xr-xml-map "bundlemgr_adj:value";
      type uint32;
      description "Load balance hash value";
    }
    leaf local-link-threshold {
      xr:xr-xml-map "bundlemgr_adj:local_link_threshold";
      type uint32;
      description
        "Threshold below which rack-local balancing is
        disabled";
    }
  }

  grouping BMA-SUBINTF-ITEM {
    description "BMA SUBINTF ITEM";

    container load-balance-data {
      description "Load balance data";
      uses BMA-LOAD-BALANCE-DATA;
    }
    leaf interface-name {
      xr:xr-xml-map "bundlemgr_adj:InterfaceName";
      type xr:Interface-name;
      description "Sub interface";
    }
  }

  grouping BMA-BRIEF-ITEM {
    description "Brief information for a single bundle";
    leaf interface-name {
      xr:xr-xml-map "bundlemgr_adj:InterfaceName";
      type xr:Interface-name;
      description "Bundle interface";
    }
    leaf sub-interface-count {
      xr:xr-xml-map "bundlemgr_adj:SubInterfaceCount";
      type uint32;
      description "Number of sub-interfaces on the bundle";
    }
    leaf member-count {
      xr:xr-xml-map "bundlemgr_adj:MemberCount";
      type uint32;
      description "Number of members configured to the bundle";
    }
    leaf total-weight {
      xr:xr-xml-map "bundlemgr_adj:TotalWeight";
      type uint32;
      description "Total weighting (relative bandwidth) of bundle";
    }

    list sub-interface {
      description "Sub-interfaces of the bundle";
      uses BMA-SUBINTF-ITEM;
    }
  }

  grouping BMA-BRIEF-DATA {
    description "BMA BRIEF DATA";

    list bundle-data {
      description "Data for all bundles on node";
      uses BMA-BRIEF-ITEM;
    }
  }
}
