submodule Cisco-IOS-XR-dnx-driver-oper-sub1 {

  belongs-to Cisco-IOS-XR-dnx-driver-oper {
    prefix Cisco-IOS-XR-dnx-driver-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR dnx-driver package operational data.

     Copyright (c) 2013-2016 by Cisco Systems, Inc.
     All rights reserved.";

  revision "2015-11-09" {
    description
      "IOS XR 6.0 revision.";
  }

  typedef Asic-init-method {
    type enumeration {
      enum asic-init-method-unset {
        value -1;
        description "asic init method unset";
      }
      enum asic-init-method-no-reset {
        value 0;
        description "asic init method no reset";
      }
      enum asic-init-method-pon-reset {
        value 1;
        description "asic init method pon reset";
      }
      enum asic-init-method-pon-reset-on-intr {
        value 2;
        description "asic init method pon reset on intr";
      }
      enum asic-init-method-hard-reset {
        value 3;
        description "asic init method hard reset";
      }
      enum asic-init-method-warmboot {
        value 4;
        description "asic init method warmboot";
      }
      enum asic-init-method-issu-wb {
        value 5;
        description "asic init method issu wb";
      }
      enum asic-init-method-pci-shutdown {
        value 6;
        description "asic init method pci shutdown";
      }
      enum asic-init-method-quiesce {
        value 7;
        description "asic init method quiesce";
      }
      enum asic-init-method-issu-started {
        value 8;
        description "asic init method issu started";
      }
      enum asic-init-method-issu-rollback {
        value 9;
        description "asic init method issu rollback";
      }
      enum asic-init-method-issu-abort {
        value 10;
        description "asic init method issu abort";
      }
      enum asic-init-method-slice-cleanup {
        value 11;
        description "asic init method slice cleanup";
      }
      enum asic-init-method-lc-remove {
        value 12;
        description "asic init method lc remove";
      }
      enum asic-init-method-node-down {
        value 13;
        description "asic init method node down";
      }
      enum asic-init-method-intr {
        value 14;
        description "asic init method intr";
      }
      enum asic-init-method-board-reload {
        value 15;
        description "asic init method board reload";
      }
      enum asic-init-method-max {
        value 16;
        description "asic init method max";
      }
    }
    description "Asic init method";
  }
  typedef Asic-access-state {
    type enumeration {
      enum asic-state-unset {
        value -1;
        description "asic state unset";
      }
      enum asic-state-none {
        value 0;
        description "asic state none";
      }
      enum asic-state-device-off-line {
        value 1;
        description "asic state device off line";
      }
      enum asic-state-device-created {
        value 2;
        description "asic state device created";
      }
      enum asic-state-device-online {
        value 3;
        description "asic state device online";
      }
      enum asic-state-warmboot {
        value 4;
        description "asic state warmboot";
      }
      enum asic-state-de-init-start {
        value 5;
        description "asic state de init start";
      }
      enum asic-state-intr-de-init {
        value 6;
        description "asic state intr de init";
      }
      enum asic-state-bcm-detach {
        value 7;
        description "asic state bcm detach";
      }
      enum asic-state-soc-de-init {
        value 8;
        description "asic state soc de init";
      }
      enum asic-state-de-init-done {
        value 9;
        description "asic state de init done";
      }
      enum asic-state-soc-init {
        value 10;
        description "asic state soc init";
      }
      enum asic-state-bcm-init {
        value 11;
        description "asic state bcm init";
      }
      enum asic-state-intr-init {
        value 12;
        description "asic state intr init";
      }
      enum asic-state-soc-init-start {
        value 13;
        description "asic state soc init start";
      }
      enum asic-state-bcm-init-start {
        value 14;
        description "asic state bcm init start";
      }
      enum asic-state-intr-init-start {
        value 15;
        description "asic state intr init start";
      }
      enum asic-state-hard-reset {
        value 16;
        description "asic state hard reset";
      }
      enum asic-state-normal {
        value 17;
        description "asic state normal";
      }
      enum asic-state-exception {
        value 18;
        description "asic state exception";
      }
      enum asic-state-hp-attached {
        value 19;
        description "asic state hp attached";
      }
      enum asic-state-quiesce {
        value 20;
        description "asic state quiesce";
      }
      enum asic-state-issu-started {
        value 21;
        description "asic state issu started";
      }
      enum asic-state-issu-started-nn {
        value 22;
        description "asic state issu started nn";
      }
      enum asic-state-issu-abort {
        value 23;
        description "asic state issu abort";
      }
      enum asic-state-max {
        value 24;
        description "asic state max";
      }
    }
    description "Asic access state";
  }
  typedef Asic-oper-state {
    type enumeration {
      enum asic-oper-unset {
        value -1;
        description "asic oper unset";
      }
      enum asic-oper-unknown {
        value 0;
        description "asic oper unknown";
      }
      enum asic-oper-up {
        value 1;
        description "asic oper up";
      }
      enum asic-oper-down {
        value 2;
        description "asic oper down";
      }
      enum asic-card-down {
        value 3;
        description "asic card down";
      }
    }
    description "Asic oper state";
  }
  typedef Slice-state {
    type enumeration {
      enum slice-oper-unset {
        value -1;
        description "slice oper unset";
      }
      enum slice-oper-down {
        value 0;
        description "slice oper down";
      }
      enum slice-oper-up {
        value 1;
        description "slice oper up";
      }
      enum slice-oper-na {
        value 2;
        description "slice oper na";
      }
    }
    description "Slice state";
  }
  typedef Fc-mode {
    type enumeration {
      enum fc-mode-unset {
        value -1;
        description "fc mode unset";
      }
      enum fc-mode-unavail {
        value 0;
        description "fc mode unavail";
      }
      enum fc-mode-inband {
        value 1;
        description "fc mode inband";
      }
      enum fc-mode-oob {
        value 2;
        description "fc mode oob";
      }
    }
    description "Fc mode";
  }
  typedef Link-error-state {
    type enumeration {
      enum link-error-unset {
        value -1;
        description "link error unset";
      }
      enum link-error-none {
        value 0;
        description "link error none";
      }
      enum link-error-shut {
        value 1;
        description "link error shut";
      }
      enum link-error-max {
        value 2;
        description "link error max";
      }
    }
    description "Link error state";
  }
  typedef Oper-state {
    type enumeration {
      enum oper-unset {
        value -1;
        description "oper unset";
      }
      enum oper-unknown {
        value 0;
        description "oper unknown";
      }
      enum oper-up {
        value 1;
        description "oper up";
      }
      enum oper-down {
        value 2;
        description "oper down";
      }
      enum card-down {
        value 3;
        description "card down";
      }
    }
    description "Oper state";
  }
  typedef Admin-state {
    type enumeration {
      enum admin-unset {
        value -1;
        description "admin unset";
      }
      enum admin-up {
        value 0;
        description "admin up";
      }
      enum admin-down {
        value 1;
        description "admin down";
      }
    }
    description "Admin state";
  }
  typedef Link-stage {
    type enumeration {
      enum link-stage-unset {
        value -1;
        description "link stage unset";
      }
      enum link-stage-unused {
        value 0;
        description "link stage unused";
      }
      enum link-stage-fia {
        value 1;
        description "link stage fia";
      }
      enum link-stage-s1 {
        value 2;
        description "link stage s1";
      }
      enum link-stage-s2 {
        value 3;
        description "link stage s2";
      }
      enum link-stage-s3 {
        value 4;
        description "link stage s3";
      }
      enum link-stage-unknown {
        value 5;
        description "link stage unknown";
      }
    }
    description "Link stage";
  }
  typedef Link {
    type enumeration {
      enum link-type-unset {
        value -1;
        description "link type unset";
      }
      enum link-type-unavail {
        value 0;
        description "link type unavail";
      }
      enum link-type-tx {
        value 1;
        description "link type tx";
      }
      enum link-type-rx {
        value 2;
        description "link type rx";
      }
    }
    description "Link";
  }
  typedef Asic {
    type enumeration {
      enum asic-unset {
        value -1;
        description "asic unset";
      }
      enum asic-unavail {
        value 0;
        description "asic unavail";
      }
      enum asic-fia {
        value 1;
        description "asic fia";
      }
      enum asic-s123 {
        value 2;
        description "asic s123";
      }
      enum asic-s13 {
        value 3;
        description "asic s13";
      }
      enum asic-s2 {
        value 4;
        description "asic s2";
      }
      enum asic-b2b {
        value 5;
        description "asic b2b";
      }
      enum asic-unknown {
        value 6;
        description "asic unknown";
      }
    }
    description "Asic";
  }
  typedef Rack {
    type enumeration {
      enum rack-type-unset {
        value -1;
        description "rack type unset";
      }
      enum rack-type-lcc {
        value 0;
        description "rack type lcc";
      }
      enum rack-type-fcc {
        value 1;
        description "rack type fcc";
      }
    }
    description "Rack";
  }

  grouping FIA-EDM-LINK-OVF-COUNTERS {
    description "FIA EDM LINK OVF COUNTERS";
    leaf tx-control-cells-counter {
      xr:xr-xml-map "fia_edm_defs:TX_Control_cells_counter";
      type string {
        length "0..6";
      }
      description "TX Control cells counter";
    }
    leaf tx-data-cell-counter {
      xr:xr-xml-map "fia_edm_defs:TX_Data_cell_counter";
      type string {
        length "0..6";
      }
      description "TX Data cell counter";
    }
    leaf tx-data-byte-counter {
      xr:xr-xml-map "fia_edm_defs:TX_Data_byte_counter";
      type string {
        length "0..6";
      }
      description "TX Data byte counter";
    }
    leaf rx-crc-errors-counter {
      xr:xr-xml-map "fia_edm_defs:RX_CRC_errors_counter";
      type string {
        length "0..6";
      }
      description "RX CRC errors counter";
    }
    leaf rx-lfec-fec-correctable-error {
      xr:xr-xml-map "fia_edm_defs:RX_LFEC_FEC_correctable_error";
      type string {
        length "0..6";
      }
      description "RX LFEC FEC correctable error";
    }
    leaf rx-8b-10b-disparity-errors {
      xr:xr-xml-map "fia_edm_defs:RX_8b_10b_disparity_errors";
      type string {
        length "0..6";
      }
      description "RX 8b 10b disparity errors";
    }
    leaf rx-control-cells-counter {
      xr:xr-xml-map "fia_edm_defs:RX_Control_cells_counter";
      type string {
        length "0..6";
      }
      description "RX Control cells counter";
    }
    leaf rx-data-cell-counter {
      xr:xr-xml-map "fia_edm_defs:RX_Data_cell_counter";
      type string {
        length "0..6";
      }
      description "RX Data cell counter";
    }
    leaf rx-data-byte-counter {
      xr:xr-xml-map "fia_edm_defs:RX_Data_byte_counter";
      type string {
        length "0..6";
      }
      description "RX Data byte counter";
    }
    leaf rx-dropped-retransmitted-control {
      xr:xr-xml-map "fia_edm_defs:RX_dropped_retransmitted_control";
      type string {
        length "0..6";
      }
      description "RX dropped retransmitted control";
    }
    leaf tx-asyn-fifo-rate {
      xr:xr-xml-map "fia_edm_defs:TX_Asyn_fifo_rate";
      type string {
        length "0..6";
      }
      description "TX Asyn fifo rate";
    }
    leaf rx-asyn-fifo-rate {
      xr:xr-xml-map "fia_edm_defs:RX_Asyn_fifo_rate";
      type string {
        length "0..6";
      }
      description "RX Asyn fifo rate";
    }
    leaf rx-lfec-fec-uncorrectable-errors {
      xr:xr-xml-map "fia_edm_defs:RX_LFEC_FEC_uncorrectable_errors";
      type string {
        length "0..6";
      }
      description "RX LFEC FEC uncorrectable errors";
    }
    leaf rx-8b-10b-code-errors {
      xr:xr-xml-map "fia_edm_defs:RX_8b_10b_code_errors";
      type string {
        length "0..6";
      }
      description "RX 8b 10b code errors";
    }
  }

  grouping FIA-EDM-LINK-COUNTERS {
    description "FIA EDM LINK COUNTERS";
    leaf tx-control-cells-counter {
      xr:xr-xml-map "fia_edm_defs:TX_Control_cells_counter";
      type uint64;
      description "TX Control cells counter";
    }
    leaf tx-data-cell-counter {
      xr:xr-xml-map "fia_edm_defs:TX_Data_cell_counter";
      type uint64;
      description "TX Data cell counter";
    }
    leaf tx-data-byte-counter {
      xr:xr-xml-map "fia_edm_defs:TX_Data_byte_counter";
      type uint64;
      description "TX Data byte counter";
    }
    leaf rx-crc-errors-counter {
      xr:xr-xml-map "fia_edm_defs:RX_CRC_errors_counter";
      type uint64;
      description "RX CRC errors counter";
    }
    leaf rx-lfec-fec-correctable-error {
      xr:xr-xml-map "fia_edm_defs:RX_LFEC_FEC_correctable_error";
      type uint64;
      description "RX LFEC FEC correctable error";
    }
    leaf rx-8b-10b-disparity-errors {
      xr:xr-xml-map "fia_edm_defs:RX_8b_10b_disparity_errors";
      type uint64;
      description "RX 8b 10b disparity errors";
    }
    leaf rx-control-cells-counter {
      xr:xr-xml-map "fia_edm_defs:RX_Control_cells_counter";
      type uint64;
      description "RX Control cells counter";
    }
    leaf rx-data-cell-counter {
      xr:xr-xml-map "fia_edm_defs:RX_Data_cell_counter";
      type uint64;
      description "RX Data cell counter";
    }
    leaf rx-data-byte-counter {
      xr:xr-xml-map "fia_edm_defs:RX_Data_byte_counter";
      type uint64;
      description "RX Data byte counter";
    }
    leaf rx-dropped-retransmitted-control {
      xr:xr-xml-map "fia_edm_defs:RX_dropped_retransmitted_control";
      type uint64;
      description "RX dropped retransmitted control";
    }
    leaf tx-asyn-fifo-rate {
      xr:xr-xml-map "fia_edm_defs:TX_Asyn_fifo_rate";
      type uint64;
      description "TX Asyn fifo rate";
    }
    leaf rx-asyn-fifo-rate {
      xr:xr-xml-map "fia_edm_defs:RX_Asyn_fifo_rate";
      type uint64;
      description "RX Asyn fifo rate";
    }
    leaf rx-lfec-fec-uncorrectable-errors {
      xr:xr-xml-map "fia_edm_defs:RX_LFEC_FEC_uncorrectable_errors";
      type uint64;
      description "RX LFEC FEC uncorrectable errors";
    }
    leaf rx-8b-10b-code-errors {
      xr:xr-xml-map "fia_edm_defs:RX_8b_10b_code_errors";
      type uint64;
      description "RX 8b 10b code errors";
    }
  }

  grouping FIA-EDM-LINK-ERROR-STATUS {
    description "FIA EDM LINK ERROR STATUS";
    leaf link-crc-error {
      xr:xr-xml-map "fia_edm_defs:link_crc_error";
      type uint32;
      description "link crc error";
    }
    leaf link-size-error {
      xr:xr-xml-map "fia_edm_defs:link_size_error";
      type uint32;
      description "link size error";
    }
    leaf link-mis-align-error {
      xr:xr-xml-map "fia_edm_defs:link_mis_align_error";
      type uint32;
      description "link mis align error";
    }
    leaf link-code-group-error {
      xr:xr-xml-map "fia_edm_defs:link_code_group_error";
      type uint32;
      description "link code group error";
    }
    leaf link-no-sig-lock-error {
      xr:xr-xml-map "fia_edm_defs:link_no_sig_lock_error";
      type uint32;
      description "link no sig lock error";
    }
    leaf link-no-sig-accept-error {
      xr:xr-xml-map "fia_edm_defs:link_no_sig_accept_error";
      type uint32;
      description "link no sig accept error";
    }
    leaf link-tokens-error {
      xr:xr-xml-map "fia_edm_defs:link_tokens_error";
      type uint32;
      description "link tokens error";
    }
    leaf error-token-count {
      xr:xr-xml-map "fia_edm_defs:error_token_count";
      type uint32;
      description "error token count";
    }
  }

  grouping FIA-EDM-STATS-ASIC-FMAC {
    description "FIA EDM STATS ASIC FMAC";

    container link-error-status {
      description "link error status";
      uses FIA-EDM-LINK-ERROR-STATUS;
    }

    container link-counters {
      description "link counters";
      uses FIA-EDM-LINK-COUNTERS;
    }

    container ovf-status {
      description "ovf status";
      uses FIA-EDM-LINK-OVF-COUNTERS;
    }
  }

  grouping FIA-EDM-STATS-ASIC-FMAC-INFO {
    description "FIA EDM STATS ASIC FMAC INFO";

    container aggr-stats {
      description "aggr stats";
      uses FIA-EDM-STATS-ASIC-FMAC;
    }

    container incr-stats {
      description "incr stats";
      uses FIA-EDM-STATS-ASIC-FMAC;
    }
    leaf valid {
      xr:xr-xml-map "fia_edm_defs:valid";
      type boolean;
      description "valid";
    }
    leaf rack-no {
      xr:xr-xml-map "fia_edm_defs:rack_no";
      type uint32;
      description "rack no";
    }
    leaf slot-no {
      xr:xr-xml-map "fia_edm_defs:slot_no";
      type uint32;
      description "slot no";
    }
    leaf asic-instance {
      xr:xr-xml-map "fia_edm_defs:asic_instance";
      type uint32;
      description "asic instance";
    }
    leaf link-no {
      xr:xr-xml-map "fia_edm_defs:link_no";
      type uint32;
      description "link no";
    }
    leaf link-valid {
      xr:xr-xml-map "fia_edm_defs:link_valid";
      type boolean;
      description "link valid";
    }
  }

  grouping FIA-EDM-DEVICE-STATS-FIELD-INFO {
    description "FIA EDM DEVICE STATS FIELD INFO";
    leaf field-name {
      xr:xr-xml-map "fia_edm_defs:Field_Name";
      type string {
        length "0..51";
      }
      description "Field Name";
    }
    leaf field-value {
      xr:xr-xml-map "fia_edm_defs:Field_Value";
      type uint64;
      description "Field Value";
    }
    leaf is-ovf {
      xr:xr-xml-map "fia_edm_defs:Is_Ovf";
      type boolean;
      description "Is Ovf";
    }
  }

  grouping FIA-EDM-DEVICE-STATS-BLK-INFO {
    description "FIA EDM DEVICE STATS BLK INFO";
    leaf block-name {
      xr:xr-xml-map "fia_edm_defs:Block_Name";
      type string {
        length "0..11";
      }
      description "Block Name";
    }
    leaf num-fields {
      xr:xr-xml-map "fia_edm_defs:Num_Fields";
      type uint8;
      description "Num Fields";
    }

    list field-info {
      max-elements "200";
      description "field info";
      uses FIA-EDM-DEVICE-STATS-FIELD-INFO;
    }
  }

  grouping FIA-EDM-DEVICE-STATS-ASIC-INFO {
    description "FIA EDM DEVICE STATS ASIC INFO";
    leaf num-blocks {
      xr:xr-xml-map "fia_edm_defs:Num_Blocks";
      type uint8;
      description "Num Blocks";
    }

    list block-info {
      max-elements "15";
      description "block info";
      uses FIA-EDM-DEVICE-STATS-BLK-INFO;
    }
  }

  grouping FIA-EDM-STATS-INFO {
    description "FIA EDM STATS INFO";

    container stats-info {
      description "stats info";
      uses FIA-EDM-DEVICE-STATS-ASIC-INFO;
    }
    leaf valid {
      xr:xr-xml-map "fia_edm_defs:valid";
      type boolean;
      description "valid";
    }
    leaf rack-no {
      xr:xr-xml-map "fia_edm_defs:rack_no";
      type uint32;
      description "rack no";
    }
    leaf slot-no {
      xr:xr-xml-map "fia_edm_defs:slot_no";
      type uint32;
      description "slot no";
    }
    leaf asic-instance {
      xr:xr-xml-map "fia_edm_defs:asic_instance";
      type uint32;
      description "asic instance";
    }
    leaf chip-ver {
      xr:xr-xml-map "fia_edm_defs:chip_ver";
      type uint16;
      description "chip ver";
    }
  }

  grouping FIA-EDM-DIAG-SHELL-OUTPUT {
    description "FIA EDM DIAG SHELL OUTPUT";
    leaf output-xr {
      xr:xr-xml-map "fia_edm_defs:output-xr";
      type string;
      description "output xr";
    }
  }

  grouping FIA-EDM-REG-INFO {
    description "FIA EDM REG INFO";
    leaf output {
      xr:xr-xml-map "fia_edm_defs:output";
      type string;
      description "output";
    }
  }

  grouping FIA-EDM-TXLINK-STATS {
    description "FIA EDM TXLINK STATS";
    leaf dummy {
      xr:xr-xml-map "fia_edm_defs:dummy";
      type uint32;
      description "dummy";
    }
  }

  grouping FIA-EDM-TXLINK {
    description "FIA EDM TXLINK";

    container this-link {
      description "this link";
      uses FIA-EDM-LINK-IDENTITY;
    }

    container far-end-link {
      description "far end link";
      uses FIA-EDM-LINK-IDENTITY;
    }

    container stats {
      description "stats";
      uses FIA-EDM-TXLINK-STATS;
    }

    container history {
      description "history";
      uses FIA-EDM-HISTORY;
    }
    leaf speed {
      xr:xr-xml-map "fia_edm_defs:speed";
      type uint32;
      description "speed";
    }
    leaf stage {
      xr:xr-xml-map "fia_edm_defs:stage";
      type uint8;
      description "stage";
    }
    leaf is-link-valid {
      xr:xr-xml-map "fia_edm_defs:is_link_valid";
      type boolean;
      description "is link valid";
    }
    leaf is-conf-pending {
      xr:xr-xml-map "fia_edm_defs:is_conf_pending";
      type boolean;
      description "is conf pending";
    }
    leaf is-power-enabled {
      xr:xr-xml-map "fia_edm_defs:is_power_enabled";
      type boolean;
      description "is power enabled";
    }
    leaf coeff1 {
      xr:xr-xml-map "fia_edm_defs:coeff1";
      type uint32;
      description "coeff1";
    }
    leaf coeff2 {
      xr:xr-xml-map "fia_edm_defs:coeff2";
      type uint32;
      description "coeff2";
    }
    leaf admin-state {
      xr:xr-xml-map "fia_edm_defs:AdminState";
      type Admin-state;
      description "Admin State";
    }
    leaf oper-state {
      xr:xr-xml-map "fia_edm_defs:OperState";
      type Oper-state;
      description "Oper State";
    }
    leaf error-state {
      xr:xr-xml-map "fia_edm_defs:ErrorState";
      type Link-error-state;
      description "Error State";
    }
    leaf num-admin-shuts {
      xr:xr-xml-map "fia_edm_defs:num_admin_shuts";
      type uint32;
      description "num admin shuts";
    }
  }

  grouping FIA-EDM-OIR-HISTORY {
    description "FIA EDM OIR HISTORY";
    leaf card-flag {
      xr:xr-xml-map "fia_edm_defs:card_flag";
      type int32;
      description "card flag";
    }
    leaf card-type {
      xr:xr-xml-map "fia_edm_defs:card_type";
      type int32;
      description "card type";
    }
    leaf reg-flag {
      xr:xr-xml-map "fia_edm_defs:reg_flag";
      type int32;
      description "reg flag";
    }
    leaf evt-flag {
      xr:xr-xml-map "fia_edm_defs:evt_flag";
      type int32;
      description "evt flag";
    }
    leaf rack-num {
      xr:xr-xml-map "fia_edm_defs:rack_num";
      type int32;
      description "rack num";
    }
    leaf instance {
      xr:xr-xml-map "fia_edm_defs:instance";
      type int32;
      description "instance";
    }
    leaf cur-card-state {
      xr:xr-xml-map "fia_edm_defs:cur_card_state";
      type int32;
      description "cur card state";
    }
  }

  grouping FIA-EDM-OIR-RECORD-CIRCULAR-BUFFER {
    description "FIA EDM OIR RECORD CIRCULAR BUFFER";
    leaf count {
      xr:xr-xml-map "fia_edm_defs:count";
      type int32;
      description "count";
    }
    leaf start {
      xr:xr-xml-map "fia_edm_defs:start";
      type int32;
      description "start";
    }
    leaf end {
      xr:xr-xml-map "fia_edm_defs:end";
      type int32;
      description "end";
    }

    list fia-oir-info {
      max-elements "10";
      description "fia oir info";
      uses FIA-EDM-OIR-HISTORY;
    }
  }

  grouping FIA-EDM-CARD-INFO {
    description "FIA EDM CARD INFO";

    container oir-circular-buffer {
      description "oir circular buffer";
      uses FIA-EDM-OIR-RECORD-CIRCULAR-BUFFER;
    }
    leaf card-type {
      xr:xr-xml-map "fia_edm_defs:card_type";
      type int32;
      description "card type";
    }
    leaf card-name {
      xr:xr-xml-map "fia_edm_defs:card_name";
      type string;
      description "card name";
    }
    leaf slot-no {
      xr:xr-xml-map "fia_edm_defs:slot_no";
      type int32;
      description "slot no";
    }
    leaf card-flag {
      xr:xr-xml-map "fia_edm_defs:card_flag";
      type int32;
      description "card flag";
    }
    leaf evt-flag {
      xr:xr-xml-map "fia_edm_defs:evt_flag";
      type int32;
      description "evt flag";
    }
    leaf reg-flag {
      xr:xr-xml-map "fia_edm_defs:reg_flag";
      type int32;
      description "reg flag";
    }
    leaf instance {
      xr:xr-xml-map "fia_edm_defs:instance";
      type int32;
      description "instance";
    }
    leaf card-state {
      xr:xr-xml-map "fia_edm_defs:card_state";
      type uint8;
      description "card state";
    }
    leaf exp-num-asics {
      xr:xr-xml-map "fia_edm_defs:exp_num_asics";
      type uint32;
      description "exp num asics";
    }
    leaf exp-num-asics-per-fsdb {
      xr:xr-xml-map "fia_edm_defs:exp_num_asics_per_fsdb";
      type uint32;
      description "exp num asics per fsdb";
    }
    leaf is-powered {
      xr:xr-xml-map "fia_edm_defs:is_powered";
      type boolean;
      description "is powered";
    }
    leaf cxp-avail-bitmap {
      xr:xr-xml-map "fia_edm_defs:cxp_avail_bitmap";
      type uint64;
      description "cxp avail bitmap";
    }
    leaf num-ilkns-per-asic {
      xr:xr-xml-map "fia_edm_defs:num_ilkns_per_asic";
      type uint32;
      description "num ilkns per asic";
    }
    leaf num-local-ports-per-ilkn {
      xr:xr-xml-map "fia_edm_defs:num_local_ports_per_ilkn";
      type uint32;
      description "num local ports per ilkn";
    }
    leaf num-cos-per-port {
      xr:xr-xml-map "fia_edm_defs:num_cos_per_port";
      type uint8;
      description "num cos per port";
    }
  }

  grouping FIA-EDM-DEVICE {
    description "FIA EDM DEVICE";

    container asic-id {
      description "asic id";
      uses FIA-EDM-ASIC-IDENTITY;
    }
    leaf is-valid {
      xr:xr-xml-map "fia_edm_defs:is_valid";
      type boolean;
      description "is valid";
    }
    leaf fapid {
      xr:xr-xml-map "fia_edm_defs:fapid";
      type uint32;
      description "fapid";
    }
    leaf hotplug-event {
      xr:xr-xml-map "fia_edm_defs:hotplug_event";
      type uint32;
      description "hotplug event";
    }
    leaf slice-state {
      xr:xr-xml-map "fia_edm_defs:SliceState";
      type Slice-state;
      description "Slice State";
    }
    leaf admin-state {
      xr:xr-xml-map "fia_edm_defs:AdminState";
      type Admin-state;
      description "Admin State";
    }
    leaf oper-state {
      xr:xr-xml-map "fia_edm_defs:OperState";
      type Asic-oper-state;
      description "Oper State";
    }
    leaf asic-state {
      xr:xr-xml-map "fia_edm_defs:AsicState";
      type Asic-access-state;
      description "Asic State";
    }
    leaf last-init-cause {
      xr:xr-xml-map "fia_edm_defs:last_init_cause";
      type Asic-init-method;
      description "last init cause";
    }
    leaf num-pon-resets {
      xr:xr-xml-map "fia_edm_defs:num_pon_resets";
      type uint32;
      description "num pon resets";
    }
    leaf num-hard-resets {
      xr:xr-xml-map "fia_edm_defs:num_hard_resets";
      type uint32;
      description "num hard resets";
    }
    leaf local-switch-state {
      xr:xr-xml-map "fia_edm_defs:local_switch_state";
      type boolean;
      description "local switch state";
    }
  }

  grouping FIA-EDM-DRIVER-INFO {
    description "FIA EDM DRIVER INFO";
    leaf drv-version {
      xr:xr-xml-map "fia_edm_defs:drv_version";
      type uint32;
      description "drv version";
    }
    leaf coeff-major-rev {
      xr:xr-xml-map "fia_edm_defs:coeff_major_rev";
      type uint32;
      description "coeff major rev";
    }
    leaf coeff-minor-rev {
      xr:xr-xml-map "fia_edm_defs:coeff_minor_rev";
      type uint32;
      description "coeff minor rev";
    }
    leaf functional-role {
      xr:xr-xml-map "fia_edm_defs:functional_role";
      type uint8;
      description "functional role";
    }
    leaf issu-role {
      xr:xr-xml-map "fia_edm_defs:issu_role";
      type uint8;
      description "issu role";
    }
    leaf rack-name {
      xr:xr-xml-map "fia_edm_defs:rack_name";
      type string;
      description "rack name";
    }
    leaf rack-type {
      xr:xr-xml-map "fia_edm_defs:rack_type";
      type int32;
      description "rack type";
    }
    leaf rack-num {
      xr:xr-xml-map "fia_edm_defs:rack_num";
      type uint8;
      description "rack num";
    }
    leaf is-driver-ready {
      xr:xr-xml-map "fia_edm_defs:is_driver_ready";
      type boolean;
      description "is driver ready";
    }
    leaf card-avail-mask {
      xr:xr-xml-map "fia_edm_defs:card_avail_mask";
      type uint32;
      description "card avail mask";
    }
    leaf asic-avail-mask {
      xr:xr-xml-map "fia_edm_defs:asic_avail_mask";
      type uint64;
      description "asic avail mask";
    }
    leaf exp-asic-avail-mask {
      xr:xr-xml-map "fia_edm_defs:exp_asic_avail_mask";
      type uint64;
      description "exp asic avail mask";
    }
    leaf ucmc-ratio {
      xr:xr-xml-map "fia_edm_defs:ucmc_ratio";
      type uint32;
      description "ucmc ratio";
    }
    leaf asic-oper-notify-to-fsdb-pending-bmap {
      xr:xr-xml-map "fia_edm_defs:asic_oper_notify_to_fsdb_pending_"+
        "bmap";
      type uint64;
      description "asic oper notify to fsdb pending bmap";
    }
    leaf is-full-fgid-download-req {
      xr:xr-xml-map "fia_edm_defs:is_full_fgid_download_req";
      type boolean;
      description "is full fgid download req";
    }
    leaf is-fgid-download-in-progress {
      xr:xr-xml-map "fia_edm_defs:is_fgid_download_in_progress";
      type boolean;
      description "is fgid download in progress";
    }
    leaf is-fgid-download-completed {
      xr:xr-xml-map "fia_edm_defs:is_fgid_download_completed";
      type boolean;
      description "is fgid download completed";
    }
    leaf fsdb-conn-active {
      xr:xr-xml-map "fia_edm_defs:fsdb_conn_active";
      type boolean;
      description "fsdb conn active";
    }
    leaf fgid-conn-active {
      xr:xr-xml-map "fia_edm_defs:fgid_conn_active";
      type boolean;
      description "fgid conn active";
    }
    leaf issu-mgr-conn-active {
      xr:xr-xml-map "fia_edm_defs:issu_mgr_conn_active";
      type boolean;
      description "issu mgr conn active";
    }
    leaf fsdb-reg-active {
      xr:xr-xml-map "fia_edm_defs:fsdb_reg_active";
      type boolean;
      description "fsdb reg active";
    }
    leaf fgid-reg-active {
      xr:xr-xml-map "fia_edm_defs:fgid_reg_active";
      type boolean;
      description "fgid reg active";
    }
    leaf issu-mgr-reg-active {
      xr:xr-xml-map "fia_edm_defs:issu_mgr_reg_active";
      type boolean;
      description "issu mgr reg active";
    }
    leaf num-pm-conn-reqs {
      xr:xr-xml-map "fia_edm_defs:num_pm_conn_reqs";
      type uint8;
      description "num pm conn reqs";
    }
    leaf num-fsdb-conn-reqs {
      xr:xr-xml-map "fia_edm_defs:num_fsdb_conn_reqs";
      type uint8;
      description "num fsdb conn reqs";
    }
    leaf num-fgid-conn-reqs {
      xr:xr-xml-map "fia_edm_defs:num_fgid_conn_reqs";
      type uint8;
      description "num fgid conn reqs";
    }
    leaf num-fstats-conn-reqs {
      xr:xr-xml-map "fia_edm_defs:num_fstats_conn_reqs";
      type uint8;
      description "num fstats conn reqs";
    }
    leaf num-cm-conn-reqs {
      xr:xr-xml-map "fia_edm_defs:num_cm_conn_reqs";
      type uint8;
      description "num cm conn reqs";
    }
    leaf num-issu-mgr-conn-reqs {
      xr:xr-xml-map "fia_edm_defs:num_issu_mgr_conn_reqs";
      type uint8;
      description "num issu mgr conn reqs";
    }
    leaf num-peer-fia-conn-reqs {
      xr:xr-xml-map "fia_edm_defs:num_peer_fia_conn_reqs";
      type uint8;
      description "num peer fia conn reqs";
    }
    leaf is-gaspp-registered {
      xr:xr-xml-map "fia_edm_defs:is_gaspp_registered";
      type boolean;
      description "is gaspp registered";
    }
    leaf is-cih-registered {
      xr:xr-xml-map "fia_edm_defs:is_cih_registered";
      type boolean;
      description "is cih registered";
    }
    leaf drvr-initial-startup-timestamp {
      xr:xr-xml-map "fia_edm_defs:drvr_initial_startup_timestamp";
      type string;
      description "drvr initial startup timestamp";
    }
    leaf drvr-current-startup-timestamp {
      xr:xr-xml-map "fia_edm_defs:drvr_current_startup_timestamp";
      type string;
      description "drvr current startup timestamp";
    }
    leaf num-intf-ports {
      xr:xr-xml-map "fia_edm_defs:num_intf_ports";
      type uint32;
      description "num intf ports";
    }
    leaf uc-weight {
      xr:xr-xml-map "fia_edm_defs:uc_weight";
      type uint8;
      description "uc weight";
    }
    leaf respawn-count {
      xr:xr-xml-map "fia_edm_defs:respawn_count";
      type uint8;
      description "respawn count";
    }
    leaf total-asics {
      xr:xr-xml-map "fia_edm_defs:total_asics";
      type uint8;
      description "total asics";
    }
    leaf issu-ready-ntfy-pending {
      xr:xr-xml-map "fia_edm_defs:issu_ready_ntfy_pending";
      type boolean;
      description "issu ready ntfy pending";
    }
    leaf issu-abort-sent {
      xr:xr-xml-map "fia_edm_defs:issu_abort_sent";
      type boolean;
      description "issu abort sent";
    }
    leaf issu-abort-rcvd {
      xr:xr-xml-map "fia_edm_defs:issu_abort_rcvd";
      type boolean;
      description "issu abort rcvd";
    }
    leaf fc-mode {
      xr:xr-xml-map "fia_edm_defs:FCMode";
      type Fc-mode;
      description "FC Mode";
    }
    leaf board-rev-id {
      xr:xr-xml-map "fia_edm_defs:board_rev_id";
      type uint32;
      description "board rev id";
    }

    list device-info {
      max-elements "32";
      description "device info";
      uses FIA-EDM-DEVICE;
    }

    list card-info {
      max-elements "16";
      description "card info";
      uses FIA-EDM-CARD-INFO;
    }
  }

  grouping FIA-EDM-STATE-CHANGE {
    description "FIA EDM STATE CHANGE";
    leaf admin-state {
      xr:xr-xml-map "fia_edm_defs:AdminState";
      type Admin-state;
      description "Admin State";
    }
    leaf oper-state {
      xr:xr-xml-map "fia_edm_defs:OperState";
      type Oper-state;
      description "Oper State";
    }
    leaf error-state {
      xr:xr-xml-map "fia_edm_defs:ErrorState";
      type Link-error-state;
      description "Error State";
    }
    leaf timestamp {
      xr:xr-xml-map "fia_edm_defs:timestamp";
      type uint64;
      description "timestamp";
    }
    leaf reasons {
      xr:xr-xml-map "fia_edm_defs:reasons";
      type string;
      description "reasons";
    }
  }

  grouping FIA-EDM-HISTORY {
    description "FIA EDM HISTORY";
    leaf histnum {
      xr:xr-xml-map "fia_edm_defs:histnum";
      type uint8;
      description "histnum";
    }
    leaf start-index {
      xr:xr-xml-map "fia_edm_defs:start_index";
      type uint8;
      description "start index";
    }

    list hist {
      max-elements "5";
      description "hist";
      uses FIA-EDM-STATE-CHANGE;
    }
  }

  grouping FIA-EDM-ASIC-IDENTITY {
    description "FIA EDM ASIC IDENTITY";
    leaf rack-type {
      xr:xr-xml-map "fia_edm_defs:RackType";
      type Rack;
      description "Rack Type";
    }
    leaf asic-type {
      xr:xr-xml-map "fia_edm_defs:AsicType";
      type Asic;
      description "Asic Type";
    }
    leaf rack-num {
      xr:xr-xml-map "fia_edm_defs:rack_num";
      type uint32;
      description "rack num";
    }
    leaf slot-num {
      xr:xr-xml-map "fia_edm_defs:slot_num";
      type uint32;
      description "slot num";
    }
    leaf asic-instance {
      xr:xr-xml-map "fia_edm_defs:asic_instance";
      type uint32;
      description "asic instance";
    }
  }

  grouping FIA-EDM-LINK-IDENTITY {
    description "FIA EDM LINK IDENTITY";

    container asic-id {
      description "asic id";
      uses FIA-EDM-ASIC-IDENTITY;
    }
    leaf link-type {
      xr:xr-xml-map "fia_edm_defs:LinkType";
      type Link;
      description "Link Type";
    }
    leaf link-stage {
      xr:xr-xml-map "fia_edm_defs:LinkStage";
      type Link-stage;
      description "Link Stage";
    }
    leaf link-num {
      xr:xr-xml-map "fia_edm_defs:link_num";
      type uint32;
      description "link num";
    }
    leaf phy-link-num {
      xr:xr-xml-map "fia_edm_defs:phy_link_num";
      type uint32;
      description "phy link num";
    }
  }

  grouping FIA-EDM-RXLINK {
    description "FIA EDM RXLINK";

    container this-link {
      description "this link";
      uses FIA-EDM-LINK-IDENTITY;
    }

    container far-end-link {
      description "far end link";
      uses FIA-EDM-LINK-IDENTITY;
    }

    container far-end-link-in-hw {
      description "far end link in hw";
      uses FIA-EDM-LINK-IDENTITY;
    }

    container history {
      description "history";
      uses FIA-EDM-HISTORY;
    }
    leaf speed {
      xr:xr-xml-map "fia_edm_defs:speed";
      type uint32;
      description "speed";
    }
    leaf stage {
      xr:xr-xml-map "fia_edm_defs:Stage";
      type Link-stage;
      description "Stage";
    }
    leaf is-link-valid {
      xr:xr-xml-map "fia_edm_defs:is_link_valid";
      type boolean;
      description "is link valid";
    }
    leaf is-conf-pending {
      xr:xr-xml-map "fia_edm_defs:is_conf_pending";
      type boolean;
      description "is conf pending";
    }
    leaf admin-state {
      xr:xr-xml-map "fia_edm_defs:AdminState";
      type Admin-state;
      description "Admin State";
    }
    leaf oper-state {
      xr:xr-xml-map "fia_edm_defs:OperState";
      type Oper-state;
      description "Oper State";
    }
    leaf error-state {
      xr:xr-xml-map "fia_edm_defs:ErrorState";
      type Link-error-state;
      description "Error State";
    }
    leaf flags {
      xr:xr-xml-map "fia_edm_defs:flags";
      type string;
      description "flags";
    }
    leaf flap-cnt {
      xr:xr-xml-map "fia_edm_defs:flap_cnt";
      type uint32;
      description "flap cnt";
    }
    leaf num-admin-shuts {
      xr:xr-xml-map "fia_edm_defs:num_admin_shuts";
      type uint32;
      description "num admin shuts";
    }
  }
}
