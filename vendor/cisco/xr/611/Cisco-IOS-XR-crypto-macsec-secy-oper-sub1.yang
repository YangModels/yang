submodule Cisco-IOS-XR-crypto-macsec-secy-oper-sub1 {

  belongs-to Cisco-IOS-XR-crypto-macsec-secy-oper {
    prefix Cisco-IOS-XR-crypto-macsec-secy-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR crypto-macsec-secy package operational data.

     Copyright (c) 2013-2016 by Cisco Systems, Inc.
     All rights reserved.";

  revision "2015-11-09" {
    description
      "IOS XR 6.0 revision.";
  }


  grouping MACSEC-RX-SC-STATS {
    description "MACSEC RX SC STATS";
    leaf rx-sci {
      xr:xr-xml-map "show_macsec_ea:RxSCI";
      type uint64;
      description "Rx SCI";
    }
    leaf in-pkts-unchecked {
      xr:xr-xml-map "show_macsec_ea:InPktsUnchecked";
      type uint64;
      description "InPktsUnchecked";
    }
    leaf in-pkts-delayed {
      xr:xr-xml-map "show_macsec_ea:InPktsDelayed";
      type uint64;
      description "InPktsDelayed";
    }
    leaf in-pkts-late {
      xr:xr-xml-map "show_macsec_ea:InPktsLate";
      type uint64;
      description "InPktsLate";
    }
    leaf in-pkts-ok {
      xr:xr-xml-map "show_macsec_ea:InPktsOK";
      type uint64;
      description "InPktsOK";
    }
    leaf in-pkts-invalid {
      xr:xr-xml-map "show_macsec_ea:InPktsInvalid";
      type uint64;
      description "InPktsInvalid";
    }
    leaf in-pkts-not-valid {
      xr:xr-xml-map "show_macsec_ea:InPktsNotValid";
      type uint64;
      description "InPktsNotValid";
    }
    leaf in-pkts-not-using-sa {
      xr:xr-xml-map "show_macsec_ea:InPktsNotUsingSA";
      type uint64;
      description "InPktsNotUsingSA";
    }
    leaf in-pkts-unused-sa {
      xr:xr-xml-map "show_macsec_ea:InPktsUnusedSA";
      type uint64;
      description "InPktsUnusedSA";
    }
    leaf in-pkts-untagged-hit {
      xr:xr-xml-map "show_macsec_ea:InPktsUntaggedHit";
      type uint64;
      description "InPktsUntaggedHit";
    }
    leaf in-octets-validated {
      xr:xr-xml-map "show_macsec_ea:InOctetsValidated";
      type uint64;
      description "InOctetsValidated";
    }
    leaf in-octets-decrypted {
      xr:xr-xml-map "show_macsec_ea:InOctetsDecrypted";
      type uint64;
      description "InOctetsDecrypted";
    }
  }

  grouping MACSEC-TX-SC-STATS {
    description "MACSEC TX SC STATS";
    leaf tx-sci {
      xr:xr-xml-map "show_macsec_ea:TxSCI";
      type uint64;
      description "Tx SCI";
    }
    leaf out-pkts-protected {
      xr:xr-xml-map "show_macsec_ea:OutPktsProtected";
      type uint64;
      description "OutPktsProtected";
    }
    leaf out-pkts-encrypted {
      xr:xr-xml-map "show_macsec_ea:OutPktsEncrypted";
      type uint64;
      description "OutPktsEncrypted";
    }
    leaf out-octets-protected {
      xr:xr-xml-map "show_macsec_ea:OutOctetsProtected";
      type uint64;
      description "OutOctetsProtected";
    }
    leaf out-octets-encrypted {
      xr:xr-xml-map "show_macsec_ea:OutOctetsEncrypted";
      type uint64;
      description "OutOctetsEncrypted";
    }
    leaf out-pkts-too-long {
      xr:xr-xml-map "show_macsec_ea:OutPktsTooLong";
      type uint64;
      description "OutPktsTooLong";
    }
  }

  grouping MACSEC-IF-STATS {
    description "MACSEC IF STATS";
    leaf in-pkts-untagged {
      xr:xr-xml-map "show_macsec_ea:InPktsUntagged";
      type uint64;
      description "InPktsUntagged";
    }
    leaf in-pkts-no-tag {
      xr:xr-xml-map "show_macsec_ea:InPktsNoTag";
      type uint64;
      description "InPktsNoTag";
    }
    leaf in-pkts-bad-tag {
      xr:xr-xml-map "show_macsec_ea:InPktsBadTag";
      type uint64;
      description "InPktsBadTag";
    }
    leaf in-pkts-unknown-sci {
      xr:xr-xml-map "show_macsec_ea:InPktsUnknownSCI";
      type uint64;
      description "InPktsUnknownSCI";
    }
    leaf in-pkts-no-sci {
      xr:xr-xml-map "show_macsec_ea:InPktsNoSCI";
      type uint64;
      description "InPktsNoSCI";
    }
    leaf in-pkts-overrun {
      xr:xr-xml-map "show_macsec_ea:InPktsOverrun";
      type uint64;
      description "InPktsOverrun";
    }
    leaf in-octets-validated {
      xr:xr-xml-map "show_macsec_ea:InOctetsValidated";
      type uint64;
      description "InOctetsValidated";
    }
    leaf in-octets-decrypted {
      xr:xr-xml-map "show_macsec_ea:InOctetsDecrypted";
      type uint64;
      description "InOctetsDecrypted";
    }
    leaf out-pkts-untagged {
      xr:xr-xml-map "show_macsec_ea:OutPktsUntagged";
      type uint64;
      description "OutPktsUntagged";
    }
    leaf out-pkts-too-long {
      xr:xr-xml-map "show_macsec_ea:OutPktsTooLong";
      type uint64;
      description "OutPktsTooLong";
    }
    leaf out-octets-protected {
      xr:xr-xml-map "show_macsec_ea:OutOctetsProtected";
      type uint64;
      description "OutOctetsProtected";
    }
    leaf out-octets-encrypted {
      xr:xr-xml-map "show_macsec_ea:OutOctetsEncrypted";
      type uint64;
      description "OutOctetsEncrypted";
    }
  }

  grouping MACSEC-SECY-STATS {
    description "MACSEC SECY STATS";

    container intf-stats {
      description "Interface stats";
      uses MACSEC-IF-STATS;
    }

    container tx-sc-stats {
      description "Tx SC Stats";
      uses MACSEC-TX-SC-STATS;
    }

    list rx-sc-stats {
      description "RX SC Stats List";
      uses MACSEC-RX-SC-STATS;
    }
  }
}
