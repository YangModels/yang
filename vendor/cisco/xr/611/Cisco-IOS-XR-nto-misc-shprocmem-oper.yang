module Cisco-IOS-XR-nto-misc-shprocmem-oper {

  /*** NAMESPACE / PREFIX DEFINITION ***/

  namespace "http://cisco.com/ns/yang"+
    "/Cisco-IOS-XR-nto-misc-shprocmem-oper";


  prefix "nto-misc-shprocmem-oper";

  /*** LINKAGE (IMPORTS / INCLUDES) ***/

  import Cisco-IOS-XR-types { prefix "xr"; }

  include Cisco-IOS-XR-nto-misc-shprocmem-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR nto-misc-shprocmem package operational data.

     This module contains definitions
     for the following management objects:
       processes-memory: Process statistics

     Copyright (c) 2013-2016 by Cisco Systems, Inc.
     All rights reserved.";

  revision "2015-11-09" {
    description
      "IOS XR 6.0 revision.";
  }


  container processes-memory {
    xr:xr-xml-map "nto_misc_shprocmem_oper:ProcessesMemory";
    config false;
    description "Process statistics";

    container nodes {
      xr:xr-xml-map "nto_misc_shprocmem_oper:NodeTable";
      description "List of nodes";

      list node {
        xr:xr-xml-map "nto_misc_shprocmem_oper:Node";
        key "node-name";
        description "Node ID";

        container job-ids {
          xr:xr-xml-map "nto_misc_shprocmem_oper:JobTable";
          description "List of jobs";

          list job-id {
            xr:xr-xml-map "nto_misc_shprocmem_oper:JobId";
            key "job-id";
            description "Job Id";
            leaf job-id {
              xr:xr-xml-map "nto_misc_shprocmem_oper:JobId";
              type int32;
              description "Job Id";
            }
            uses PROCESSESMEMORY-ENTRY;
          }
        }
        leaf node-name {
          xr:xr-xml-map "nto_misc_shprocmem_oper:NodeName";
          type xr:Node-id;
          description "Node name";
        }
      }
    }
  }
}
