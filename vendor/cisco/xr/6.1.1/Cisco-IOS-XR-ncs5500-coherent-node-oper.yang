module Cisco-IOS-XR-ncs5500-coherent-node-oper {

  /*** NAMESPACE / PREFIX DEFINITION ***/

  namespace "http://cisco.com/ns/yang"+
    "/Cisco-IOS-XR-ncs5500-coherent-node-oper";


  prefix "ncs5500-coherent-node-oper";

  /*** LINKAGE (IMPORTS / INCLUDES) ***/

  import Cisco-IOS-XR-types { prefix "xr"; }

  include Cisco-IOS-XR-ncs5500-coherent-node-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ncs5500-coherent-node package operational data.

     This module contains definitions
     for the following management objects:
       coherent: Coherent node  operational data

     Copyright (c) 2013-2016 by Cisco Systems, Inc.
     All rights reserved.";

  revision "2015-11-09" {
    description
      "IOS XR 6.0 revision.";
  }


  container coherent {
    xr:xr-xml-map "coh_node_oper:Coherent";
    config false;
    description "Coherent node  operational data";

    container nodes {
      xr:xr-xml-map "coh_node_oper:NodeTable";
      description "Coherent list of nodes";

      list node {
        xr:xr-xml-map "coh_node_oper:Node";
        key "node-name";
        description
          "Coherent discovery operational data for a
          particular node";

        container coherent-time-stats {
          xr:xr-xml-map "coh_node_oper:CoherentTimeStats";
          description "Coherent driver performace information";
          uses COH-TIME-STATS;
        }

        container devicemapping {
          xr:xr-xml-map "coh_node_oper:Devicemapping";
          description "Coherent node data for device _mapping";
          uses COH-DEV-MAP-DATA;
        }

        container coherenthealth {
          xr:xr-xml-map "coh_node_oper:Coherenthealth";
          description "Coherent node data for driver health";
          uses COH-HEALTH-DATA;
        }

        container port-mode-all-info {
          xr:xr-xml-map "coh_node_oper:PortModeAllInfo";
          description "PortMode all operational data";
          uses COH-PORTMODE-ALL-DETAILS;
        }
        leaf node-name {
          xr:xr-xml-map "coh_node_oper:NodeName";
          type xr:Node-id;
          description "The node name";
        }
      }
    }
  }
}
