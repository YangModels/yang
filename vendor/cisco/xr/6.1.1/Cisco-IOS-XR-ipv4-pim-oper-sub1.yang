submodule Cisco-IOS-XR-ipv4-pim-oper-sub1 {

  belongs-to Cisco-IOS-XR-ipv4-pim-oper {
    prefix Cisco-IOS-XR-ipv4-pim-oper;
  }

  /*** LINKAGE (IMPORTS / INCLUDES) ***/

  import ietf-inet-types { prefix "inet"; }

  import ietf-yang-types { prefix "yang"; }

  import Cisco-IOS-XR-types { prefix "xr"; }

  include Cisco-IOS-XR-ipv4-pim-oper-sub2 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR ipv4-pim package operational data.

     Copyright (c) 2013-2016 by Cisco Systems, Inc.
     All rights reserved.";

  revision "2015-11-09" {
    description
      "IOS XR 6.0 revision.";
  }

  typedef Pim-show-range-client {
    type enumeration {
      enum no-client {
        value 0;
        description "no client";
      }
      enum embedded-config {
        value 1;
        description "embedded config";
      }
      enum embedded {
        value 2;
        description "embedded";
      }
      enum permanent {
        value 3;
        description "permanent";
      }
      enum auto-rp {
        value 4;
        description "auto rp";
      }
      enum bsr {
        value 5;
        description "bsr";
      }
      enum config {
        value 6;
        description "config";
      }
      enum static {
        value 7;
        description "static";
      }
    }
    description "Pim show range client";
  }
  typedef Pim-show-protocol {
    type enumeration {
      enum no-route {
        value 0;
        description "no route";
      }
      enum sm {
        value 1;
        description "sm";
      }
      enum dm {
        value 2;
        description "dm";
      }
      enum bidir {
        value 3;
        description "bidir";
      }
      enum ssm {
        value 4;
        description "ssm";
      }
      enum maximum {
        value 5;
        description "maximum";
      }
      enum any {
        value 6;
        description "any";
      }
    }
    description "Pim show protocol";
  }

  grouping PIM-ISSU-BAG {
    description "ISSU information";
    leaf informationvalid {
      xr:xr-xml-map "pim:InformationValid";
      type boolean;
      description "Is Information valid ?";
    }
    leaf role-ha {
      xr:xr-xml-map "pim:RoleHA";
      type int32;
      description "HA role";
    }
    leaf role-issu {
      xr:xr-xml-map "pim:RoleISSU";
      type int32;
      description "ISSU role";
    }
    leaf phase-issu {
      xr:xr-xml-map "pim:PhaseISSU";
      type int32;
      description "ISSU Phase";
    }
    leaf ha-option-issu {
      xr:xr-xml-map "pim:HAOptionISSU";
      type int32;
      description "HA Option ISSU";
    }
    leaf last-ready-bool {
      xr:xr-xml-map "pim:LastReadyBool";
      type boolean;
      description "Boolean of whether Ready Nfn was sent";
    }
    leaf last-ready-sent {
      xr:xr-xml-map "pim:LastReadySent";
      type uint64;
      description "Time when ISSU Ready was sent";
    }
    leaf last-ha-role-notification-received {
      xr:xr-xml-map "pim:LastHARoleNotificationReceived";
      type uint64;
      description "Time when last HA role nfn was received";
    }
    leaf last-issu-role-notification-received {
      xr:xr-xml-map "pim:LastISSURoleNotificationReceived";
      type uint64;
      description "Time when last ISSU role nfn was received";
    }
    leaf last-issu-phase-notification-received {
      xr:xr-xml-map "pim:LastISSUPhaseNotificationReceived";
      type uint64;
      description "Time when last ISSU Phase nfn was received";
    }
    leaf is-eoc-received {
      xr:xr-xml-map "pim:IsEOCReceived";
      type boolean;
      description "Was EOC received ?";
    }
    leaf eoc-received-timestamp {
      xr:xr-xml-map "pim:EOCReceivedTimestamp";
      type uint64;
      description "Time when EOC was received";
    }
    leaf is-ihms-done-received {
      xr:xr-xml-map "pim:IsIHMSDoneReceived";
      type boolean;
      description "Was IHMS done received ?";
    }
    leaf ihms-received-timestamp {
      xr:xr-xml-map "pim:IHMSReceivedTimestamp";
      type uint64;
      description "Time when IHMS done was received";
    }
    leaf is-rib-sync-received {
      xr:xr-xml-map "pim:IsRIBSyncReceived";
      type boolean;
      description "Was RIB Sync received ?";
    }
    leaf rib-sync-received-timestamp {
      xr:xr-xml-map "pim:RIBSyncReceivedTimestamp";
      type uint64;
      description "Time when RIB Sync was received";
    }
    leaf is-nbr-sync-received {
      xr:xr-xml-map "pim:IsNBRSyncReceived";
      type boolean;
      description "Was NBR Sync achieved ?";
    }
    leaf nbr-sync-received-timestamp {
      xr:xr-xml-map "pim:NBRSyncReceivedTimestamp";
      type uint64;
      description "Time when NBR Sync was achieved";
    }
  }

  grouping PIM-NSF-BAG {
    description "PIM NSF state";
    leaf configured-state {
      xr:xr-xml-map "pim:ConfiguredState";
      type boolean;
      description "Is Multicast NSF Configured";
    }
    leaf nsf-state {
      xr:xr-xml-map "pim:NSFState";
      type boolean;
      description "Are we currently in NSF";
    }
    leaf nsf-timeout {
      xr:xr-xml-map "pim:NSFTimeout";
      type uint32;
      units "second";
      description "Multicast NSF timeout in seconds";
    }
    leaf nsf-time-left {
      xr:xr-xml-map "pim:NSFTimeLeft";
      type uint32;
      units "second";
      description "Multicast NSF time left in seconds";
    }
    leaf waiting-timer {
      xr:xr-xml-map "pim:WaitingTimer";
      type boolean;
      description "Waiting for NSF timer expiry";
    }
    leaf waiting-membership {
      xr:xr-xml-map "pim:WaitingMembership";
      type boolean;
      description "Waiting for IGMP/MLD";
    }
    leaf respawn-count {
      xr:xr-xml-map "pim:RespawnCount";
      type uint32;
      description "Respawn Count";
    }
    leaf last-nsf-on {
      xr:xr-xml-map "pim:LastNSFOn";
      type int64;
      description "Last NSF time ON";
    }
    leaf last-nsf-off {
      xr:xr-xml-map "pim:LastNSFOff";
      type int64;
      description "Last NSF time off";
    }
    leaf last-nsf-on-sec {
      xr:xr-xml-map "pim:LastNSFOnSec";
      type int32;
      units "second";
      description "Last NSF time ON in Seconds";
    }
    leaf last-nsf-off-sec {
      xr:xr-xml-map "pim:LastNSFOffSec";
      type int32;
      units "second";
      description "Last NSF time OFF in Seconds";
    }
    leaf last-icd-notif-recv {
      xr:xr-xml-map "pim:LastICDNotifRecv";
      type int64;
      description "Last ICD Notif Recv";
    }
    leaf last-icd-notif-recv-sec {
      xr:xr-xml-map "pim:LastICDNotifRecvSec";
      type int32;
      units "second";
      description "Last ICD Notif Recv in Seconds";
    }
  }

  grouping PIM-NSR-BAG {
    description "NSR Related information";
    leaf state {
      xr:xr-xml-map "pim:State";
      type uint8;
      description "NSR state";
    }
    leaf partner-connected {
      xr:xr-xml-map "pim:PartnerConnected";
      type boolean;
      description "Partner process connected";
    }
    leaf rmf-notification-done {
      xr:xr-xml-map "pim:RMFNotificationDone";
      type boolean;
      description "RMF Notification done";
    }
    leaf rmf-timer-valid {
      xr:xr-xml-map "pim:RMFTimerValid";
      type boolean;
      description "Is RMF timer running ?";
    }
    leaf rmf-timer-expiry {
      xr:xr-xml-map "pim:RMFTimerExpiry";
      type uint64;
      description "Time for RMF timer to expire";
    }
    leaf last-connection-up {
      xr:xr-xml-map "pim:LastConnectionUp";
      type uint64;
      description "Time when connection went up";
    }
    leaf last-connection-dn {
      xr:xr-xml-map "pim:LastConnectionDn";
      type uint64;
      description "Time when connection went down";
    }
    leaf last-rmf-ready {
      xr:xr-xml-map "pim:LastRMFReady";
      type uint64;
      description "Time when RMF Rdy notif was sent";
    }
    leaf last-rmf-not-ready {
      xr:xr-xml-map "pim:LastRMFNotReady";
      type uint64;
      description "Time when RMF Not-Rdy notif was sent";
    }
    leaf count-connection-up {
      xr:xr-xml-map "pim:CountConnectionUp";
      type uint32;
      description "No. of times connection went up";
    }
    leaf count-connection-dn {
      xr:xr-xml-map "pim:CountConnectionDn";
      type uint32;
      description "No. of times connection went down";
    }
    leaf count-rmf-ready {
      xr:xr-xml-map "pim:CountRMFReady";
      type uint32;
      description "No. of times RMF Ready notif was sent";
    }
    leaf count-rmf-not-ready {
      xr:xr-xml-map "pim:CountRMFNotReady";
      type uint32;
      description "No. of times RMF Not Ready notif was sent";
    }
  }

  grouping PIM-CHKPT-TABLE-STATS {
    description "PIM chkpt table stats";
    leaf table-description {
      xr:xr-xml-map "pim:TableDescription";
      type string;
      description "Table description";
    }
    leaf table-name {
      xr:xr-xml-map "pim:TableName";
      type uint32;
      description "Table name";
    }
    leaf is-mirrored {
      xr:xr-xml-map "pim:IsMirrored";
      type boolean;
      description "Table mirrored";
    }
    leaf-list statistic {
      xr:xr-xml-map "pim:Statistics";
      type uint32;
      description "Stats array";
    }
  }

  grouping PIM-CHKPT-STATS {
    description "PIM chkpt stats";

    list checkpoint-table {
      description "Array of chkpt table stats";
      uses PIM-CHKPT-TABLE-STATS;
    }
  }

  grouping PIM-MSTATIC-BAG {
    description "Multicast Static Routes entry";

    container prefix {
      description "Prefix";
      uses PIM-ADDRTYPE;
    }

    container nexthop {
      description "Next Hop";
      uses PIM-ADDRTYPE;
    }
    leaf interface-name {
      xr:xr-xml-map "pim:InterfaceName";
      type xr:Interface-name;
      description "Interface Handle";
    }
    leaf distance {
      xr:xr-xml-map "pim:Distance";
      type uint32;
      description "Distance";
    }
    leaf prefix-length-xr {
      xr:xr-xml-map "pim:prefix-length-xr";
      type uint8;
      description "Prefix Length";
    }
    leaf is-via-lsm {
      xr:xr-xml-map "pim:IsViaLSM";
      type boolean;
      description "LSM flag";
    }
  }

  grouping PIM-RPF-RDRCT-BNDL-BAG {
    description "PIM RPF Redirect bundle information";
    leaf rpf-redirect-bundle-name {
      xr:xr-xml-map "pim:RPFRedirectBundleName";
      type string {
        length "0..33";
      }
      description "RPF redirect bundle name";
    }
    leaf rpf-redirect-interface-name {
      xr:xr-xml-map "pim:RPFRedirectInterfaceName";
      type string {
        length "0..33";
      }
      description "RPF redirect interface name";
    }
    leaf available-bandwidth {
      xr:xr-xml-map "pim:AvailableBandwidth";
      type int32;
      units "kbit/s";
      description "Bandwidth available in Kbps";
    }
    leaf allocated-bandwidth {
      xr:xr-xml-map "pim:AllocatedBandwidth";
      type int32;
      units "kbit/s";
      description "Bandwidth allocated in Kbps";
    }
    leaf total-bandwidth {
      xr:xr-xml-map "pim:TotalBandwidth";
      type int32;
      units "kbit/s";
      description "Total bandwidth used in Kbps";
    }
    leaf topology-bandwidth-used {
      xr:xr-xml-map "pim:TopologyBandwidthUsed";
      type int32;
      units "kbit/s";
      description "Bandwidth used by topology in Kbps";
    }
    leaf snooping-bandwidth-used {
      xr:xr-xml-map "pim:SnoopingBandwidthUsed";
      type int32;
      units "kbit/s";
      description "Bandwidth used by snooped entries in Kbps";
    }
    leaf allocated-threshold-bandwidth {
      xr:xr-xml-map "pim:AllocatedThresholdBandwidth";
      type int32;
      units "kbit/s";
      description "Configured threshold in Kbps";
    }
    leaf available-threshold-bandwidth {
      xr:xr-xml-map "pim:AvailableThresholdBandwidth";
      type int32;
      units "kbit/s";
      description "Available threshold in Kbps";
    }
  }

  grouping PIM-RPF-RDRCT-RINTF-BAG {
    description
      "PIM RPF-redirct bundle non-local route OLE
      information";

    container rpf-address {
      description "RPF Address";
      uses PIM-ADDRTYPE;
    }
    leaf interface-name {
      xr:xr-xml-map "pim:InterfaceName";
      type xr:Interface-name;
      description "Interface name";
    }
    leaf uptime {
      xr:xr-xml-map "pim:Uptime";
      type uint64;
      units "second";
      description "Uptime in seconds";
    }
    leaf expiry {
      xr:xr-xml-map "pim:Expiry";
      type uint64;
      units "second";
      description "Expiry in seconds";
    }
    leaf is-rpf-interface {
      xr:xr-xml-map "pim:IsRPFInterface";
      type boolean;
      description "Is RPF Interface";
    }
    leaf is-outgoing-interface {
      xr:xr-xml-map "pim:IsOutgoingInterface";
      type boolean;
      description "Is outgoing Interface";
    }
    leaf is-snoop-interface {
      xr:xr-xml-map "pim:IsSnoopInterface";
      type boolean;
      description "Is snooping Interface";
    }
  }

  grouping PIM-RPF-RDRCT-ROUTE-BAG {
    description "PIM RPF Redirect route information";

    container group-address-xr {
      description "Group ddress";
      uses PIM-ADDRTYPE;
    }

    container source-address-xr {
      description "Source address";
      uses PIM-ADDRTYPE;
    }
    leaf bandwidth {
      xr:xr-xml-map "pim:Bandwidth";
      type uint32;
      units "kbit/s";
      description "Bandwidth in Kbps";
    }
    leaf uptime {
      xr:xr-xml-map "pim:Uptime";
      type uint64;
      units "second";
      description "Uptime in seconds";
    }

    list interface {
      description "Outgoing interface list";
      uses PIM-RPF-RDRCT-RINTF-BAG;
    }
  }

  grouping PIM-ANYCAST-RP-ENTRY {
    description "PIM Anycast RP entry";

    container prefix {
      description "Anycast-RP Range Prefix";
      uses PIM-ADDRTYPE;
    }
    leaf prefix-length {
      xr:xr-xml-map "pim:PrefixLength";
      type uint8;
      description "Anycast-RP Range Prefix Length";
    }
    leaf ancast-rp-marked {
      xr:xr-xml-map "pim:AncastRPMarked";
      type boolean;
      description "Anycast-RP Range marked";
    }
  }

  grouping PIM-RT-EXTCOMM {
    description "PIM Route-target entry";
    leaf route-target {
      xr:xr-xml-map "pim:RouteTarget";
      type yang:hex-string;
      description "Route Target Extended community value";
    }
    leaf configured {
      xr:xr-xml-map "pim:Configured";
      type boolean;
      description "Configured Route Target";
    }
    leaf anycast-rp {
      xr:xr-xml-map "pim:AnycastRP";
      type boolean;
      description "Anycast-RP Group";
    }
    leaf anycast-rp-marked {
      xr:xr-xml-map "pim:AnycastRPMarked";
      type boolean;
      description "Anycast-RP Group marked";
    }
    leaf update-pending {
      xr:xr-xml-map "pim:UpdatePending";
      type boolean;
      description "Update Pending to BGP";
    }
    leaf bgp-auto-discovery {
      xr:xr-xml-map "pim:BGPAutoDiscovery";
      type boolean;
      description "BGP Auto Discovery";
    }
    leaf segment-border {
      xr:xr-xml-map "pim:SegmentBorder";
      type boolean;
      description "Segment Border";
    }
  }

  grouping PIM-CONTEXT-BAG {
    description "PIM Context bag";

    container remote-default-group {
      description "Remote Default Group";
      uses PIM-ADDRTYPE;
    }

    container rpf-default-table {
      description "RPF Default Table";
      uses PIM-TABLE-CTX-BAG;
    }
    leaf vrf-id {
      xr:xr-xml-map "pim:VRF_ID";
      type uint32;
      description "VRF ID";
    }
    leaf table-id {
      xr:xr-xml-map "pim:TableID";
      type uint32;
      description "Table ID";
    }
    leaf murib-id {
      xr:xr-xml-map "pim:MURIB_ID";
      type uint32;
      description "MURIB ID";
    }
    leaf rpf-id {
      xr:xr-xml-map "pim:RPF_ID";
      type uint32;
      description "RPF ID";
    }
    leaf remote-table-id {
      xr:xr-xml-map "pim:RemoteTableID";
      type uint32;
      description "Remote Table ID";
    }
    leaf mdt-default-group {
      xr:xr-xml-map "pim:MDTDefaultGroup";
      type inet:ipv4-address;
      description "MDT Default group";
    }
    leaf mdt-interface {
      xr:xr-xml-map "pim:MDTInterface";
      type xr:Interface-name;
      description "MDT handle";
    }
    leaf mdt-gre-rpf-identifier {
      xr:xr-xml-map "pim:MDT_GRE_RPFIdentifier";
      type uint32;
      description "GRE-MDT RPF Identifier";
    }
    leaf mdt-gre-remote-rpf-identifier {
      xr:xr-xml-map "pim:MDT_GRE_RemoteRPFIdentifier";
      type uint32;
      description "GRE-MDT Remote RPF Identifier";
    }
    leaf is-unicast-rib-registration {
      xr:xr-xml-map "pim:IsUnicastRIBRegistration";
      type boolean;
      description "Ucast RIB Registration";
    }
    leaf is-multicast-rib-registration {
      xr:xr-xml-map "pim:IsMulticastRIBRegistration";
      type boolean;
      description "Mcast RIB Registration";
    }
    leaf is-active {
      xr:xr-xml-map "pim:IsActive";
      type boolean;
      description "Active";
    }
    leaf is-active-ital {
      xr:xr-xml-map "pim:IsActiveITAL";
      type boolean;
      description "Active ITAL";
    }
    leaf is-mrib-register {
      xr:xr-xml-map "pim:IsMRIBRegister";
      type boolean;
      description "MRIB Register";
    }
    leaf is-mdt-owner {
      xr:xr-xml-map "pim:IsMDTOwner";
      type boolean;
      description "MDT Owner";
    }
    leaf is-routing-enabled {
      xr:xr-xml-map "pim:IsRoutingEnabled";
      type boolean;
      description "Routing Enabled";
    }
    leaf is-socket-add-required {
      xr:xr-xml-map "pim:IsSocketAddRequired";
      type boolean;
      description "VRF required on Socket";
    }
    leaf is-socket-added {
      xr:xr-xml-map "pim:IsSocketAdded";
      type boolean;
      description "VRF added on Socket";
    }
    leaf is-lpts-socket-add-required {
      xr:xr-xml-map "pim:IsLPTSSocketAddRequired";
      type boolean;
      description "VRF LPTS filter required on Socket";
    }
    leaf is-lpts-socket-added {
      xr:xr-xml-map "pim:IsLPTSSocketAdded";
      type boolean;
      description "VRF LPTS filter added on Socket";
    }
    leaf is-udp-socket-add-required {
      xr:xr-xml-map "pim:IsUDPSocketAddRequired";
      type boolean;
      description "VRF added on UDP Socket";
    }
    leaf is-udp-socket-added {
      xr:xr-xml-map "pim:IsUDPSocketAdded";
      type boolean;
      description "VRF added on UDP Socket";
    }
    leaf is-udp-socket-bind-required {
      xr:xr-xml-map "pim:IsUDPSocketBindRequired";
      type boolean;
      description "VRF bind required on UDP Socket";
    }
    leaf is-udp-socket-bind {
      xr:xr-xml-map "pim:IsUDPSocketBind";
      type boolean;
      description "VRF bound on UDP Socket";
    }
    leaf is-register-injection-socket-add-required {
      xr:xr-xml-map "pim:IsRegisterInjectionSocketAddRequired";
      type boolean;
      description "VRF required on Register Injection Socket";
    }
    leaf is-register-injection-socket-added {
      xr:xr-xml-map "pim:IsRegisterInjectionSocketAdded";
      type boolean;
      description "VRF added on Register Injection Socket";
    }
    leaf is-register-injection-lpts-socket-add-required {
      xr:xr-xml-map "pim:IsRegisterInjectionLPTSSocketAddRequired";
      type boolean;
      description
        "VRF LPTS filter required on Register Injection
        Socket";
    }
    leaf is-register-injection-lpts-socket-added {
      xr:xr-xml-map "pim:IsRegisterInjectionLPTSSocketAdded";
      type boolean;
      description
        "VRF LPTS filter added on Register Injection
        Socket";
    }
    leaf is-m-host-publish-pending {
      xr:xr-xml-map "pim:IsMHostPublishPending";
      type boolean;
      description "Publish pending for MHost Default interface";
    }
    leaf mhost-interface {
      xr:xr-xml-map "pim:MHostInterface";
      type xr:Interface-name;
      description "MHost handle";
    }
    leaf mhost-default-interface-config {
      xr:xr-xml-map "pim:MHostDefaultInterfaceConfig";
      type string;
      description "Configured Mhost Defint";
    }
    leaf mdt-mtu {
      xr:xr-xml-map "pim:MDT_MTU";
      type uint32;
      description "MDT MTU";
    }
    leaf maximum-mdt-aggregation {
      xr:xr-xml-map "pim:MaximumMDTAggregation";
      type uint32;
      description "MDT max aggregation";
    }
    leaf mdt-data-switchover-interval {
      xr:xr-xml-map "pim:MDTDataSwitchoverInterval";
      type uint32;
      description "Data MDT Switchover interval";
    }
    leaf mdt-data-announce-interval {
      xr:xr-xml-map "pim:MDTDataAnnounceInterval";
      type uint32;
      description "Data MDT Announce interval";
    }
    leaf non-default-vrf-count-on-socket {
      xr:xr-xml-map "pim:NonDefaultVRFCountOnSocket";
      type uint32;
      description "Count of non-default vrfs on raw socket";
    }
    leaf neighbor-filter-name {
      xr:xr-xml-map "pim:NeighborFilterName";
      type string;
      description "Neighbor Filter Name";
    }
    leaf mdt-neighbor-filter-name {
      xr:xr-xml-map "pim:MDTNeighborFilterName";
      type string;
      description "MDT Neighbor Filter Name";
    }
    leaf allow-rp-configured {
      xr:xr-xml-map "pim:AllowRPConfigured";
      type boolean;
      description "Allow RP Configured";
    }
    leaf allow-rp-group-list {
      xr:xr-xml-map "pim:AllowRPGroupList";
      type string {
        length "0..64";
      }
      description "Allow RP Group-List ACL Name";
    }
    leaf allow-rp-rp-list {
      xr:xr-xml-map "pim:AllowRP_RPList";
      type string {
        length "0..64";
      }
      description "Allow RP RP-list ACL Name";
    }
    leaf sg-expiry-timer-configured {
      xr:xr-xml-map "pim:SGExpiryTimerConfigured";
      type boolean;
      description "S,G Expiry Timer Configured";
    }
    leaf sg-expiry-time {
      xr:xr-xml-map "pim:SGExpiryTime";
      type uint16;
      units "second";
      description "S,G Expiry Time Configured, in seconds";
    }
    leaf sg-expiry-timer-sg-list {
      xr:xr-xml-map "pim:SGExpiryTimerSGList";
      type string {
        length "0..64";
      }
      description "S,G expiry timer ACL name";
    }
    leaf mldp-mdt-name {
      xr:xr-xml-map "pim:MLDP_MDTName";
      type string;
      description "MLDP MDT Name";
    }
    leaf mldp-mdt-interface {
      xr:xr-xml-map "pim:MLDP_MDTInterface";
      type xr:Interface-name;
      description "MLDP MDT handle";
    }
    leaf mldp-mdt-mtu {
      xr:xr-xml-map "pim:MLDP_MDT_MTU";
      type uint32;
      description "MLDP MDT MTU";
    }
    leaf mldp-maximum-mdt-aggregation {
      xr:xr-xml-map "pim:MLDPMaximumMDTAggregation";
      type uint32;
      description "MLDP MDT max aggregation";
    }
    leaf mldp-mdt-data-switchover-interval {
      xr:xr-xml-map "pim:MLDP_MDTDataSwitchoverInterval";
      type uint32;
      description "MLDP Data MDT Switchover interval";
    }
    leaf mldp-mdt-data-announce-interval {
      xr:xr-xml-map "pim:MLDP_MDTDataAnnounceInterval";
      type uint32;
      description "MLDP Data MDT Announce interval";
    }
    leaf mldp-mdt-rpf-identifier {
      xr:xr-xml-map "pim:MLDP_MDT_RPFIdentifier";
      type uint32;
      description "MLDP RPF-ID";
    }
    leaf mldp-mdt-remote-rpf-identifier {
      xr:xr-xml-map "pim:MLDP_MDT_RemoteRPFIdentifier";
      type uint32;
      description "MLDP Remote RPF-ID";
    }
    leaf is-create-mldp-mdt-interface {
      xr:xr-xml-map "pim:IsCreateMLDP_MDTInterface";
      type boolean;
      description "Create MLDP MDT interface";
    }
    leaf is-mldp-mdt-owner {
      xr:xr-xml-map "pim:IsMLDP_MDTOwner";
      type boolean;
      description "MLDP MDT Owner";
    }
    leaf mldp-root-count {
      xr:xr-xml-map "pim:MLDPRootCount";
      type uint32;
      description "MLDP Root count";
    }
    leaf mldp-head-lsm-identifier {
      xr:xr-xml-map "pim:MLDPHeadLSMIdentifier";
      type uint32;
      description "MLDP Head LSM-ID";
    }
    leaf mldp-remote-head-lsm-identifier {
      xr:xr-xml-map "pim:MLDPRemoteHeadLSMIdentifier";
      type uint32;
      description "MLDP Remote Head LSM-ID";
    }
    leaf organization-unique-identifier {
      xr:xr-xml-map "pim:OrganizationUniqueIdentifier";
      type uint32;
      description "OUI for VPN-ID";
    }
    leaf vpn-index {
      xr:xr-xml-map "pim:VPNIndex";
      type uint32;
      description "VPN Index";
    }
    leaf mldp-partitioned-mdt-configured {
      xr:xr-xml-map "pim:MLDPPartitionedMDTConfigured";
      type boolean;
      description "MLDP Partitioned MDT";
    }
    leaf mldp-remote-partitioned-mdt-configured {
      xr:xr-xml-map "pim:MLDPRemotePartitionedMDTConfigured";
      type boolean;
      description "MLDP Remote Partitioned MDT";
    }
    leaf mldp-partioned-mp2m-ptree {
      xr:xr-xml-map "pim:MLDPPartionedMP2MPTree";
      type boolean;
      description "MP2MP Partitioned MDT tree";
    }
    leaf mldp-partitioned-head-lsm-identifier {
      xr:xr-xml-map "pim:MLDPPartitionedHeadLSMIdentifier";
      type uint32;
      description "Partitioned MDT Head LSM-ID";
    }
    leaf mldp-head-local-label {
      xr:xr-xml-map "pim:MLDPHeadLocalLabel";
      type uint32;
      description "Partitioned MDT Head local label";
    }
    leaf mldp-partitioned-mdt-identifier {
      xr:xr-xml-map "pim:MLDPPartitionedMDTIdentifier";
      type uint32;
      description "MLDP Partitioned MDT Identifier";
    }
    leaf bgp-auto-discovery-configured {
      xr:xr-xml-map "pim:BGPAutoDiscoveryConfigured";
      type boolean;
      description "BGP Auto-Discovery configured";
    }
    leaf suppress-pim-data-mdt-tlv {
      xr:xr-xml-map "pim:SuppressPIMDataMDT_TLV";
      type boolean;
      description "Suppress PIM Data-MDT TLV Announcements";
    }
    leaf inter-autonomous-system-enabled {
      xr:xr-xml-map "pim:InterAutonomousSystemEnabled";
      type boolean;
      description "Inter-AS Enabled";
    }
    leaf bgp-source-active-announce {
      xr:xr-xml-map "pim:BGPSourceActiveAnnounce";
      type boolean;
      description "Send BGP Source-Active Announcements";
    }
    leaf bgp-i-pmsi-added {
      xr:xr-xml-map "pim:BGP_I_PMSIAdded";
      type boolean;
      description "BGP I-PMSI Added";
    }
    leaf mldp-bsr-control-tree-added {
      xr:xr-xml-map "pim:MLDP_BSRControlTreeAdded";
      type boolean;
      description "MLDP BSR Control tree added";
    }
    leaf mldp-auto-rp-discovery-tree-added {
      xr:xr-xml-map "pim:MLDPAutoRPDiscoveryTreeAdded";
      type boolean;
      description "MLDP Autorp Discovery Control tree added";
    }
    leaf mldp-auto-rp-announce-tree-added {
      xr:xr-xml-map "pim:MLDPAutoRPAnnounceTreeAdded";
      type boolean;
      description "MLDP Autorp Announce Control tree added";
    }
    leaf bgp-auto-discovery-type {
      xr:xr-xml-map "pim:BGPAutoDiscoveryType";
      type uint32;
      description "BGP Auto Discovery Type";
    }
    leaf mdt-partitioned-mdt-control-identifier {
      xr:xr-xml-map "pim:MDTPartitionedMDTControlIdentifier";
      type uint32;
      description "Partitioned MDT Control Identifier";
    }
    leaf mdt-partitioned-ir-control-identifier {
      xr:xr-xml-map "pim:MDTPartitionedIRControlIdentifier";
      type uint32;
      description "Partitioned IR MDT Control Identifier";
    }
    leaf mldp-control-head-lsm-identifier {
      xr:xr-xml-map "pim:MLDPControlHeadLSMIdentifier";
      type uint32;
      description "MLDP MVPN Identifier";
    }
    leaf umh {
      xr:xr-xml-map "pim:UMH";
      type boolean;
      description "Join UMH Core-Tree";
    }
    leaf suppress-shared-tree-join {
      xr:xr-xml-map "pim:SuppressSharedTreeJoin";
      type boolean;
      description "Suppress Shared-Tree Joins";
    }
    leaf rsvp-te-mdt-name {
      xr:xr-xml-map "pim:RSVP_TE_MDTName";
      type string;
      description "RSVP-TE MDT Name";
    }
    leaf rsvp-te-mdt-interface {
      xr:xr-xml-map "pim:RSVP_TE_MDTInterface";
      type xr:Interface-name;
      description "RSVP-TEMDT handle";
    }
    leaf rsvp-te-mdt-mtu {
      xr:xr-xml-map "pim:RSVP_TE_MDT_MTU";
      type uint32;
      description "RSVP-TEMDT MTU";
    }
    leaf rsvp-te-maximum-mdt-aggregation {
      xr:xr-xml-map "pim:RSVP_TEMaximumMDTAggregation";
      type uint32;
      description "RSVP-TE MDT max aggregation";
    }
    leaf rsvp-te-mdt-data-switchover-interval {
      xr:xr-xml-map "pim:RSVP_TE_MDTDataSwitchoverInterval";
      type uint32;
      description "RSVP-TE Data MDT Switchover interval";
    }
    leaf rsvp-te-mdt-data-announce-interval {
      xr:xr-xml-map "pim:RSVP_TE_MDTDataAnnounceInterval";
      type uint32;
      description "RSVP-TE Data MDT Announce interval";
    }
    leaf rsvp-te-mdt-rpf-identifier {
      xr:xr-xml-map "pim:RSVP_TE_MDT_RPFIdentifier";
      type uint32;
      description "RSVP-TE RPF-ID";
    }
    leaf is-create-rsvp-te-mdt-interface {
      xr:xr-xml-map "pim:IsCreateRSVP_TE_MDTInterface";
      type boolean;
      description "Create RSVP-TE MDT interface";
    }
    leaf is-rsvp-te-mdt-owner {
      xr:xr-xml-map "pim:IsRSVP_TE_MDTOwner";
      type boolean;
      description "RSVP-TE MDT Owner";
    }
    leaf rsvp-te-mdt-static-p2mp-count {
      xr:xr-xml-map "pim:RSVP_TE_MDTStaticP2MPCount";
      type uint32;
      description "Number of Static P2MP-TE MDT";
    }
    leaf p2mpte-li-drop {
      xr:xr-xml-map "pim:P2MPTE_LI_Drop";
      type uint32;
      description "Route LI updates dropped for P2MP";
    }
    leaf ir-mdt-name {
      xr:xr-xml-map "pim:IR_MDTName";
      type string;
      description "IR MDT Name";
    }
    leaf ir-mdt-interface {
      xr:xr-xml-map "pim:IR_MDTInterface";
      type xr:Interface-name;
      description "IRMDT handle";
    }
    leaf ir-mdt-mtu {
      xr:xr-xml-map "pim:IR_MDT_MTU";
      type uint32;
      description "IRMDT MTU";
    }
    leaf ir-maximum-mdt-aggregation {
      xr:xr-xml-map "pim:IRMaximumMDTAggregation";
      type uint32;
      description "IR MDT max aggregation";
    }
    leaf ir-mdt-data-switchover-interval {
      xr:xr-xml-map "pim:IR_MDTDataSwitchoverInterval";
      type uint32;
      description "IR Data MDT Switchover interval";
    }
    leaf ir-mdt-data-announce-interval {
      xr:xr-xml-map "pim:IR_MDTDataAnnounceInterval";
      type uint32;
      description "IR Data MDT Announce interval";
    }
    leaf ir-mdt-rpf-identifier {
      xr:xr-xml-map "pim:IR_MDT_RPFIdentifier";
      type uint32;
      description "IR RPF-ID";
    }
    leaf ir-mdt-tail-label {
      xr:xr-xml-map "pim:IR_MDT_TailLabel";
      type uint32;
      description "IR Tail Label";
    }
    leaf is-create-ir-mdt-interface {
      xr:xr-xml-map "pim:IsCreateIR_MDTInterface";
      type boolean;
      description "Create IR MDT interface";
    }
    leaf is-ir-mdt-owner {
      xr:xr-xml-map "pim:IsIR_MDTOwner";
      type boolean;
      description "IR MDT Owner";
    }
    leaf in-b-and-mdt-name {
      xr:xr-xml-map "pim:IN_BAND_MDTName";
      type string;
      description "Inband MDT Name";
    }
    leaf in-b-and-mdt-interface {
      xr:xr-xml-map "pim:IN_BAND_MDTInterface";
      type xr:Interface-name;
      description "Inband MDT handle";
    }
    leaf in-b-and-mdt-mtu {
      xr:xr-xml-map "pim:IN_BAND_MDT_MTU";
      type uint32;
      description "Inband MDT MTU";
    }
    leaf in-band-maximum-mdt-aggregation {
      xr:xr-xml-map "pim:IN_BANDMaximumMDTAggregation";
      type uint32;
      description "Inband MDT max aggregation";
    }
    leaf in-b-and-mdt-data-switchover-interval {
      xr:xr-xml-map "pim:IN_BAND_MDTDataSwitchoverInterval";
      type uint32;
      description "Inband Data MDT Switchover interval";
    }
    leaf in-b-and-mdt-data-announce-interval {
      xr:xr-xml-map "pim:IN_BAND_MDTDataAnnounceInterval";
      type uint32;
      description "Inband Data MDT Announce interval";
    }
    leaf in-b-and-mdt-rpf-identifier {
      xr:xr-xml-map "pim:IN_BAND_MDT_RPFIdentifier";
      type uint32;
      description "Inband RPF-ID";
    }
    leaf is-create-in-b-and-mdt-interface {
      xr:xr-xml-map "pim:IsCreateIN_BAND_MDTInterface";
      type boolean;
      description "Create Inband MDT interface";
    }
    leaf is-in-b-and-mdt-owner {
      xr:xr-xml-map "pim:IsIN_BAND_MDTOwner";
      type boolean;
      description "Inband MDT Owner";
    }
    leaf in-band-signaling-local-enabled {
      xr:xr-xml-map "pim:InBandSignalingLocalEnabled";
      type boolean;
      description "Inband signaling Local enabled";
    }
    leaf in-band-signaling-remote-enabled {
      xr:xr-xml-map "pim:InBandSignalingRemoteEnabled";
      type boolean;
      description "Inband signaling Remote enabled";
    }
    leaf valid-rd-present {
      xr:xr-xml-map "pim:ValidRDPresent";
      type boolean;
      description "RD is valid";
    }
    leaf stale-rd-present {
      xr:xr-xml-map "pim:StaleRDPresent";
      type boolean;
      description "RD is stale";
    }
    leaf route-distinguisher {
      xr:xr-xml-map "pim:RouteDistinguisher";
      type yang:hex-string;
      description "RD value";
    }
    leaf gin-b-and-mdt-name {
      xr:xr-xml-map "pim:GIN_BAND_MDTName";
      type string;
      description "Inband MDT Name";
    }
    leaf gin-b-and-mdt-interface {
      xr:xr-xml-map "pim:GIN_BAND_MDTInterface";
      type xr:Interface-name;
      description "Inband MDT handle";
    }
    leaf gin-b-and-mdt-mtu {
      xr:xr-xml-map "pim:GIN_BAND_MDT_MTU";
      type uint32;
      description "Inband MDT MTU";
    }
    leaf gin-band-maximum-mdt-aggregation {
      xr:xr-xml-map "pim:GIN_BANDMaximumMDTAggregation";
      type uint32;
      description "Inband MDT max aggregation";
    }
    leaf gin-b-and-mdt-data-switchover-interval {
      xr:xr-xml-map "pim:GIN_BAND_MDTDataSwitchoverInterval";
      type uint32;
      description "Inband Data MDT Switchover interval";
    }
    leaf gin-b-and-mdt-data-announce-interval {
      xr:xr-xml-map "pim:GIN_BAND_MDTDataAnnounceInterval";
      type uint32;
      description "Inband Data MDT Announce interval";
    }
    leaf gin-b-and-mdt-rpf-identifier {
      xr:xr-xml-map "pim:GIN_BAND_MDT_RPFIdentifier";
      type uint32;
      description "Inband RPF-ID";
    }
    leaf is-create-gin-b-and-mdt-interface {
      xr:xr-xml-map "pim:IsCreateGIN_BAND_MDTInterface";
      type boolean;
      description "Create Inband MDT interface";
    }
    leaf is-gin-b-and-mdt-owner {
      xr:xr-xml-map "pim:IsGIN_BAND_MDTOwner";
      type boolean;
      description "Inband MDT Owner";
    }
    leaf is-pim-nsf-rib-converged {
      xr:xr-xml-map "pim:IsPIM_NSF_RIBConverged";
      type boolean;
      description "PIM NSF RIB converged";
    }
    leaf is-pim-nsf-rib-converge-received {
      xr:xr-xml-map "pim:IsPIM_NSF_RIBConvergeReceived";
      type boolean;
      description "PIM NSF RIB converge received";
    }
    leaf is-rib-multipath-enabled {
      xr:xr-xml-map "pim:IsRIBMultipathEnabled";
      type boolean;
      description "PIM RIB multiplath enabled";
    }
    leaf is-rib-multipath-interface-hash {
      xr:xr-xml-map "pim:IsRIBMultipathInterfaceHash";
      type boolean;
      description "PIM RIB multipath interface hash";
    }
    leaf is-rib-multipath-source-hash {
      xr:xr-xml-map "pim:IsRIBMultipathSourceHash";
      type boolean;
      description "PIM RIB multipath source based hash";
    }
    leaf is-rib-multipath-source-next-hop-hash {
      xr:xr-xml-map "pim:IsRIBMultipathSourceNextHopHash";
      type boolean;
      description "PIM RIB multipath source-nexthop hash";
    }
    leaf rump-enabled {
      xr:xr-xml-map "pim:RUMPEnabled";
      type boolean;
      description "PIM is using MuRIB";
    }
    leaf is-create-mdt-interface {
      xr:xr-xml-map "pim:IsCreateMDTInterface";
      type boolean;
      description "Create MDT interface";
    }
    leaf is-auto-rp-listen-enabled {
      xr:xr-xml-map "pim:IsAutoRPListenEnabled";
      type boolean;
      description "Auto RP Listen Enabled";
    }
    leaf is-all-interface-disable-operation {
      xr:xr-xml-map "pim:IsAllInterfaceDisableOperation";
      type boolean;
      description "PIM all interface disable operation";
    }
    leaf is-default-granges {
      xr:xr-xml-map "pim:IsDefaultGranges";
      type boolean;
      description "Default granges";
    }
    leaf is-auto-rp-listen-sock-add {
      xr:xr-xml-map "pim:IsAutoRPListenSockAdd";
      type boolean;
      description "Auto RP listen sock add";
    }
    leaf is-redistribution-reset {
      xr:xr-xml-map "pim:IsRedistributionReset";
      type boolean;
      description "Pending redist reset";
    }
    leaf redistribution-reset-count {
      xr:xr-xml-map "pim:RedistributionResetCount";
      type uint32;
      description "Redist reset count";
    }
    leaf rpf-policy-name {
      xr:xr-xml-map "pim:RPFPolicyName";
      type string;
      description "RPF topology selection route-policy name";
    }
    leaf table-count {
      xr:xr-xml-map "pim:TableCount";
      type uint32;
      description "Number of configured Tables";
    }
    leaf active-table-count {
      xr:xr-xml-map "pim:ActiveTableCount";
      type uint32;
      description "Number of active Tables";
    }
    leaf anycast-rp-policy-name {
      xr:xr-xml-map "pim:AnycastRPPolicyName";
      type string;
      description "Anycast-RP Policy Name";
    }
    leaf anycast-rp-configured {
      xr:xr-xml-map "pim:AnycastRPConfigured";
      type boolean;
      description "Anycast-RP config";
    }
    leaf bgp-remote-on {
      xr:xr-xml-map "pim:BGPRemoteOn";
      type boolean;
      description "BGP remote interface status";
    }
    leaf bgp-remote-interface-name {
      xr:xr-xml-map "pim:BGPRemoteInterfaceName";
      type string;
      description "BGP remote interface name";
    }
    leaf bgp-remote-interface {
      xr:xr-xml-map "pim:BGPRemoteInterface";
      type xr:Interface-name;
      description "BGP remote interface handle";
    }
    leaf bgp-remote-address {
      xr:xr-xml-map "pim:BGPRemoteAddress";
      type inet:ipv4-address;
      description "BGP remote interface address";
    }
    leaf bgp-remote-state {
      xr:xr-xml-map "pim:BGPRemoteState";
      type uint32;
      description "BGP remote interface state";
    }
    leaf-list mldp-root-address {
      xr:xr-xml-map "pim:MLDPRootAddresses";
      type uint32;
      description "MLDP Root addresses";
    }

    list export-route-target {
      description "Export Route Targets";
      uses PIM-RT-EXTCOMM;
    }

    list import-route-target {
      description "Import Route Targets";
      uses PIM-RT-EXTCOMM;
    }

    list anycast-rp-range {
      description "Anycast-RP Ranges";
      uses PIM-ANYCAST-RP-ENTRY;
    }
  }

  grouping PIM-NBR-SUMM-BAG {
    description "PIM neighbor summary";
    leaf number-of-neighbors {
      xr:xr-xml-map "pim:NumberOfNeighbors";
      type int32;
      description "Number of neighbors";
    }
    leaf number-of-external-neighbors {
      xr:xr-xml-map "pim:NumberOfExternalNeighbors";
      type int32;
      description "Number of external neighbors";
    }
  }

  grouping PIM-TABLE-CTX-BAG {
    description "PIM Table context";
    leaf afi {
      xr:xr-xml-map "pim:AFI";
      type uint32;
      description "AFI";
    }
    leaf safi {
      xr:xr-xml-map "pim:SAFI";
      type uint32;
      description "SAFI";
    }
    leaf table-name {
      xr:xr-xml-map "pim:TableName";
      type string;
      description "Table name";
    }
    leaf vrf-id {
      xr:xr-xml-map "pim:VRF_ID";
      type uint32;
      description "VRF ID";
    }
    leaf table-id {
      xr:xr-xml-map "pim:TableID";
      type uint32;
      description "Table ID";
    }
    leaf is-active {
      xr:xr-xml-map "pim:IsActive";
      type boolean;
      description "Active status";
    }
    leaf is-ital-registration-done {
      xr:xr-xml-map "pim:IsITALRegistrationDone";
      type boolean;
      description "ITAL reg status";
    }
    leaf is-rib-registration-done {
      xr:xr-xml-map "pim:IsRIBRegistrationDone";
      type boolean;
      description "RIB reg status";
    }
    leaf is-rib-convergence-received {
      xr:xr-xml-map "pim:IsRIBConvergenceReceived";
      type boolean;
      description "RIB Convergence receive status";
    }
    leaf is-rib-convergence {
      xr:xr-xml-map "pim:IsRIBConvergence";
      type boolean;
      description "RIB Convergence status";
    }
    leaf rpf-registrations {
      xr:xr-xml-map "pim:RPFRegistrations";
      type uint32;
      description "RPF Registration count";
    }
  }

  grouping PIM-BIDIR-DF-BAG {
    description "PIM Bidirectional DF entry";

    container rp-address-xr {
      description "RP Address";
      uses PIM-ADDRTYPE;
    }

    container df-winner {
      description "DF Winner";
      uses PIM-ADDRTYPE;
    }
    leaf pim-interface-name {
      xr:xr-xml-map "pim:PIMInterfaceName";
      type string;
      description "Interface Name";
    }
    leaf are-we-df {
      xr:xr-xml-map "pim:AreWeDF";
      type boolean;
      description "Are we DF";
    }
    leaf rp-lan {
      xr:xr-xml-map "pim:RP_LAN";
      type boolean;
      description "Is this the RP LAN";
    }
    leaf metric {
      xr:xr-xml-map "pim:Metric";
      type uint32;
      description "Metric";
    }
    leaf metric-preference {
      xr:xr-xml-map "pim:MetricPreference";
      type uint32;
      description "Metric Preference";
    }
    leaf uptime {
      xr:xr-xml-map "pim:Uptime";
      type uint64;
      units "second";
      description "Uptime in seconds";
    }
  }

  grouping PIM-GRE-PATH-BAG {
    description "PIM GRE path information";

    container gre-neighbor {
      description "GRE neighbor";
      uses PIM-ADDRTYPE;
    }

    container gre-next-hop {
      description "GRE nexthop";
      uses PIM-ADDRTYPE;
    }
    leaf gre-interface-name {
      xr:xr-xml-map "pim:GREInterfaceName";
      type xr:Interface-name;
      description "GRE Interface";
    }
    leaf is-gre-interface-disabled {
      xr:xr-xml-map "pim:IsGREInterfaceDisabled";
      type boolean;
      description "Is the gre interface disabled ?";
    }
    leaf is-via-lsm {
      xr:xr-xml-map "pim:IsViaLSM";
      type boolean;
      description "Via LSM";
    }
    leaf is-connector-attribute-present {
      xr:xr-xml-map "pim:IsConnectorAttributePresent";
      type boolean;
      description "Connector attribute present";
    }
    leaf extranet-vrf-name {
      xr:xr-xml-map "pim:ExtranetVRFName";
      type string {
        length "0..33";
      }
      description "Extranet VRF name";
    }
  }

  grouping PIM-GRE-INFO-BAG {
    description "PIM GRE information";

    container registered-address {
      description "Address registered";
      uses PIM-ADDRTYPE;
    }
    leaf metric {
      xr:xr-xml-map "pim:Metric";
      type uint32;
      description "Metric";
    }
    leaf metric-preference {
      xr:xr-xml-map "pim:MetricPreference";
      type uint32;
      description "Metric preference";
    }
    leaf is-connected {
      xr:xr-xml-map "pim:IsConnected";
      type uint8;
      description "Are we connected ?";
    }

    list gre-path {
      description "GRE Paths list";
      uses PIM-GRE-PATH-BAG;
    }
  }

  grouping PIM-GRE-HASH-BAG {
    description "PIM GRE Hash Outcome";
    leaf next-hop-interface {
      xr:xr-xml-map "pim:NextHopInterface";
      type xr:Interface-name;
      description "Next hop neighbor interface";
    }
  }

  grouping PIM-SUMMARY-BAG {
    description "PIM Summary Bag";
    leaf route-limit {
      xr:xr-xml-map "pim:RouteLimit";
      type uint32;
      description "Maximum routes";
    }
    leaf route-count {
      xr:xr-xml-map "pim:RouteCount";
      type uint32;
      description "Current routes";
    }
    leaf route-low-water-mark {
      xr:xr-xml-map "pim:RouteLowWaterMark";
      type uint32;
      description
        "The number of routes below which the throttle on
        route creation will be lifted";
    }
    leaf is-route-limit-reached {
      xr:xr-xml-map "pim:IsRouteLimitReached";
      type boolean;
      description "Is route creation throttled";
    }
    leaf topology-interface-state-limit {
      xr:xr-xml-map "pim:TopologyInterfaceStateLimit";
      type uint32;
      description "Maximum Topology Interface State count";
    }
    leaf topology-interface-state-count {
      xr:xr-xml-map "pim:TopologyInterfaceStateCount";
      type uint32;
      description "Current Topology Interface State count";
    }
    leaf rxi-low-water-mark {
      xr:xr-xml-map "pim:RXILowWaterMark";
      type uint32;
      description
        "The rxi below which the throttle on interface
        creation will be lifted";
    }
    leaf rxi-limit-reached {
      xr:xr-xml-map "pim:RXILimitReached";
      type boolean;
      description "Is interface creation throttled";
    }
    leaf register-limit {
      xr:xr-xml-map "pim:RegisterLimit";
      type uint32;
      description "Maximum registers";
    }
    leaf register-count {
      xr:xr-xml-map "pim:RegisterCount";
      type uint32;
      description "Current registers";
    }
    leaf register-limit-reached {
      xr:xr-xml-map "pim:RegisterLimitReached";
      type boolean;
      description "Is PIM SM register handling throttled";
    }
    leaf ranges-limit {
      xr:xr-xml-map "pim:RangesLimit";
      type uint32;
      description "Maximum group ranges from Autorp";
    }
    leaf ranges-count {
      xr:xr-xml-map "pim:RangesCount";
      type uint32;
      description "Current group ranges from Autorp";
    }
    leaf ranges-threshold {
      xr:xr-xml-map "pim:RangesThreshold";
      type uint32;
      description "OOR theshold of grange ranges from AutoRP";
    }
    leaf is-ranges-limit-reached {
      xr:xr-xml-map "pim:IsRangesLimitReached";
      type boolean;
      description
        "Is Auto-RP group-to-RP mapping range creation
        throttled";
    }
    leaf bsr-ranges-limit {
      xr:xr-xml-map "pim:BSRRangesLimit";
      type uint32;
      description "Maximum group ranges from BSR";
    }
    leaf bsr-ranges-count {
      xr:xr-xml-map "pim:BSRRangesCount";
      type uint32;
      description "Current group ranges from BSR";
    }
    leaf bsr-range-threshold {
      xr:xr-xml-map "pim:BSRRangeThreshold";
      type uint32;
      description "Threshold group range from BSR";
    }
    leaf is-bsr-ranges-threshold-reached {
      xr:xr-xml-map "pim:IsBSRRangesThresholdReached";
      type boolean;
      description
        "Is VRF-specific BSR group-to-RP mapping range
        creation throttled";
    }
    leaf bsr-candidate-rp-set-limit {
      xr:xr-xml-map "pim:BSRCandidateRPSetLimit";
      type uint32;
      description "Maximum crp-set from BSR";
    }
    leaf bsr-candidate-rp-set-count {
      xr:xr-xml-map "pim:BSRCandidateRPSetCount";
      type uint32;
      description "Current crp-set count from BSR";
    }
    leaf bsr-candidate-rp-set-threshold {
      xr:xr-xml-map "pim:BSRCandidateRPSetThreshold";
      type uint32;
      description "Threshold crp-set from BSR";
    }
    leaf is-maximum-enforcement-disabled {
      xr:xr-xml-map "pim:IsMaximumEnforcementDisabled";
      type boolean;
      description "Is maximum enforcement disabled";
    }
    leaf is-node-low-memory {
      xr:xr-xml-map "pim:IsNodeLowMemory";
      type boolean;
      description "Is node in low memory condition";
    }
    leaf route-threshold {
      xr:xr-xml-map "pim:RouteThreshold";
      type uint32;
      description "Threshold routes";
    }
    leaf global-auto-rp-ranges-limit {
      xr:xr-xml-map "pim:GlobalAutoRPRangesLimit";
      type uint32;
      description "Global Auto-RP maximum group ranges";
    }
    leaf is-global-auto-rp-ranges-limit-reached {
      xr:xr-xml-map "pim:IsGlobalAutoRPRangesLimitReached";
      type boolean;
      description
        "Is global AutoRP group-to-RP mapping range
        creation throttled";
    }
    leaf global-bsr-ranges-limit {
      xr:xr-xml-map "pim:GlobalBSRRangesLimit";
      type uint32;
      description "Global BSR maximum group ranges";
    }
    leaf global-bsr-ranges-count {
      xr:xr-xml-map "pim:GlobalBSRRangesCount";
      type uint32;
      description "Global BSR current group ranges";
    }
    leaf global-bsr-ranges-threshold {
      xr:xr-xml-map "pim:GlobalBSRRangesThreshold";
      type uint32;
      description "Global BSR Threshold group ranges";
    }
    leaf is-global-bsr-ranges-limit-reached {
      xr:xr-xml-map "pim:IsGlobalBSRRangesLimitReached";
      type boolean;
      description
        "Is global BSR group-to-RP mapping range creation
        throttled";
    }
    leaf global-bsr-candidate-rp-set-limit {
      xr:xr-xml-map "pim:GlobalBSRCandidateRPSetLimit";
      type uint32;
      description "Global BSR maximum crp-set";
    }
    leaf global-bsr-candidate-rp-set-count {
      xr:xr-xml-map "pim:GlobalBSRCandidateRPSetCount";
      type uint32;
      description "Global BSR current crp-set count";
    }
    leaf global-bsr-candidate-rp-set-threshold {
      xr:xr-xml-map "pim:GlobalBSRCandidateRPSetThreshold";
      type uint32;
      description "Global BSR Threshold crp-set";
    }
    leaf is-global-route-limit-reached {
      xr:xr-xml-map "pim:IsGlobalRouteLimitReached";
      type boolean;
      description "Is global route creation throttled";
    }
    leaf topology-interface-state-threshold {
      xr:xr-xml-map "pim:TopologyInterfaceStateThreshold";
      type uint32;
      description "Topology Interface State threshold";
    }
    leaf is-global-rxi-limit-reached {
      xr:xr-xml-map "pim:IsGlobalRXILimitReached";
      type boolean;
      description "Is global interface creation throttled";
    }
    leaf register-threshold {
      xr:xr-xml-map "pim:RegisterThreshold";
      type uint32;
      description "Threshold registers";
    }
    leaf global-register-limit {
      xr:xr-xml-map "pim:GlobalRegisterLimit";
      type uint32;
      description "Maximum global registers";
    }
    leaf is-global-register-limit-reached {
      xr:xr-xml-map "pim:IsGlobalRegisterLimitReached";
      type boolean;
      description "Is global PIM SM register handling throttled";
    }
  }

  grouping PIM-PKTQ-STATS {
    description "PIM packet queue statistics per priority";
    leaf enqueued-packets {
      xr:xr-xml-map "pim:EnqueuedPackets";
      type uint32;
      description "Total number of packets enqueued to this queue";
    }
    leaf dequeued-packets {
      xr:xr-xml-map "pim:DequeuedPackets";
      type uint32;
      description
        "Total number of packets dequeued from this queue";
    }
    leaf high-water-mark-packets {
      xr:xr-xml-map "pim:HighWaterMarkPackets";
      type uint32;
      description
        "Highest number of packets enqueued in this queue";
    }
    leaf high-water-mark-bytes {
      xr:xr-xml-map "pim:HighWaterMarkBytes";
      type uint32;
      units "byte";
      description "Highest number of bytes enqueued in this queue";
    }
    leaf tail-drops {
      xr:xr-xml-map "pim:TailDrops";
      type uint32;
      description
        "Number packets dropped from this queue due to
        max size";
    }
  }

  grouping PIM-PKTQ-STATE {
    description "PIM packet queue state per priority";
    leaf max-queue-size {
      xr:xr-xml-map "pim:MaxQueueSize";
      type uint32;
      units "byte";
      description "Maximum size of queue in bytes";
    }
    leaf queue-size-bytes {
      xr:xr-xml-map "pim:QueueSizeBytes";
      type uint32;
      units "byte";
      description "Size of queue in bytes";
    }
    leaf queue-size-packets {
      xr:xr-xml-map "pim:QueueSizePackets";
      type uint32;
      description "Size of queue in number of packets";
    }
  }

  grouping PIM-PKTQ {
    description "PIM packet queue state and statistics";

    container packet-queue-state {
      description "State of the queue";
      uses PIM-PKTQ-STATE;
    }

    container packet-queue-stats {
      description "Statistics about the queue";
      uses PIM-PKTQ-STATS;
    }
    leaf packet-queue-priority {
      xr:xr-xml-map "pim:PacketQueuePriority";
      type uint32;
      description "Priority of this packet queue";
    }
  }

  grouping PIM-TRAFFIC-BAG {
    description "PIM Traffic counters";
    leaf elapsed-time {
      xr:xr-xml-map "pim:ElapsedTime";
      type uint32;
      units "second";
      description "Running time for counters in seconds";
    }
    leaf inputs {
      xr:xr-xml-map "pim:Inputs";
      type uint32;
      description "Packets in";
    }
    leaf outputs {
      xr:xr-xml-map "pim:Outputs";
      type uint32;
      description "Packets out";
    }
    leaf format-error {
      xr:xr-xml-map "pim:FormatError";
      type uint32;
      description "Malformed packets in";
    }
    leaf pakman-error {
      xr:xr-xml-map "pim:PakmanError";
      type uint32;
      description "Pakman packets dropped";
    }
    leaf standby-packets-error {
      xr:xr-xml-map "pim:StandbyPacketsError";
      type uint32;
      description "Packets received in standby state";
    }
    leaf checksum-error {
      xr:xr-xml-map "pim:ChecksumError";
      type uint32;
      description "Checksum errors";
    }
    leaf socket-error {
      xr:xr-xml-map "pim:SocketError";
      type uint32;
      description "Socket errors";
    }
    leaf send-queue-full {
      xr:xr-xml-map "pim:SendQueueFull";
      type uint32;
      description "Packets dropped since send queue was full";
    }
    leaf boundary-acl-rx-drop {
      xr:xr-xml-map "pim:BoundaryACLRxDrop";
      type uint32;
      description "Inc. JP dropped since boundary ACL confg";
    }
    leaf boundary-acl-tx-drop {
      xr:xr-xml-map "pim:BoundaryACLTxDrop";
      type uint32;
      description "Out JP dropped since boundary ACL confg";
    }
    leaf no-socket-connection {
      xr:xr-xml-map "pim:NoSocketConnection";
      type uint32;
      description "Packets dropped since no socket connection";
    }
    leaf no-source-address {
      xr:xr-xml-map "pim:NoSourceAddress";
      type uint32;
      description "Packets dropped since no source address";
    }
    leaf input-hello {
      xr:xr-xml-map "pim:InputHello";
      type uint32;
      description "Hello packets in";
    }
    leaf output-hello {
      xr:xr-xml-map "pim:OutputHello";
      type uint32;
      description "Hello packets out";
    }
    leaf input-jp {
      xr:xr-xml-map "pim:InputJP";
      type uint32;
      description "Join Prune packets in";
    }
    leaf output-jp {
      xr:xr-xml-map "pim:OutputJP";
      type uint32;
      description "Join Prune packets out";
    }
    leaf input-data-register {
      xr:xr-xml-map "pim:InputDataRegister";
      type uint32;
      description "Data Register packets in";
    }
    leaf input-null-register {
      xr:xr-xml-map "pim:InputNullRegister";
      type uint32;
      description "Null Register packets in";
    }
    leaf output-data-register {
      xr:xr-xml-map "pim:OutputDataRegister";
      type uint32;
      description "Data Register packets out";
    }
    leaf output-null-register {
      xr:xr-xml-map "pim:OutputNullRegister";
      type uint32;
      description "Null Register packets out";
    }
    leaf input-register-stop {
      xr:xr-xml-map "pim:InputRegisterStop";
      type uint32;
      description "Register Stop packets in";
    }
    leaf output-register-stop {
      xr:xr-xml-map "pim:OutputRegisterStop";
      type uint32;
      description "Register Stop packets out";
    }
    leaf input-assert {
      xr:xr-xml-map "pim:InputAssert";
      type uint32;
      description "Assert packets in";
    }
    leaf input-assert-batched {
      xr:xr-xml-map "pim:InputAssertBatched";
      type uint32;
      description "Batched Assert packets in";
    }
    leaf output-assert {
      xr:xr-xml-map "pim:OutputAssert";
      type uint32;
      description "Assert packets out";
    }
    leaf output-assert-batched {
      xr:xr-xml-map "pim:OutputAssertBatched";
      type uint32;
      description "Batched Assert packets out";
    }
    leaf input-df-election {
      xr:xr-xml-map "pim:InputDFElection";
      type uint32;
      description "DF Election packets in";
    }
    leaf output-df-election {
      xr:xr-xml-map "pim:OutputDFElection";
      type uint32;
      description "DF Election packets out";
    }
    leaf input-bsr-message {
      xr:xr-xml-map "pim:InputBSRMessage";
      type uint32;
      description "Input BSR Messages";
    }
    leaf output-bsr-message {
      xr:xr-xml-map "pim:OutputBSRMessage";
      type uint32;
      description "Output BSR Messages";
    }
    leaf input-candidate-rp-advertisement {
      xr:xr-xml-map "pim:InputCandidateRPAdvertisement";
      type uint32;
      description "Input Candidate-RP Advertisment";
    }
    leaf output-candidate-rp-advertisement {
      xr:xr-xml-map "pim:OutputCandidateRPAdvertisement";
      type uint32;
      description "Output Candidate-RP Advertisment";
    }
    leaf input-ecmp-redirect {
      xr:xr-xml-map "pim:InputEcmpRedirect";
      type uint32;
      description "Input Ecmp Redirect";
    }
    leaf output-ecmp-redirect {
      xr:xr-xml-map "pim:OutputEcmpRedirect";
      type uint32;
      description "Output Ecmp Redirect";
    }
    leaf output-loop-error {
      xr:xr-xml-map "pim:OutputLoopError";
      type uint32;
      description "Output on loopback error";
    }
    leaf mldp-mdt-invalid-lsm-identifier {
      xr:xr-xml-map "pim:MLDP_MDTInvalidLSM_Identifier";
      type uint32;
      description " Invalid LSM ID";
    }
    leaf input-no-idb-error {
      xr:xr-xml-map "pim:InputNoIDBError";
      type uint32;
      description "No IDB for intf error";
    }
    leaf input-no-vrf-error {
      xr:xr-xml-map "pim:InputNoVRFError";
      type uint32;
      description "No VRF for idb error";
    }
    leaf input-no-pim-error {
      xr:xr-xml-map "pim:InputNoPIMError";
      type uint32;
      description "PIM Disabled on intf error";
    }
    leaf input-pim-version-error {
      xr:xr-xml-map "pim:InputPIMVersionError";
      type uint32;
      description "Invalid PIM version error";
    }
    leaf output-join-group {
      xr:xr-xml-map "pim:OutputJoinGroup";
      type uint32;
      description "Output Join Groups";
    }
    leaf output-prune-group {
      xr:xr-xml-map "pim:OutputPruneGroup";
      type uint32;
      description "Output Prune Groups";
    }
    leaf output-join-prune-bytes {
      xr:xr-xml-map "pim:OutputJoinPruneBytes";
      type uint32;
      units "byte";
      description "Output JP Bytes";
    }
    leaf output-hello-bytes {
      xr:xr-xml-map "pim:OutputHelloBytes";
      type uint32;
      units "byte";
      description "Output Hello Bytes";
    }
    leaf non-supported-packets {
      xr:xr-xml-map "pim:NonSupportedPackets";
      type uint32;
      description "PIM non supported pckets";
    }
    leaf invalid-registers {
      xr:xr-xml-map "pim:InvalidRegisters";
      type uint32;
      description "PIM invalid registers received";
    }
    leaf invalid-join-prunes {
      xr:xr-xml-map "pim:InvalidJoinPrunes";
      type uint32;
      description "PIM invalid Join/Prunes received";
    }
    leaf packet-packman-error {
      xr:xr-xml-map "pim:PacketPackmanError";
      type uint32;
      description "Packets Dropped due to Pakman Error";
    }
    leaf packet-read-socket-error {
      xr:xr-xml-map "pim:PacketReadSocketError";
      type uint32;
      description "Packet Read Socket Error";
    }
    leaf packet-queue-last-clear {
      xr:xr-xml-map "pim:PacketQueueLastClear";
      type uint32;
      units "second";
      description
        "Time in seconds since the last clear of all
        packet queues stats";
    }
    leaf packets-standby {
      xr:xr-xml-map "pim:PacketsStandby";
      type uint32;
      description "Packets Dropped due to Standby Error";
    }
    leaf no-mdt-socket-connection {
      xr:xr-xml-map "pim:NoMDTSocketConnection";
      type uint32;
      description "Packets dropped since no mdt socket connection";
    }
    leaf mdt-send-queue-full {
      xr:xr-xml-map "pim:MDTSendQueueFull";
      type uint32;
      description "Packets dropped since mdt send queue was full";
    }
    leaf mdt-socket-error {
      xr:xr-xml-map "pim:MDTSocketError";
      type uint32;
      description "MDT Socket errors";
    }
    leaf mdt-join-tlv-sent {
      xr:xr-xml-map "pim:MDTJoinTLVSent";
      type uint32;
      description "Data MDT Join Msgs sent";
    }
    leaf mdt-join-tlv-received {
      xr:xr-xml-map "pim:MDTJoinTLVReceived";
      type uint32;
      description "Data MDT Join Msgs received";
    }
    leaf mdt-join-bad-type {
      xr:xr-xml-map "pim:MDTJoinBadType";
      type uint32;
      description "Data MDT TLV bad type";
    }
    leaf mdt-drop-local-source-address {
      xr:xr-xml-map "pim:MDTDropLocalSourceAddress";
      type uint32;
      description
        "Data MDT Join msgs dropped due to local source
        addr";
    }
    leaf mdt-drop-null-local-address {
      xr:xr-xml-map "pim:MDTDropNullLocalAddress";
      type uint32;
      description
        "Data MDT Join msgs dropped due to null local
        addr";
    }
    leaf mdt-drop-no-idb {
      xr:xr-xml-map "pim:MDTDropNoIDB";
      type uint32;
      description "Data MDT Join msgs dropped due to idb missing";
    }
    leaf mdt-drop-no-vrf {
      xr:xr-xml-map "pim:MDTDropNoVRF";
      type uint32;
      description "Data MDT Join msgs dropped due to vrf missing";
    }
    leaf invalid-destination-packets {
      xr:xr-xml-map "pim:InvalidDestinationPackets";
      type uint32;
      description "Control Packets with Invalid Destination";
    }
    leaf mdt-joins-drop-multiple-encapsulation {
      xr:xr-xml-map "pim:MDTJoinsDropMultipleEncapsulation";
      type uint32;
      description
        "MDT Join msgs dropped due to multiple Encap
        limitation";
    }
    leaf truncated-pim-packets {
      xr:xr-xml-map "pim:TruncatedPIMPackets";
      type uint32;
      description
        "Packets dropped due to truncated Joins or Prunes";
    }
    leaf-list packet-enqueued {
      xr:xr-xml-map "pim:PacketEnqueued";
      type uint32;
      max-elements "2";
      description
        "Packets Enqueued per priority Deprecated by
        PacketQueue";
    }
    leaf-list packet-dequeued {
      xr:xr-xml-map "pim:PacketDequeued";
      type uint32;
      max-elements "2";
      description
        "Packets Dequeued per priority Deprecated by
        PacketQueue";
    }
    leaf-list packet-queue-length {
      xr:xr-xml-map "pim:PacketQueueLength";
      type uint32;
      max-elements "2";
      description
        "Packet Queue Length per priority Deprecated by
        PacketQueue";
    }
    leaf-list packet-queue-size {
      xr:xr-xml-map "pim:PacketQueueSize";
      type uint32;
      max-elements "2";
      description
        "Packet Queue Size per priority Deprecated by
        PacketQueue";
    }
    leaf-list packet-tail-drop {
      xr:xr-xml-map "pim:PacketTailDrop";
      type uint32;
      max-elements "2";
      description
        "Packet Tail Drop per priority Deprecated by
        PacketQueue";
    }

    list packet-queue {
      max-elements "2";
      description "Packet queue state and statistics";
      uses PIM-PKTQ;
    }
  }

  grouping PIM-GRP-MAP-INFOSRC-BAG {
    description "PIM group-map source information";

    container source-of-information {
      description "The source of information";
      uses PIM-ADDRTYPE;
    }

    container group-map-information {
      description "Group Mapping information";
      uses PIM-GRP-MAP-BAG;
    }
    leaf holdtime {
      xr:xr-xml-map "pim:Holdtime";
      type int32;
      units "second";
      description "Holdtime in seconds";
    }
    leaf expires {
      xr:xr-xml-map "pim:Expires";
      type uint64;
      units "second";
      description "Mapping expiry time in seconds";
    }
    leaf uptime {
      xr:xr-xml-map "pim:Uptime";
      type uint64;
      units "second";
      description "Mapping uptime in seconds";
    }
  }

  grouping PIM-BGP-SAFI-BAG {
    description "PIM BGP SAFI bag";

    container source {
      description "Source address";
      uses PIM-ADDRTYPE;
    }

    container group {
      description "Group address";
      uses PIM-ADDRTYPE;
    }

    container next-hop {
      description "Next hop address";
      uses PIM-ADDRTYPE;
    }
    leaf route-distinguisher {
      xr:xr-xml-map "pim:RouteDistinguisher";
      type string {
        length "0..256";
      }
      description "Router ID";
    }
    leaf extranet-path-count {
      xr:xr-xml-map "pim:ExtranetPathCount";
      type uint32;
      description "Count of dependent extranet paths";
    }
    leaf is-bgp-added {
      xr:xr-xml-map "pim:IsBGPAdded";
      type boolean;
      description "SAFI learnt from BGP";
    }
  }

  grouping PIM-TT-OLE-BAG {
    description "PIM topology OLE information";

    container assert-winner {
      description "Assert Winner";
      uses PIM-ADDRTYPE;
    }
    leaf interface-name {
      xr:xr-xml-map "pim:InterfaceName";
      type xr:Interface-name;
      description "Interface Identifier";
    }
    leaf uptime {
      xr:xr-xml-map "pim:Uptime";
      type uint64;
      units "second";
      description "Uptime in seconds";
    }
    leaf expiry {
      xr:xr-xml-map "pim:Expiry";
      type uint64;
      units "second";
      description "Expiry in seconds";
    }
    leaf bgp-c-mcast-prune-delay-timer {
      xr:xr-xml-map "pim:BgpCMcastPruneDelayTimer";
      type uint64;
      units "second";
      description "BGP C-MCAST Prune Suppression in seconds";
    }
    leaf jp-timer {
      xr:xr-xml-map "pim:JPTimer";
      type int32;
      units "second";
      description "Join-Prune Timer (secs)";
    }
    leaf jp-state {
      xr:xr-xml-map "pim:JPState";
      type int32;
      description "Join-Prune State";
    }
    leaf assert-timer {
      xr:xr-xml-map "pim:AssertTimer";
      type int32;
      units "second";
      description "Assert Timer in seconds";
    }
    leaf local-members {
      xr:xr-xml-map "pim:LocalMembers";
      type int32;
      description "Local Information";
    }
    leaf internal-interest-info {
      xr:xr-xml-map "pim:InternalInterestInfo";
      type int32;
      description "Internal Interest";
    }
    leaf forwarding-state {
      xr:xr-xml-map "pim:ForwardingState";
      type int32;
      description "Forward or Prune";
    }
    leaf immediate-state {
      xr:xr-xml-map "pim:ImmediateState";
      type int32;
      description "Immediate fwding state";
    }
    leaf last-hop {
      xr:xr-xml-map "pim:LastHop";
      type boolean;
      description "Are we last hop ?";
    }
    leaf mldp-inband-mdt {
      xr:xr-xml-map "pim:MLDPInbandMDT";
      type boolean;
      description "MLDP Inband MDT interface";
    }
    leaf mldp-stale {
      xr:xr-xml-map "pim:MLDPStale";
      type boolean;
      description "OLE is stale";
    }
    leaf sa-prune {
      xr:xr-xml-map "pim:SAPrune";
      type boolean;
      description "BGP SA Prune state";
    }
    leaf admin-boundary {
      xr:xr-xml-map "pim:AdminBoundary";
      type boolean;
      description "Is this an administrative boundary ?";
    }
    leaf igmp-membership {
      xr:xr-xml-map "pim:IgmpMembership";
      type boolean;
      description "IGMP membership";
    }
    leaf mdt-safi-join {
      xr:xr-xml-map "pim:MDTSafiJoin";
      type boolean;
      description "MDT Safi join";
    }
    leaf mvpn-safi-join {
      xr:xr-xml-map "pim:MVPNSafiJoin";
      type boolean;
      description "MVPN Safi join";
    }
    leaf local-mdt-join {
      xr:xr-xml-map "pim:LocalMDTJoin";
      type boolean;
      description "Default MDT Join";
    }
    leaf data-mdt-join {
      xr:xr-xml-map "pim:DataMDTJoin";
      type boolean;
      description "Data MDT join";
    }
    leaf mvp-nv6-safi-join {
      xr:xr-xml-map "pim:MVPNv6SafiJoin";
      type boolean;
      description "MVPN IPv6 Safi join";
    }
    leaf bgp-c-mcast-join {
      xr:xr-xml-map "pim:BgpCMcastJoin";
      type boolean;
      description "BGP C-Mcast join";
    }
    leaf vrf-name {
      xr:xr-xml-map "pim:VRFName";
      type string {
        length "0..33";
      }
      description "VRF which physically owns";
    }
    leaf extranet-interface {
      xr:xr-xml-map "pim:ExtranetInterface";
      type boolean;
      description "Is this an Extranet Interface ?";
    }
  }

  grouping PIM-TT-ROUTE-BAG {
    description "PIM topology table route";

    container group-address-xr {
      description "Group Address";
      uses PIM-ADDRTYPE;
    }

    container source-address-xr {
      description "Source Address";
      uses PIM-ADDRTYPE;
    }

    container rp-address {
      description "RP Address (If rpt)";
      uses PIM-ADDRTYPE;
    }

    container rpf-neighbor {
      description "RPF Neighbor";
      uses PIM-ADDRTYPE;
    }

    container secondary-rpf-neighbor {
      description "Secondary RPF Neighbor";
      uses PIM-ADDRTYPE;
    }

    container rpf-root {
      description "Root of this mcast tree";
      uses PIM-ADDRTYPE;
    }

    container proxy-address {
      description "RPF Proxy address.";
      uses PIM-ADDRTYPE;
    }

    container orig-src-address {
      description "Orig Src Address.";
      uses PIM-ADDRTYPE;
    }
    leaf limit-reached {
      xr:xr-xml-map "pim:LimitReached";
      type boolean;
      description
        "Have we throttled the creation of routes or
        interfaces ?";
    }
    leaf low-memory {
      xr:xr-xml-map "pim:LowMemory";
      type boolean;
      description "Node is running low on memory";
    }
    leaf protocol {
      xr:xr-xml-map "pim:Protocol";
      type Pim-show-protocol;
      description "The PIM protocol";
    }
    leaf wildcard {
      xr:xr-xml-map "pim:Wildcard";
      type boolean;
      description "WC -Wildcard";
    }
    leaf rpt-xr {
      xr:xr-xml-map "pim:rpt-xr";
      type boolean;
      description "Is this on the RPT ?";
    }
    leaf spt {
      xr:xr-xml-map "pim:SPT";
      type boolean;
      description "Is this on the SPT ?";
    }
    leaf uptime {
      xr:xr-xml-map "pim:Uptime";
      type uint64;
      units "second";
      description "Uptime in seconds";
    }
    leaf expiry {
      xr:xr-xml-map "pim:Expiry";
      type uint64;
      description "When this entry expires";
    }
    leaf alive {
      xr:xr-xml-map "pim:Alive";
      type int32;
      units "second";
      description "Alive time in seconds (-1 if never)";
    }
    leaf register-received-timer {
      xr:xr-xml-map "pim:RegisterReceivedTimer";
      type int32;
      units "second";
      description
        "Register Received Timer in seconds (-1 if never)";
    }
    leaf remote-source {
      xr:xr-xml-map "pim:RemoteSource";
      type boolean;
      description "MSDP told us";
    }
    leaf rpf-interface-name {
      xr:xr-xml-map "pim:RPFInterfaceName";
      type xr:Interface-name;
      description "Interface Identifier";
    }
    leaf rpf-vrf-name {
      xr:xr-xml-map "pim:RPF_VRFName";
      type string {
        length "0..33";
      }
      description "RPF VRF Name";
    }
    leaf rpf-safi {
      xr:xr-xml-map "pim:RPF_SAFI";
      type uint8;
      description "Unicast or mcast";
    }
    leaf rpf-table-name {
      xr:xr-xml-map "pim:RPFTableName";
      type string;
      description "RPF Table name";
    }
    leaf rpf-drop {
      xr:xr-xml-map "pim:RPFDrop";
      type boolean;
      description "RPF route-policy drop";
    }
    leaf rpf-extranet {
      xr:xr-xml-map "pim:RPFExtranet";
      type boolean;
      description "Extranet RPF route-policy";
    }
    leaf is-via-lsm {
      xr:xr-xml-map "pim:IsViaLSM";
      type boolean;
      description "Via LSM";
    }
    leaf secondary-rpf-interface-name {
      xr:xr-xml-map "pim:SecondaryRPFInterfaceName";
      type xr:Interface-name;
      description "Secondary Interface Identifier";
    }
    leaf connected {
      xr:xr-xml-map "pim:Connected";
      type boolean;
      description "Is Connected ?";
    }
    leaf proxy {
      xr:xr-xml-map "pim:Proxy";
      type boolean;
      description "Is the RPF target a proxy?";
    }
    leaf rpf-proxy-enabled {
      xr:xr-xml-map "pim:RPFProxyEnabled";
      type boolean;
      description "Is rpf if proxy enabled?";
    }
    leaf mofrr-enabled {
      xr:xr-xml-map "pim:mofrr_enabled";
      type boolean;
      description "Is this SG MoFRR enabled?";
    }
    leaf rib-mo-frr-enabled {
      xr:xr-xml-map "pim:RIB_MoFRREnabled";
      type boolean;
      description "Is this SG MoFRR enabled?";
    }
    leaf jp-timer {
      xr:xr-xml-map "pim:JPTimer";
      type int32;
      description "Join-Prune Timer";
    }
    leaf jp-status {
      xr:xr-xml-map "pim:JPStatus";
      type int32;
      description "Join-Prune Status";
    }
    leaf suppress-registers {
      xr:xr-xml-map "pim:SuppressRegisters";
      type int32;
      description "When the Null register probe expires";
    }
    leaf assume-alive {
      xr:xr-xml-map "pim:AssumeAlive";
      type boolean;
      description "The Assume Alive Bit";
    }
    leaf probe-alive {
      xr:xr-xml-map "pim:ProbeAlive";
      type boolean;
      description "The Probe Alive Bit";
    }
    leaf really-alive {
      xr:xr-xml-map "pim:ReallyAlive";
      type boolean;
      description "The Really Alive Bit";
    }
    leaf inherit-alive {
      xr:xr-xml-map "pim:InheritAlive";
      type boolean;
      description "The Inherit Alive Bit";
    }
    leaf inherit-spt {
      xr:xr-xml-map "pim:InheritSpt";
      type boolean;
      description "The Inherit SPT Bit";
    }
    leaf signal-sources {
      xr:xr-xml-map "pim:SignalSources";
      type boolean;
      description "Signal Sources on route?";
    }
    leaf dont-check-connected {
      xr:xr-xml-map "pim:DontCheckConnected";
      type boolean;
      description
        "Do we need to make the connected check on this
        route ?";
    }
    leaf register-received {
      xr:xr-xml-map "pim:RegisterReceived";
      type boolean;
      description "Have registers been received for this source ?";
    }
    leaf last-hop {
      xr:xr-xml-map "pim:LastHop";
      type boolean;
      description "Are we last hop ?";
    }
    leaf sending-registers {
      xr:xr-xml-map "pim:SendingRegisters";
      type boolean;
      description "Are we sending registers for this route ?";
    }
    leaf sending-null-registers {
      xr:xr-xml-map "pim:SendingNullRegisters";
      type boolean;
      description "Are we sending null registers for this route ?";
    }
    leaf sa-sent {
      xr:xr-xml-map "pim:SASent";
      type boolean;
      description "BGP SA sent";
    }
    leaf sa-received {
      xr:xr-xml-map "pim:SAReceived";
      type boolean;
      description "BGP SA received";
    }
    leaf sa-joined {
      xr:xr-xml-map "pim:SAJoined";
      type boolean;
      description "BGP SA join";
    }
    leaf anycast-rp-match {
      xr:xr-xml-map "pim:AnycastRPMatch";
      type boolean;
      description "Group matches Anycast-RP policy";
    }
    leaf anycast-rp-route-target {
      xr:xr-xml-map "pim:AnycastRPRouteTarget";
      type inet:ipv4-address;
      description "Anycast-RP RT";
    }
    leaf bgp-join {
      xr:xr-xml-map "pim:BGPJoin";
      type boolean;
      description "BGP C JOIN";
    }
    leaf bgpjp-time {
      xr:xr-xml-map "pim:BGPJPTime";
      type uint64;
      description "BGP C JP Time";
    }
    leaf customer-routing-type {
      xr:xr-xml-map "pim:CustomerRoutingType";
      type int32;
      description "Type of Customer Routing in the MVPN";
    }
    leaf extranet-route {
      xr:xr-xml-map "pim:ExtranetRoute";
      type boolean;
      description "Is a Extranet route ?";
    }
    leaf mofrr-active {
      xr:xr-xml-map "pim:MofrrActive";
      type boolean;
      description "Is MoFRR Active?";
    }
    leaf mofrr-primary {
      xr:xr-xml-map "pim:MofrrPrimary";
      type boolean;
      description "Is this Mofrr Primary?";
    }
    leaf mofrr-backup {
      xr:xr-xml-map "pim:MofrrBackup";
      type boolean;
      description "Is this Mofrr Backup?";
    }
    leaf vxlan {
      xr:xr-xml-map "pim:Vxlan";
      type boolean;
      description "Is this VXLAN?";
    }

    list outgoing-interface {
      description "Outgoing interface list";
      uses PIM-TT-OLE-BAG;
    }
  }

  grouping PIM-BIDIR-DF-STATE-BAG {
    description "PIM Bidirectional DF state";

    container rp-address-xr {
      description "RP Address";
      uses PIM-ADDRTYPE;
    }
    leaf pim-interface-name {
      xr:xr-xml-map "pim:PIMInterfaceName";
      type string;
      description "Interface Name";
    }
    leaf election-state {
      xr:xr-xml-map "pim:ElectionState";
      type string;
      description "DF Election State";
    }
    leaf time-seconds {
      xr:xr-xml-map "pim:TimeSeconds";
      type uint64;
      units "second";
      description "Timer expires (seconds)";
    }
    leaf time-nano-seconds {
      xr:xr-xml-map "pim:TimeNanoSeconds";
      type uint64;
      units "nanosecond";
      description "Timer expires (nseconds)";
    }
    leaf our-metric {
      xr:xr-xml-map "pim:OurMetric";
      type uint32;
      description "Metric";
    }
    leaf our-metric-preference {
      xr:xr-xml-map "pim:OurMetricPreference";
      type uint32;
      description "MetricPreference";
    }
  }

  grouping PIM-TUNNEL-INFO-BAG {
    description "PIM tunnel information";

    container source-address {
      description "Source addr known to PIM";
      uses PIM-ADDRTYPE;
    }

    container rp-address {
      description "RP addr known to PIM";
      uses PIM-ADDRTYPE;
    }

    container source-address-netio {
      description "Source addr from netio";
      uses PIM-ADDRTYPE;
    }

    container group-address-netio {
      description "Group addr from netio";
      uses PIM-ADDRTYPE;
    }
    leaf vrf-name {
      xr:xr-xml-map "pim:VRFName";
      type string {
        length "0..33";
      }
      description "VRF Name";
    }
  }

  grouping PIM-RPF-SUMMARY-BAG {
    description "PIM RPF count summary";
    leaf default-safi {
      xr:xr-xml-map "pim:DefaultSAFI";
      type uint32;
      description "Default RPF Table SAFI";
    }
    leaf default-table-name {
      xr:xr-xml-map "pim:DefaultTableName";
      type string;
      description "Default RPF Table Name";
    }
    leaf is-mbgp-configured {
      xr:xr-xml-map "pim:IsMBGPConfigured";
      type boolean;
      description "Is MBGP configured?";
    }
    leaf is-ospf-te-configured {
      xr:xr-xml-map "pim:IsOSPF_TEConfigured";
      type boolean;
      description "Is OSPF TE configured?";
    }
    leaf is-isis-te-configured {
      xr:xr-xml-map "pim:IsISIS_TEConfigured";
      type boolean;
      description "Is ISIS TE configured?";
    }
    leaf is-isis-mtr-configured {
      xr:xr-xml-map "pim:IsISIS_MTRConfigured";
      type boolean;
      description "Is ISIS MTR configured?";
    }
    leaf mo-frr-configured {
      xr:xr-xml-map "pim:MoFRRConfigured";
      type boolean;
      description "Is MoFRR configured?";
    }
    leaf rib-mo-frr-configured {
      xr:xr-xml-map "pim:RIB_MoFRRConfigured";
      type boolean;
      description "Is MoFRR RIB configured?";
    }
    leaf rump-enabled {
      xr:xr-xml-map "pim:RUMP_Enabled";
      type boolean;
      description "Is RUMP MuRIB enabled?";
    }
    leaf rib-convergence-timeout {
      xr:xr-xml-map "pim:RIBConvergenceTimeout";
      type uint32;
      units "second";
      description "RIB convergence timeout in seconds";
    }
    leaf rib-convergence-time-left {
      xr:xr-xml-map "pim:RIBConvergenceTimeLeft";
      type uint32;
      units "second";
      description "RIB convergence time left in seconds";
    }
    leaf is-multipath-enabled {
      xr:xr-xml-map "pim:IsMultipathEnabled";
      type boolean;
      description "Is Multipath Enabled ?";
    }
    leaf is-multipath-interface-hash-enabled {
      xr:xr-xml-map "pim:IsMultipathInterfaceHashEnabled";
      type boolean;
      description "Is Multipath Interface Hash Extension Enabled ?";
    }
    leaf is-multipath-source-hash-enabled {
      xr:xr-xml-map "pim:IsMultipathSourceHashEnabled";
      type boolean;
      description "Is Multipath Source based Hash Enabled ?";
    }
    leaf is-multipath-source-next-hop-hash-enabled {
      xr:xr-xml-map "pim:IsMultipathSourceNextHopHashEnabled";
      type boolean;
      description "Is Multipath Source-Nexthop Hash Enabled ?";
    }
    leaf rpf-registrations {
      xr:xr-xml-map "pim:RPFRegistrations";
      type uint32;
      description "RPF Registration count";
    }
    leaf is-rib-convergence {
      xr:xr-xml-map "pim:IsRIBConvergence";
      type boolean;
      description "RIB Convergence status";
    }
  }

  grouping PIM-RPF-POLICY-TEST-BAG {
    description "PIM RPF policy test statistics";

    container source-address-xr {
      description "Source address";
      uses PIM-ADDRTYPE;
    }

    container group-address-xr {
      description "Source address";
      uses PIM-ADDRTYPE;
    }
    leaf policy-name {
      xr:xr-xml-map "pim:PolicyName";
      type string;
      description "RPF policy name";
    }
    leaf extended-community-rt {
      xr:xr-xml-map "pim:ExtendedCommunityRT";
      type string {
        length "0..33";
      }
      description "Route Target";
    }
    leaf pass {
      xr:xr-xml-map "pim:Pass";
      type boolean;
      description "Pass";
    }
    leaf default-table {
      xr:xr-xml-map "pim:DefaultTable";
      type boolean;
      description "Default table selected";
    }
    leaf vrf-name {
      xr:xr-xml-map "pim:VRFName";
      type string {
        length "0..33";
      }
      description "VRF name";
    }
    leaf afi {
      xr:xr-xml-map "pim:AFI";
      type uint32;
      description "AFI";
    }
    leaf safi {
      xr:xr-xml-map "pim:SAFI";
      type uint32;
      description "SAFI";
    }
    leaf table-name {
      xr:xr-xml-map "pim:TableName";
      type string;
      description "Table name";
    }
    leaf table-exists {
      xr:xr-xml-map "pim:TableExists";
      type boolean;
      description "Table exists";
    }
    leaf table-active {
      xr:xr-xml-map "pim:TableActive";
      type boolean;
      description "Table active";
    }
  }

  grouping PIM-RPF-POLICY-STATS-BAG {
    description "PIM RPF policy statistics";
    leaf policy-name {
      xr:xr-xml-map "pim:PolicyName";
      type string;
      description "RPF policy name";
    }
    leaf requests {
      xr:xr-xml-map "pim:Requests";
      type uint32;
      description "Number of RPF lookup requests";
    }
    leaf pass {
      xr:xr-xml-map "pim:Pass";
      type uint32;
      description "Number of RPF pass";
    }
    leaf drop {
      xr:xr-xml-map "pim:Drop";
      type uint32;
      description "Number of RPF drops";
    }
    leaf default-table {
      xr:xr-xml-map "pim:DefaultTable";
      type uint32;
      description "Number of RPF lookup in default-only Table";
    }
    leaf any-table {
      xr:xr-xml-map "pim:AnyTable";
      type uint32;
      description "Number of RPF lookup in any Table";
    }
  }

  grouping PIM-BSR-ELECTION-BAG {
    description "PIM BSR Election State";

    container bsr-address {
      description "BSR address";
      uses PIM-ADDRTYPE;
    }

    container candidate-bsr-address {
      description "C-BSR address";
      uses PIM-ADDRTYPE;
    }
    leaf bsr-priority {
      xr:xr-xml-map "pim:BSRPriority";
      type uint8;
      description "BSR Priority";
    }
    leaf bsr-mask-length {
      xr:xr-xml-map "pim:BSRMaskLength";
      type uint8;
      description "Hash Function Mask Length";
    }
    leaf bsr-up-time {
      xr:xr-xml-map "pim:BSRUpTime";
      type uint16;
      description "BSR Uptime";
    }
    leaf bootstrap-timeout {
      xr:xr-xml-map "pim:BootstrapTimeout";
      type uint16;
      description "Bootstrap Timeout";
    }
    leaf candidate-bsr-state {
      xr:xr-xml-map "pim:CandidateBSRState";
      type uint32;
      description "BSR Candidate State";
    }
    leaf bsr-election-state {
      xr:xr-xml-map "pim:BSRElectionState";
      type uint32;
      description "BSR Election State";
    }
    leaf bsr-scope {
      xr:xr-xml-map "pim:BSRScope";
      type uint16;
      description "BSR Scope";
    }
    leaf candidate-bsr-flag {
      xr:xr-xml-map "pim:CandidateBSRFlag";
      type boolean;
      description "BSR Candidate Config Flag";
    }
    leaf candidate-bsr-priority {
      xr:xr-xml-map "pim:CandidateBSRPriority";
      type uint8;
      description "C-BSR Priority";
    }
    leaf candidate-bsr-mask-length {
      xr:xr-xml-map "pim:CandidateBSRMaskLength";
      type uint8;
      description "C-BSR Hash Func. Mask Len";
    }
  }

  grouping PIM-BSR-CRP-ACL-BAG {
    description "PIM BSR Candidate RP Access-list";
    leaf candidate-rp-mode {
      xr:xr-xml-map "pim:CandidateRPMode";
      type Pim-show-protocol;
      description "Cand-RP Mode";
    }
    leaf acl-name {
      xr:xr-xml-map "pim:ACLName";
      type string {
        length "0..33";
      }
      description "Group Access-List Name";
    }
  }

  grouping PIM-BSR-CANDIDATE-RP-BAG {
    description "PIM BSR Candidate RP";

    container candidate-rp {
      description "Cand-RP Address";
      uses PIM-ADDRTYPE;
    }
    leaf candidate-rp-mode {
      xr:xr-xml-map "pim:CandidateRPMode";
      type Pim-show-protocol;
      description "Cand-RP Mode";
    }
    leaf candidate-rp-scope {
      xr:xr-xml-map "pim:CandidateRPScope";
      type int32;
      description "Cand-RP Scope";
    }
    leaf crp-priority {
      xr:xr-xml-map "pim:CRPPriority";
      type uint8;
      description "Cand-RP Priority";
    }
    leaf crp-holdtime {
      xr:xr-xml-map "pim:CRPHoldtime";
      type uint16;
      description "Cand-RP Holdtime";
    }
    leaf candidate-rp-advance-interval {
      xr:xr-xml-map "pim:CandidateRPAdvanceInterval";
      type uint16;
      units "second";
      description "Cand-RP Adv Interval in seconds";
    }
    leaf candidate-rp-uptime {
      xr:xr-xml-map "pim:CandidateRPUptime";
      type uint16;
      description "Cand-RP uptime";
    }
    leaf acl-name {
      xr:xr-xml-map "pim:ACLName";
      type string {
        length "0..33";
      }
      description "Group Access-List Name";
    }

    list crp-access {
      max-elements "2";
      description "Group Ranges Using this Cand-RP";
      uses PIM-BSR-CRP-ACL-BAG;
    }
  }

  grouping PIM-BSR-CRP-BAG {
    description "PIM BSR C-RP";

    list pim-bsr-crp-bag {
      description "pim bsr crp bag";

      container candidate-rp-address {
        description "C-RP address";
        uses PIM-ADDRTYPE;
      }
      leaf candidate-rp-holdtime {
        type uint16;
        description "C-RP Holdtime";
      }
      leaf candidate-rp-priority {
        type uint8;
        description "C-RP Priority";
      }
      leaf candidate-rp-up-time {
        type uint16;
        description "C-RP Uptime";
      }
      leaf candidate-rp-expires {
        type uint16;
        description "C-RP Expires";
      }
      leaf protocol {
        type Pim-show-protocol;
        description "PIM Protocol";
      }
    }
  }

  grouping PIM-BSR-RP-CACHE-BAG {
    description "PIM BSR RP cache";

    container group-prefix-xr {
      description "Group Prefix";
      uses PIM-ADDRTYPE;
    }

    container candidate-rp-list {
      description "C-RP list for this prefix";
      uses PIM-BSR-CRP-BAG;
    }
    leaf group-prefix-length {
      xr:xr-xml-map "pim:GroupPrefixLength";
      type uint32;
      description "Group Prefix Length";
    }
    leaf candidate-rp-group-count {
      xr:xr-xml-map "pim:CandidateRPGroupCount";
      type uint32;
      description "C-RP count for this Prefix";
    }
  }

  grouping PIM-RL-RP-RANGE-BAG {
    description "PIM RP range list information";

    container prefix {
      description "Group range prefix";
      uses PIM-ADDRTYPE;
    }

    container source-of-information {
      description "Source of information";
      uses PIM-ADDRTYPE;
    }
    leaf prefix-length {
      xr:xr-xml-map "pim:PrefixLength";
      type int32;
      description "Group range prefix length";
    }
    leaf uptime {
      xr:xr-xml-map "pim:Uptime";
      type uint64;
      units "second";
      description "Uptime in seconds";
    }
    leaf expires {
      xr:xr-xml-map "pim:Expires";
      type uint64;
      description "When mapping expires";
    }
  }

  grouping PIM-RL-BAG {
    description "PIM range list information";

    container rp-address-xr {
      description "Rendezvous point address";
      uses PIM-ADDRTYPE;
    }

    container source-of-information {
      description "Source of information";
      uses PIM-ADDRTYPE;
    }
    leaf protocol {
      xr:xr-xml-map "pim:Protocol";
      type Pim-show-protocol;
      description "PIM protocol";
    }
    leaf client-xr {
      xr:xr-xml-map "pim:client-xr";
      type Pim-show-range-client;
      description "Client mapping learnt via";
    }
    leaf expires {
      xr:xr-xml-map "pim:Expires";
      type uint64;
      description "When mapping expires";
    }

    list group-range {
      description "List of group ranges";
      uses PIM-RL-RP-RANGE-BAG;
    }
  }

  grouping PIM-IDB-SUMM-BAG {
    description "PIM IFRS interface summary";
    leaf interface-count {
      xr:xr-xml-map "pim:InterfaceCount";
      type uint32;
      description "Number of interfaces";
    }
    leaf configuration-count {
      xr:xr-xml-map "pim:ConfigurationCount";
      type uint32;
      description "Configuration counts";
    }
  }

  grouping PIM-NBR-BAG {
    description "PIM neighbor information";
    leaf interface-name-xr {
      xr:xr-xml-map "pim:interface-name-xr";
      type xr:Interface-name;
      description "Interface Identifier";
    }
    leaf uptime {
      xr:xr-xml-map "pim:Uptime";
      type uint64;
      units "second";
      description "Uptime in seconds";
    }
    leaf expires {
      xr:xr-xml-map "pim:Expires";
      type uint64;
      units "second";
      description "Neighbor expiry in seconds";
    }
    leaf expiry-timer {
      xr:xr-xml-map "pim:ExpiryTimer";
      type uint64;
      units "second";
      description "Expiry timer in seconds";
    }
    leaf is-this-neighbor-us {
      xr:xr-xml-map "pim:IsThisNeighborUs";
      type boolean;
      description "Is this neighbor us ?";
    }
    leaf is-this-neighbor-dr {
      xr:xr-xml-map "pim:IsThisNeighborDR";
      type boolean;
      description "Is this neighbor the DR";
    }
    leaf is-dr-priority-capable {
      xr:xr-xml-map "pim:IsDRPriorityCapable";
      type boolean;
      description "Is this neighbor DR priority capable ?";
    }
    leaf dr-priority {
      xr:xr-xml-map "pim:DRPriority";
      type uint32;
      description "DR priority";
    }
    leaf is-bidirectional-capable {
      xr:xr-xml-map "pim:IsBidirectionalCapable";
      type boolean;
      description "Is this neighbor bidir capable ?";
    }
    leaf is-proxy-capable {
      xr:xr-xml-map "pim:IsProxyCapable";
      type boolean;
      description "Is this neighbor proxy capable?";
    }
    leaf is-batch-asserts-capable {
      xr:xr-xml-map "pim:IsBatchAssertsCapable";
      type boolean;
      description "Is this neighbor capable of batching asserts?";
    }
    leaf is-ecmp-redirect-capable {
      xr:xr-xml-map "pim:IsEcmpRedirectCapable";
      type boolean;
      description "Is this neighbor capable of Ecmp Redirect?";
    }
    leaf is-bfd-state {
      xr:xr-xml-map "pim:IsBFDState";
      type boolean;
      description "Is the neighbor bfd session created";
    }
    leaf propagation-delay {
      xr:xr-xml-map "pim:PropagationDelay";
      type uint16;
      description "Propagation Delay";
    }
    leaf override-interval {
      xr:xr-xml-map "pim:OverrideInterval";
      type uint16;
      description "Override Interval";
    }

    list neighbor-address-xr {
      description "List of Neighbor Addresses";
      uses PIM-ADDRTYPE;
    }
  }

  grouping PIM-GRP-MAP-BAG {
    description "PIM group-map basic information";

    container prefix {
      description "Group range prefix";
      uses PIM-ADDRTYPE;
    }

    container rp-address {
      description "Rendezvous Point Address";
      uses PIM-ADDRTYPE;
    }
    leaf prefix-length {
      xr:xr-xml-map "pim:PrefixLength";
      type int32;
      description "Group range prefix length";
    }
    leaf client {
      xr:xr-xml-map "pim:Client";
      type Pim-show-range-client;
      description "Client mapping learnt from";
    }
    leaf protocol {
      xr:xr-xml-map "pim:Protocol";
      type Pim-show-protocol;
      description "Protocol mode of the range";
    }
    leaf group-count {
      xr:xr-xml-map "pim:GroupCount";
      type uint32;
      description "No. of groups in this range";
    }
    leaf is-used {
      xr:xr-xml-map "pim:IsUsed";
      type boolean;
      description "Is this mapping being used?";
    }
    leaf mrib-active {
      xr:xr-xml-map "pim:MRIBActive";
      type boolean;
      description "Is this mapping active in MRIB?";
    }
    leaf is-override {
      xr:xr-xml-map "pim:IsOverride";
      type boolean;
      description "Is this the override range?";
    }
    leaf priority {
      xr:xr-xml-map "pim:Priority";
      type uint32;
      description "Bootstrap priority";
    }
  }

  grouping PIM-GRP-MAP-INFORPF-BAG {
    description "PIM group-map information";

    container rpf-neighbor {
      description "RPF neighbor to the RP";
      uses PIM-ADDRTYPE;
    }

    container group-map-information {
      description "Group Mapping information";
      uses PIM-GRP-MAP-BAG;
    }
    leaf are-we-rp {
      xr:xr-xml-map "pim:AreWeRP";
      type boolean;
      description "Are we the RP?";
    }
    leaf rpf-interface-name {
      xr:xr-xml-map "pim:RPFInterfaceName";
      type xr:Interface-name;
      description "RPF interface to the RP";
    }
    leaf rpf-vrf-name {
      xr:xr-xml-map "pim:RPF_VRFName";
      type string {
        length "0..33";
      }
      description "RPF VRF Name";
    }
  }

  grouping PIM-MROUTE-BAG {
    description "Multicast Route MIB entry";

    container source-address-xr {
      description "Source Address";
      uses PIM-ADDRTYPE;
    }

    container group-address-xr {
      description "Group Address";
      uses PIM-ADDRTYPE;
    }

    container rpf-neighbor {
      description "The RPF Neighbor";
      uses PIM-ADDRTYPE;
    }

    container rpf-root {
      description "Root of this mcast tree";
      uses PIM-ADDRTYPE;
    }
    leaf upstream-assert-timer {
      xr:xr-xml-map "pim:UpstreamAssertTimer";
      type int32;
      description "Upstream Assert Timer";
    }
    leaf assert-metric {
      xr:xr-xml-map "pim:AssertMetric";
      type uint32;
      description "Assert Metric";
    }
    leaf assert-metric-preference {
      xr:xr-xml-map "pim:AssertMetricPreference";
      type uint32;
      description "Assert Metric Preference";
    }
    leaf assert-rpt-bit {
      xr:xr-xml-map "pim:AssertRPTBit";
      type boolean;
      description "Assert RPT Bit";
    }
    leaf spt-bit {
      xr:xr-xml-map "pim:SPTBit";
      type boolean;
      description "Is SPT bit set ?";
    }
    leaf rpf-mask {
      xr:xr-xml-map "pim:RPFMask";
      type uint32;
      description "Mask of the multicast root";
    }
    leaf rpf-safi {
      xr:xr-xml-map "pim:RPF_SAFI";
      type uint8;
      description "Unicast or mcast";
    }
    leaf rpf-table-name {
      xr:xr-xml-map "pim:RPFTableName";
      type string;
      description "RPF Table name";
    }
    leaf rpf-drop {
      xr:xr-xml-map "pim:RPFDrop";
      type boolean;
      description "RPF route-policy drop";
    }
    leaf rpf-extranet {
      xr:xr-xml-map "pim:RPFExtranet";
      type boolean;
      description "Extranet RPF route-policy";
    }
    leaf rpf-interface-name {
      xr:xr-xml-map "pim:RPFInterfaceName";
      type xr:Interface-name;
      description "RPF interface name ";
    }
    leaf rpf-vrf-name {
      xr:xr-xml-map "pim:RPF_VRFName";
      type string {
        length "0..33";
      }
      description "RPF VRF Name";
    }
    leaf bidirectional-route {
      xr:xr-xml-map "pim:BidirectionalRoute";
      type boolean;
      description "Is this Bidir ?";
    }
    leaf uptime {
      xr:xr-xml-map "pim:Uptime";
      type uint64;
      description "Uptime of route";
    }
    leaf protocol {
      xr:xr-xml-map "pim:Protocol";
      type Pim-show-protocol;
      description "The PIM protocol";
    }
  }

  grouping PIM-JPSTATS-BAG {
    description "PIM join-prune statistic";
    leaf interface-name-xr {
      xr:xr-xml-map "pim:interface-name-xr";
      type xr:Interface-name;
      description "Interface Identifier";
    }
    leaf mtu {
      xr:xr-xml-map "pim:MTU";
      type uint32;
      description "Interface MTU";
    }
    leaf transmitted {
      xr:xr-xml-map "pim:Transmitted";
      type uint32;
      description "Transmitted";
    }
    leaf transmitted100 {
      xr:xr-xml-map "pim:Transmitted100";
      type uint16;
      description "Transmitted 100 average";
    }
    leaf transmitted-1k {
      xr:xr-xml-map "pim:Transmitted_1K";
      type uint16;
      description "Transmitted 1K average";
    }
    leaf transmitted-10k {
      xr:xr-xml-map "pim:Transmitted_10K";
      type uint16;
      description "Transmitted 10K average";
    }
    leaf transmitted-50k {
      xr:xr-xml-map "pim:Transmitted_50K";
      type uint16;
      description "Deprecated by Transmitted100";
    }
    leaf received {
      xr:xr-xml-map "pim:Received";
      type uint32;
      description "Received";
    }
    leaf received100 {
      xr:xr-xml-map "pim:Received100";
      type uint16;
      description "Received 100 average";
    }
    leaf received-1k {
      xr:xr-xml-map "pim:Received_1K";
      type uint16;
      description "Received 1K average";
    }
    leaf received-10k {
      xr:xr-xml-map "pim:Received_10K";
      type uint16;
      description "Received 10K average";
    }
    leaf received-50k {
      xr:xr-xml-map "pim:Received_50K";
      type uint16;
      description "Deprecated by Received100";
    }
  }

  grouping PIM-TT-SUMM-BAG {
    description "PIM topology table summary";

    container group-address {
      description "Group Address";
      uses PIM-ADDRTYPE;
    }
    leaf group-ranges {
      xr:xr-xml-map "pim:GroupRanges";
      type uint32;
      description "No. of (*,G/M) routes";
    }
    leaf active-group-ranges {
      xr:xr-xml-map "pim:ActiveGroupRanges";
      type uint32;
      description "No. of (*,G/M) routes active in mrib";
    }
    leaf groute-count {
      xr:xr-xml-map "pim:GRouteCount";
      type uint32;
      description "No. of (*,G) routes";
    }
    leaf sg-route-count {
      xr:xr-xml-map "pim:SGRouteCount";
      type uint32;
      description "No. of (S,G) routes";
    }
    leaf sgr-route-count {
      xr:xr-xml-map "pim:SGRRouteCount";
      type uint32;
      description "No. of (S,G)RPT routes";
    }
    leaf is-node-low-memory {
      xr:xr-xml-map "pim:IsNodeLowMemory";
      type boolean;
      description "Is node in low memory condition";
    }
  }

  grouping PIM-IFSTATS-BAG {
    description "PIM Interface Statistics";
    leaf input-hello {
      xr:xr-xml-map "pim:InputHello";
      type uint32;
      description "Hello packets in";
    }
    leaf output-hello {
      xr:xr-xml-map "pim:OutputHello";
      type uint32;
      description "Hello packets out";
    }
    leaf input-register {
      xr:xr-xml-map "pim:InputRegister";
      type uint32;
      description "Register packets in";
    }
    leaf output-register {
      xr:xr-xml-map "pim:OutputRegister";
      type uint32;
      description "Register packets out";
    }
    leaf input-register-stop {
      xr:xr-xml-map "pim:InputRegisterStop";
      type uint32;
      description "Register Stop packets in";
    }
    leaf output-register-stop {
      xr:xr-xml-map "pim:OutputRegisterStop";
      type uint32;
      description "Register Stop packets out";
    }
    leaf input-jp {
      xr:xr-xml-map "pim:InputJP";
      type uint32;
      description "Join Prune packets in";
    }
    leaf output-jp {
      xr:xr-xml-map "pim:OutputJP";
      type uint32;
      description "Join Prune packets out";
    }
    leaf input-bsr-message {
      xr:xr-xml-map "pim:InputBSRMessage";
      type uint32;
      description "Input BSR Messages";
    }
    leaf output-bsr-message {
      xr:xr-xml-map "pim:OutputBSRMessage";
      type uint32;
      description "Output BSR Messages";
    }
    leaf input-assert {
      xr:xr-xml-map "pim:InputAssert";
      type uint32;
      description "Assert packets in";
    }
    leaf output-assert {
      xr:xr-xml-map "pim:OutputAssert";
      type uint32;
      description "Assert packets out";
    }
    leaf input-graft-message {
      xr:xr-xml-map "pim:InputGraftMessage";
      type uint32;
      description "Input Graft Messages";
    }
    leaf output-graft-message {
      xr:xr-xml-map "pim:OutputGraftMessage";
      type uint32;
      description "Output Graft Messages";
    }
    leaf input-graft-ack-message {
      xr:xr-xml-map "pim:InputGraftAckMessage";
      type uint32;
      description "Input Graft Ack Messages";
    }
    leaf output-graft-ack-message {
      xr:xr-xml-map "pim:OutputGraftAckMessage";
      type uint32;
      description "Output Graft Ack Messages";
    }
    leaf input-candidate-rp-advertisement {
      xr:xr-xml-map "pim:InputCandidateRPAdvertisement";
      type uint32;
      description "Input Candidate-RP Advertisment";
    }
    leaf output-candidate-rp-advertisement {
      xr:xr-xml-map "pim:OutputCandidateRPAdvertisement";
      type uint32;
      description "Output Candidate-RP Advertisment";
    }
    leaf input-df-election {
      xr:xr-xml-map "pim:InputDFElection";
      type uint32;
      description "DF Election packets in";
    }
    leaf output-df-election {
      xr:xr-xml-map "pim:OutputDFElection";
      type uint32;
      description "DF Election packets out";
    }
    leaf input-miscellaneous {
      xr:xr-xml-map "pim:InputMiscellaneous";
      type uint32;
      description "Miscellaneous packet in";
    }
  }

  grouping PIM-RPF-PATH-BAG {
    description "PIM RPF path information";

    container rpf-neighbor {
      description "RPF neighbor";
      uses PIM-ADDRTYPE;
    }

    container rpf-nexthop {
      description "RPF nexthop";
      uses PIM-ADDRTYPE;
    }
    leaf rpf-interface-name {
      xr:xr-xml-map "pim:RPFInterfaceName";
      type xr:Interface-name;
      description "RPF Interface";
    }
    leaf is-rpf-interface-disabled {
      xr:xr-xml-map "pim:IsRPFInterfaceDisabled";
      type boolean;
      description "Is the rpf interface disabled ?";
    }
    leaf is-via-lsm {
      xr:xr-xml-map "pim:IsViaLSM";
      type boolean;
      description "Via LSM";
    }
    leaf is-via-mlsm {
      xr:xr-xml-map "pim:IsViaMLSM";
      type boolean;
      description "Via Mstatic LSM";
    }
    leaf is-connector-attribute-present {
      xr:xr-xml-map "pim:IsConnectorAttributePresent";
      type boolean;
      description "Connector attribute present";
    }
    leaf connector {
      xr:xr-xml-map "pim:Connector";
      type yang:hex-string;
      description "Connector Attribute";
    }
    leaf extranet-vrf-name {
      xr:xr-xml-map "pim:ExtranetVRFName";
      type string {
        length "0..33";
      }
      description "Extranet VRF name";
    }
  }

  grouping PIM-RPF-INFO-BAG {
    description "PIM RPF information";

    container registered-address-xr {
      description "Address registered";
      uses PIM-ADDRTYPE;
    }
    leaf metric {
      xr:xr-xml-map "pim:Metric";
      type uint32;
      description "Metric";
    }
    leaf metric-preference {
      xr:xr-xml-map "pim:MetricPreference";
      type uint32;
      description "Metric preference";
    }
    leaf is-connected {
      xr:xr-xml-map "pim:IsConnected";
      type uint8;
      description "Are we connected ?";
    }
    leaf is-rpf-bgp-route {
      xr:xr-xml-map "pim:IsRPF_BGPRoute";
      type boolean;
      description "Is RPF through BGP route";
    }

    list rpf-path {
      description "RPF Paths list";
      uses PIM-RPF-PATH-BAG;
    }
  }

  grouping PIM-RPF-REGADDR-BAG {
    description "PIM RPF REGADDR BAG";

    container rib-registration-address {
      description "RPF registered address";
      uses PIM-ADDRTYPE;
    }
    leaf rpf-registered-address-references {
      xr:xr-xml-map "pim:RPFRegisteredAddressReferences";
      type uint32;
      description "RPF registered address reference count";
    }
  }

  grouping PIM-RPF-NBR-BAG {
    description "PIM RPF neighbor information";

    container rib-neighbor-address {
      description "RIB neighbor address";
      uses PIM-ADDRTYPE;
    }
    leaf rib-neighbor-interface {
      xr:xr-xml-map "pim:RIBNeighborInterface";
      type xr:Interface-name;
      description "Rib neighbor interface";
    }

    list rpf-registered-addresses {
      description "RPF registered addresses list";
      uses PIM-RPF-REGADDR-BAG;
    }
  }

  grouping PIM-RPF-HASH-BAG {
    description "PIM RPF Hash Outcome";

    container next-hop-address {
      description "Next hop neighbor address";
      uses PIM-ADDRTYPE;
    }

    container secondary-next-hop-address {
      description "Secondary Next hop neighbor address";
      uses PIM-ADDRTYPE;
    }
    leaf next-hop-multipath-enabled {
      xr:xr-xml-map "pim:NextHopMultipathEnabled";
      type boolean;
      description "Next hop multipath enabled?";
    }
    leaf next-hop-interface {
      xr:xr-xml-map "pim:NextHopInterface";
      type xr:Interface-name;
      description "Next hop neighbor interface";
    }
    leaf secondary-next-hop-interface {
      xr:xr-xml-map "pim:SecondaryNextHopInterface";
      type xr:Interface-name;
      description "Secondary Next hop neighbor interface";
    }
  }

  grouping PIM-IDB-BAG {
    description "PIM interface";

    container dr-address {
      description "PIM Designated Router";
      uses PIM-ADDRTYPE;
    }
    leaf interface-name-xr {
      xr:xr-xml-map "pim:interface-name-xr";
      type xr:Interface-name;
      description "Interface Identfier";
    }
    leaf interface-address-mask {
      xr:xr-xml-map "pim:InterfaceAddressMask";
      type uint8;
      description "Interface IP Address Mask";
    }
    leaf is-enabled {
      xr:xr-xml-map "pim:IsEnabled";
      type boolean;
      description "Is PIM enabled on this IF ?";
    }
    leaf neighbor-count {
      xr:xr-xml-map "pim:NeighborCount";
      type uint16;
      description "No. of neighbors on this IF";
    }
    leaf external-neighbor-count {
      xr:xr-xml-map "pim:ExternalNeighborCount";
      type uint16;
      description "No. of external neighbors on this IF";
    }
    leaf hello-interval {
      xr:xr-xml-map "pim:HelloInterval";
      type uint16;
      description "Hello Interval";
    }
    leaf dr-priority {
      xr:xr-xml-map "pim:DRPriority";
      type uint32;
      description "DR Priority";
    }
    leaf hello-expiry {
      xr:xr-xml-map "pim:HelloExpiry";
      type uint64;
      description "Hello Timer Expiry";
    }
    leaf are-we-dr {
      xr:xr-xml-map "pim:AreWeDR";
      type boolean;
      description "Are we the DR on this IF ?";
    }
    leaf bfd-enabled {
      xr:xr-xml-map "pim:BFDEnabled";
      type boolean;
      description "BFD state";
    }
    leaf bfd-interval {
      xr:xr-xml-map "pim:BFDInterval";
      type uint32;
      description "BFD Interval";
    }
    leaf bfd-multiplier {
      xr:xr-xml-map "pim:BFDMultiplier";
      type uint32;
      description "BFD Multiplier";
    }
    leaf virtual-interface {
      xr:xr-xml-map "pim:VirtualInterface";
      type boolean;
      description " is this a Virtual Interfaces ?";
    }
    leaf passive-interface {
      xr:xr-xml-map "pim:PassiveInterface";
      type boolean;
      description "Passive PIM interface";
    }
    leaf neighbor-filter-name {
      xr:xr-xml-map "pim:NeighborFilterName";
      type string;
      description "Neighbor Filter Name";
    }
    leaf join-prune-interval {
      xr:xr-xml-map "pim:JoinPruneInterval";
      type uint16;
      description "Join-Prune Interval";
    }
    leaf prune-delay-enabled {
      xr:xr-xml-map "pim:PruneDelayEnabled";
      type boolean;
      description "Prune Delay Enabled";
    }
    leaf configured-propagation-delay {
      xr:xr-xml-map "pim:ConfiguredPropagationDelay";
      type uint16;
      description "Configured Propagation Delay";
    }
    leaf propagation-delay {
      xr:xr-xml-map "pim:PropagationDelay";
      type uint16;
      description "Propagation Delay";
    }
    leaf configured-override-interval {
      xr:xr-xml-map "pim:ConfiguredOverrideInterval";
      type uint16;
      description "Configured Override Interval";
    }
    leaf override-interval {
      xr:xr-xml-map "pim:OverrideInterval";
      type uint16;
      description "Override Interval";
    }
    leaf generation-id {
      xr:xr-xml-map "pim:GenerationID";
      type uint32;
      description "Generation Identifier";
    }
    leaf is-bidirectional-capable {
      xr:xr-xml-map "pim:IsBidirectionalCapable";
      type boolean;
      description "Bidir Capable";
    }
    leaf is-proxy-capable {
      xr:xr-xml-map "pim:IsProxyCapable";
      type boolean;
      description "Proxy Capable";
    }
    leaf is-batch-asserts-capable {
      xr:xr-xml-map "pim:IsBatchAssertsCapable";
      type boolean;
      description "Batch Asserts Capable";
    }
    leaf idb-oor-enabled {
      xr:xr-xml-map "pim:IDBOorEnabled";
      type boolean;
      description "Interface oor enabled";
    }
    leaf idb-acl-provided {
      xr:xr-xml-map "pim:IDBAclProvided";
      type boolean;
      description "ACL name provided";
    }
    leaf idb-max-count {
      xr:xr-xml-map "pim:IDBMaxCount";
      type uint32;
      description "Interface ole max count";
    }
    leaf idb-threshold-count {
      xr:xr-xml-map "pim:IDBThresholdCount";
      type uint32;
      description "Interface ole threshold count";
    }
    leaf idb-current-count {
      xr:xr-xml-map "pim:IDBCurrentCount";
      type uint32;
      description "Interface ole current count";
    }
    leaf idb-acl-name {
      xr:xr-xml-map "pim:IDBAclName";
      type string {
        length "0..64";
      }
      description "Interface ole ACL Name";
    }

    list interface-address {
      description "List of Interface IP Addresses";
      uses PIM-ADDRTYPE;
    }
  }
}
