submodule Cisco-IOS-XR-manageability-perfmgmt-oper-sub1 {

  belongs-to Cisco-IOS-XR-manageability-perfmgmt-oper {
    prefix Cisco-IOS-XR-manageability-perfmgmt-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR manageability-perfmgmt package operational data.

     Copyright (c) 2013-2016 by Cisco Systems, Inc.
     All rights reserved.";

  revision "2015-11-09" {
    description
      "IOS XR 6.0 revision.";
  }


  grouping PM-INTERFACE-DATARATE-BAG {
    description "Datarate information";
    leaf time-stamp {
      xr:xr-xml-map "manageability_perf_stats:TimeStamp";
      type uint64;
      units "second";
      description "Timestamp of sample in seconds drom UCT";
    }
    leaf input-data-rate {
      xr:xr-xml-map "manageability_perf_stats:InputDataRate";
      type uint32;
      units "bit/s";
      description "Input datarate in 1000's of bps";
    }
    leaf input-packet-rate {
      xr:xr-xml-map "manageability_perf_stats:InputPacketRate";
      type uint32;
      units "packet/s";
      description "Input packets per second";
    }
    leaf output-data-rate {
      xr:xr-xml-map "manageability_perf_stats:OutputDataRate";
      type uint32;
      units "bit/s";
      description "Output datarate in 1000's of bps";
    }
    leaf output-packet-rate {
      xr:xr-xml-map "manageability_perf_stats:OutputPacketRate";
      type uint32;
      units "packet/s";
      description "Output packets per second";
    }
    leaf input-peak-rate {
      xr:xr-xml-map "manageability_perf_stats:InputPeakRate";
      type uint32;
      description "Peak input datarate";
    }
    leaf input-peak-pkts {
      xr:xr-xml-map "manageability_perf_stats:InputPeakPkts";
      type uint32;
      description "Peak input packet rate";
    }
    leaf output-peak-rate {
      xr:xr-xml-map "manageability_perf_stats:OutputPeakRate";
      type uint32;
      description "Peak output datarate";
    }
    leaf output-peak-pkts {
      xr:xr-xml-map "manageability_perf_stats:OutputPeakPkts";
      type uint32;
      description "Peak output packet rate";
    }
    leaf bandwidth {
      xr:xr-xml-map "manageability_perf_stats:Bandwidth";
      type uint32;
      units "kbit/s";
      description "Bandwidth (in kbps)";
    }
  }

  grouping PM-INTERFACE-BASIC-STATS {
    description "PM Interface Basic Counters";
    leaf time-stamp {
      xr:xr-xml-map "manageability_perf_stats:TimeStamp";
      type uint64;
      units "second";
      description "Timestamp of sample in seconds from UCT";
    }
    leaf in-packets {
      xr:xr-xml-map "manageability_perf_stats:InPackets";
      type uint64;
      description "Packets received";
    }
    leaf in-octets {
      xr:xr-xml-map "manageability_perf_stats:InOctets";
      type uint64;
      units "byte";
      description "Bytes received";
    }
    leaf out-packets {
      xr:xr-xml-map "manageability_perf_stats:OutPackets";
      type uint64;
      description "Packets sent";
    }
    leaf out-octets {
      xr:xr-xml-map "manageability_perf_stats:OutOctets";
      type uint64;
      units "byte";
      description "Bytes sent";
    }
    leaf input-total-drops {
      xr:xr-xml-map "manageability_perf_stats:InputTotalDrops";
      type uint64;
      description "Inbound correct packets discarded";
    }
    leaf input-queue-drops {
      xr:xr-xml-map "manageability_perf_stats:InputQueueDrops";
      type uint64;
      description "Input queue drops";
    }
    leaf input-total-errors {
      xr:xr-xml-map "manageability_perf_stats:InputTotalErrors";
      type uint64;
      description "Inbound incorrect packets discarded";
    }
    leaf output-total-drops {
      xr:xr-xml-map "manageability_perf_stats:OutputTotalDrops";
      type uint64;
      description "Outbound correct packets discarded";
    }
    leaf output-queue-drops {
      xr:xr-xml-map "manageability_perf_stats:OutputQueueDrops";
      type uint64;
      description "Output queue drops";
    }
    leaf output-total-errors {
      xr:xr-xml-map "manageability_perf_stats:OutputTotalErrors";
      type uint64;
      description "Outbound incorrect packets discarded";
    }
  }

  grouping PM-INTERFACE-GENERIC-BAG {
    description "PM Interface Generic Counters";
    leaf time-stamp {
      xr:xr-xml-map "manageability_perf_stats:TimeStamp";
      type uint64;
      units "second";
      description "Timestamp of sample in seconds drom UCT";
    }
    leaf in-packets {
      xr:xr-xml-map "manageability_perf_stats:InPackets";
      type uint64;
      description "Packets received";
    }
    leaf in-octets {
      xr:xr-xml-map "manageability_perf_stats:InOctets";
      type uint64;
      units "byte";
      description "Bytes received";
    }
    leaf out-packets {
      xr:xr-xml-map "manageability_perf_stats:OutPackets";
      type uint64;
      description "Packets sent";
    }
    leaf out-octets {
      xr:xr-xml-map "manageability_perf_stats:OutOctets";
      type uint64;
      units "byte";
      description "Bytes sent";
    }
    leaf in-ucast-pkts {
      xr:xr-xml-map "manageability_perf_stats:InUcastPkts";
      type uint64;
      description "Unicast packets received";
    }
    leaf in-multicast-pkts {
      xr:xr-xml-map "manageability_perf_stats:InMulticastPkts";
      type uint64;
      description "Multicast packets received";
    }
    leaf in-broadcast-pkts {
      xr:xr-xml-map "manageability_perf_stats:InBroadcastPkts";
      type uint64;
      description "Broadcast packets received";
    }
    leaf out-ucast-pkts {
      xr:xr-xml-map "manageability_perf_stats:OutUcastPkts";
      type uint64;
      description "Unicast packets sent";
    }
    leaf out-multicast-pkts {
      xr:xr-xml-map "manageability_perf_stats:OutMulticastPkts";
      type uint64;
      description "Multicast packets sent";
    }
    leaf out-broadcast-pkts {
      xr:xr-xml-map "manageability_perf_stats:OutBroadcastPkts";
      type uint64;
      description "Broadcast packets sent";
    }
    leaf output-total-drops {
      xr:xr-xml-map "manageability_perf_stats:OutputTotalDrops";
      type uint32;
      description "Outbound correct packets discarded";
    }
    leaf input-total-drops {
      xr:xr-xml-map "manageability_perf_stats:InputTotalDrops";
      type uint32;
      description "Inbound correct packets discarded";
    }
    leaf input-queue-drops {
      xr:xr-xml-map "manageability_perf_stats:InputQueueDrops";
      type uint32;
      description "Input queue drops";
    }
    leaf input-unknown-proto {
      xr:xr-xml-map "manageability_perf_stats:InputUnknownProto";
      type uint32;
      description "Inbound packets discarded with unknown proto";
    }
    leaf output-total-errors {
      xr:xr-xml-map "manageability_perf_stats:OutputTotalErrors";
      type uint32;
      description "Outbound incorrect packets discarded";
    }
    leaf output-underrun {
      xr:xr-xml-map "manageability_perf_stats:OutputUnderrun";
      type uint32;
      description "Output underruns";
    }
    leaf input-total-errors {
      xr:xr-xml-map "manageability_perf_stats:InputTotalErrors";
      type uint32;
      description "Inbound incorrect packets discarded";
    }
    leaf input-crc {
      xr:xr-xml-map "manageability_perf_stats:InputCRC";
      type uint32;
      description "Inbound packets discarded with incorrect CRC";
    }
    leaf input-overrun {
      xr:xr-xml-map "manageability_perf_stats:InputOverrun";
      type uint32;
      description "Input overruns";
    }
    leaf input-frame {
      xr:xr-xml-map "manageability_perf_stats:InputFrame";
      type uint32;
      description "Inbound framing errors";
    }
  }

  grouping PM-BGP-NBR-BAG {
    description "PM BGP Neighbor Information";
    leaf time-stamp {
      xr:xr-xml-map "manageability_perf_stats:TimeStamp";
      type uint64;
      units "second";
      description "Timestamp of sample in seconds drom UCT";
    }
    leaf input-messages {
      xr:xr-xml-map "manageability_perf_stats:InputMessages";
      type uint32;
      description "Number of messages received";
    }
    leaf output-messages {
      xr:xr-xml-map "manageability_perf_stats:OutputMessages";
      type uint32;
      description "Number of messages sent";
    }
    leaf input-update-messages {
      xr:xr-xml-map "manageability_perf_stats:InputUpdateMessages";
      type uint32;
      description "Number of update messages received";
    }
    leaf output-update-messages {
      xr:xr-xml-map "manageability_perf_stats:OutputUpdateMessages";
      type uint32;
      description "Number of update messages sent";
    }
    leaf conn-established {
      xr:xr-xml-map "manageability_perf_stats:ConnEstablished";
      type uint32;
      description "Number of times the connection was established";
    }
    leaf conn-dropped {
      xr:xr-xml-map "manageability_perf_stats:ConnDropped";
      type uint32;
      description "Number of times connection was dropped";
    }
    leaf errors-received {
      xr:xr-xml-map "manageability_perf_stats:ErrorsReceived";
      type uint32;
      description
        "Number of error notifications received on the
        connection";
    }
    leaf errors-sent {
      xr:xr-xml-map "manageability_perf_stats:ErrorsSent";
      type uint32;
      description
        "Number of error notifications sent on the
        connection";
    }
  }

  grouping PM-NODE-MEM-BAG {
    description "PM System Resources Memory Information";
    leaf time-stamp {
      xr:xr-xml-map "manageability_perf_stats:TimeStamp";
      type uint64;
      units "second";
      description "Timestamp of sample in seconds drom UCT";
    }
    leaf curr-memory {
      xr:xr-xml-map "manageability_perf_stats:CurrMemory";
      type uint32;
      units "byte";
      description "Current application memory (Bytes) in use";
    }
    leaf peak-memory {
      xr:xr-xml-map "manageability_perf_stats:PeakMemory";
      type uint32;
      units "megabyte";
      description "Max. system memory (MBytes) used since bootup";
    }
  }

  grouping PM-NODE-PROCESS-BAG {
    description "PM Process CPU and Memory Information";
    leaf time-stamp {
      xr:xr-xml-map "manageability_perf_stats:TimeStamp";
      type uint64;
      units "second";
      description "Timestamp of sample in seconds drom UCT";
    }
    leaf peak-memory {
      xr:xr-xml-map "manageability_perf_stats:PeakMemory";
      type uint32;
      units "kilobyte";
      description
        "Max. dynamic memory (KBytes) used since startup
        time";
    }
    leaf average-cpu-used {
      xr:xr-xml-map "manageability_perf_stats:AverageCPUUsed";
      type uint32;
      description "Average %CPU utilization";
    }
    leaf no-threads {
      xr:xr-xml-map "manageability_perf_stats:NoThreads";
      type uint32;
      description "Number of threads";
    }
  }

  grouping PM-NODE-CPU-BAG {
    description "PM System Resources CPU Information";
    leaf time-stamp {
      xr:xr-xml-map "manageability_perf_stats:TimeStamp";
      type uint64;
      units "second";
      description "Timestamp of sample in seconds drom UCT";
    }
    leaf no-processes {
      xr:xr-xml-map "manageability_perf_stats:NoProcesses";
      type uint32;
      description "Number of processes in the system";
    }
    leaf average-cpu-used {
      xr:xr-xml-map "manageability_perf_stats:AverageCPUUsed";
      type uint32;
      description "Average system %CPU utilization";
    }
  }

  grouping PM-MPLS-LDP-BAG {
    description "PM MPLS LDP Neighbor bag";
    leaf time-stamp {
      xr:xr-xml-map "manageability_perf_stats:TimeStamp";
      type uint64;
      units "second";
      description "Timestamp of sample in seconds drom UCT";
    }
    leaf total-msgs-sent {
      xr:xr-xml-map "manageability_perf_stats:TotalMsgsSent";
      type uint16;
      description "Total messages sent";
    }
    leaf total-msgs-rcvd {
      xr:xr-xml-map "manageability_perf_stats:TotalMsgsRcvd";
      type uint16;
      description "Total messages received";
    }
    leaf init-msgs-sent {
      xr:xr-xml-map "manageability_perf_stats:InitMsgsSent";
      type uint16;
      description "Init messages sent";
    }
    leaf init-msgs-rcvd {
      xr:xr-xml-map "manageability_perf_stats:InitMsgsRcvd";
      type uint16;
      description "Tnit messages received";
    }
    leaf address-msgs-sent {
      xr:xr-xml-map "manageability_perf_stats:AddressMsgsSent";
      type uint16;
      description "Address messages sent";
    }
    leaf address-msgs-rcvd {
      xr:xr-xml-map "manageability_perf_stats:AddressMsgsRcvd";
      type uint16;
      description "Address messages received";
    }
    leaf address-withdraw-msgs-sent {
      xr:xr-xml-map "manageability_perf_stats:AddressWithdrawMsgsSe"+
        "nt";
      type uint16;
      description "Address withdraw messages sent";
    }
    leaf address-withdraw-msgs-rcvd {
      xr:xr-xml-map "manageability_perf_stats:AddressWithdrawMsgsRc"+
        "vd";
      type uint16;
      description "Address withdraw messages received";
    }
    leaf label-mapping-msgs-sent {
      xr:xr-xml-map "manageability_perf_stats:LabelMappingMsgsSent";
      type uint16;
      description "Label mapping messages sent";
    }
    leaf label-mapping-msgs-rcvd {
      xr:xr-xml-map "manageability_perf_stats:LabelMappingMsgsRcvd";
      type uint16;
      description "Label mapping messages received";
    }
    leaf label-withdraw-msgs-sent {
      xr:xr-xml-map "manageability_perf_stats:LabelWithdrawMsgsSent";
      type uint16;
      description "Label withdraw messages sent";
    }
    leaf label-withdraw-msgs-rcvd {
      xr:xr-xml-map "manageability_perf_stats:LabelWithdrawMsgsRcvd";
      type uint16;
      description "Label withdraw messages received";
    }
    leaf label-release-msgs-sent {
      xr:xr-xml-map "manageability_perf_stats:LabelReleaseMsgsSent";
      type uint16;
      description "Label release messages sent";
    }
    leaf label-release-msgs-rcvd {
      xr:xr-xml-map "manageability_perf_stats:LabelReleaseMsgsRcvd";
      type uint16;
      description "Label release messages received";
    }
    leaf notification-msgs-sent {
      xr:xr-xml-map "manageability_perf_stats:NotificationMsgsSent";
      type uint16;
      description "Notification messages sent";
    }
    leaf notification-msgs-rcvd {
      xr:xr-xml-map "manageability_perf_stats:NotificationMsgsRcvd";
      type uint16;
      description "Notification messages received";
    }
    leaf keepalive-msgs-sent {
      xr:xr-xml-map "manageability_perf_stats:KeepaliveMsgsSent";
      type uint16;
      description "Keepalive messages sent";
    }
    leaf keepalive-msgs-rcvd {
      xr:xr-xml-map "manageability_perf_stats:KeepaliveMsgsRcvd";
      type uint16;
      description "Keepalive messages received";
    }
  }

  grouping PM-OSPF-V3PROTO-BAG {
    description "PM OSPF v3 Protocol Information";
    leaf time-stamp {
      xr:xr-xml-map "manageability_perf_stats:TimeStamp";
      type uint64;
      units "second";
      description "Timestamp of sample in seconds drom UCT";
    }
    leaf input-packets {
      xr:xr-xml-map "manageability_perf_stats:InputPackets";
      type uint32;
      description "Total number of packets received";
    }
    leaf output-packets {
      xr:xr-xml-map "manageability_perf_stats:OutputPackets";
      type uint32;
      description "Total number of packets sent";
    }
    leaf input-hello-packets {
      xr:xr-xml-map "manageability_perf_stats:InputHelloPackets";
      type uint32;
      description "Number of Hello packets received";
    }
    leaf output-hello-packets {
      xr:xr-xml-map "manageability_perf_stats:OutputHelloPackets";
      type uint32;
      description "Number of Hello packets sent";
    }
    leaf input-db-ds {
      xr:xr-xml-map "manageability_perf_stats:InputDBDs";
      type uint32;
      description "Number of DBD packets received";
    }
    leaf input-db-ds-lsa {
      xr:xr-xml-map "manageability_perf_stats:InputDBDsLSA";
      type uint32;
      description "Number of LSA received in DBD packets";
    }
    leaf output-db-ds {
      xr:xr-xml-map "manageability_perf_stats:OutputDBDs";
      type uint32;
      description "Number of DBD packets sent";
    }
    leaf output-db-ds-lsa {
      xr:xr-xml-map "manageability_perf_stats:OutputDBDsLSA";
      type uint32;
      description "Number of LSA sent in DBD packets";
    }
    leaf input-ls-requests {
      xr:xr-xml-map "manageability_perf_stats:InputLSRequests";
      type uint32;
      description "Number of LS Requests received";
    }
    leaf input-ls-requests-lsa {
      xr:xr-xml-map "manageability_perf_stats:InputLSRequestsLSA";
      type uint32;
      description "Number of LSA received in LS Requests";
    }
    leaf output-ls-requests {
      xr:xr-xml-map "manageability_perf_stats:OutputLSRequests";
      type uint32;
      description "Number of LS Requests sent";
    }
    leaf output-ls-requests-lsa {
      xr:xr-xml-map "manageability_perf_stats:OutputLSRequestsLSA";
      type uint32;
      description "Number of LSA sent in LS Requests";
    }
    leaf input-lsa-updates {
      xr:xr-xml-map "manageability_perf_stats:InputLSAUpdates";
      type uint32;
      description "Number of LSA Updates received";
    }
    leaf input-lsa-updates-lsa {
      xr:xr-xml-map "manageability_perf_stats:InputLSAUpdatesLSA";
      type uint32;
      description "Number of LSA received in LSA Updates";
    }
    leaf output-lsa-updates {
      xr:xr-xml-map "manageability_perf_stats:OutputLSAUpdates";
      type uint32;
      description "Number of LSA Updates sent";
    }
    leaf output-lsa-updates-lsa {
      xr:xr-xml-map "manageability_perf_stats:OutputLSAUpdatesLSA";
      type uint32;
      description "Number of LSA sent in LSA Updates";
    }
    leaf input-lsa-acks {
      xr:xr-xml-map "manageability_perf_stats:InputLSAAcks";
      type uint32;
      description "Number of LSA Acknowledgements received";
    }
    leaf input-lsa-acks-lsa {
      xr:xr-xml-map "manageability_perf_stats:InputLSAAcksLSA";
      type uint32;
      description "Number of LSA received in LSA Acknowledgements";
    }
    leaf output-lsa-acks {
      xr:xr-xml-map "manageability_perf_stats:OutputLSAAcks";
      type uint32;
      description "Number of LSA Acknowledgements sent";
    }
    leaf output-lsa-acks-lsa {
      xr:xr-xml-map "manageability_perf_stats:OutputLSAAcksLSA";
      type uint32;
      description "Number of LSA sent in LSA Acknowledgements";
    }
  }

  grouping PM-OSPF-V2PROTO-BAG {
    description "PM OSPF v2 Protocol Information";
    leaf time-stamp {
      xr:xr-xml-map "manageability_perf_stats:TimeStamp";
      type uint64;
      units "second";
      description "Timestamp of sample in seconds drom UCT";
    }
    leaf input-packets {
      xr:xr-xml-map "manageability_perf_stats:InputPackets";
      type uint32;
      description "Total number of packets received";
    }
    leaf output-packets {
      xr:xr-xml-map "manageability_perf_stats:OutputPackets";
      type uint32;
      description "Total number of packets sent";
    }
    leaf input-hello-packets {
      xr:xr-xml-map "manageability_perf_stats:InputHelloPackets";
      type uint32;
      description "Number of Hello packets received";
    }
    leaf output-hello-packets {
      xr:xr-xml-map "manageability_perf_stats:OutputHelloPackets";
      type uint32;
      description "Number of Hello packets sent";
    }
    leaf input-db-ds {
      xr:xr-xml-map "manageability_perf_stats:InputDBDs";
      type uint32;
      description "Number of DBD packets received";
    }
    leaf input-db-ds-lsa {
      xr:xr-xml-map "manageability_perf_stats:InputDBDsLSA";
      type uint32;
      description "Number of LSA received in DBD packets";
    }
    leaf output-db-ds {
      xr:xr-xml-map "manageability_perf_stats:OutputDBDs";
      type uint32;
      description "Number of DBD packets sent";
    }
    leaf output-db-ds-lsa {
      xr:xr-xml-map "manageability_perf_stats:OutputDBDsLSA";
      type uint32;
      description "Number of LSA sent in DBD packets";
    }
    leaf input-ls-requests {
      xr:xr-xml-map "manageability_perf_stats:InputLSRequests";
      type uint32;
      description "Number of LS Requests received";
    }
    leaf input-ls-requests-lsa {
      xr:xr-xml-map "manageability_perf_stats:InputLSRequestsLSA";
      type uint32;
      description "Number of LSA received in LS Requests";
    }
    leaf output-ls-requests {
      xr:xr-xml-map "manageability_perf_stats:OutputLSRequests";
      type uint32;
      description "Number of LS Requests sent";
    }
    leaf output-ls-requests-lsa {
      xr:xr-xml-map "manageability_perf_stats:OutputLSRequestsLSA";
      type uint32;
      description "Number of LSA sent in LS Requests";
    }
    leaf input-lsa-updates {
      xr:xr-xml-map "manageability_perf_stats:InputLSAUpdates";
      type uint32;
      description "Number of LSA Updates received";
    }
    leaf input-lsa-updates-lsa {
      xr:xr-xml-map "manageability_perf_stats:InputLSAUpdatesLSA";
      type uint32;
      description "Number of LSA received in LSA Updates";
    }
    leaf output-lsa-updates {
      xr:xr-xml-map "manageability_perf_stats:OutputLSAUpdates";
      type uint32;
      description "Number of LSA Updates sent";
    }
    leaf output-lsa-updates-lsa {
      xr:xr-xml-map "manageability_perf_stats:OutputLSAUpdatesLSA";
      type uint32;
      description "Number of LSA sent in LSA Updates";
    }
    leaf input-lsa-acks {
      xr:xr-xml-map "manageability_perf_stats:InputLSAAcks";
      type uint32;
      description "Number of LSA Acknowledgements received";
    }
    leaf input-lsa-acks-lsa {
      xr:xr-xml-map "manageability_perf_stats:InputLSAAcksLSA";
      type uint32;
      description "Number of LSA received in LSA Acknowledgements";
    }
    leaf output-lsa-acks {
      xr:xr-xml-map "manageability_perf_stats:OutputLSAAcks";
      type uint32;
      description "Number of LSA Acknowledgements sent";
    }
    leaf output-lsa-acks-lsa {
      xr:xr-xml-map "manageability_perf_stats:OutputLSAAcksLSA";
      type uint32;
      description "Number of LSA sent in LSA Acknowledgements";
    }
    leaf checksum-errors {
      xr:xr-xml-map "manageability_perf_stats:ChecksumErrors";
      type uint32;
      description "Number of packets received with checksum errors";
    }
  }
}
