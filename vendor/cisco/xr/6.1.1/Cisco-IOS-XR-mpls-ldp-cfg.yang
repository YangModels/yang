module Cisco-IOS-XR-mpls-ldp-cfg {

  /*** NAMESPACE / PREFIX DEFINITION ***/

  namespace "http://cisco.com/ns/yang/Cisco-IOS-XR-mpls-ldp-cfg";


  prefix "mpls-ldp-cfg";

  /*** LINKAGE (IMPORTS / INCLUDES) ***/

  import ietf-inet-types { prefix "inet"; }

  import Cisco-IOS-XR-types { prefix "xr"; }

  import Cisco-IOS-XR-snmp-agent-cfg { prefix "a1"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR mpls-ldp package configuration.

     This module contains definitions
     for the following management objects:
       mpls-ldp: MPLS LDP configuration

     This YANG module augments the
       Cisco-IOS-XR-snmp-agent-cfg
     module with configuration data.

     Copyright (c) 2013-2016 by Cisco Systems, Inc.
     All rights reserved.";

  revision "2015-11-09" {
    description
      "IOS XR 6.0 revision.";
  }

  typedef Mpls-ldp-nbr-password {
    type enumeration {
      enum disable {
        value 1;
        description
          "Disable the global default password for this
          neighbor";
      }
      enum specified {
        value 2;
        description "Specify a password for this neighbor";
      }
    }
    description "Mpls ldp nbr password";
  }
  typedef Mpls-ldp-label-allocation {
    type enumeration {
      enum acl {
        value 1;
        description "Allocate label for prefixes permitted by ACL";
      }
      enum host {
        value 2;
        description "Allocate label for host routes only";
      }
    }
    description "Mpls ldp label allocation";
  }
  typedef Mpls-ldp-downstream-on-demand {
    type enumeration {
      enum peer-acl {
        value 1;
        description "Downstream on Demand peers permitted by ACL";
      }
    }
    description "Mpls ldp downstream on demand";
  }
  typedef Mpls-ldp-targeted-accept {
    type enumeration {
      enum all {
        value 1;
        description "Accept targeted hello from all";
      }
      enum from {
        value 2;
        description "Accept targeted hello from peer ACL";
      }
    }
    description "Mpls ldp targeted accept";
  }
  typedef Mpls-ldp-interval-time {
    type uint32 {
      range "1..65535";
    }
    description "Mpls ldp interval time";
  }
  typedef Mpls-ldp-mesh-group-id {
    type uint32 {
      range "0..4294967295";
    }
    description "Mpls ldp mesh group id";
  }
  typedef Mpls-ldp-exp-null {
    type enumeration {
      enum all {
        value 1;
        description
          "Advertise explicit-null for all connected
          prefixes to all peers";
      }
      enum for {
        value 2;
        description
          "Advertise explicit-null for prefix(es)
          permitted by prefix ACL";
      }
      enum to {
        value 3;
        description
          "Advertise explicit-null for all connected
          prefixes to peer(s) permitted by peer ACL";
      }
      enum for-to {
        value 4;
        description
          "Advertise explicit-null for prefix(es)
          permitted by prefix ACL to peer(s) permitted by
          peer ACL";
      }
    }
    description "Mpls ldp exp null";
  }
  typedef Mpls-ldp-hold-time {
    type uint32 {
      range "1..65535";
    }
    description "Mpls ldp hold time";
  }
  typedef Mpls-ldp-dscp {
    type uint32 {
      range "0..63";
    }
    description "Mpls ldp dscp";
  }
  typedef Mpls-ldpaf-name {
    type enumeration {
      enum ipv4 {
        value 4;
        description "IPv4";
      }
      enum ipv6 {
        value 6;
        description "IPv6";
      }
    }
    description "Mpls ldpaf name";
  }
  typedef Mpls-ldp-transport-address {
    type enumeration {
      enum interface {
        value 1;
        description "Use interface IP address";
      }
      enum address {
        value 2;
        description "Use given IP address";
      }
    }
    description "Mpls ldp transport address";
  }
  typedef Mpls-ldp-session-protection {
    type enumeration {
      enum all {
        value 1;
        description "Protect all peer sessions";
      }
      enum for {
        value 2;
        description "Protect peer session(s) permitted by peer ACL";
      }
      enum all-with-duration {
        value 3;
        description
          "Protect all peer sessions and holdup protection
          for given duration";
      }
      enum for-with-duration {
        value 4;
        description
          "Protect peer session(s) permitted by peer ACL
          and holdup protection for given duration";
      }
      enum all-with-forever {
        value 5;
        description
          "Protect all peer sessions and holdup protection
          forever";
      }
      enum for-with-forever {
        value 6;
        description
          "Protect peer session(s) permitted by peer ACL
          and holdup protection forever";
      }
    }
    description "Mpls ldp session protection";
  }
  typedef Mpls-ldp-label-advertise {
    type enumeration {
      enum for {
        value 1;
        description
          "Advertise label for prefix(es) permitted by
          prefix ACL";
      }
      enum for-to {
        value 2;
        description
          "Advertise label for prefix(es) permitted by
          prefix ACL to peer(s) permitted by peer ACL";
      }
    }
    description "Mpls ldp label advertise";
  }
  typedef Mpls-ldp-advertise-bgpacl {
    type enumeration {
      enum peer-acl {
        value 1;
        description
          "BGP prefixes advertised to peers permitted by
          ACL";
      }
    }
    description "Mpls ldp advertise bgpacl";
  }

  grouping AF-TABLE {
    description "Common node of default-vrf, vrf";

    container afs {
      xr:xr-xml-map "mldp_af_cfg:AFTable";
      description "Address Family specific operational data";

      list af {
        xr:xr-xml-map "mldp_af_cfg:AF";
        key "af-name";
        description "Operational data for given Address Family";

        container mldp-recursive-fec {
          xr:xr-xml-map "mldp_af_cfg:MLDPRecursiveFEC";
          description "MPLS mLDP Recursive FEC";
          leaf enable-mldp-recursive-fec {
            xr:xr-xml-map "mldp_af_cfg:EnableMLDPRecursiveFEC";
            type empty;
            description "Enable MPLS mLDP Recursive FEC";
          }
        }

        container mo-frr {
          xr:xr-xml-map "mldp_af_cfg:MoFRR";
          description "MPLS mLDP MoFRR";
          leaf enable-mo-frr {
            xr:xr-xml-map "mldp_af_cfg:EnableMoFRR";
            type empty;
            description "Enable MPLS mLDP MoFRR";
          }
        }

        container make-before-break {
          xr:xr-xml-map "mldp_af_cfg:MakeBeforeBreak";
          description "MPLS mLDP Make-Before-Break configuration";

          container signaling {
            xr:xr-xml-map "mldp_af_cfg:Signaling";
            description "Enable MPLS mLDP MBB signaling";
            leaf forward-delay {
              xr:xr-xml-map "mldp_af_cfg:ForwardDelay";
              type uint32 {
                range "0..600";
              }
              units "second";
              description "Forwarding Delay in Seconds";
            }
            leaf delete-delay {
              xr:xr-xml-map "mldp_af_cfg:DeleteDelay";
              type uint32 {
                range "0..60";
              }
              units "second";
              description "Delete Delay in seconds";
            }
          }
        }

        container csc {
          xr:xr-xml-map "mldp_af_cfg:CSC";
          description "MPLS mLDP CSC";
          leaf enable-csc {
            xr:xr-xml-map "mldp_af_cfg:EnableCSC";
            type empty;
            description "Enable MPLS mLDP CSC";
          }
        }
        leaf enable {
          xr:xr-xml-map "mldp_af_cfg:Enable";
          type empty;
          description
            "Enable Multicast Label Distribution Protocol
            (mLDP) under AF.";
        }
        leaf mldp-rib-unicast-always {
          xr:xr-xml-map "mldp_af_cfg:MLDP_RIBUnicastAlways";
          type empty;
          description
            "Enable MPLS MLDP RIB unicast-always
            configuration";
        }
        leaf af-name {
          xr:xr-xml-map "mldp_af_cfg:AFName";
          type Mpls-ldpaf-name;
          description "Address Family name";
        }
      }
    }
  }

  container mpls-ldp {
    xr:xr-xml-map "mpls_ldp_common_cfg:MPLS_LDP";
    description "MPLS LDP configuration";

    container default-vrf {
      xr:xr-xml-map "mpls_ldp_common_cfg:DefaultVRF";
      description "Global VRF attribute configuration for MPLS LDP";

      container afs {
        xr:xr-xml-map "mpls_ldp_gl_af_cfg:AFTable";
        description
          "Address Family specific configuration for MPLS
          LDP";

        list af {
          xr:xr-xml-map "mpls_ldp_gl_af_cfg:AF";
          key "af-name";
          description "Configure data for given Address Family";

          container label {
            xr:xr-xml-map "mpls_ldp_gl_af_cfg:Label";
            description "Configure Label policies and control";

            container remote {
              xr:xr-xml-map "mpls_ldp_gl_af_cfg:Remote";
              description
                "Configure remote/peer label policies and
                control";

              container accept {
                xr:xr-xml-map "mpls_ldp_gl_af_cfg:Accept";
                description "Configure inbound label acceptance";

                container peer-accept-policies {
                  xr:xr-xml-map "mpls_ldp_gl_af_cfg:PeerAcceptPolic"+
                    "yTable";
                  description
                    "Configuration related to neighbors for
                    inbound label acceptance";

                  list peer-accept-policy {
                    xr:xr-xml-map "mpls_ldp_gl_af_cfg:PeerAcceptPol"+
                      "icy";
                    key "lsr-id label-space-id";
                    description
                      "Control acceptance of labels from a
                      neighbor for prefix(es) using ACL";
                    leaf lsr-id {
                      xr:xr-xml-map "mpls_ldp_gl_af_cfg:LSR_ID";
                      type inet:ipv4-address-no-zone;
                      description "LSR ID of neighbor";
                    }
                    leaf label-space-id {
                      xr:xr-xml-map "mpls_ldp_gl_af_cfg:LabelSpaceI"+
                        "D";
                      type uint32;
                      description "Label space ID of neighbor";
                    }
                    leaf prefix-acl-name {
                      xr:xr-xml-map "mpls_ldp_gl_af_cfg:PrefixACLNa"+
                        "me";
                      type string;
                      mandatory true;
                      description "Name of prefix ACL";
                    }
                  }
                }
              }
            }

            container local {
              xr:xr-xml-map "mpls_ldp_gl_af_cfg:Local";
              description
                "Configure local label policies and control";

              container advertise {
                xr:xr-xml-map "mpls_ldp_gl_af_cfg:Advertise";
                description
                  "Configure outbound label advertisement";

                container peer-advertise-policies {
                  xr:xr-xml-map "mpls_ldp_gl_af_cfg:PeerAdvertisePo"+
                    "licyTable";
                  description
                    "Configure peer centric outbound label
                    advertisement using ACL";

                  list peer-advertise-policy {
                    xr:xr-xml-map "mpls_ldp_gl_af_cfg:PeerAdvertise"+
                      "Policy";
                    key "lsr-id label-space-id";
                    description
                      "Control advertisement of prefix(es) using
                      ACL";
                    leaf lsr-id {
                      xr:xr-xml-map "mpls_ldp_gl_af_cfg:LSR_ID";
                      type inet:ipv4-address-no-zone;
                      description "LSR ID of neighbor";
                    }
                    leaf label-space-id {
                      xr:xr-xml-map "mpls_ldp_gl_af_cfg:LabelSpaceI"+
                        "D";
                      type uint32;
                      description "Label space ID of neighbor";
                    }
                    leaf prefix-acl-name {
                      xr:xr-xml-map "mpls_ldp_gl_af_cfg:PrefixACLNa"+
                        "me";
                      type string;
                      mandatory true;
                      description "Name of prefix ACL";
                    }
                  }
                }

                container prefix-advertise-policies {
                  xr:xr-xml-map "mpls_ldp_gl_af_cfg:PrefixAdvertise"+
                    "PolicyTable";
                  description
                    "Configure prefix centric outbound label
                    advertisement using ACL";

                  list prefix-advertise-policy {
                    xr:xr-xml-map "mpls_ldp_gl_af_cfg:PrefixAdverti"+
                      "sePolicy";
                    key "prefix-acl-name";
                    description
                      "Control advertisement of prefix(es) using
                      ACL";
                    leaf prefix-acl-name {
                      xr:xr-xml-map "mpls_ldp_gl_af_cfg:PrefixACLNa"+
                        "me";
                      type xr:Cisco-ios-xr-string;
                      description "Name of prefix ACL";
                    }
                    leaf advertise-type {
                      xr:xr-xml-map "mpls_ldp_gl_af_cfg:AdvertiseTy"+
                        "pe";
                      type Mpls-ldp-label-advertise;
                      description "Label advertise type";
                    }
                    leaf peer-acl-name {
                      xr:xr-xml-map "mpls_ldp_gl_af_cfg:PeerACLName";
                      when "../advertise-type = 'for-to'" {
                        description "../AdvertiseType = ForTo";
                      }
                      type string;
                      description "Name of peer ACL";
                    }
                  }
                }

                container explicit-null {
                  xr:xr-xml-map "mpls_ldp_gl_af_cfg:ExplicitNull";
                  description
                    "Configure advertisment of explicit-null
                    for connected prefixes.";
                  leaf explicit-null-type {
                    xr:xr-xml-map "mpls_ldp_gl_af_cfg:ExplicitNullT"+
                      "ype";
                    type Mpls-ldp-exp-null;
                    description "Explicit Null command variant";
                  }
                  leaf prefix-acl-name {
                    xr:xr-xml-map "mpls_ldp_gl_af_cfg:PrefixACLName";
                    when "../explicit-null-type = 'for' or"+
                      " ../explicit-null-type = 'for-to'" {
                        description
                          "../ExplicitNullType = For or .
                          ./ExplicitNullType = ForTo";
                    }
                    type string;
                    description "Name of prefix ACL";
                  }
                  leaf peer-acl-name {
                    xr:xr-xml-map "mpls_ldp_gl_af_cfg:PeerACLName";
                    when "../explicit-null-type = 'to' or"+
                      " ../explicit-null-type = 'for-to'" {
                        description
                          "../ExplicitNullType = To or .
                          ./ExplicitNullType = ForTo";
                    }
                    type string;
                    description "Name of peer ACL";
                  }
                }

                container interfaces {
                  xr:xr-xml-map "mpls_ldp_gl_af_cfg:InterfaceTable";
                  description
                    "Configure outbound label advertisement for
                    an interface";

                  list interface {
                    xr:xr-xml-map "mpls_ldp_gl_af_cfg:Interface";
                    key "interface-name";
                    description
                      "Control advertisement of interface's host
                      IP address";
                    leaf interface-name {
                      xr:xr-xml-map "mpls_ldp_gl_af_cfg:InterfaceNa"+
                        "me";
                      type xr:Interface-name;
                      description "Name of interface";
                    }
                  }
                }
                leaf disable {
                  xr:xr-xml-map "mpls_ldp_gl_af_cfg:Disable";
                  type empty;
                  description "Disable label advertisement";
                }
              }

              container allocate {
                xr:xr-xml-map "mpls_ldp_gl_af_cfg:Allocate";
                description
                  "Control local label allocation for
                  prefix(es)";
                leaf allocation-type {
                  xr:xr-xml-map "mpls_ldp_gl_af_cfg:AllocationType";
                  type Mpls-ldp-label-allocation;
                  description "Label allocation type";
                }
                leaf prefix-acl-name {
                  xr:xr-xml-map "mpls_ldp_gl_af_cfg:PrefixACLName";
                  when "../allocation-type = 'acl'" {
                    description "../AllocationType = ACL";
                  }
                  type string;
                  description "Name of prefix ACL";
                }
              }
              leaf implicit-null-override {
                xr:xr-xml-map "mpls_ldp_gl_af_cfg:ImplicitNullOverr"+
                  "ide";
                type string;
                description
                  "Control use of implicit-null label for set
                  of prefix(es)";
              }
              leaf default-route {
                xr:xr-xml-map "mpls_ldp_gl_af_cfg:DefaultRoute";
                type empty;
                description
                  "Enable MPLS forwarding for default route";
              }
            }
          }

          container discovery {
            xr:xr-xml-map "mpls_ldp_gl_af_cfg:Discovery";
            description "Configure Discovery parameters";

            container targeted-hello-accept {
              xr:xr-xml-map "mpls_ldp_gl_af_cfg:TargetedHelloAccept";
              description
                "Configure acceptance from and responding to
                targeted hellos.";
              leaf accept-type {
                xr:xr-xml-map "mpls_ldp_gl_af_cfg:AcceptType";
                type Mpls-ldp-targeted-accept;
                description "Type of acceptance";
              }
              leaf peer-acl-name {
                xr:xr-xml-map "mpls_ldp_gl_af_cfg:PeerACLName";
                when "../accept-type = 'from'" {
                  description "../AcceptType = From";
                }
                type string;
                description "Name of peer ACL";
              }
            }
            leaf transport-address {
              xr:xr-xml-map "mpls_ldp_gl_af_cfg:TransportAddress";
              type inet:ip-address-no-zone;
              description
                "Global discovery transport address for
                address family";
            }
          }

          container traffic-engineering {
            xr:xr-xml-map "mpls_ldp_gl_af_cfg:TrafficEngineering";
            description
              "MPLS Traffic Engingeering parameters for LDP";

            container auto-tunnel-mesh {
              xr:xr-xml-map "mpls_ldp_gl_af_cfg:AutoTunnelMesh";
              description
                "MPLS Traffic Engineering auto-tunnel mesh
                parameters for LDP";

              container group-ids {
                xr:xr-xml-map "mpls_ldp_gl_af_cfg:GroupIDTable";
                description
                  "Enable interfaces in specific MPLS TE
                  auto-tunnel mesh-groups";

                list group-id {
                  xr:xr-xml-map "mpls_ldp_gl_af_cfg:GroupID";
                  key "mesh-group-id";
                  description
                    "Auto-mesh group identifier to enable";
                  leaf mesh-group-id {
                    xr:xr-xml-map "mpls_ldp_gl_af_cfg:MeshGroupID";
                    type Mpls-ldp-mesh-group-id;
                    description "Mesh group ID";
                  }
                }
              }
              leaf group-all {
                xr:xr-xml-map "mpls_ldp_gl_af_cfg:GroupAll";
                type empty;
                description
                  "Enable all MPLS TE auto-tunnel mesh-group
                  interfaces";
              }
            }
          }

          container neighbor {
            xr:xr-xml-map "mpls_ldp_gl_af_cfg:Neighbor";
            description "Configuration related to Neighbors";

            container addresses {
              xr:xr-xml-map "mpls_ldp_gl_af_cfg:AddressTable";
              description
                "Configuration related to neighbors using
                neighbor address";

              list address {
                xr:xr-xml-map "mpls_ldp_gl_af_cfg:Address";
                key "ip-address";
                description
                  "IP address based configuration related to a
                  neighbor";
                leaf targeted {
                  xr:xr-xml-map "mpls_ldp_gl_af_cfg:Targeted";
                  type empty;
                  description
                    "Establish targeted session with given
                    address";
                }
                leaf ip-address {
                  xr:xr-xml-map "mpls_ldp_gl_af_cfg:IPAddress";
                  type inet:ip-address-no-zone;
                  description "The IP address";
                }
              }
            }
          }

          container redistribution-protocol {
            xr:xr-xml-map "mpls_ldp_gl_af_cfg:RedistributionProtoco"+
              "l";
            description
              "MPLS LDP configuration for protocol
              redistribution";

            container bgp {
              xr:xr-xml-map "mpls_ldp_gl_af_cfg:BGP";
              description
                "MPLS LDP configuration for protocol
                redistribution";

              container as {
                xr:xr-xml-map "mpls_ldp_gl_af_cfg:AS";
                description
                  "MPLS LDP configuration for protocol
                  redistribution";
                leaf as-xx {
                  xr:xr-xml-map "mpls_ldp_gl_af_cfg:AS_XX";
                  type uint32 {
                    range "0..65535";
                  }
                  description
                    "First half of BGP AS number in XX.YY
                    format.  Mandatory Must be a non-zero
                    value if second half is zero.";
                }
                leaf as-yy {
                  xr:xr-xml-map "mpls_ldp_gl_af_cfg:AS_YY";
                  type uint32 {
                    range "0..4294967295";
                  }
                  description
                    "Second half of BGP AS number in XX.YY
                    format. Mandatory Must be a non-zero value
                    if first half is zero.";
                }
              }

              container advertise-to {
                xr:xr-xml-map "mpls_ldp_gl_af_cfg:AdvertiseTo";
                description
                  "ACL containing list of neighbors for BGP
                  route redistribution";
                leaf type {
                  xr:xr-xml-map "mpls_ldp_gl_af_cfg:Type";
                  type Mpls-ldp-advertise-bgpacl;
                  description "advertise to peer acl type";
                }
                leaf peer-acl-name {
                  xr:xr-xml-map "mpls_ldp_gl_af_cfg:PeerACLName";
                  when "../type = 'peer-acl'" {
                    description "../Type = PeerACL";
                  }
                  type string;
                  description "Name of peer ACL";
                }
              }
            }
          }
          leaf enable {
            xr:xr-xml-map "mpls_ldp_gl_af_cfg:Enable";
            type empty;
            description "Enable Address Family";
          }
          leaf af-name {
            xr:xr-xml-map "mpls_ldp_gl_af_cfg:AFName";
            type Mpls-ldpaf-name;
            description "Address Family type";
          }
        }
      }

      container global {
        xr:xr-xml-map "mpls_ldp_vrf_gl_cfg:Global";
        description "Default VRF Global configuration for MPLS LDP";

        container session {
          xr:xr-xml-map "mpls_ldp_vrf_gl_cfg:Session";
          description "LDP Session parameters";

          container protection {
            xr:xr-xml-map "mpls_ldp_vrf_gl_cfg:Protection";
            description "Configure Session Protection parameters";
            leaf protection-type {
              xr:xr-xml-map "mpls_ldp_vrf_gl_cfg:ProtectionType";
              type Mpls-ldp-session-protection;
              description "Session protection type";
            }
            leaf peer-acl-name {
              xr:xr-xml-map "mpls_ldp_vrf_gl_cfg:PeerACLName";
              when "../protection-type = 'for' or"+
                " ../protection-type = 'for-with-duration' or"+
                " ../protection-type = 'for-with-forever'" {
                  description
                    "../ProtectionType = For or .
                    ./ProtectionType = ForWithDuration or .
                    ./ProtectionType = ForWithForever";
              }
              type string;
              description "Name of peer ACL";
            }
            leaf duration {
              xr:xr-xml-map "mpls_ldp_vrf_gl_cfg:Duration";
              when "../protection-type = 'all-with-duration' or"+
                " ../protection-type = 'for-with-duration'" {
                  description
                    "../ProtectionType = AllWithDuration or .
                    ./ProtectionType = ForWithDuration";
              }
              type uint32 {
                range "30..2147483";
              }
              description "Holdup duration";
            }
          }

          container downstream-on-demand {
            xr:xr-xml-map "mpls_ldp_vrf_gl_cfg:DownstreamOnDemand";
            description
              "ACL with the list of neighbors configured for
              Downstream on Demand";
            leaf type {
              xr:xr-xml-map "mpls_ldp_vrf_gl_cfg:Type";
              type Mpls-ldp-downstream-on-demand;
              description "Downstream on demand type";
            }
            leaf peer-acl-name {
              xr:xr-xml-map "mpls_ldp_vrf_gl_cfg:PeerACLName";
              when "../type = 'peer-acl'" {
                description "../Type = PeerACL";
              }
              type string;
              description "Name of peer ACL";
            }
          }
        }

        container neighbor {
          xr:xr-xml-map "mpls_ldp_vrf_gl_cfg:Neighbor";
          description "Configuration related to Neighbors";

          container ldp-ids {
            xr:xr-xml-map "mpls_ldp_vrf_gl_cfg:LDPIDTable";
            description
              "Configuration related to Neighbors using LDP
              Id";

            list ldp-id {
              xr:xr-xml-map "mpls_ldp_vrf_gl_cfg:LDP_ID";
              key "lsr-id label-space-id";
              description
                "LDP ID based configuration related to a
                neigbor";

              container password {
                xr:xr-xml-map "mpls_ldp_vrf_gl_cfg:Password";
                description
                  "Password for MD5 authentication for this
                  neighbor";
                leaf command-type {
                  xr:xr-xml-map "mpls_ldp_vrf_gl_cfg:CommandType";
                  type Mpls-ldp-nbr-password;
                  description
                    "Command type for password configuration";
                }
                leaf password {
                  xr:xr-xml-map "mpls_ldp_vrf_gl_cfg:Password";
                  when "../command-type = 'specified'" {
                    description "../CommandType = Specified";
                  }
                  type xr:Proprietary-password;
                  description "The neighbor password";
                }
              }
              leaf lsr-id {
                xr:xr-xml-map "mpls_ldp_vrf_gl_cfg:LSR_ID";
                type inet:ipv4-address-no-zone;
                description "LSR ID of neighbor";
              }
              leaf label-space-id {
                xr:xr-xml-map "mpls_ldp_vrf_gl_cfg:LabelSpaceID";
                type uint32;
                description "Label space ID of neighbor";
              }
            }
          }

          container dual-stack {
            xr:xr-xml-map "mpls_ldp_vrf_gl_cfg:DualStack";
            description
              "Configuration related to neighbor transport";

            container transport-connection {
              xr:xr-xml-map "mpls_ldp_vrf_gl_cfg:TransportConnectio"+
                "n";
              description
                "Configuration related to neighbor transport";

              container prefer {
                xr:xr-xml-map "mpls_ldp_vrf_gl_cfg:Prefer";
                description
                  "Configuration related to neighbor
                  dual-stack xport-connection preference";
                leaf ipv4 {
                  xr:xr-xml-map "mpls_ldp_vrf_gl_cfg:IPv4";
                  type empty;
                  description
                    "Configuration related to neighbor
                    dual-stack xport-connection preference
                    ipv4";
                }
              }
              leaf max-wait {
                xr:xr-xml-map "mpls_ldp_vrf_gl_cfg:MaxWait";
                type uint32 {
                  range "0..60";
                }
                units "second";
                description
                  "Configuration related to neighbor
                  dual-stack xport-connection max-wait";
              }
            }
            leaf tlv-compliance {
              xr:xr-xml-map "mpls_ldp_vrf_gl_cfg:TLVCompliance";
              type empty;
              description
                "Configuration to enable neighbor dual-stack
                tlv-compliance";
            }
          }
          leaf password {
            xr:xr-xml-map "mpls_ldp_vrf_gl_cfg:Password";
            type xr:Proprietary-password;
            description "Default password for all neigbors";
          }
        }

        container graceful-restart {
          xr:xr-xml-map "mpls_ldp_vrf_gl_cfg:GracefulRestart";
          description
            "Configuration for per-VRF LDP Graceful Restart
            parameters";

          container helper-peer {
            xr:xr-xml-map "mpls_ldp_vrf_gl_cfg:HelperPeer";
            description
              "Configure parameters related to GR peer(s)
              opearating in helper mode";
            leaf maintain-on-local-reset {
              xr:xr-xml-map "mpls_ldp_vrf_gl_cfg:MaintainOnLocalRes"+
                "et";
              type string;
              description
                "Maintain the state of a GR peer upon a local
                reset";
            }
          }
        }
        leaf router-id {
          xr:xr-xml-map "mpls_ldp_vrf_gl_cfg:RouterID";
          type inet:ipv4-address-no-zone;
          description "Configuration for LDP Router ID (LDP ID)";
        }
      }

      container interfaces {
        xr:xr-xml-map "mpls_ldp_common_cfg:InterfaceTable";
        description
          "MPLS LDP configuration pertaining to interfaces";

        list interface {
          xr:xr-xml-map "mpls_ldp_common_cfg:Interface";
          key "interface-name";
          description
            "MPLS LDP configuration for a particular
            interface";

          container afs {
            xr:xr-xml-map "mpls_ldp_gl_if_af_cfg:AFTable";
            description
              "Address Family specific configuration for
              MPLS LDP intf";

            list af {
              xr:xr-xml-map "mpls_ldp_gl_if_af_cfg:AF";
              key "af-name";
              description "Configure data for given Address Family";

              container discovery {
                xr:xr-xml-map "mpls_ldp_gl_if_af_cfg:Discovery";
                description
                  "Configure interface discovery parameters";

                container transport-address {
                  xr:xr-xml-map "mpls_ldp_gl_if_af_cfg:TransportAdd"+
                    "ress";
                  description
                    "MPLS LDP configuration for interface
                    discovery transportaddress.";
                  leaf address-type {
                    xr:xr-xml-map "mpls_ldp_gl_if_af_cfg:AddressTyp"+
                      "e";
                    type Mpls-ldp-transport-address;
                    description "Transport address option";
                  }
                  leaf address {
                    xr:xr-xml-map "mpls_ldp_gl_if_af_cfg:Address";
                    when "../address-type = 'address'" {
                      description "../AddressType = Address";
                    }
                    type inet:ip-address-no-zone;
                    description "IP address";
                  }
                }
              }

              container igp {
                xr:xr-xml-map "mpls_ldp_gl_if_af_cfg:IGP";
                description "LDP interface IGP configuration";
                leaf disable-auto-config {
                  xr:xr-xml-map "mpls_ldp_gl_if_af_cfg:DisableAutoC"+
                    "onfig";
                  type empty;
                  description
                    "Disable IGP Auto-config on this interface";
                }
              }

              container mldp {
                xr:xr-xml-map "mldp_if_cfg:MLDP";
                description
                  "Interface configuration parameters for mLDP";
                leaf disable {
                  xr:xr-xml-map "mldp_if_cfg:Disable";
                  type empty;
                  description
                    "Disable mLDP on LDP enabled interface";
                }
              }
              leaf enable {
                xr:xr-xml-map "mpls_ldp_gl_if_af_cfg:Enable";
                type empty;
                description "Enable Address Family";
              }
              leaf af-name {
                xr:xr-xml-map "mpls_ldp_gl_if_af_cfg:AFName";
                type Mpls-ldpaf-name;
                description "Address Family name";
              }
            }
          }

          container global {
            xr:xr-xml-map "mpls_ldp_gl_if_cfg:Global";
            description
              "Per VRF interface Global configuration for
              MPLS LDP";

            container discovery {
              xr:xr-xml-map "mpls_ldp_gl_if_cfg:Discovery";
              description
                "Configure interface discovery parameters";

              container link-hello {
                xr:xr-xml-map "mpls_ldp_gl_if_cfg:LinkHello";
                description "LDP Link Hellos";
                leaf interval {
                  xr:xr-xml-map "mpls_ldp_gl_if_cfg:Interval";
                  type Mpls-ldp-interval-time;
                  units "second";
                  default "5";
                  description "Link Hello interval";
                }
                leaf dual-stack {
                  xr:xr-xml-map "mpls_ldp_gl_if_cfg:DualStack";
                  type Mpls-ldpaf-name;
                  default "ipv4";
                  description
                    "Dual Stack Address Family Preference";
                }
                leaf hold-time {
                  xr:xr-xml-map "mpls_ldp_gl_if_cfg:HoldTime";
                  type Mpls-ldp-hold-time;
                  units "second";
                  default "15";
                  description
                    "Time (seconds) - 65535 implies infinite";
                }
              }
              leaf disable-quick-start {
                xr:xr-xml-map "mpls_ldp_gl_if_cfg:DisableQuickStart";
                type empty;
                description "Disable discovery's quick start mode";
              }
            }

            container igp {
              xr:xr-xml-map "mpls_ldp_gl_if_cfg:IGP";
              description "LDP IGP configuration";

              container sync {
                xr:xr-xml-map "mpls_ldp_gl_if_cfg:Sync";
                description "LDP IGP synchronization";

                container delay {
                  xr:xr-xml-map "mpls_ldp_gl_if_cfg:Delay";
                  description "LDP IGP synchronization delay time";

                  container on-session-up {
                    xr:xr-xml-map "mpls_ldp_gl_if_cfg:OnSessionUp";
                    description
                      "Interface sync up delay after session up";
                    leaf disable {
                      xr:xr-xml-map "mpls_ldp_gl_if_cfg:Disable";
                      type empty;
                      description "Disable delay after session up";
                    }
                    leaf timeout {
                      xr:xr-xml-map "mpls_ldp_gl_if_cfg:Timeout";
                      type uint32 {
                        range "5..300";
                      }
                      units "second";
                      description "Time (seconds)";
                    }
                  }
                }
              }
            }
          }
          leaf enable {
            xr:xr-xml-map "mpls_ldp_common_cfg:Enable";
            type empty;
            description
              "Enable Label Distribution Protocol (LDP) on
              thisinterface";
          }
          leaf interface-name {
            xr:xr-xml-map "mpls_ldp_common_cfg:InterfaceName";
            type xr:Interface-name;
            description "Name of interface";
          }
        }
      }
    }

    container vrfs {
      xr:xr-xml-map "mpls_ldp_common_cfg:VRFTable";
      description "VRF Table attribute configuration for MPLS LDP";

      list vrf {
        xr:xr-xml-map "mpls_ldp_common_cfg:VRF";
        key "vrf-name";
        description "VRF attribute configuration for MPLS LDP";

        container global {
          xr:xr-xml-map "mpls_ldp_vrf_cfg:Global";
          description "Per VRF Global configuration for MPLS LDP";

          container session {
            xr:xr-xml-map "mpls_ldp_vrf_cfg:Session";
            description "LDP Session parameters";

            container downstream-on-demand {
              xr:xr-xml-map "mpls_ldp_vrf_cfg:DownstreamOnDemand";
              description
                "ACL with the list of neighbors configured
                for Downstream on Demand";
              leaf type {
                xr:xr-xml-map "mpls_ldp_vrf_cfg:Type";
                type Mpls-ldp-downstream-on-demand;
                description "Downstream on demand type";
              }
              leaf peer-acl-name {
                xr:xr-xml-map "mpls_ldp_vrf_cfg:PeerACLName";
                when "../type = 'peer-acl'" {
                  description "../Type = PeerACL";
                }
                type string;
                description "Name of peer ACL";
              }
            }
          }

          container neighbor {
            xr:xr-xml-map "mpls_ldp_vrf_cfg:Neighbor";
            description "Configuration related to Neighbors";

            container ldp-ids {
              xr:xr-xml-map "mpls_ldp_vrf_cfg:LDPIDTable";
              description
                "Configuration related to Neighbors using LDP
                Id";

              list ldp-id {
                xr:xr-xml-map "mpls_ldp_vrf_cfg:LDP_ID";
                key "lsr-id label-space-id";
                description
                  "LDP ID based configuration related to a
                  neigbor";

                container password {
                  xr:xr-xml-map "mpls_ldp_vrf_cfg:Password";
                  description
                    "Password for MD5 authentication for this
                    neighbor";
                  leaf command-type {
                    xr:xr-xml-map "mpls_ldp_vrf_cfg:CommandType";
                    type Mpls-ldp-nbr-password;
                    description
                      "Command type for password configuration";
                  }
                  leaf password {
                    xr:xr-xml-map "mpls_ldp_vrf_cfg:Password";
                    when "../command-type = 'specified'" {
                      description "../CommandType = Specified";
                    }
                    type xr:Proprietary-password;
                    description "The neighbor password";
                  }
                }
                leaf lsr-id {
                  xr:xr-xml-map "mpls_ldp_vrf_cfg:LSR_ID";
                  type inet:ipv4-address-no-zone;
                  description "LSR ID of neighbor";
                }
                leaf label-space-id {
                  xr:xr-xml-map "mpls_ldp_vrf_cfg:LabelSpaceID";
                  type uint32;
                  description "Label space ID of neighbor";
                }
              }
            }
            leaf password {
              xr:xr-xml-map "mpls_ldp_vrf_cfg:Password";
              xr:xr-cli-map "ldp vrf <string> neighbor password (cl"+
                "ear <text>)|(encrypted <text>) ";
              type xr:Proprietary-password;
              description "Default password for all neigbors";
            }
          }

          container graceful-restart {
            xr:xr-xml-map "mpls_ldp_vrf_cfg:GracefulRestart";
            description
              "Configuration for per-VRF LDP Graceful
              Restart parameters";

            container helper-peer {
              xr:xr-xml-map "mpls_ldp_vrf_cfg:HelperPeer";
              description
                "Configure parameters related to GR peer(s)
                opearating in helper mode";
              leaf maintain-on-local-reset {
                xr:xr-xml-map "mpls_ldp_vrf_cfg:MaintainOnLocalRese"+
                  "t";
                xr:xr-cli-map "ldp vrf <string> graceful-restart he"+
                  "lper-peer maintain-on-local-reset for <string> ";
                type string;
                description
                  "Maintain the state of a GR peer upon a
                  local reset";
              }
            }
          }
          leaf router-id {
            xr:xr-xml-map "mpls_ldp_vrf_cfg:RouterID";
            xr:xr-cli-map "ldp vrf <string> router-id <IPv4 address"+
              "> ";
            type inet:ipv4-address-no-zone;
            description "Configuration for LDP Router ID (LDP ID)";
          }
        }

        container afs {
          xr:xr-xml-map "mpls_ldp_vrf_af_cfg:AFTable";
          description
            "Address Family specific configuration for MPLS
            LDP vrf";

          list af {
            xr:xr-xml-map "mpls_ldp_vrf_af_cfg:AF";
            key "af-name";
            description "Configure data for given Address Family";

            container discovery {
              xr:xr-xml-map "mpls_ldp_vrf_af_cfg:Discovery";
              description "Configure Discovery parameters";
              leaf transport-address {
                xr:xr-xml-map "mpls_ldp_vrf_af_cfg:TransportAddress";
                xr:xr-cli-map "ldp vrf <string> address-family (ipv"+
                  "4)|(ipv6) discovery transport-address <IPv4 addr"+
                  "ess> ";
                type string;
                description
                  "Global discovery transport address for
                  address family";
              }
            }

            container label {
              xr:xr-xml-map "mpls_ldp_vrf_af_cfg:Label";
              description "Configure Label policies and control";

              container remote {
                xr:xr-xml-map "mpls_ldp_vrf_af_cfg:Remote";
                description
                  "Configure remote/peer label policies and
                  control";

                container accept {
                  xr:xr-xml-map "mpls_ldp_vrf_af_cfg:Accept";
                  description "Configure inbound label acceptance";

                  container peer-accept-policies {
                    xr:xr-xml-map "mpls_ldp_vrf_af_cfg:PeerAcceptPo"+
                      "licyTable";
                    description
                      "Configuration related to Neighbors for
                      inbound label acceptance";

                    list peer-accept-policy {
                      must "peer-accept-policy-data or lsr-id" {
                        description
                          "peer-accept-policy-data or lsr-id must
                          be present.";
                      }
                      key "label-space-id";
                      description
                        "Control acceptasnce of labels from a
                        neighbor for prefix(es) using ACL";

                      grouping PEER-ACCEPT-POLICY-CONTENT {
                        description "Content grouping.";
                        leaf prefix-acl-name {
                          xr:xr-xml-map "mpls_ldp_vrf_af_cfg:Prefix"+
                            "ACLName";
                          type string;
                          mandatory true;
                          description "Name of prefix ACL";
                        }
                      }

                      container peer-accept-policy-data {
                        xr:xr-xml-map "mpls_ldp_vrf_af_cfg:PeerAcce"+
                          "ptPolicy";
                        xr:xr-cli-map "ldp vrf <string> address-fam"+
                          "ily (ipv4)|(ipv6) label remote accept fr"+
                          "om <IPv4 address> <number> for <string> ";
                        description "Data container.";
                        uses PEER-ACCEPT-POLICY-CONTENT;
                      }
                      leaf label-space-id {
                        xr:xr-xml-map "mpls_ldp_vrf_af_cfg:LabelSpa"+
                          "ceID";
                        xr:xr-cli-map "ldp vrf <string> address-fam"+
                          "ily (ipv4)|(ipv6) label remote accept fr"+
                          "om <IPv4 address> <number> for <string> ";
                        type uint32;
                        description "Label space ID of neighbor";
                      }

                      list lsr-id {
                        xr:xr-xml-map "mpls_ldp_vrf_af_cfg:PeerAcce"+
                          "ptPolicy";
                        xr:xr-cli-map "ldp vrf <string> address-fam"+
                          "ily (ipv4)|(ipv6) label remote accept fr"+
                          "om <IPv4 address> <number> for <string> ";
                        key "lsr-id";
                        description "keys: lsr-id";
                        leaf lsr-id {
                          xr:xr-xml-map "mpls_ldp_vrf_af_cfg:LSR_ID";
                          type inet:ipv4-address-no-zone;
                          description "LSR ID of neighbor";
                        }
                        uses PEER-ACCEPT-POLICY-CONTENT;
                      }
                    }
                  }
                }
              }

              container local {
                xr:xr-xml-map "mpls_ldp_vrf_af_cfg:Local";
                description
                  "Configure local label policies and control";

                container advertise {
                  xr:xr-xml-map "mpls_ldp_vrf_af_cfg:Advertise";
                  description
                    "Configure outbound label advertisement";

                  container peer-advertise-policies {
                    xr:xr-xml-map "mpls_ldp_vrf_af_cfg:PeerAdvertis"+
                      "ePolicyTable";
                    description
                      "Configure peer centric outbound label
                      advertisement using ACL";

                    list peer-advertise-policy {
                      must "peer-advertise-policy-data or lsr-id" {
                        description
                          "peer-advertise-policy-data or lsr-id
                          must be present.";
                      }
                      key "label-space-id";
                      description
                        "Control advertisement of prefix(es)
                        using ACL";

                      grouping PEER-ADVERTISE-POLICY-CONTENT {
                        description "Content grouping.";
                        leaf prefix-acl-name {
                          xr:xr-xml-map "mpls_ldp_vrf_af_cfg:Prefix"+
                            "ACLName";
                          type string;
                          mandatory true;
                          description "Name of prefix ACL";
                        }
                      }

                      container peer-advertise-policy-data {
                        xr:xr-xml-map "mpls_ldp_vrf_af_cfg:PeerAdve"+
                          "rtisePolicy";
                        xr:xr-cli-map "ldp vrf <string> address-fam"+
                          "ily (ipv4)|(ipv6) label local advertise "+
                          "to <IPv4 address> <number> for <string> ";
                        description "Data container.";
                        uses PEER-ADVERTISE-POLICY-CONTENT;
                      }
                      leaf label-space-id {
                        xr:xr-xml-map "mpls_ldp_vrf_af_cfg:LabelSpa"+
                          "ceID";
                        xr:xr-cli-map "ldp vrf <string> address-fam"+
                          "ily (ipv4)|(ipv6) label local advertise "+
                          "to <IPv4 address> <number> for <string> ";
                        type uint32;
                        description "Label space ID of neighbor";
                      }

                      list lsr-id {
                        xr:xr-xml-map "mpls_ldp_vrf_af_cfg:PeerAdve"+
                          "rtisePolicy";
                        xr:xr-cli-map "ldp vrf <string> address-fam"+
                          "ily (ipv4)|(ipv6) label local advertise "+
                          "to <IPv4 address> <number> for <string> ";
                        key "lsr-id";
                        description "keys: lsr-id";
                        leaf lsr-id {
                          xr:xr-xml-map "mpls_ldp_vrf_af_cfg:LSR_ID";
                          type inet:ipv4-address-no-zone;
                          description "LSR ID of neighbor";
                        }
                        uses PEER-ADVERTISE-POLICY-CONTENT;
                      }
                    }
                  }

                  container interfaces {
                    xr:xr-xml-map "mpls_ldp_vrf_af_cfg:InterfaceTab"+
                      "le";
                    description
                      "Configure outbound label advertisement
                      for an interface";

                    list interface {
                      xr:xr-xml-map "mpls_ldp_vrf_af_cfg:Interface";
                      xr:xr-cli-map "ldp vrf <string> address-famil"+
                        "y (ipv4)|(ipv6) label local advertise inte"+
                        "rface <interface> ";
                      key "interface-name";
                      description
                        "Control advertisement of interface's
                        host IP address";
                      leaf interface-name {
                        xr:xr-xml-map "mpls_ldp_vrf_af_cfg:Interfac"+
                          "eName";
                        type xr:Interface-name;
                        description "Name of interface";
                      }
                    }
                  }

                  container explicit-null {
                    xr:xr-xml-map "mpls_ldp_vrf_af_cfg:ExplicitNull";
                    description
                      "Configure advertisment of explicit-null
                      for connected prefixes.";
                    leaf explicit-null-type {
                      xr:xr-xml-map "mpls_ldp_vrf_af_cfg:ExplicitNu"+
                        "llType";
                      type Mpls-ldp-exp-null;
                      description "Explicit Null command variant";
                    }
                    leaf prefix-acl-name {
                      xr:xr-xml-map "mpls_ldp_vrf_af_cfg:PrefixACLN"+
                        "ame";
                      when "../explicit-null-type = 'for' or"+
                        " ../explicit-null-type = 'for-to'" {
                          description
                            "../ExplicitNullType = For or .
                            ./ExplicitNullType = ForTo";
                      }
                      type string;
                      description "Name of prefix ACL";
                    }
                    leaf peer-acl-name {
                      xr:xr-xml-map "mpls_ldp_vrf_af_cfg:PeerACLNam"+
                        "e";
                      when "../explicit-null-type = 'to' or"+
                        " ../explicit-null-type = 'for-to'" {
                          description
                            "../ExplicitNullType = To or .
                            ./ExplicitNullType = ForTo";
                      }
                      type string;
                      description "Name of peer ACL";
                    }
                  }
                  leaf disable {
                    xr:xr-xml-map "mpls_ldp_vrf_af_cfg:Disable";
                    xr:xr-cli-map "ldp vrf <string> address-family "+
                      "(ipv4)|(ipv6) label local advertise disable ";
                    type empty;
                    description "Disable label advertisement";
                  }
                }

                container allocate {
                  xr:xr-xml-map "mpls_ldp_vrf_af_cfg:Allocate";
                  description
                    "Control local label allocation for
                    prefix(es)";
                  leaf allocation-type {
                    xr:xr-xml-map "mpls_ldp_vrf_af_cfg:AllocationTy"+
                      "pe";
                    type Mpls-ldp-label-allocation;
                    description "Label allocation type";
                  }
                  leaf prefix-acl-name {
                    xr:xr-xml-map "mpls_ldp_vrf_af_cfg:PrefixACLNam"+
                      "e";
                    when "../allocation-type = 'acl'" {
                      description "../AllocationType = ACL";
                    }
                    type string;
                    description "Name of prefix ACL";
                  }
                }
                leaf implicit-null-override {
                  xr:xr-xml-map "mpls_ldp_vrf_af_cfg:ImplicitNullOv"+
                    "erride";
                  xr:xr-cli-map "ldp vrf <string> address-family (i"+
                    "pv4)|(ipv6) label local implicit-null-override"+
                    " for <string> ";
                  type string;
                  description
                    "Control use of implicit-null label for set
                    of prefix(es)";
                }
                leaf default-route {
                  xr:xr-xml-map "mpls_ldp_vrf_af_cfg:DefaultRoute";
                  xr:xr-cli-map "ldp vrf <string> address-family (i"+
                    "pv4)|(ipv6) label local default-route ";
                  type empty;
                  description
                    "Enable MPLS forwarding for default route";
                }
              }
            }
            leaf enable {
              xr:xr-xml-map "mpls_ldp_vrf_af_cfg:Enable";
              type empty;
              description "Enable Address Family";
            }
            leaf af-name {
              xr:xr-xml-map "mpls_ldp_vrf_af_cfg:AFName";
              type Mpls-ldpaf-name;
              description "Address Family name";
            }
          }
        }

        container interfaces {
          xr:xr-xml-map "mpls_ldp_vrf_if_cfg:InterfaceTable";
          description
            "MPLS LDP configuration pertaining to
            interfaces";

          list interface {
            xr:xr-xml-map "mpls_ldp_vrf_if_cfg:Interface";
            key "interface-name";
            description
              "MPLS LDP configuration for a particular
              interface";

            container afs {
              xr:xr-xml-map "mpls_ldp_vrf_if_af_cfg:AFTable";
              description
                "Address Family specific configuration for
                MPLS LDP vrf intf";

              list af {
                xr:xr-xml-map "mpls_ldp_vrf_if_af_cfg:AF";
                key "af-name";
                description
                  "Configure data for given Address Family";

                container discovery {
                  xr:xr-xml-map "mpls_ldp_vrf_if_af_cfg:Discovery";
                  description
                    "Configure interface discovery parameters";

                  container transport-address {
                    xr:xr-xml-map "mpls_ldp_vrf_if_af_cfg:Transport"+
                      "Address";
                    description
                      "MPLS LDP configuration for interface
                      discovery transportaddress.";
                    leaf address-type {
                      xr:xr-xml-map "mpls_ldp_vrf_if_af_cfg:Address"+
                        "Type";
                      type Mpls-ldp-transport-address;
                      description "Transport address option";
                    }
                    leaf address {
                      xr:xr-xml-map "mpls_ldp_vrf_if_af_cfg:Address";
                      when "../address-type = 'address'" {
                        description "../AddressType = Address";
                      }
                      type inet:ip-address-no-zone;
                      description "IP address";
                    }
                  }
                }
                leaf enable {
                  xr:xr-xml-map "mpls_ldp_vrf_if_af_cfg:Enable";
                  type empty;
                  description "Enable Address Family";
                }
                leaf af-name {
                  xr:xr-xml-map "mpls_ldp_vrf_if_af_cfg:AFName";
                  type Mpls-ldpaf-name;
                  description "Address Family name";
                }
              }
            }
            leaf enable {
              xr:xr-xml-map "mpls_ldp_vrf_if_cfg:Enable";
              type empty;
              description
                "Enable Label Distribution Protocol (LDP) on
                thisinterface";
            }
            leaf interface-name {
              xr:xr-xml-map "mpls_ldp_vrf_if_cfg:InterfaceName";
              type xr:Interface-name;
              description "Name of interface";
            }
          }
        }
        leaf enable {
          xr:xr-xml-map "mpls_ldp_vrf_cfg:Enable";
          type empty;
          description "Enable VRF";
        }
        leaf vrf-name {
          xr:xr-xml-map "mpls_ldp_common_cfg:VRFName";
          type xr:Cisco-ios-xr-string;
          description "VRF Name";
        }
      }
    }

    container global {
      xr:xr-xml-map "mpls_ldp_common_cfg:Global";
      description "Global configuration for MPLS LDP";

      container entropy-label {
        xr:xr-xml-map "mpls_ldp_gl_cfg:EntropyLabel";
        description "Configure for LDP Entropy-Label";
        leaf enable {
          xr:xr-xml-map "mpls_ldp_gl_cfg:Enable";
          xr:xr-cli-map "ldp entropy-label ";
          type empty;
          description "none";
        }
      }

      container session {
        xr:xr-xml-map "mpls_ldp_gl_cfg:Session";
        description "LDP Session parameters";

        container backoff-time {
          xr:xr-xml-map "mpls_ldp_gl_cfg:BackoffTime";
          description "Configure Session Backoff parameters";
          leaf initial-backoff-time {
            xr:xr-xml-map "mpls_ldp_gl_cfg:InitialBackoffTime";
            type uint32 {
              range "5..2147483";
            }
            units "second";
            default "15";
            description "Initial session backoff time (seconds)";
          }
          leaf max-backoff-time {
            xr:xr-xml-map "mpls_ldp_gl_cfg:MaxBackoffTime";
            type uint32 {
              range "5..2147483";
            }
            units "second";
            default "120";
            description "Maximum session backoff time (seconds)";
          }
        }
        leaf hold-time {
          xr:xr-xml-map "mpls_ldp_gl_cfg:HoldTime";
          xr:xr-cli-map "ldp session holdtime <number> ";
          type uint32 {
            range "15..65535";
          }
          units "second";
          default "180";
          description "LDP Session holdtime";
        }
      }

      container igp {
        xr:xr-xml-map "mpls_ldp_gl_cfg:IGP";
        description "LDP IGP configuration";

        container sync {
          xr:xr-xml-map "mpls_ldp_gl_cfg:Sync";
          description "LDP IGP synchronization";

          container delay {
            xr:xr-xml-map "mpls_ldp_gl_cfg:Delay";
            description "LDP IGP synchronization delay time";
            leaf on-session-up {
              xr:xr-xml-map "mpls_ldp_gl_cfg:OnSessionUp";
              xr:xr-cli-map "ldp igp sync delay on-session-up <numb"+
                "er> ";
              type uint32 {
                range "5..300";
              }
              units "second";
              description
                "Interface sync up delay after session up";
            }
            leaf on-proc-restart {
              xr:xr-xml-map "mpls_ldp_gl_cfg:OnProcRestart";
              xr:xr-cli-map "ldp igp sync delay on-proc-restart <nu"+
                "mber> ";
              type uint32 {
                range "60..600";
              }
              units "second";
              description
                "Global sync up delay to be used after
                process restart";
            }
          }
        }
      }

      container enable-logging {
        xr:xr-xml-map "mpls_ldp_gl_cfg:EnableLogging";
        description "Enable logging of events";
        leaf nsr {
          xr:xr-xml-map "mpls_ldp_gl_cfg:NSR";
          xr:xr-cli-map "ldp log nsr ";
          type empty;
          description "Enable logging of NSR events";
        }
        leaf neighbor-changes {
          xr:xr-xml-map "mpls_ldp_gl_cfg:NeighborChanges";
          xr:xr-cli-map "ldp log neighbor ";
          type empty;
          description "Enable logging of neighbor events";
        }
        leaf adjacency {
          xr:xr-xml-map "mpls_ldp_gl_cfg:Adjacency";
          xr:xr-cli-map "ldp log hello-adjacency ";
          type empty;
          description "Enable logging of adjacency events";
        }
        leaf session-protection {
          xr:xr-xml-map "mpls_ldp_gl_cfg:SessionProtection";
          xr:xr-cli-map "ldp log session-protection ";
          type empty;
          description "Enable logging of session protection events";
        }
        leaf gr-session-changes {
          xr:xr-xml-map "mpls_ldp_gl_cfg:GRSessionChanges";
          xr:xr-cli-map "ldp log graceful-restart ";
          type empty;
          description
            "Enable logging of Graceful Restart (GR) events";
        }
      }

      container signalling {
        xr:xr-xml-map "mpls_ldp_gl_cfg:Signalling";
        description "Configure LDP signalling parameters";
        leaf dscp {
          xr:xr-xml-map "mpls_ldp_gl_cfg:DSCP";
          xr:xr-cli-map "ldp signalling dscp <number> ";
          type Mpls-ldp-dscp;
          default "48";
          description "DSCP for control packets";
        }
      }

      container nsr {
        xr:xr-xml-map "mpls_ldp_gl_cfg:NSR";
        description "Configure LDP Non-Stop Routing";
        leaf enable {
          xr:xr-xml-map "mpls_ldp_gl_cfg:Enable";
          xr:xr-cli-map "ldp nsr ";
          type empty;
          description "none";
        }
      }

      container graceful-restart {
        xr:xr-xml-map "mpls_ldp_gl_cfg:GracefulRestart";
        description
          "Configuration for LDP Graceful Restart
          parameters";
        leaf reconnect-timeout {
          xr:xr-xml-map "mpls_ldp_gl_cfg:ReconnectTimeout";
          xr:xr-cli-map "ldp graceful-restart reconnect-timeout <nu"+
            "mber> ";
          type uint32 {
            range "60..1800";
          }
          units "second";
          default "120";
          description
            "Configure Graceful Restart Reconnect Timeout
            value";
        }
        leaf enable {
          xr:xr-xml-map "mpls_ldp_gl_cfg:Enable";
          xr:xr-cli-map "ldp graceful-restart ";
          type empty;
          description "none";
        }
        leaf forwarding-hold-time {
          xr:xr-xml-map "mpls_ldp_gl_cfg:ForwardingHoldTime";
          xr:xr-cli-map "ldp graceful-restart forwarding-state-hold"+
            "time <number> ";
          type uint32 {
            range "60..1800";
          }
          units "second";
          default "180";
          description "Configure Graceful Restart Session holdtime";
        }
      }

      container discovery {
        xr:xr-xml-map "mpls_ldp_gl_cfg:Discovery";
        description "Configure Discovery parameters";

        container link-hello {
          xr:xr-xml-map "mpls_ldp_gl_cfg:LinkHello";
          description "LDP Link Hellos";
          leaf interval {
            xr:xr-xml-map "mpls_ldp_gl_cfg:Interval";
            xr:xr-cli-map "ldp discovery hello interval <number> ";
            type Mpls-ldp-interval-time;
            units "second";
            default "5";
            description "Link Hello interval";
          }
          leaf hold-time {
            xr:xr-xml-map "mpls_ldp_gl_cfg:HoldTime";
            xr:xr-cli-map "ldp discovery hello holdtime <number> ";
            type Mpls-ldp-hold-time;
            units "second";
            default "15";
            description "Time (seconds) - 65535 implies infinite";
          }
        }

        container targeted-hello {
          xr:xr-xml-map "mpls_ldp_gl_cfg:TargetedHello";
          description "LDP Targeted Hellos";
          leaf interval {
            xr:xr-xml-map "mpls_ldp_gl_cfg:Interval";
            xr:xr-cli-map "ldp discovery targeted-hello interval <n"+
              "umber> ";
            type Mpls-ldp-interval-time;
            units "second";
            default "10";
            description "Targeted Hello interval";
          }
          leaf hold-time {
            xr:xr-xml-map "mpls_ldp_gl_cfg:HoldTime";
            xr:xr-cli-map "ldp discovery targeted-hello holdtime <n"+
              "umber> ";
            type Mpls-ldp-hold-time;
            units "second";
            default "90";
            description "Time (seconds) - 65535 implies infinite";
          }
        }
        leaf disable-instance-tlv {
          xr:xr-xml-map "mpls_ldp_gl_cfg:DisableInstanceTLV";
          xr:xr-cli-map "ldp discovery instance-tlv disable ";
          type empty;
          description
            "Disable transmit and receive processing for
            private Instance TLV in LDP discovery hello
            messages";
        }
        leaf disable-quick-start {
          xr:xr-xml-map "mpls_ldp_gl_cfg:DisableQuickStart";
          xr:xr-cli-map "ldp discovery quick-start disable ";
          type empty;
          description "Disable discovery's quick start mode";
        }
      }

      container mldp {
        xr:xr-xml-map "mldp_cfg:MLDP";
        description "MPLS mLDP configuration";

        container vrfs {
          xr:xr-xml-map "mldp_cfg:VRFTable";
          description
            "VRF Table attribute configuration for MPLS LDP";

          list vrf {
            xr:xr-xml-map "mldp_cfg:VRF";
            key "vrf-name";
            description "VRF attribute configuration for MPLS LDP";
            leaf vrf-name {
              xr:xr-xml-map "mldp_cfg:VRFName";
              type xr:Cisco-ios-xr-string;
              description "VRF Name";
            }
            uses AF-TABLE;
          }
        }

        container default-vrf {
          xr:xr-xml-map "mldp_cfg:DefaultVRF";
          description
            "Default VRF attribute configuration for mLDP";
          uses AF-TABLE;
        }

        container mldp-global {
          xr:xr-xml-map "mldp_cfg:MLDP_Global";
          description "Global configuration for mLDP";

          container logging {
            xr:xr-xml-map "mldp_cfg:Logging";
            description "MPLS mLDP logging";
            leaf notifications {
              xr:xr-xml-map "mldp_cfg:Notifications";
              type empty;
              description "MPLS mLDP logging notificataions";
            }
          }
        }
        leaf enable {
          xr:xr-xml-map "mldp_cfg:Enable";
          type empty;
          description
            "Enable Multicast Label Distribution Protocol
            (mLDP)";
        }
      }
      leaf disable-implicit-ipv4 {
        xr:xr-xml-map "mpls_ldp_gl_cfg:DisableImplicitIPv4";
        xr:xr-cli-map "ldp default-vrf implicit-ipv4 disable ";
        type empty;
        description
          "Disable the implicit enabling for IPv4 address
          family";
      }
      leaf ltrace-buf-multiplier {
        xr:xr-xml-map "mpls_ldp_gl_cfg:LtraceBufMultiplier";
        xr:xr-cli-map "ldp ltrace-buffer multiplier <number> ";
        type uint32 {
          range "1..5";
        }
        default "1";
        description "Configure Ltrace Buffer Multiplier";
      }
    }
    leaf enable {
      xr:xr-xml-map "mpls_ldp_common_cfg:Enable";
      type empty;
      description
        "Enable Label Distribution Protocol (LDP)
        globally.Without creating this object the LDP
        feature will not be enabled. Deleting this
        object will stop the LDP feature.";
    }
  }

  augment "/a1:snmp/a1:notification" {

    container mpls-ldp {
      xr:xr-xml-map "mpls_ldpmib_cfg:MPLS_LDP";
      description "MPLS-LDP-STD-MIB notification configuration";
      leaf session-up {
        xr:xr-xml-map "mpls_ldpmib_cfg:SessionUp";
        type empty;
        description "Enable mplsLdpSessionUp notification";
      }
      leaf init-session-threshold-exceeded {
        xr:xr-xml-map "mpls_ldpmib_cfg:InitSessionThresholdExceeded";
        type empty;
        description
          "Enable mplsLdpInitSessionThresholdExceeded
          notification";
      }
      leaf session-down {
        xr:xr-xml-map "mpls_ldpmib_cfg:SessionDown";
        type empty;
        description "Enable mplsLdpSessionDown notification";
      }
    }
    description
      "This augment extends the configuration data of
      'Cisco-IOS-XR-snmp-agent-cfg'";
  }
}
