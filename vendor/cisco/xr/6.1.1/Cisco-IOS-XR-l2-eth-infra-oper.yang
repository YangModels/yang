module Cisco-IOS-XR-l2-eth-infra-oper {

  /*** NAMESPACE / PREFIX DEFINITION ***/

  namespace "http://cisco.com/ns"+
    "/yang/Cisco-IOS-XR-l2-eth-infra-oper";


  prefix "l2-eth-infra-oper";

  /*** LINKAGE (IMPORTS / INCLUDES) ***/

  import Cisco-IOS-XR-types { prefix "xr"; }

  import Cisco-IOS-XR-l2-eth-infra-datatypes { prefix "dt1"; }

  include Cisco-IOS-XR-l2-eth-infra-oper-sub3 {
    revision-date 2015-11-09;
  }

  include Cisco-IOS-XR-l2-eth-infra-oper-sub2 {
    revision-date 2015-11-09;
  }

  include Cisco-IOS-XR-l2-eth-infra-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR l2-eth-infra package operational data.

     This module contains definitions
     for the following management objects:
       mac-accounting: MAC accounting operational data
       vlan: vlan
       ethernet-encapsulation: ethernet encapsulation

     Copyright (c) 2013-2016 by Cisco Systems, Inc.
     All rights reserved.";

  revision "2015-11-09" {
    description
      "IOS XR 6.0 revision.";
  }


  container mac-accounting {
    xr:xr-xml-map "ether_mac_acc_oper:MACAccounting";
    config false;
    description "MAC accounting operational data";

    container interfaces {
      xr:xr-xml-map "ether_mac_acc_oper:InterfaceTable";
      description
        "MAC accounting interface table in MIB
        lexicographic order";

      list interface {
        xr:xr-xml-map "ether_mac_acc_oper:Interface";
        key "interface-name";
        description
          "Operational data and statistics for an
          interface configured with MAC accounting
          enabled";
        leaf interface-name {
          xr:xr-xml-map "ether_mac_acc_oper:InterfaceName";
          type xr:Interface-name;
          description "The interface name";
        }
        uses MAC-ACC-INTF;
      }
    }
  }

  container vlan {
    xr:xr-xml-map "vlan_oper:VLAN";
    config false;
    description "vlan";

    container nodes {
      xr:xr-xml-map "vlan_oper:NodeTable";
      description "Per node VLAN operational data";

      list node {
        xr:xr-xml-map "vlan_oper:Node";
        key "node-id";
        description
          "The VLAN operational data for a particular node";

        container trunks {
          xr:xr-xml-map "vlan_oper:TrunkTable";
          description "VLAN trunk table (specific to this node)";

          list trunk {
            xr:xr-xml-map "vlan_oper:Trunk";
            key "interface";
            description
              "Operational data for trunk interfaces
              configured with VLANs";
            leaf interface {
              xr:xr-xml-map "vlan_oper:Interface";
              type xr:Interface-name;
              description "The interface name";
            }
            uses VLAN-TRUNK;
          }
        }

        container interfaces {
          xr:xr-xml-map "vlan_oper:InterfaceTable";
          description
            "VLAN interface table (specific to this node)";

          list interface {
            xr:xr-xml-map "vlan_oper:Interface";
            key "interface";
            description
              "Operational data for a sub-interface
              configured with VLANs";
            leaf interface {
              xr:xr-xml-map "vlan_oper:Interface";
              type xr:Interface-name;
              description "The interface name";
            }
            uses VLAN-INTF;
          }
        }

        container tag-allocations {
          xr:xr-xml-map "vlan_oper:TagAllocationTable";
          description
            "VLAN tag allocation table (specific to this
            node)";

          list tag-allocation {
            xr:xr-xml-map "vlan_oper:TagAllocation";
            description
              "Operational data for a sub-interface
              configured with VLANs";
            leaf interface {
              xr:xr-xml-map "vlan_oper:Interface";
              type xr:Interface-name;
              description "The interface name";
            }
            leaf first-tag {
              xr:xr-xml-map "vlan_oper:FirstTag";
              type dt1:Vlan-tag;
              description "The first (outermost) tag";
            }
            leaf second-tag {
              xr:xr-xml-map "vlan_oper:SecondTag";
              type dt1:Vlan-tag-or-any;
              description "The second tag";
            }
            uses VLAN-INTF;
          }
        }
        leaf node-id {
          xr:xr-xml-map "vlan_oper:NodeID";
          type xr:Node-id;
          description "The identifier for the node";
        }
      }
    }
  }

  container ethernet-encapsulation {
    xr:xr-xml-map "ether_caps_oper:EthernetEncapsulation";
    config false;
    description "ethernet encapsulation";

    container nodes {
      xr:xr-xml-map "ether_caps_oper:NodeTable";
      description
        "Per node Ethernet encapsulation operational data";

      list node {
        xr:xr-xml-map "ether_caps_oper:Node";
        key "node-name";
        description
          "The Ethernet encaps operational data for a
          particular node";

        container unicast-mac-filters {
          xr:xr-xml-map "ether_caps_oper:UnicastMACFilterTable";
          description
            "Unicast MAC filter table (specific to this
            node)";

          list unicast-mac-filter {
            xr:xr-xml-map "ether_caps_oper:UnicastMACFilter";
            key "interface-name";
            description
              "Operational data for interface with MAC
              filters configured";
            leaf interface-name {
              xr:xr-xml-map "ether_caps_oper:InterfaceName";
              type xr:Interface-name;
              description "The interface name";
            }
            uses ETHER-CAPS-UCAST-FILTER;
          }
        }
        leaf node-name {
          xr:xr-xml-map "ether_caps_oper:NodeName";
          type xr:Node-id;
          description "The identifier for the node";
        }
      }
    }
  }
}
