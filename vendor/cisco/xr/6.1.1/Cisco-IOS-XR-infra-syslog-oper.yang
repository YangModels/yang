module Cisco-IOS-XR-infra-syslog-oper {

  /*** NAMESPACE / PREFIX DEFINITION ***/

  namespace "http://cisco.com/ns"+
    "/yang/Cisco-IOS-XR-infra-syslog-oper";


  prefix "infra-syslog-oper";

  /*** LINKAGE (IMPORTS / INCLUDES) ***/

  import Cisco-IOS-XR-types { prefix "xr"; }

  include Cisco-IOS-XR-infra-syslog-oper-sub1 {
    revision-date 2016-06-24;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR infra-syslog package operational data.

     This module contains definitions
     for the following management objects:
       logging: Logging History data
       syslog: syslog

     Copyright (c) 2013-2016 by Cisco Systems, Inc.
     All rights reserved.";

  revision "2016-06-24" {
    description
      "Schema added for Show logging files CLI";
  }

  revision "2015-01-07" {
    description
      "IOS XR 5.3.1 revision.";
  }


  container logging {
    xr:xr-xml-map "infra_syslog_oper:Logging";
    config false;
    description "Logging History data";

    container history {
      xr:xr-xml-map "infra_syslog_oper:History";
      description "Syslog Info ";
      leaf properties {
        xr:xr-xml-map "infra_syslog_oper:Properties";
        type string;
        description "Syslog Properties";
      }
      leaf message {
        xr:xr-xml-map "infra_syslog_oper:Message";
        type string;
        description "Syslog Message";
      }
    }
  }

  container syslog {
    xr:xr-xml-map "infra_syslog_oper:Syslog";
    config false;
    description "syslog";

    container logging-files {
      xr:xr-xml-map "infra_syslog_oper:LoggingFiles";
      description "Logging Files information";
      uses FILE-LOG-LIST-PATH;
    }

    container an-remote-servers {
      xr:xr-xml-map "infra_syslog_oper:ANRemoteServers";
      description "Logging AN remote servers information";
      uses AN-REMOTE-LOG-SERVERS;
    }

    container messages {
      xr:xr-xml-map "infra_syslog_oper:MessageTable";
      description "Message table information";

      list message {
        xr:xr-xml-map "infra_syslog_oper:Message";
        key "message-id";
        description "A system message";
        leaf message-id {
          xr:xr-xml-map "infra_syslog_oper:MessageID";
          type int32;
          description "Message ID of the system message";
        }
        uses SYSTEM-MESSAGE;
      }
    }

    container logging-statistics {
      xr:xr-xml-map "infra_syslog_oper:LoggingStatistics";
      description "Logging statistics information";
      uses SYSTEM-MESSAGE-STATISTICS;
    }
  }
}
