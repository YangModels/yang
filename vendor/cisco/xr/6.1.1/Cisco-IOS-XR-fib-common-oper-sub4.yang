submodule Cisco-IOS-XR-fib-common-oper-sub4 {

  belongs-to Cisco-IOS-XR-fib-common-oper {
    prefix Cisco-IOS-XR-fib-common-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR fib-common package operational data.

     Copyright (c) 2013-2016 by Cisco Systems, Inc.
     All rights reserved.";

  revision "2015-11-09" {
    description
      "IOS XR 6.0 revision.";
  }


  grouping FIB-STATISTICS-BAG-DROPS {
    description "FIB drop statistics";
    leaf no-route-packets {
      xr:xr-xml-map "fib_statistics:NoRoutePackets";
      type uint64;
      description "no route pkt";
    }
    leaf punt-unreachable-packets {
      xr:xr-xml-map "fib_statistics:PuntUnreachablePackets";
      type uint64;
      description "Punt generate unreach pkt";
    }
    leaf df-unreachable-packets {
      xr:xr-xml-map "fib_statistics:DFUnreachablePackets";
      type uint64;
      description "DF unreachable pkt";
    }
    leaf encapsulation-failure-packets {
      xr:xr-xml-map "fib_statistics:EncapsulationFailurePackets";
      type uint64;
      description "encapsulation failure pkt";
    }
    leaf incomplete-adjacency-packets {
      xr:xr-xml-map "fib_statistics:IncompleteAdjacencyPackets";
      type uint64;
      description "incomplete adjacency pkt";
    }
    leaf unresolved-prefix-packets {
      xr:xr-xml-map "fib_statistics:UnresolvedPrefixPackets";
      type uint64;
      description "unresolved prefix pkt";
    }
    leaf unsupported-feature-packets {
      xr:xr-xml-map "fib_statistics:UnsupportedFeaturePackets";
      type uint64;
      description "unsupported feature pkt";
    }
    leaf discard-packets {
      xr:xr-xml-map "fib_statistics:DiscardPackets";
      type uint64;
      description "discard pkt";
    }
    leaf checksum-error-packets {
      xr:xr-xml-map "fib_statistics:ChecksumErrorPackets";
      type uint64;
      description "checksum error pkt";
    }
    leaf fragmenation-consumed-packets {
      xr:xr-xml-map "fib_statistics:FragmenationConsumedPackets";
      type uint64;
      description "frag consumed packet pkt";
    }
    leaf fragmenation-failure-packets {
      xr:xr-xml-map "fib_statistics:FragmenationFailurePackets";
      type uint64;
      description "fragmenation failure pkt";
    }
    leaf null-packets {
      xr:xr-xml-map "fib_statistics:NullPackets";
      type uint64;
      description "null0 pkt";
    }
    leaf rpf-check-failure-packets {
      xr:xr-xml-map "fib_statistics:RPFCheckFailurePackets";
      type uint64;
      description "RPF check failures pkt";
    }
    leaf acl-in-rpf-packets {
      xr:xr-xml-map "fib_statistics:ACLInRPFPackets";
      type uint64;
      description "ACL in RPF pkt";
    }
    leaf rp-destination-drop-packets {
      xr:xr-xml-map "fib_statistics:RPDestinationDropPackets";
      type uint64;
      description "rp dest drop pkt";
    }
    leaf total-number-of-drop-packets {
      xr:xr-xml-map "fib_statistics:TotalNumberOfDropPackets";
      type uint64;
      description "the total number of drop pkt";
    }
    leaf mpls-disabled-interface {
      xr:xr-xml-map "fib_statistics:MPLSDisabledInterface";
      type uint64;
      description "mpls disabled in interface";
    }
    leaf gre-lookup-failed-drop {
      xr:xr-xml-map "fib_statistics:GRELookupFailedDrop";
      type uint64;
      description "GRE tunnel lookup failed drop pkt";
    }
    leaf gre-error-drop {
      xr:xr-xml-map "fib_statistics:GREErrorDrop";
      type uint64;
      description "GRE processing errors";
    }
    leaf lisp-punt-drops {
      xr:xr-xml-map "fib_statistics:LISPPuntDrops";
      type uint64;
      description "LISP Punt drops";
    }
    leaf lisp-encap-error-drops {
      xr:xr-xml-map "fib_statistics:LispEncapErrorDrops";
      type uint64;
      description "Lisp encap error drops";
    }
    leaf lisp-decap-error-drops {
      xr:xr-xml-map "fib_statistics:LispDecapErrorDrops";
      type uint64;
      description "Lisp decap error drops";
    }
    leaf multi-label-drops {
      xr:xr-xml-map "fib_statistics:MultiLabelDrops";
      type uint64;
      description "Drops for the packets with multi[le labels";
    }
  }
}
