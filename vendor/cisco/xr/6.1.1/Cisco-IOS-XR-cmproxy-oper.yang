module Cisco-IOS-XR-cmproxy-oper {

  /*** NAMESPACE / PREFIX DEFINITION ***/

  namespace "http://cisco.com/ns/yang/Cisco-IOS-XR-cmproxy-oper";


  prefix "cmproxy-oper";

  /*** LINKAGE (IMPORTS / INCLUDES) ***/

  import Cisco-IOS-XR-types { prefix "xr"; }

  include Cisco-IOS-XR-cmproxy-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR cmproxy package operational data.

     This module contains definitions
     for the following management objects:
       sdr-inventory-vm: Platform VM information

     Copyright (c) 2013-2016 by Cisco Systems, Inc.
     All rights reserved.";

  revision "2015-11-09" {
    description
      "IOS XR 6.0 revision.";
  }


  container sdr-inventory-vm {
    xr:xr-xml-map "cmp_node_vm_oper:SDRInventoryVM";
    config false;
    description "Platform VM information";

    container nodes {
      xr:xr-xml-map "cmp_node_vm_oper:NodeTable";
      description "Node directory";

      list node {
        xr:xr-xml-map "cmp_node_vm_oper:Node";
        key "name";
        description "Node name";

        container node-entries {
          xr:xr-xml-map "cmp_node_vm_oper:VMInformation";
          description "VM Information";

          list node-entry {
            xr:xr-xml-map "cmp_node_vm_oper:NodeEntry";
            key "name";
            description "VM information for a node";
            leaf name {
              xr:xr-xml-map "cmp_node_vm_oper:Name";
              type xr:Cisco-ios-xr-string;
              description "Node name";
            }
            uses CMP-INV-ST;
          }
        }
        leaf name {
          xr:xr-xml-map "cmp_node_vm_oper:Name";
          type xr:Cisco-ios-xr-string;
          description "Node name";
        }
      }
    }
  }
}
