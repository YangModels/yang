submodule Cisco-IOS-XR-snmp-entitymib-oper-sub1 {

  belongs-to Cisco-IOS-XR-snmp-entitymib-oper {
    prefix Cisco-IOS-XR-snmp-entitymib-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR snmp-entitymib package operational data.

     Copyright (c) 2013-2016 by Cisco Systems, Inc.
     All rights reserved.";

  revision "2015-11-09" {
    description
      "IOS XR 6.0 revision.";
  }


  grouping ENTMIB-NODE2PATH-INFO {
    description "ENTITY-MIB Node To Path Map Record";
    leaf physical-index {
      xr:xr-xml-map "entmib_show:PhysicalIndex";
      type uint32;
      description "entPhysicalIndex";
    }
    leaf ent-physical-name {
      xr:xr-xml-map "entmib_show:EntPhysicalName";
      type string;
      description "entPhysicalName";
    }
    leaf location {
      xr:xr-xml-map "entmib_show:Location";
      type string;
      description "invmgr EDM path";
    }
    leaf ent-physical-descr {
      xr:xr-xml-map "entmib_show:EntPhysicalDescr";
      type string;
      description "EntPhysicalDescription";
    }
    leaf ent-physical-firmware-rev {
      xr:xr-xml-map "entmib_show:EntPhysicalFirmwareRev";
      type string;
      description "entphysicalFirmwareRev";
    }
    leaf ent-physical-hardware-rev {
      xr:xr-xml-map "entmib_show:EntPhysicalHardwareRev";
      type string;
      description "entphysicalHardwareRev";
    }
    leaf ent-physical-modelname {
      xr:xr-xml-map "entmib_show:EntPhysicalModelname";
      type string;
      description "entphysicalModelName";
    }
    leaf ent-physical-serial-num {
      xr:xr-xml-map "entmib_show:EntPhysicalSerialNum";
      type string;
      description "entphysicalSerialNum";
    }
    leaf ent-physical-software-rev {
      xr:xr-xml-map "entmib_show:EntPhysicalSoftwareRev";
      type string;
      description "entphysicalSoftwareRev";
    }
    leaf ent-physical-mfg-name {
      xr:xr-xml-map "entmib_show:EntPhysicalMfgName";
      type string;
      description "entphysicalMfgName";
    }
  }
}
