module Cisco-IOS-XR-pbr-cfg {

  /*** NAMESPACE / PREFIX DEFINITION ***/

  namespace "http://cisco.com/ns/yang/Cisco-IOS-XR-pbr-cfg";


  prefix "pbr-cfg";

  /*** LINKAGE (IMPORTS / INCLUDES) ***/

  import Cisco-IOS-XR-types { prefix "xr"; }

  import Cisco-IOS-XR-ifmgr-cfg { prefix "a1"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR pbr package configuration.

     This YANG module augments the
       Cisco-IOS-XR-ifmgr-cfg
     module with configuration data.

     Copyright (c) 2013-2016 by Cisco Systems, Inc.
     All rights reserved.";

  revision "2016-03-08" {
    description
      "Moved augment statement to a separate file";
  }

  revision "2015-11-09" {
    description
      "IOS XR 6.0 revision.";
  }


  augment "/a1:interface-configurations/a1:interface-configuration" {

    container pbr {
      xr:xr-xml-map "pbr_interface_cfg:PBR";
      description "Interface PBR configuration";

      container service-policy {
        xr:xr-xml-map "pbr_interface_cfg:ServicePolicy";
        description "PBR service policy configuration";
        leaf input {
          xr:xr-xml-map "pbr_interface_cfg:Input";
          type string;
          description "Ingress service policy";
        }
      }
      leaf service-policy-in {
        xr:xr-xml-map "pbr_interface_cfg:ServicePolicyIn";
        type string;
        description "Class for subscriber ingress policy";
      }
    }
    description
      "This augment extends the configuration data of
      'Cisco-IOS-XR-ifmgr-cfg'";
  }
}
