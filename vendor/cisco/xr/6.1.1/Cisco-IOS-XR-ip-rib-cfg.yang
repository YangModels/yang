module Cisco-IOS-XR-ip-rib-cfg {

  /*** NAMESPACE / PREFIX DEFINITION ***/

  namespace "http://cisco.com/ns/yang/Cisco-IOS-XR-ip-rib-cfg";


  prefix "ip-rib-cfg";

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ip-rib package configuration.

     This module contains definitions
     for the following management objects:
       rib: RIB configuration.

     Copyright (c) 2013-2016 by Cisco Systems, Inc.
     All rights reserved.";

  revision "2015-11-09" {
    description
      "IOS XR 6.0 revision.";
  }


  grouping NEXT-HOP-DAMPENING-DISABLE {
    description "Common node of ipv4, ipv6";
    leaf next-hop-dampening-disable {
      xr:xr-xml-map "ip_rib_cfg:NextHopDampeningDisable";
      type empty;
      description "Disable next-hop dampening";
    }
  }

  grouping REDISTRIBUTION-HISTORY {
    description "Common node of ipv4, ipv6";

    container redistribution-history {
      xr:xr-xml-map "ip_rib_cfg:RedistributionHistory";
      description "Redistribution history related configs";

      container keep {
        xr:xr-xml-map "ip_rib_cfg:Keep";
        description
          "Retain redistribution history after disconnect.";
        leaf bcdl {
          xr:xr-xml-map "ip_rib_cfg:BCDL";
          type empty;
          description "Enable retain BCDL history";
        }
      }
      leaf bcdl-client {
        xr:xr-xml-map "ip_rib_cfg:BCDLClient";
        type uint32 {
          range "10..2000000";
        }
        description "Maximum BCDL redistribution history size.";
      }
      leaf protocol-client {
        xr:xr-xml-map "ip_rib_cfg:ProtocolClient";
        type uint32 {
          range "10..250000";
        }
        description "Maximum protocol redistribution history size.";
      }
    }
  }

  container rib {
    xr:xr-xml-map "ip_rib_cfg:RIB";
    description "RIB configuration.";

    container af {
      xr:xr-xml-map "ip_rib_cfg:AF";
      description "RIB address family configuration";

      container ipv4 {
        xr:xr-xml-map "ip_rib_cfg:IPv4";
        description "IPv4 configuration";
        uses NEXT-HOP-DAMPENING-DISABLE;
        uses REDISTRIBUTION-HISTORY;
      }

      container ipv6 {
        xr:xr-xml-map "ip_rib_cfg:IPv6";
        description "IPv6 configuration";
        uses NEXT-HOP-DAMPENING-DISABLE;
        uses REDISTRIBUTION-HISTORY;
      }
    }
    leaf max-recursion-depth {
      xr:xr-xml-map "ip_rib_cfg:MaxRecursionDepth";
      xr:xr-cli-map "rib recursion-depth-max <number> ";
      type uint32 {
        range "5..16";
      }
      description "Set maximum depth for route recursion check";
    }
  }
}
