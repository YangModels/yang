module Cisco-IOS-XR-ipv6-ma-oper {

  /*** NAMESPACE / PREFIX DEFINITION ***/

  namespace "http://cisco.com/ns/yang/Cisco-IOS-XR-ipv6-ma-oper";


  prefix "ipv6-ma-oper";

  /*** LINKAGE (IMPORTS / INCLUDES) ***/

  import Cisco-IOS-XR-types { prefix "xr"; }

  include Cisco-IOS-XR-ipv6-ma-oper-sub1 {
    revision-date 2015-10-20;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ipv6-ma package operational data.

     This module contains definitions
     for the following management objects:
       ipv6-network: IPv6 network operational data

     Copyright (c) 2013-2016 by Cisco Systems, Inc.
     All rights reserved.";

  revision "2015-10-20" {
    description
      "IPV6 MA schema file has all the latest changes.";
  }

  revision "2015-01-07" {
    description
      "IOS XR 5.3.1 revision.";
  }


  container ipv6-network {
    xr:xr-xml-map "ipv6_ma_oper:IPV6Network";
    config false;
    description "IPv6 network operational data";

    container nodes {
      xr:xr-xml-map "ipv6_ma_oper:NodeTable";
      description "Node-specific IPv6 network operational data";

      list node {
        xr:xr-xml-map "ipv6_ma_oper:Node";
        key "node-name";
        description
          "IPv6 network operational data for a particular
          node";

        container interface-data {
          xr:xr-xml-map "ipv6_ma_oper:InterfaceData";
          description "IPv6 network operational interface data";

          container vrfs {
            xr:xr-xml-map "ipv6_ma_oper:VRFTable";
            description
              "VRF specific IPv6 network operational
              interface data";

            list vrf {
              xr:xr-xml-map "ipv6_ma_oper:VRF";
              key "vrf-name";
              description "VRF ID of an interface belong to";

              container briefs {
                xr:xr-xml-map "ipv6_ma_oper:BriefTable";
                description
                  "Brief interface IPv6 network operational
                  data for a node";

                list brief {
                  xr:xr-xml-map "ipv6_ma_oper:Brief";
                  key "interface-name";
                  description
                    "Brief interface IPv6 network operational
                    data for an interface";
                  leaf interface-name {
                    xr:xr-xml-map "ipv6_ma_oper:InterfaceName";
                    type xr:Interface-name;
                    description "The name of the interface";
                  }
                  uses IPV6-IF-BRIEF;
                }
              }

              container global-details {
                xr:xr-xml-map "ipv6_ma_oper:GlobalDetailTable";
                description
                  "Detail interface IPv4 network operational
                  data for global data";

                list global-detail {
                  xr:xr-xml-map "ipv6_ma_oper:GlobalDetail";
                  key "interface-name";
                  description
                    "Detail interface IPv6 network operational
                    data for an interface";
                  leaf interface-name {
                    xr:xr-xml-map "ipv6_ma_oper:InterfaceName";
                    type xr:Interface-name;
                    description "The name of the interface";
                  }
                  uses IPV6-IF-DETAIL;
                }
              }

              container global-briefs {
                xr:xr-xml-map "ipv6_ma_oper:GlobalBriefTable";
                description
                  "Brief interface IPv6 network operational
                  data from global data";

                list global-brief {
                  xr:xr-xml-map "ipv6_ma_oper:GlobalBrief";
                  key "interface-name";
                  description
                    "Brief interface IPv6 network operational
                    data for an interface";
                  leaf interface-name {
                    xr:xr-xml-map "ipv6_ma_oper:InterfaceName";
                    type xr:Interface-name;
                    description "The name of the interface";
                  }
                  uses IPV6-IF-BRIEF;
                }
              }

              container details {
                xr:xr-xml-map "ipv6_ma_oper:DetailTable";
                description
                  "Detail interface IPv4 network operational
                  data for a node";

                list detail {
                  xr:xr-xml-map "ipv6_ma_oper:Detail";
                  key "interface-name";
                  description
                    "Detail interface IPv6 network operational
                    data for an interface";
                  leaf interface-name {
                    xr:xr-xml-map "ipv6_ma_oper:InterfaceName";
                    type xr:Interface-name;
                    description "The name of the interface";
                  }
                  uses IPV6-IF-DETAIL;
                }
              }
              leaf vrf-name {
                xr:xr-xml-map "ipv6_ma_oper:VRFName";
                type xr:Cisco-ios-xr-string;
                description "The VRF name";
              }
            }
          }

          container summary {
            xr:xr-xml-map "ipv6_ma_oper:Summary";
            description
              "Summary of IPv6 network operational interface
              data on a node";
            uses IPV6-IF-SUMMARY;
          }
        }
        leaf node-name {
          xr:xr-xml-map "ipv6_ma_oper:NodeName";
          type xr:Node-id;
          description "The node name";
        }
      }
    }
  }
}
