submodule Cisco-IOS-XR-telemetry-model-driven-oper-sub1 {

  belongs-to Cisco-IOS-XR-telemetry-model-driven-oper {
    prefix Cisco-IOS-XR-telemetry-model-driven-oper;
  }

  /*** LINKAGE (IMPORTS / INCLUDES) ***/

  import ietf-inet-types { prefix "inet"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR telemetry-model-driven package operational data.

     Copyright (c) 2013-2016 by Cisco Systems, Inc.
     All rights reserved.";

  revision "2015-11-09" {
    description
      "IOS XR 6.0 revision.";
  }

  typedef Mdt-transport-enum {
    type enumeration {
      enum not-set {
        value 0;
        description "PROTOCOL NOT SET";
      }
      enum grpc {
        value 1;
        description "GRPC";
      }
      enum tcp {
        value 2;
        description "TCP";
      }
    }
    description "MDT Transport";
  }
  typedef Mdt-encoding-enum {
    type enumeration {
      enum not-set {
        value 0;
        description "ENCODING NOT SET";
      }
      enum gpb {
        value 2;
        description "GPB";
      }
      enum self-describing-gpb {
        value 3;
        description "SELF DESCRIBING GPB";
      }
      enum json {
        value 4;
        description "JSON";
      }
    }
    description "MDT Encoding";
  }
  typedef Mdt-in6-addr {
    type inet:ipv6-address;
    description "Mdt in6 addr";
  }
  typedef Mdt-ip {
    type enumeration {
      enum ipv4 {
        value 1;
        description "IPv4";
      }
      enum ipv6 {
        value 2;
        description "IPv6";
      }
    }
    description "IP Type";
  }

  grouping MDT-DESTINATION-GROUP {
    description "Per Destination Group information";
    leaf id {
      xr:xr-xml-map "mdt_show:Id";
      type string;
      description "Destination Group name";
    }
    leaf configured {
      xr:xr-xml-map "mdt_show:Configured";
      type uint32;
      description "Set if this is configured destination group";
    }

    list destination {
      description "list of destinations defined in this group";
      uses MDT-DESTINATION;
    }
  }

  grouping MDT-SENSOR-GROUP {
    description "Per sensor group information";
    leaf id {
      xr:xr-xml-map "mdt_show:Id";
      type string;
      description "Sensor Group name";
    }
    leaf configured {
      xr:xr-xml-map "mdt_show:Configured";
      type uint32;
      description "Set if this is configured sensor group";
    }

    list sensor-path {
      description
        "Array of information for sensor paths within
        sensor group";
      uses MDT-SENSOR-PATHS;
    }
  }

  grouping MDT-SENSOR-PROFILE {
    description "Per sensor profile information";

    container sensor-group {
      description "sensor group";
      uses MDT-SENSOR-GROUP;
    }
    leaf sample-interval {
      xr:xr-xml-map "mdt_show:SampleInterval";
      type uint32;
      description "Sample interval for the sensor group (ms)";
    }
    leaf heartbeat-interval {
      xr:xr-xml-map "mdt_show:HeartbeatInterval";
      type uint32;
      description "Heartbeat interval for the sensor group (s)";
    }
    leaf suppress-redundant {
      xr:xr-xml-map "mdt_show:SuppressRedundant";
      type boolean;
      description "Suppress Redundant";
    }
  }

  grouping MDT-SUBSCRIPTION {
    description "Per subscription group information";
    leaf id {
      xr:xr-xml-map "mdt_show:Id";
      type string;
      description "Collection Subscription name";
    }
    leaf state {
      xr:xr-xml-map "mdt_show:State";
      type boolean;
      description "Subscription state";
    }

    list sensor-profile {
      description "List of sensor groups within a subscription";
      uses MDT-SENSOR-PROFILE;
    }

    list destination-grp {
      description "Array of destinations within a subscription";
      uses MDT-DESTINATION-GROUP;
    }
  }

  grouping MDT-SUBSCRIPTION-DETAILS {
    description "Per subscription group detailed information";

    container subscription {
      description "Subscription";
      uses MDT-SUBSCRIPTION;
    }
    leaf total-num-of-packets-sent {
      xr:xr-xml-map "mdt_show:Total_Num_of_Packets_sent";
      type uint64;
      description
        "Total number of packets sent for this
        subscription";
    }
    leaf total-num-of-bytes-sent {
      xr:xr-xml-map "mdt_show:Total_Num_of_Bytes_sent";
      type uint64;
      units "byte";
      description
        "Total number of bytes sent for this subscription";
    }

    list collection-group {
      description
        "List of collection groups active for this
        subscription";
      uses MDT-COLLECTION-GROUP;
    }
  }

  grouping MDT-COLLECTION-SYSDB-GROUP {
    description "Per collection group sysdb information";
    leaf path {
      xr:xr-xml-map "mdt_show:Path";
      type string;
      description "Sysdb Path";
    }
    leaf cadence {
      xr:xr-xml-map "mdt_show:Cadence";
      type uint64;
      description "Period of the collections (ms)";
    }
    leaf total-get-count {
      xr:xr-xml-map "mdt_show:TotalGetCount";
      type uint64;
      description "Total number of gets";
    }
    leaf total-list-count {
      xr:xr-xml-map "mdt_show:TotalListCount";
      type uint64;
      description "Total number of lists";
    }
    leaf total-datalist-count {
      xr:xr-xml-map "mdt_show:TotalDatalistCount";
      type uint64;
      description "Total number of datalists";
    }
    leaf total-finddata-count {
      xr:xr-xml-map "mdt_show:TotalFinddataCount";
      type uint64;
      description "Total number of finddata";
    }
    leaf total-get-bulk-count {
      xr:xr-xml-map "mdt_show:TotalGetBulkCount";
      type uint64;
      description "Total number of get bulk";
    }
    leaf total-item-count {
      xr:xr-xml-map "mdt_show:TotalItemCount";
      type uint64;
      description "Total number of items retrived from sysdb";
    }
    leaf total-get-errors {
      xr:xr-xml-map "mdt_show:TotalGetErrors";
      type uint64;
      description "Total number of get errors";
    }
    leaf total-list-errors {
      xr:xr-xml-map "mdt_show:TotalListErrors";
      type uint64;
      description "Total number of list errors";
    }
    leaf total-datalist-errors {
      xr:xr-xml-map "mdt_show:TotalDatalistErrors";
      type uint64;
      description "Total number of datalist errors";
    }
    leaf total-finddata-errors {
      xr:xr-xml-map "mdt_show:TotalFinddataErrors";
      type uint64;
      description "Total number of finddata errors";
    }
    leaf total-get-bulk-errors {
      xr:xr-xml-map "mdt_show:TotalGetBulkErrors";
      type uint64;
      description "Total number of get bulk errors";
    }
    leaf total-encode-errors {
      xr:xr-xml-map "mdt_show:TotalEncodeErrors";
      type uint64;
      description "Total number of encode errors";
    }
    leaf total-encode-notready {
      xr:xr-xml-map "mdt_show:TotalEncodeNotready";
      type uint64;
      description "Total number of encode deferred";
    }
    leaf total-send-errors {
      xr:xr-xml-map "mdt_show:TotalSendErrors";
      type uint64;
      description "Total number of send errors";
    }
    leaf total-send-drops {
      xr:xr-xml-map "mdt_show:TotalSendDrops";
      type uint64;
      description "Total number of send channel full";
    }
    leaf total-sent-bytes {
      xr:xr-xml-map "mdt_show:TotalSentBytes";
      type uint64;
      units "byte";
      description "Total number of bytes sent";
    }
    leaf total-send-packets {
      xr:xr-xml-map "mdt_show:TotalSendPackets";
      type uint64;
      description "Total number of packets sent";
    }
    leaf total-send-bytes-dropped {
      xr:xr-xml-map "mdt_show:TotalSendBytesDropped";
      type uint64;
      units "byte";
      description "Total number of send bytes dropped";
    }
    leaf total-collections {
      xr:xr-xml-map "mdt_show:TotalCollections";
      type uint64;
      description "Completed collections count";
    }
    leaf total-collections-missed {
      xr:xr-xml-map "mdt_show:TotalCollectionsMissed";
      type uint64;
      description "Total number of collections missed";
    }
    leaf max-collection-time {
      xr:xr-xml-map "mdt_show:MaxCollectionTime";
      type uint64;
      description "Maximum time for a collection (ms)";
    }
    leaf min-collection-time {
      xr:xr-xml-map "mdt_show:MinCollectionTime";
      type uint64;
      description "Minimum time for a collection (ms)";
    }
    leaf avg-collection-time {
      xr:xr-xml-map "mdt_show:AvgCollectionTime";
      type uint64;
      description "Average time for a collection (ms)";
    }
    leaf collection-method {
      xr:xr-xml-map "mdt_show:CollectionMethod";
      type uint64;
      description "Collection method in use";
    }
  }

  grouping MDT-SENSOR-PATHS {
    description "Sensor Path information";
    leaf path {
      xr:xr-xml-map "mdt_show:Path";
      type string;
      description "Sensor Path";
    }
    leaf state {
      xr:xr-xml-map "mdt_show:State";
      type uint32;
      description "State, if sensor path is resolved or not";
    }
    leaf status-str {
      xr:xr-xml-map "mdt_show:Status_Str";
      type string;
      description
        "Error str, if there are any errors resolving the
        sensor path";
    }
  }

  grouping MDT-COLLECTION-GROUP {
    description "Per collection group information";
    leaf id {
      xr:xr-xml-map "mdt_show:Id";
      type uint64;
      description "Collection Group id";
    }
    leaf cadence {
      xr:xr-xml-map "mdt_show:Cadence";
      type uint32;
      description "Period of the collections (ms)";
    }
    leaf total-collections {
      xr:xr-xml-map "mdt_show:TotalCollections";
      type uint32;
      description "Completed collections count";
    }
    leaf encoding {
      xr:xr-xml-map "mdt_show:Encoding";
      type Mdt-encoding-enum;
      description "Destination group encoding";
    }
    leaf last-collection-start-time {
      xr:xr-xml-map "mdt_show:LastCollectionStartTime";
      type uint64;
      description "Timestamp of the start of last collection";
    }
    leaf last-collection-end-time {
      xr:xr-xml-map "mdt_show:LastCollectionEndTime";
      type uint64;
      description "Timestamp of the end of last collection";
    }
    leaf max-collection-time {
      xr:xr-xml-map "mdt_show:MaxCollectionTime";
      type uint32;
      description "Maximum time for a collection (ms)";
    }
    leaf min-collection-time {
      xr:xr-xml-map "mdt_show:MinCollectionTime";
      type uint32;
      description "Minimum time for a collection (ms)";
    }
    leaf min-total-time {
      xr:xr-xml-map "mdt_show:MinTotalTime";
      type uint32;
      description "Minimum time for all processing (ms)";
    }
    leaf max-total-time {
      xr:xr-xml-map "mdt_show:MaxTotalTime";
      type uint32;
      description "Maximum time for all processing (ms)";
    }
    leaf avg-total-time {
      xr:xr-xml-map "mdt_show:AvgTotalTime";
      type uint32;
      description "Average time for all processing (ms)";
    }
    leaf total-other-errors {
      xr:xr-xml-map "mdt_show:TotalOtherErrors";
      type uint32;
      description "Total number of errors";
    }
    leaf total-not-ready {
      xr:xr-xml-map "mdt_show:TotalNotReady";
      type uint32;
      description "Total number skipped (not ready)";
    }
    leaf total-send-errors {
      xr:xr-xml-map "mdt_show:TotalSendErrors";
      type uint32;
      description "Total number of send errors";
    }
    leaf total-send-drops {
      xr:xr-xml-map "mdt_show:TotalSendDrops";
      type uint32;
      description "Total number of send drops";
    }

    list collection-path {
      description
        "Array of information for sensor paths within
        collection group";
      uses MDT-SENSOR-PATHS;
    }

    list internal-collection-group {
      description
        "Array of information for sysdb paths within
        collection group";
      uses MDT-COLLECTION-SYSDB-GROUP;
    }
  }

  grouping MDT-DESTINATION-IP-ADDRESS {
    description "MDT DESTINATION IP ADDRESS";
    leaf ip-type {
      xr:xr-xml-map "mdt_show:IPType";
      type Mdt-ip;
      description "IPType";
    }
    leaf ipv4-address {
      xr:xr-xml-map "mdt_show:IPV4Address";
      when "../ip-type = 'ipv4'" {
        description "../IPType = 'IPV4'";
      }
      type inet:ipv4-address;
      description "IPV4 Address";
    }
    leaf ipv6-address {
      xr:xr-xml-map "mdt_show:IPV6Address";
      when "../ip-type = 'ipv6'" {
        description "../IPType = 'IPV6'";
      }
      type Mdt-in6-addr;
      description "IPV6 Address";
    }
  }

  grouping MDT-DESTINATION {
    description "Per Destination information";

    container dest-ip-address {
      description "Destination IP Address";
      uses MDT-DESTINATION-IP-ADDRESS;
    }
    leaf id {
      xr:xr-xml-map "mdt_show:Id";
      type string;
      description "Destination Id";
    }
    leaf dest-port {
      xr:xr-xml-map "mdt_show:DestPort";
      type uint16;
      description "Destination Port number";
    }
    leaf encoding {
      xr:xr-xml-map "mdt_show:Encoding";
      type Mdt-encoding-enum;
      description "Destination group encoding";
    }
    leaf transport {
      xr:xr-xml-map "mdt_show:Transport";
      type Mdt-transport-enum;
      description "Destination group transport";
    }
    leaf state {
      xr:xr-xml-map "mdt_show:State";
      type uint32;
      description "State of streaming on this destination";
    }
    leaf tls {
      xr:xr-xml-map "mdt_show:TLS";
      type uint32;
      description "TLS connection to this destination";
    }
    leaf tls-host {
      xr:xr-xml-map "mdt_show:TLSHost";
      type string;
      description "TLS Hostname of this destination";
    }
    leaf total-num-of-packets-sent {
      xr:xr-xml-map "mdt_show:Total_Num_of_Packets_sent";
      type uint64;
      description
        "Total number of packets sent for this
        destination";
    }
    leaf total-num-of-bytes-sent {
      xr:xr-xml-map "mdt_show:Total_Num_of_Bytes_sent";
      type uint64;
      units "byte";
      description "Total number of bytes sent for this destination";
    }
    leaf last-collection-time {
      xr:xr-xml-map "mdt_show:LastCollectionTime";
      type uint64;
      description "Timestamp of the last collection";
    }
  }

  grouping MDT-DESTINATION-DETAIL {
    description "Per Destination detail information";

    container destination {
      description "Destination";
      uses MDT-DESTINATION;
    }

    list collection-group {
      description
        "List of collection groups for this destination
        group";
      uses MDT-COLLECTION-GROUP;
    }
  }

  grouping MDT-DESTINATION-GROUP-DETAIL {
    description "Per Destination Group detail information";
    leaf id {
      xr:xr-xml-map "mdt_show:Id";
      type string;
      description "Destination Group name";
    }
    leaf configured {
      xr:xr-xml-map "mdt_show:Configured";
      type uint32;
      description "Set if this is configured destination group";
    }

    list destination {
      description "list of destinations defined in this group";
      uses MDT-DESTINATION-DETAIL;
    }
  }
}
