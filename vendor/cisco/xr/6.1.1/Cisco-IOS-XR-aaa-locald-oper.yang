module Cisco-IOS-XR-aaa-locald-oper {

  /*** NAMESPACE / PREFIX DEFINITION ***/

  namespace "http://cisco.com/ns/yang/Cisco-IOS-XR-aaa-locald-oper";


  prefix "aaa-locald-oper";

  /*** LINKAGE (IMPORTS / INCLUDES) ***/

  import Cisco-IOS-XR-types { prefix "xr"; }

  include Cisco-IOS-XR-aaa-locald-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR aaa-locald package operational data.

     This module contains definitions
     for the following management objects:
       aaa: AAA operational data

     Copyright (c) 2013-2016 by Cisco Systems, Inc.
     All rights reserved.";

  revision "2015-11-09" {
    description
      "IOS XR 6.0 revision.";
  }


  container aaa {
    xr:xr-xml-map "aaa_locald_oper:AAA";
    config false;
    description "AAA operational data";

    container all-tasks {
      xr:xr-xml-map "aaa_locald_oper:AllTasks";
      description "All tasks supported by system";
      uses SYSTEM-SUPPORTED-TASKS;
    }

    container currentuser-detail {
      xr:xr-xml-map "aaa_locald_oper:CurrentuserDetail";
      description "Current user specific details";
      uses REMOTEUSR-DET;
    }

    container task-map {
      xr:xr-xml-map "aaa_locald_oper:TaskMap";
      description "Task map of current user";
      uses REMOTEUSR-DET;
    }

    container taskgroups {
      xr:xr-xml-map "aaa_locald_oper:TaskgroupTable";
      description "Individual taskgroups container";

      list taskgroup {
        xr:xr-xml-map "aaa_locald_oper:Taskgroup";
        key "name";
        description "Specific Taskgroup Information";
        leaf name {
          xr:xr-xml-map "aaa_locald_oper:Name";
          type string;
          description "Taskgroup name";
        }
        uses TASKGROUP-DET;
      }
    }

    container users {
      xr:xr-xml-map "aaa_locald_oper:UserTable";
      description "Container for individual local user information";

      list user {
        xr:xr-xml-map "aaa_locald_oper:User";
        key "name";
        description "Specific local user information";
        leaf name {
          xr:xr-xml-map "aaa_locald_oper:Name";
          type string;
          description "Username";
        }
        uses USER-DET;
      }
    }

    container usergroups {
      xr:xr-xml-map "aaa_locald_oper:UsergroupTable";
      description "Container for individual usergroup Information";

      list usergroup {
        xr:xr-xml-map "aaa_locald_oper:Usergroup";
        key "name";
        description "Specific Usergroup Information";
        leaf name {
          xr:xr-xml-map "aaa_locald_oper:Name";
          type string;
          description "Usergroup name";
        }
        uses USERGROUP-DET;
      }
    }

    container authen-method {
      xr:xr-xml-map "aaa_locald_oper:AuthenMethod";
      description "Current users authentication method";
      uses REMOTEUSR-DET;
    }

    container current-usergroup {
      xr:xr-xml-map "aaa_locald_oper:CurrentUsergroup";
      description "Specific Usergroup Information";
      uses REMOTEUSR-DET;
    }
  }
}
