module Cisco-IOS-XR-ipv4-dhcpd-cfg {

  /*** NAMESPACE / PREFIX DEFINITION ***/

  namespace "http://cisco.com/ns/yang/Cisco-IOS-XR-ipv4-dhcpd-cfg";


  prefix "ipv4-dhcpd-cfg";

  /*** LINKAGE (IMPORTS / INCLUDES) ***/

  import ietf-inet-types { prefix "inet"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ipv4-dhcpd package configuration.

     This module contains definitions
     for the following management objects:
       ipv4-dhcpd: DHCP IPV4 configuration

     Copyright (c) 2013-2016 by Cisco Systems, Inc.
     All rights reserved.";

  revision "2015-11-09" {
    description
      "IOS XR 6.0 revision.";
  }

  typedef Ipv4dhcpd-giaddr-policy {
    type enumeration {
      enum keep {
        value 0;
        description "Keep";
      }
      enum replace {
        value 1;
        description "Replace";
      }
      enum drop {
        value 2;
        description "Drop";
      }
    }
    description "Ipv4dhcpd giaddr policy";
  }
  typedef Ipv4dhcpd-broadcast-flag-policy {
    type enumeration {
      enum ignore {
        value 0;
        description "Ignore";
      }
      enum check {
        value 1;
        description "check";
      }
      enum unicast-always {
        value 2;
        description "Unicast always";
      }
    }
    description "Ipv4dhcpd broadcast flag policy";
  }
  typedef Ipv4dhcpd-mode {
    type enumeration {
      enum base {
        value 0;
        description "Base";
      }
      enum relay {
        value 1;
        description "Relay";
      }
      enum snoop {
        value 2;
        description "Snoop";
      }
      enum server {
        value 3;
        description "Server";
      }
      enum proxy {
        value 4;
        description "Proxy";
      }
      enum base2 {
        value 5;
        description "Base2";
      }
    }
    description "Ipv4dhcpd mode";
  }
  typedef Ipv4dhcpd-relay-info-optionvpn-mode {
    type enumeration {
      enum rfc {
        value 0;
        description "RFC";
      }
      enum cisco {
        value 1;
        description "Cisco";
      }
    }
    description "Ipv4dhcpd relay info optionvpn mode";
  }
  typedef Ipv4dhcpd-fmt {
    type enumeration {
      enum no-format {
        value 0;
        description "Not a Format String";
      }
      enum format {
        value 1;
        description "Format String";
      }
    }
    description "Ipv4dhcpd fmt";
  }
  typedef Ipv4dhcpd-relay-info-option-policy {
    type enumeration {
      enum replace {
        value 0;
        description "Replace";
      }
      enum keep {
        value 1;
        description "Keep";
      }
      enum drop {
        value 2;
        description "Drop";
      }
      enum encapsulate {
        value 3;
        description "Encapsulate";
      }
    }
    description "Ipv4dhcpd relay info option policy";
  }
  typedef Ipv4dhcpd-fmt-specifier {
    type enumeration {
      enum physical-chassis {
        value 1;
        description "Physical chassis";
      }
      enum physical-slot {
        value 2;
        description "Physical slot";
      }
      enum physical-sub-slot {
        value 3;
        description "Physical sub-slot";
      }
      enum physical-port {
        value 4;
        description "Physical port";
      }
      enum physical-sub-port {
        value 5;
        description "Physical sub-port";
      }
      enum inner-vlan-id {
        value 6;
        description "Inner VLAN ID";
      }
      enum outer-vlan-id {
        value 7;
        description "Outer VLAN ID";
      }
      enum l2-interface {
        value 8;
        description "L2 Interface";
      }
    }
    description "Ipv4dhcpd fmt specifier";
  }

  container ipv4-dhcpd {
    xr:xr-xml-map "ipv4_dhcpd_cfg:IPV4_DHCPD";
    description "DHCP IPV4 configuration";

    container vrfs {
      xr:xr-xml-map "ipv4_dhcpd_cfg:VRFTable";
      description "VRF Table";

      list vrf {
        xr:xr-xml-map "ipv4_dhcpd_cfg:VRF";
        key "vrf-name";
        description "VRF table";

        container profile {
          xr:xr-xml-map "ipv4_dhcpd_cfg:Profile";
          presence "Indicates a profile node is configured.";
          description "Profile name and mode";
          leaf vrf-profile-name {
            xr:xr-xml-map "ipv4_dhcpd_cfg:VRFProfileName";
            type string;
            mandatory true;
            description "Profile name";
          }
          leaf mode {
            xr:xr-xml-map "ipv4_dhcpd_cfg:Mode";
            type Ipv4dhcpd-mode;
            mandatory true;
            description "Dhcp mode";
          }
        }
        leaf vrf-name {
          xr:xr-xml-map "ipv4_dhcpd_cfg:VRFName";
          type xr:Cisco-ios-xr-string;
          description "VRF Name";
        }
      }
    }

    container profiles {
      xr:xr-xml-map "ipv4_dhcpd_cfg:ProfileTable";
      description "DHCP IPV4 Profile Table";

      list profile {
        xr:xr-xml-map "ipv4_dhcpd_cfg:Profile";
        key "profile-name";
        description "DHCP IPV4 Profile";

        container modes {
          xr:xr-xml-map "ipv4_dhcpd_cfg:ModeTable";
          description "DHCP IPV4 Profile modes";

          list mode {
            xr:xr-xml-map "ipv4_dhcpd_cfg:Mode";
            key "mode";
            description "DHCP IPV4 Profile mode";

            container server {
              xr:xr-xml-map "ipv4_dhcpd_cfg:Server";
              description "DHCP Server profile";
            }

            container relay {
              xr:xr-xml-map "ipv4_dhcpd_relay_cfg:Relay";
              description "DHCP Relay profile";

              container gi-addr-policy {
                xr:xr-xml-map "ipv4_dhcpd_relay_cfg:GIADDRPolicy";
                description "GIADDR policy";
                leaf policy {
                  xr:xr-xml-map "ipv4_dhcpd_relay_cfg:Policy";
                  type Ipv4dhcpd-giaddr-policy;
                  description "GIADDR policy";
                }
              }

              container vrfs {
                xr:xr-xml-map "ipv4_dhcpd_relay_cfg:VRFTable";
                description "VRF Helper Addresses";

                list vrf {
                  xr:xr-xml-map "ipv4_dhcpd_relay_cfg:VRF";
                  key "vrf-name";
                  description "VRF Name";

                  container helper-addresses {
                    xr:xr-xml-map "ipv4_dhcpd_relay_cfg:HelperAddre"+
                      "ssTable";
                    description "Helper Addresses";

                    list helper-address {
                      xr:xr-xml-map "ipv4_dhcpd_relay_cfg:HelperAdd"+
                        "ress";
                      key "ip-address";
                      description "Helper Address";
                      leaf ip-address {
                        xr:xr-xml-map "ipv4_dhcpd_relay_cfg:IPAddre"+
                          "ss";
                        type inet:ipv4-address-no-zone;
                        description "IPV4 Address";
                      }
                      leaf enable {
                        xr:xr-xml-map "ipv4_dhcpd_relay_cfg:Enable";
                        type empty;
                        description "Enable helper - deprecated";
                      }
                      leaf gateway-address {
                        xr:xr-xml-map "ipv4_dhcpd_relay_cfg:Gateway"+
                          "Address";
                        type inet:ipv4-address-no-zone;
                        description "GatewayAddress";
                      }
                    }
                  }
                  leaf vrf-name {
                    xr:xr-xml-map "ipv4_dhcpd_relay_cfg:VRFName";
                    type xr:Cisco-ios-xr-string;
                    description "VRF Name";
                  }
                }
              }

              container relay-information-option {
                xr:xr-xml-map "ipv4_dhcpd_relay_cfg:RelayInformatio"+
                  "nOption";
                description "Relay agent information option";
                leaf vpn-mode {
                  xr:xr-xml-map "ipv4_dhcpd_relay_cfg:VPNMode";
                  type Ipv4dhcpd-relay-info-optionvpn-mode;
                  description "VPN Mode";
                }
                leaf subscriber-id {
                  xr:xr-xml-map "ipv4_dhcpd_relay_cfg:SubscriberID";
                  type string;
                  description "Subscriber ID";
                }
                leaf insert {
                  xr:xr-xml-map "ipv4_dhcpd_relay_cfg:Insert";
                  type empty;
                  description
                    "Insert Relay Agent Information circuit ID
                    and remote ID suboptions in client
                    requests";
                }
                leaf check {
                  xr:xr-xml-map "ipv4_dhcpd_relay_cfg:Check";
                  type empty;
                  description
                    "Check Relay Agent Information Option in
                    server reply";
                }
                leaf vpn {
                  xr:xr-xml-map "ipv4_dhcpd_relay_cfg:VPN";
                  type empty;
                  description "Insert VPN options";
                }
                leaf allow-untrusted {
                  xr:xr-xml-map "ipv4_dhcpd_relay_cfg:AllowUntruste"+
                    "d";
                  type empty;
                  description "Forward untrusted packets";
                }
                leaf policy {
                  xr:xr-xml-map "ipv4_dhcpd_relay_cfg:Policy";
                  type Ipv4dhcpd-relay-info-option-policy;
                  description "Relay information option policy";
                }
              }

              container broadcast-policy {
                xr:xr-xml-map "ipv4_dhcpd_relay_bflag_policy_cfg:Br"+
                  "oadcastPolicy";
                description "Broadcast Flag policy";
                leaf policy {
                  xr:xr-xml-map "ipv4_dhcpd_relay_bflag_policy_cfg:"+
                    "Policy";
                  type Ipv4dhcpd-broadcast-flag-policy;
                  description "Broadcast flag policy";
                }
              }
            }
            leaf enable {
              xr:xr-xml-map "ipv4_dhcpd_cfg:Enable";
              type empty;
              description "Enable the DHCP IPV4 Profile mode";
            }
            leaf mode {
              xr:xr-xml-map "ipv4_dhcpd_cfg:Mode";
              type Ipv4dhcpd-mode;
              description "DHCP IPV4 Profile mode";
            }
          }
        }
        leaf profile-name {
          xr:xr-xml-map "ipv4_dhcpd_cfg:ProfileName";
          type xr:Cisco-ios-xr-string;
          description "Profile Name";
        }
      }
    }

    container database {
      xr:xr-xml-map "ipv4_dhcpd_cfg:Database";
      description
        "Enable DHCP binding database storage to file
        system";
      leaf proxy {
        xr:xr-xml-map "ipv4_dhcpd_cfg:Proxy";
        type empty;
        description
          "Enable DHCP proxy binding database storage to
          file system";
      }
      leaf server {
        xr:xr-xml-map "ipv4_dhcpd_cfg:Server";
        type empty;
        description
          "Enable DHCP server binding database storage to
          file system";
      }
      leaf snoop {
        xr:xr-xml-map "ipv4_dhcpd_cfg:Snoop";
        type empty;
        description
          "Enable DHCP snoop binding database storage to
          file system";
      }
      leaf full-write-interval {
        xr:xr-xml-map "ipv4_dhcpd_cfg:FullWriteInterval";
        type uint32 {
          range "1..1440";
        }
        default "10";
        description "Full file write interval (default 10 minutes)";
      }
      leaf incremental-write-interval {
        xr:xr-xml-map "ipv4_dhcpd_cfg:IncrementalWriteInterval";
        type uint32 {
          range "1..1440";
        }
        default "1";
        description
          "Incremental file write interval (default 1
          minutes)";
      }
    }

    container interfaces {
      xr:xr-xml-map "ipv4_dhcpd_cfg:InterfaceTable";
      description "DHCP IPV4 Interface Table";

      list interface {
        xr:xr-xml-map "ipv4_dhcpd_cfg:Interface";
        key "interface-name";
        description "DHCP IPV4 Interface";

        container proxy-interface {
          xr:xr-xml-map "ipv4_dhcpd_cfg:ProxyInterface";
          description "DHCP IPv4 proxy information";

          container dhcp-circuit-id {
            xr:xr-xml-map "ipv4_dhcpd_cfg:DHCPCircuitID";
            presence "Indicates a dhcp-circuit-id node is"+
              " configured.";
            description "Circuit ID value";
            leaf circuit-id {
              xr:xr-xml-map "ipv4_dhcpd_cfg:CircuitID";
              type string;
              mandatory true;
              description "DHCP IPv4 circuit ID value";
            }
            leaf format {
              xr:xr-xml-map "ipv4_dhcpd_cfg:Format";
              type Ipv4dhcpd-fmt;
              mandatory true;
              description "Format String";
            }
            leaf argument1 {
              xr:xr-xml-map "ipv4_dhcpd_cfg:Argument1";
              type Ipv4dhcpd-fmt-specifier;
              description "Argument";
            }
            leaf argument2 {
              xr:xr-xml-map "ipv4_dhcpd_cfg:Argument2";
              type Ipv4dhcpd-fmt-specifier;
              description "Argument";
            }
            leaf argument3 {
              xr:xr-xml-map "ipv4_dhcpd_cfg:Argument3";
              type Ipv4dhcpd-fmt-specifier;
              description "Argument";
            }
            leaf argument4 {
              xr:xr-xml-map "ipv4_dhcpd_cfg:Argument4";
              type Ipv4dhcpd-fmt-specifier;
              description "Argument";
            }
            leaf argument5 {
              xr:xr-xml-map "ipv4_dhcpd_cfg:Argument5";
              type Ipv4dhcpd-fmt-specifier;
              description "Argument";
            }
            leaf argument6 {
              xr:xr-xml-map "ipv4_dhcpd_cfg:Argument6";
              type Ipv4dhcpd-fmt-specifier;
              description "Argument";
            }
            leaf argument7 {
              xr:xr-xml-map "ipv4_dhcpd_cfg:Argument7";
              type Ipv4dhcpd-fmt-specifier;
              description "Argument";
            }
            leaf argument8 {
              xr:xr-xml-map "ipv4_dhcpd_cfg:Argument8";
              type Ipv4dhcpd-fmt-specifier;
              description "Argument";
            }
            leaf argument9 {
              xr:xr-xml-map "ipv4_dhcpd_cfg:Argument9";
              type Ipv4dhcpd-fmt-specifier;
              description "Argument";
            }
            leaf argument10 {
              xr:xr-xml-map "ipv4_dhcpd_cfg:Argument10";
              type Ipv4dhcpd-fmt-specifier;
              description "Argument";
            }
            leaf argument11 {
              xr:xr-xml-map "ipv4_dhcpd_cfg:Argument11";
              type Ipv4dhcpd-fmt-specifier;
              description "Argument";
            }
            leaf argument12 {
              xr:xr-xml-map "ipv4_dhcpd_cfg:Argument12";
              type Ipv4dhcpd-fmt-specifier;
              description "Argument";
            }
            leaf argument13 {
              xr:xr-xml-map "ipv4_dhcpd_cfg:Argument13";
              type Ipv4dhcpd-fmt-specifier;
              description "Argument";
            }
            leaf argument14 {
              xr:xr-xml-map "ipv4_dhcpd_cfg:Argument14";
              type Ipv4dhcpd-fmt-specifier;
              description "Argument";
            }
            leaf argument15 {
              xr:xr-xml-map "ipv4_dhcpd_cfg:Argument15";
              type Ipv4dhcpd-fmt-specifier;
              description "Argument";
            }
            leaf argument16 {
              xr:xr-xml-map "ipv4_dhcpd_cfg:Argument16";
              type Ipv4dhcpd-fmt-specifier;
              description "Argument";
            }
          }
          leaf profile {
            xr:xr-xml-map "ipv4_dhcpd_cfg:Profile";
            type string;
            description "Interface profile name";
          }
        }

        container base-interface {
          xr:xr-xml-map "ipv4_dhcpd_cfg:BaseInterface";
          description "DHCP IPv4 Base profile information";
          leaf profile {
            xr:xr-xml-map "ipv4_dhcpd_cfg:Profile";
            type string;
            description "Interface profile name";
          }
        }

        container relay-interface {
          xr:xr-xml-map "ipv4_dhcpd_cfg:RelayInterface";
          description "DHCP IPv4 relay information";

          container relay-dhcp-circuit-id {
            xr:xr-xml-map "ipv4_dhcpd_cfg:RelayDHCPCircuitID";
            presence "Indicates a relay-dhcp-circuit-id node is"+
              " configured.";
            description "Circuit ID value";
            leaf circuit-id {
              xr:xr-xml-map "ipv4_dhcpd_cfg:CircuitID";
              type string;
              mandatory true;
              description "DHCP IPv4 circuit ID value";
            }
            leaf format {
              xr:xr-xml-map "ipv4_dhcpd_cfg:Format";
              type Ipv4dhcpd-fmt;
              mandatory true;
              description "Format String";
            }
            leaf argument1 {
              xr:xr-xml-map "ipv4_dhcpd_cfg:Argument1";
              type Ipv4dhcpd-fmt-specifier;
              description "Argument";
            }
            leaf argument2 {
              xr:xr-xml-map "ipv4_dhcpd_cfg:Argument2";
              type Ipv4dhcpd-fmt-specifier;
              description "Argument";
            }
            leaf argument3 {
              xr:xr-xml-map "ipv4_dhcpd_cfg:Argument3";
              type Ipv4dhcpd-fmt-specifier;
              description "Argument";
            }
            leaf argument4 {
              xr:xr-xml-map "ipv4_dhcpd_cfg:Argument4";
              type Ipv4dhcpd-fmt-specifier;
              description "Argument";
            }
            leaf argument5 {
              xr:xr-xml-map "ipv4_dhcpd_cfg:Argument5";
              type Ipv4dhcpd-fmt-specifier;
              description "Argument";
            }
            leaf argument6 {
              xr:xr-xml-map "ipv4_dhcpd_cfg:Argument6";
              type Ipv4dhcpd-fmt-specifier;
              description "Argument";
            }
            leaf argument7 {
              xr:xr-xml-map "ipv4_dhcpd_cfg:Argument7";
              type Ipv4dhcpd-fmt-specifier;
              description "Argument";
            }
            leaf argument8 {
              xr:xr-xml-map "ipv4_dhcpd_cfg:Argument8";
              type Ipv4dhcpd-fmt-specifier;
              description "Argument";
            }
            leaf argument9 {
              xr:xr-xml-map "ipv4_dhcpd_cfg:Argument9";
              type Ipv4dhcpd-fmt-specifier;
              description "Argument";
            }
            leaf argument10 {
              xr:xr-xml-map "ipv4_dhcpd_cfg:Argument10";
              type Ipv4dhcpd-fmt-specifier;
              description "Argument";
            }
            leaf argument11 {
              xr:xr-xml-map "ipv4_dhcpd_cfg:Argument11";
              type Ipv4dhcpd-fmt-specifier;
              description "Argument";
            }
            leaf argument12 {
              xr:xr-xml-map "ipv4_dhcpd_cfg:Argument12";
              type Ipv4dhcpd-fmt-specifier;
              description "Argument";
            }
            leaf argument13 {
              xr:xr-xml-map "ipv4_dhcpd_cfg:Argument13";
              type Ipv4dhcpd-fmt-specifier;
              description "Argument";
            }
            leaf argument14 {
              xr:xr-xml-map "ipv4_dhcpd_cfg:Argument14";
              type Ipv4dhcpd-fmt-specifier;
              description "Argument";
            }
            leaf argument15 {
              xr:xr-xml-map "ipv4_dhcpd_cfg:Argument15";
              type Ipv4dhcpd-fmt-specifier;
              description "Argument";
            }
            leaf argument16 {
              xr:xr-xml-map "ipv4_dhcpd_cfg:Argument16";
              type Ipv4dhcpd-fmt-specifier;
              description "Argument";
            }
          }
        }

        container profile {
          xr:xr-xml-map "ipv4_dhcpd_cfg:Profile";
          presence "Indicates a profile node is configured.";
          description "Profile name and mode";
          leaf profile-name {
            xr:xr-xml-map "ipv4_dhcpd_cfg:ProfileName";
            type string;
            mandatory true;
            description "Profile name";
          }
          leaf mode {
            xr:xr-xml-map "ipv4_dhcpd_cfg:Mode";
            type Ipv4dhcpd-mode;
            mandatory true;
            description "DHCP mode";
          }
        }

        container server-interface {
          xr:xr-xml-map "ipv4_dhcpd_cfg:ServerInterface";
          description "DHCP IPv4 Server information";
          leaf profile {
            xr:xr-xml-map "ipv4_dhcpd_cfg:Profile";
            type string;
            description "Interface profile name";
          }
        }

        container snoop-interface {
          xr:xr-xml-map "ipv4_dhcpd_cfg:SnoopInterface";
          description "DHCP IPv4 snoop information";

          container snoop-circuit-id {
            xr:xr-xml-map "ipv4_dhcpd_cfg:SNOOPCircuitID";
            description
              "Configure circuit ID for snoop 1. Hex 2.
              ASCII";
            leaf format-type {
              xr:xr-xml-map "ipv4_dhcpd_cfg:FormatType";
              type uint32 {
                range "1..2";
              }
              description "Format type, 1. Hex 2. ASCII";
            }
            leaf circuit-id-value {
              xr:xr-xml-map "ipv4_dhcpd_cfg:CircuitIDValue";
              type string;
              description "Enter circuit-id value";
            }
          }
        }
        leaf none {
          xr:xr-xml-map "ipv4_dhcpd_cfg:None";
          type empty;
          description "DHCP IPV4 disabled";
        }
        leaf interface-name {
          xr:xr-xml-map "ipv4_dhcpd_cfg:InterfaceName";
          type xr:Interface-name;
          description "Interface Name";
        }
      }
    }

    container duplicate-mac-allowed {
      xr:xr-xml-map "ipv4_dhcpd_cfg:duplicate-mac-allowed";
      presence "Indicates a duplicate-mac-allowed node is"+
        " configured.";
      description "Allow Duplicate MAC Address";
      leaf duplicate-mac {
        xr:xr-xml-map "ipv4_dhcpd_cfg:Duplicate-Mac";
        type empty;
        mandatory true;
        description "Duplicate mac is allowed";
      }
      leaf exclude-vlan {
        xr:xr-xml-map "ipv4_dhcpd_cfg:Exclude-vlan";
        type empty;
        description "Exclude vlan";
      }
    }

    container rate-limit {
      xr:xr-xml-map "ipv4_dhcpd_cfg:RateLimit";
      description "Rate limit ingress packets";
      leaf num-period {
        xr:xr-xml-map "ipv4_dhcpd_cfg:NumPeriod";
        type uint32 {
          range "1..1000";
        }
        default "200";
        description
          "Rate limiter period in msec (default: 200 msec)";
      }
      leaf num-discover {
        xr:xr-xml-map "ipv4_dhcpd_cfg:NumDiscover";
        type uint32 {
          range "0..1000";
        }
        default "100";
        description
          "Max DISCOVER packets per rate-limiter period
          (default 100)";
      }
    }
    leaf enable {
      xr:xr-xml-map "ipv4_dhcpd_cfg:Enable";
      type empty;
      description "DHCP IPV4 configuration";
    }
    leaf allow-client-id-change {
      xr:xr-xml-map "ipv4_dhcpd_cfg:allow-client-id-change";
      type empty;
      description
        "For BNG session, allow client id change for a
        client MAC";
    }
  }
}
