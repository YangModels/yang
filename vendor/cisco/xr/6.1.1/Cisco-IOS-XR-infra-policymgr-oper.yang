module Cisco-IOS-XR-infra-policymgr-oper {

  /*** NAMESPACE / PREFIX DEFINITION ***/

  namespace "http://cisco.com/ns/yang"+
    "/Cisco-IOS-XR-infra-policymgr-oper";


  prefix "infra-policymgr-oper";

  /*** LINKAGE (IMPORTS / INCLUDES) ***/

  import Cisco-IOS-XR-types { prefix "xr"; }

  include Cisco-IOS-XR-infra-policymgr-oper-sub2 {
    revision-date 2015-11-09;
  }

  include Cisco-IOS-XR-infra-policymgr-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR infra-policymgr package operational data.

     This module contains definitions
     for the following management objects:
       policy-manager: Policy-map operational data

     Copyright (c) 2013-2016 by Cisco Systems, Inc.
     All rights reserved.";

  revision "2015-11-09" {
    description
      "IOS XR 6.0 revision.";
  }

  typedef Policymgr-policy-map {
    type enumeration {
      enum qos {
        value 1;
        description "QoS Policymap";
      }
      enum pbr {
        value 2;
        description "PBR Policymap";
      }
      enum traffic {
        value 3;
        description "TRAFFIC Policymap";
      }
      enum subscriber-control {
        value 4;
        description "SUBSCONTROL Policymap";
      }
      enum accounting {
        value 5;
        description "ACCOUNTING Policymap";
      }
      enum redirect {
        value 6;
        description "REDIRECT Policy map";
      }
      enum flow-monitor {
        value 7;
        description "FlOWMONITOR Policy map";
      }
    }
    description "Policymgr policy map";
  }
  typedef Policymgr-class-map {
    type enumeration {
      enum qos {
        value 1;
        description "QoS Classmap";
      }
      enum pbr {
        value 2;
        description "PBR Classmap";
      }
      enum traffic {
        value 3;
        description "TRAFFIC Classmap";
      }
      enum subscriber-control {
        value 4;
        description "SUBSCONTROL Classmap";
      }
    }
    description "Policymgr class map";
  }

  grouping TARGETS {
    description "Common node of node, global";

    container target-policy-map-types {
      xr:xr-xml-map "policymgr_oper:Targets";
      description "Targets of a policymap";

      list target-policy-map-type {
        xr:xr-xml-map "policymgr_oper:TargetPolicyMapType";
        key "type";
        description "Policymgr application type";

        container policy-map-targets {
          xr:xr-xml-map "policymgr_oper:PolicyMapTargetTable";
          description "Policy-map table";

          list policy-map-target {
            xr:xr-xml-map "policymgr_oper:PolicyMapTarget";
            key "policy-map-name";
            description "Policy-map targets";
            leaf policy-map-name {
              xr:xr-xml-map "policymgr_oper:PolicyMapName";
              type string {
                length "0..63";
              }
              description "Name of policy-map";
            }
            uses PLMGR-PMAP-STR-TARGETS-BG;
          }
        }

        container policy-map-target-summary {
          xr:xr-xml-map "policymgr_oper:PolicyMapTargetSummary";
          description "Policy-map table";
          uses PLMGR-PMAP-TARGETS-SUMMARY-BG;
        }

        container target-summary-per-policy-maps {
          xr:xr-xml-map "policymgr_oper:TargetSummaryPerPolicyMapTa"+
            "ble";
          description "Policy-map table per Policy-map";

          list target-summary-per-policy-map {
            xr:xr-xml-map "policymgr_oper:TargetSummaryPerPolicyMap";
            key "policy-map-name";
            description "Policy-map targets summary";
            leaf policy-map-name {
              xr:xr-xml-map "policymgr_oper:PolicyMapName";
              type string {
                length "0..63";
              }
              description "Name of policy-map";
            }
            uses PLMGR-PMAP-TARGETS-SUMMARY-BG;
          }
        }
        leaf type {
          xr:xr-xml-map "policymgr_oper:Type";
          type Policymgr-policy-map;
          description "The application type";
        }
      }
    }
  }

  grouping CLASS-MAP {
    description "Common node of node, global";

    container class-map {
      xr:xr-xml-map "policymgr_oper:ClassMap";
      description "List of classmap details";

      container class-map-types {
        xr:xr-xml-map "policymgr_oper:ClassMapTypeTable";
        description "Application type of a classmap";

        list class-map-type {
          xr:xr-xml-map "policymgr_oper:ClassMapType";
          key "type";
          description "Policymgr application type";

          container class-map-details {
            xr:xr-xml-map "policymgr_oper:ClassMapDetailTable";
            description "Class-map detail table";

            list class-map-detail {
              xr:xr-xml-map "policymgr_oper:ClassMapDetail";
              key "class-map-name";
              description "Class-map detail information";
              leaf class-map-name {
                xr:xr-xml-map "policymgr_oper:ClassMapName";
                type string {
                  length "0..63";
                }
                description "Name of class-map";
              }
              uses PLMGR-APP-DB-BG;
            }
          }

          container class-maps {
            xr:xr-xml-map "policymgr_oper:ClassMapTable";
            description "Class-map definition table";

            list class-map {
              xr:xr-xml-map "policymgr_oper:ClassMap";
              key "class-map-name";
              description "Class-map configuration";
              leaf class-map-name {
                xr:xr-xml-map "policymgr_oper:ClassMapName";
                type string {
                  length "0..63";
                }
                description "Name of class-map";
              }
              uses CLASS-MAP-BG;
            }
          }

          container class-map-briefs {
            xr:xr-xml-map "policymgr_oper:ClassMapBriefTable";
            description "Class-map brief table";

            list class-map-brief {
              xr:xr-xml-map "policymgr_oper:ClassMapBrief";
              key "class-map-name";
              description "Class-map brief information";
              leaf class-map-name {
                xr:xr-xml-map "policymgr_oper:ClassMapName";
                type string {
                  length "0..63";
                }
                description "Name of class-map";
              }
              uses PLMGR-APP-DB-BG;
            }
          }
          leaf type {
            xr:xr-xml-map "policymgr_oper:Type";
            type Policymgr-class-map;
            description "The application type";
          }
        }
      }
    }
  }

  grouping SUMMARY {
    description "Common node of node, global";

    container summary {
      xr:xr-xml-map "policymgr_oper:Summary";
      description
        "Summary of policy-maps and class-maps configured";
      uses PLMGR-SUMMARY-BG;
    }
  }

  grouping POLICY-MAP {
    description "Common node of node, global";

    container policy-map {
      xr:xr-xml-map "policymgr_oper:PolicyMap";
      description "List of policymap details";

      container transient-policy-map-type-xr {
        xr:xr-xml-map "policymgr_oper:TransientPolicyMapTypeTable";
        description "Application type of transient policy-map";

        list transient-policy-map-type {
          xr:xr-xml-map "policymgr_oper:TransientPolicyMapTypes";
          key "type";
          description "Transient policy-map type";

          container transient-policy-map-names {
            xr:xr-xml-map "policymgr_oper:TransientPolicyDefinition"+
              "Table";
            description "Transient policy-map definition table";

            list transient-policy-map-name {
              xr:xr-xml-map "policymgr_oper:TransientPolicyMapName";
              key "policy-map-name";
              description "Transient policy-map definition table";

              container class-handles {
                xr:xr-xml-map "policymgr_oper:TransientPolicyClassH"+
                  "andleTable";
                description
                  "Transient policy-map class handle table";

                list class-handle {
                  xr:xr-xml-map "policymgr_oper:ClassHandle";
                  key "inline-classhandle";
                  description "Transient policy-map class handle";
                  leaf inline-classhandle {
                    xr:xr-xml-map "policymgr_oper:InlineClasshandle";
                    type int32;
                    description "inline class handle";
                  }
                  uses POLICY-MAP-BG;
                }
              }

              container class-seq-nums {
                xr:xr-xml-map "policymgr_oper:TransientPolicyClassS"+
                  "eqNumTable";
                description
                  "Transient policy-map sequence number table";

                list class-seq-num {
                  xr:xr-xml-map "policymgr_oper:ClassSeqNum";
                  key "sequence-num";
                  description
                    "Transient policy-map sequence number";
                  leaf sequence-num {
                    xr:xr-xml-map "policymgr_oper:SequenceNum";
                    type int32;
                    description "sequence number";
                  }
                  uses POLICY-MAP-BG;
                }
              }

              container definition {
                xr:xr-xml-map "policymgr_oper:Definition";
                description "Transient Policy-map type name";
                uses POLICY-MAP-BG;
              }
              leaf policy-map-name {
                xr:xr-xml-map "policymgr_oper:PolicyMapName";
                type string {
                  length "0..63";
                }
                description "Name of policy-map";
              }
            }
          }
          leaf type {
            xr:xr-xml-map "policymgr_oper:Type";
            type Policymgr-policy-map;
            description "The application type";
          }
        }
      }

      container policy-map-unused-types {
        xr:xr-xml-map "policymgr_oper:PolicyMapUnusedTable";
        description "Policy-map unused table";

        list policy-map-unused-type {
          xr:xr-xml-map "policymgr_oper:PolicyMapUnusedType";
          key "type";
          description "Policy-map unused";

          container unuseds {
            xr:xr-xml-map "policymgr_oper:PolicyMapUnused";
            description "Policy-map unused";

            list unused {
              xr:xr-xml-map "policymgr_oper:Unused";
              key "policy-map-name";
              description "Policy-map unused information";
              leaf policy-map-name {
                xr:xr-xml-map "policymgr_oper:PolicyMapName";
                type string {
                  length "0..63";
                }
                description "Name of policy-map";
              }
              uses PLMGR-APP-DB-BG;
            }
          }
          leaf type {
            xr:xr-xml-map "policymgr_oper:Type";
            type Policymgr-policy-map;
            description "The application type";
          }
        }
      }

      container transient-p-map-app-type-tables {
        xr:xr-xml-map "policymgr_oper:TransientPMapNameTypeTable";
        description
          "Application type of transient pmap-name type
          table";

        list transient-p-map-app-type-table {
          xr:xr-xml-map "policymgr_oper:TransientPMapAppTypeTable";
          key "type";
          description "Transient Policy Map application type";

          container transient-p-map-names {
            xr:xr-xml-map "policymgr_oper:TransientPMapNameTable";
            description "Transient pmap-name table";

            list transient-p-map-name {
              xr:xr-xml-map "policymgr_oper:TransientPMapName";
              key "policy-map-name";
              description "Policy-map configuration";
              leaf policy-map-name {
                xr:xr-xml-map "policymgr_oper:PolicyMapName";
                type string {
                  length "0..63";
                }
                description "Name of policy-map";
              }
              uses POLICY-MAP-BG;
            }
          }
          leaf type {
            xr:xr-xml-map "policymgr_oper:Type";
            type Policymgr-policy-map;
            description "The application type";
          }
        }
      }

      container policy-map-types {
        xr:xr-xml-map "policymgr_oper:PolicyMapTypeTable";
        description "Application type of a policymap";

        list policy-map-type {
          xr:xr-xml-map "policymgr_oper:PolicyMapType";
          key "type";
          description "Policymgr application type";

          container policy-maps {
            xr:xr-xml-map "policymgr_oper:PolicyMapTable";
            description "Policy-map definition table";

            list policy-map {
              xr:xr-xml-map "policymgr_oper:PolicyMap";
              key "policy-map-name";
              description "Policy-map configuration";
              leaf policy-map-name {
                xr:xr-xml-map "policymgr_oper:PolicyMapName";
                type string {
                  length "0..63";
                }
                description "Name of policy-map";
              }
              uses POLICY-MAP-BG;
            }
          }

          container policy-map-details {
            xr:xr-xml-map "policymgr_oper:PolicyMapDetailTable";
            description "Policy-map table";

            list policy-map-detail {
              xr:xr-xml-map "policymgr_oper:PolicyMapDetail";
              key "policy-map-name";
              description "Policy-map detail information";
              leaf policy-map-name {
                xr:xr-xml-map "policymgr_oper:PolicyMapName";
                type string {
                  length "0..63";
                }
                description "Name of policy-map";
              }
              uses PLMGR-APP-DB-BG;
            }
          }
          leaf type {
            xr:xr-xml-map "policymgr_oper:Type";
            type Policymgr-policy-map;
            description "The application type";
          }
        }
      }

      container transient-policy-map-types {
        xr:xr-xml-map "policymgr_oper:TransientPolicyMapListTable";
        description "Application type of transient policy-map list";

        list transient-policy-map-type {
          xr:xr-xml-map "policymgr_oper:TransientPolicyMapType";
          key "type";
          description "Transient policy-map type";

          container transient-list-unuseds {
            xr:xr-xml-map "policymgr_oper:TransientListUnusedTable";
            description "Transient policy-map list unused table";

            list transient-list-unused {
              xr:xr-xml-map "policymgr_oper:TransientListUnused";
              key "policy-map-name";
              description "Policy-map list unused";
              leaf policy-map-name {
                xr:xr-xml-map "policymgr_oper:PolicyMapName";
                type string {
                  length "0..63";
                }
                description "Name of policy-map";
              }
              uses PLMGR-APP-DB-BG;
            }
          }
          leaf type {
            xr:xr-xml-map "policymgr_oper:Type";
            type Policymgr-policy-map;
            description "The application type";
          }
        }
      }
    }
  }

  grouping DETAIL {
    description "Common node of transient-input, transient-output";

    container detail {
      xr:xr-xml-map "policymgr_oper:Detail";
      description "Policy map";
      uses POLICY-MAP-APPLIED-SHOW-BG;
    }
  }

  grouping POLICYMGR-OPER-DETAIL {
    description
      "Common node of transient-input,
      transient-outputCommon node of output, input";

    container detail {
      xr:xr-xml-map "policymgr_oper:Detail";
      description "WORD interface name";
      uses POLICY-MAP-APPLIED-SHOW-BG;
    }
  }

  container policy-manager {
    xr:xr-xml-map "policymgr_oper:PolicyManager";
    config false;
    description "Policy-map operational data";

    container global {
      xr:xr-xml-map "policymgr_oper:Global";
      description "Global QOS operational data";

      container policy-map-applied-types {
        xr:xr-xml-map "policymgr_oper:Applied";
        description "List of Applied policymap details";

        list policy-map-applied-type {
          xr:xr-xml-map "policymgr_oper:PolicyMapAppliedType";
          key "type";
          description "Policymgr application type";

          container if-names {
            xr:xr-xml-map "policymgr_oper:IfNameTable";
            description "Interface table";

            list if-name {
              xr:xr-xml-map "policymgr_oper:IfName";
              key "interface-name";
              description "WORD interface name";

              container input {
                xr:xr-xml-map "policymgr_oper:Input";
                description "Input direction table";
                uses POLICYMGR-OPER-DETAIL;
              }

              container output {
                xr:xr-xml-map "policymgr_oper:Output";
                description "Output direction table";
                uses POLICYMGR-OPER-DETAIL;
              }
              leaf interface-name {
                xr:xr-xml-map "policymgr_oper:InterfaceName";
                type xr:Interface-name;
                description "Name of the interface";
              }
            }
          }
          leaf type {
            xr:xr-xml-map "policymgr_oper:Type";
            type Policymgr-policy-map;
            description "The application type";
          }
        }
      }

      container transient-policy-map-targets-types {
        xr:xr-xml-map "policymgr_oper:TransientTargets";
        description "Transient policy-map target table";

        list transient-policy-map-targets-type {
          xr:xr-xml-map "policymgr_oper:TransientPolicyMapTargetsTy"+
            "pe";
          key "type";
          description "Transient Policymgr application type";

          container transient-target-summary-per-policy-maps {
            xr:xr-xml-map "policymgr_oper:TransientTargetSummaryPer"+
              "PolicyMapTable";
            description "Transient Policy-map table per Policy-map";

            list transient-target-summary-per-policy-map {
              xr:xr-xml-map "policymgr_oper:TransientTargetSummaryP"+
                "erPolicyMap";
              key "policy-map-name";
              description "Policy-map targets summary";
              leaf policy-map-name {
                xr:xr-xml-map "policymgr_oper:PolicyMapName";
                type string {
                  length "0..63";
                }
                description "Name of policy-map";
              }
              uses PLMGR-PMAP-TARGETS-SUMMARY-BG;
            }
          }

          container transient-policy-map-target-summary {
            xr:xr-xml-map "policymgr_oper:TransientPolicyMapTargetS"+
              "ummary";
            description "Transient Policy-map table";
            uses PLMGR-PMAP-TARGETS-SUMMARY-BG;
          }

          container transient-policy-map-targets {
            xr:xr-xml-map "policymgr_oper:TransientPolicyMapTargetT"+
              "able";
            description "Transient Policy-map table";

            list transient-policy-map-target {
              xr:xr-xml-map "policymgr_oper:TransientPolicyMapTarge"+
                "t";
              key "policy-map-name";
              description "Transient Policy-map targets";
              leaf policy-map-name {
                xr:xr-xml-map "policymgr_oper:PolicyMapName";
                type string {
                  length "0..63";
                }
                description "Name of policy-map";
              }
              uses PLMGR-PMAP-STR-TARGETS-BG;
            }
          }
          leaf type {
            xr:xr-xml-map "policymgr_oper:Type";
            type Policymgr-policy-map;
            description "The application type";
          }
        }
      }

      container transient-policy-map-applied-types {
        xr:xr-xml-map "policymgr_oper:TransientApplied";
        description "Transient policy-map applied type";

        list transient-policy-map-applied-type {
          xr:xr-xml-map "policymgr_oper:TransientPolicyMapAppliedTy"+
            "pe";
          key "type";
          description "Transient policy-map applied type";

          container transient-interface-names {
            xr:xr-xml-map "policymgr_oper:TransientInterfaceTable";
            description "Interface table";

            list transient-interface-name {
              xr:xr-xml-map "policymgr_oper:TransientInterfaceName";
              key "interface-name";
              description "WORD interface name";

              container transient-output {
                xr:xr-xml-map "policymgr_oper:TransientOutput";
                description "Output direction table";
                uses DETAIL;
              }

              container transient-input {
                xr:xr-xml-map "policymgr_oper:TransientInput";
                description "Input direction table";
                uses DETAIL;
              }
              leaf interface-name {
                xr:xr-xml-map "policymgr_oper:InterfaceName";
                type xr:Interface-name;
                description "Name of the interface";
              }
            }
          }
          leaf type {
            xr:xr-xml-map "policymgr_oper:Type";
            type Policymgr-policy-map;
            description "The application type";
          }
        }
      }
      uses TARGETS;
      uses CLASS-MAP;
      uses POLICY-MAP;
      uses SUMMARY;
    }

    container nodes {
      xr:xr-xml-map "policymgr_oper:NodeTable";
      description "Node-specific Policymgr operational data";

      list node {
        xr:xr-xml-map "policymgr_oper:Node";
        key "node-name";
        description
          "Policymgr operational data for a particular
          node";
        leaf node-name {
          xr:xr-xml-map "policymgr_oper:NodeName";
          type xr:Node-id;
          description "Node name";
        }
        uses TARGETS;
        uses CLASS-MAP;
        uses POLICY-MAP;
        uses SUMMARY;
      }
    }
  }
}
