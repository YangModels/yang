module Cisco-IOS-XR-iedge4710-oper {

  /*** NAMESPACE / PREFIX DEFINITION ***/

  namespace "http://cisco.com/ns/yang/Cisco-IOS-XR-iedge4710-oper";


  prefix "iedge4710-oper";

  /*** LINKAGE (IMPORTS / INCLUDES) ***/

  import ietf-inet-types { prefix "inet"; }

  import ietf-yang-types { prefix "yang"; }

  import Cisco-IOS-XR-types { prefix "xr"; }

  include Cisco-IOS-XR-iedge4710-oper-sub3 {
    revision-date 2015-11-09;
  }

  include Cisco-IOS-XR-iedge4710-oper-sub2 {
    revision-date 2015-11-09;
  }

  include Cisco-IOS-XR-iedge4710-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR iedge4710 package operational data.

     This module contains definitions
     for the following management objects:
       subscriber: Subscriber operational data
       iedge-license-manager: iedge license manager

     Copyright (c) 2013-2016 by Cisco Systems, Inc.
     All rights reserved.";

  revision "2015-11-09" {
    description
      "IOS XR 6.0 revision.";
  }

  typedef Subscriber-author-state-filter-flag {
    type enumeration {
      enum un-authorized {
        value 0;
        description "UnAuthorized";
      }
      enum authorized {
        value 1;
        description "Authorized";
      }
    }
    description "Subscriber author state filter flag";
  }
  typedef Subscriber-address-family-filter-flag {
    type enumeration {
      enum ipv4-only {
        value 0;
        description "IPv4 only";
      }
      enum ipv6-only {
        value 1;
        description "IPv6 only";
      }
      enum ipv4-all {
        value 2;
        description "IPv4 all";
      }
      enum ipv6-all {
        value 3;
        description "IPv6 all";
      }
      enum dual-all {
        value 4;
        description "Dual all";
      }
      enum dual-part-up {
        value 5;
        description "Dual part up";
      }
      enum dual-up {
        value 6;
        description "Dual up";
      }
      enum lac {
        value 7;
        description "LAC";
      }
    }
    description "Subscriber address family filter flag";
  }
  typedef Subscriber-state-filter-flag {
    type enumeration {
      enum initializing {
        value 0;
        description "Initializing";
      }
      enum connecting {
        value 1;
        description "Connecting";
      }
      enum connected {
        value 2;
        description "Connected";
      }
      enum activated {
        value 3;
        description "Activated";
      }
      enum idle {
        value 4;
        description "Idle";
      }
      enum disconnecting {
        value 5;
        description "Disconnecting";
      }
      enum end {
        value 6;
        description "End";
      }
    }
    description "Subscriber state filter flag";
  }
  typedef Subscriber-authen-state-filter-flag {
    type enumeration {
      enum un-authenticated {
        value 0;
        description "UnAuthenticated";
      }
      enum authenticated {
        value 1;
        description "Authenticated";
      }
    }
    description "Subscriber authen state filter flag";
  }

  container subscriber {
    xr:xr-xml-map "iedge_base_oper:Subscriber";
    config false;
    description "Subscriber operational data";

    container manager {
      xr:xr-xml-map "iedge_manager_oper:Manager";
      description "Subscriber manager operational data";

      container nodes {
        xr:xr-xml-map "iedge_manager_oper:NodeTable";
        description "Subscriber manager list of nodes";

        list node {
          xr:xr-xml-map "iedge_manager_oper:Node";
          key "node-name";
          description
            "Subscriber manager operational data for a
            particular node";

          container statistics {
            xr:xr-xml-map "iedge_manager_oper:Statistics";
            description "Subscriber manager statistics";

            container aaa {
              xr:xr-xml-map "iedge_manager_oper:AAA";
              description "AAA statistics";

              container aggregate-accounting {
                xr:xr-xml-map "iedge_manager_oper:AggregateAccounti"+
                  "ng";
                description "Aggregate accounting statistics";
                uses IEDGE-STATS-COORD-ACCT-DATA;
              }

              container authentication {
                xr:xr-xml-map "iedge_manager_oper:Authentication";
                description "Authentication statistics";
                uses IEDGE-STATS-COORD-AUTH-DATA;
              }

              container aggregate-mobility {
                xr:xr-xml-map "iedge_manager_oper:AggregateMobility";
                description "Aggregate mobility statistics";
                uses IEDGE-STATS-MOB-DATA;
              }

              container aggregate-authentication {
                xr:xr-xml-map "iedge_manager_oper:AggregateAuthenti"+
                  "cation";
                description "Aggregate authentication statistics";
                uses IEDGE-STATS-COORD-AUTH-DATA;
              }

              container change-of-authorization {
                xr:xr-xml-map "iedge_manager_oper:ChangeOfAuthoriza"+
                  "tion";
                description
                  "Change of authorization (COA) statistics";
                uses IEDGE-STATS-CH-DATA;
              }

              container authorization {
                xr:xr-xml-map "iedge_manager_oper:Authorization";
                description "Authorization statistics";
                uses IEDGE-STATS-COORD-AUTH-DATA;
              }

              container aggregate-authorization {
                xr:xr-xml-map "iedge_manager_oper:AggregateAuthoriz"+
                  "ation";
                description "Aggregate authorization statistics";
                uses IEDGE-STATS-COORD-AUTH-DATA;
              }

              container accounting {
                xr:xr-xml-map "iedge_manager_oper:Accounting";
                description "Accounting statistics";
                uses IEDGE-STATS-COORD-ACCT-DATA;
              }

              container mobility {
                xr:xr-xml-map "iedge_manager_oper:Mobility";
                description "Mobility statistics";
                uses IEDGE-STATS-MOB-DATA;
              }

              container aggregate-change-of-authorization {
                xr:xr-xml-map "iedge_manager_oper:AggregateChangeOf"+
                  "Authorization";
                description
                  "Aggregate change of authorization (COA)
                  statistics";
                uses IEDGE-STATS-CH-DATA;
              }
            }

            container aggregate-summary {
              xr:xr-xml-map "iedge_manager_oper:AggregateSummary";
              description "Aggregate summary of statistics";
              uses IEDGE-STATS-SUMMARY-DATA;
            }

            container srg {
              xr:xr-xml-map "iedge_manager_oper:SRG";
              description "Geo Redundancy statistics";
              uses IEDGE-STATS-SRG-DATA;
            }
          }
          leaf node-name {
            xr:xr-xml-map "iedge_manager_oper:NodeName";
            type xr:Node-id;
            description "Node name";
          }
        }
      }
    }

    container session {
      xr:xr-xml-map "iedge_session_oper:Session";
      description "Subscriber session operational data";

      container nodes {
        xr:xr-xml-map "iedge_session_oper:NodeTable";
        description "List of subscriber session supported nodes";

        list node {
          xr:xr-xml-map "iedge_session_oper:Node";
          key "node-name";
          description
            "Subscriber session operational data for a
            particular node";

          container author-summaries {
            xr:xr-xml-map "iedge_session_oper:AuthorSummaryTable";
            description
              "Summary information filtered by authorization
              state";

            list author-summary {
              xr:xr-xml-map "iedge_session_oper:AuthorSummary";
              key "author-state";
              description "authorization summary";
              leaf author-state {
                xr:xr-xml-map "iedge_session_oper:AuthorState";
                type Subscriber-author-state-filter-flag;
                description "Authorization state";
              }
              uses SUBSCRIBER-SESSION-SUMMARY;
            }
          }

          container summary {
            xr:xr-xml-map "iedge_session_oper:Summary";
            description "Subscriber session summary information";
            uses SUBSCRIBER-SESSION-SUMMARY;
          }

          container mac-summaries {
            xr:xr-xml-map "iedge_session_oper:MACSummaryTable";
            description
              "Summary information filtered by MAC address";

            list mac-summary {
              xr:xr-xml-map "iedge_session_oper:MACSummary";
              key "mac-address";
              description "MAC address summary";
              leaf mac-address {
                xr:xr-xml-map "iedge_session_oper:MACAddress";
                type yang:mac-address;
                description "Subscriber MAC address";
              }
              uses SUBSCRIBER-SESSION-SUMMARY;
            }
          }

          container interface-summaries {
            xr:xr-xml-map "iedge_session_oper:InterfaceSummaryTable";
            description "Summary information filtered by interface";

            list interface-summary {
              xr:xr-xml-map "iedge_session_oper:InterfaceSummary";
              key "interface-name";
              description "Interface summary";
              leaf interface-name {
                xr:xr-xml-map "iedge_session_oper:InterfaceName";
                type xr:Interface-name;
                description "Interface name";
              }
              uses SUBSCRIBER-SESSION-SUMMARY;
            }
          }

          container authentication-summaries {
            xr:xr-xml-map "iedge_session_oper:AuthenticationSummary"+
              "Table";
            description
              "Summary information filtered by
              authentication state";

            list authentication-summary {
              xr:xr-xml-map "iedge_session_oper:AuthenticationSumma"+
                "ry";
              key "authentication-state";
              description "authentication summary";
              leaf authentication-state {
                xr:xr-xml-map "iedge_session_oper:AuthenticationSta"+
                  "te";
                type Subscriber-authen-state-filter-flag;
                description "Authentication state";
              }
              uses SUBSCRIBER-SESSION-SUMMARY;
            }
          }

          container state-summaries {
            xr:xr-xml-map "iedge_session_oper:StateSummaryTable";
            description
              "Summary information filtered by session state";

            list state-summary {
              xr:xr-xml-map "iedge_session_oper:StateSummary";
              key "state";
              description "State summary";
              leaf state {
                xr:xr-xml-map "iedge_session_oper:State";
                type Subscriber-state-filter-flag;
                description "Subscriber state";
              }
              uses SUBSCRIBER-SESSION-SUMMARY;
            }
          }

          container ipv4-address-vrf-summaries {
            xr:xr-xml-map "iedge_session_oper:IPv4AddressVRFSummary"+
              "Table";
            description
              "Summary information filtered by IPv4 address
              and VRF";

            list ipv4-address-vrf-summary {
              xr:xr-xml-map "iedge_session_oper:IPv4AddressVRFSumma"+
                "ry";
              description "IPv4 address and VRF summary";
              leaf vrf-name {
                xr:xr-xml-map "iedge_session_oper:VRFName";
                type xr:Cisco-ios-xr-string;
                description "VRF name";
              }
              leaf address {
                xr:xr-xml-map "iedge_session_oper:Address";
                type inet:ipv4-address-no-zone;
                description "Subscriber IPv4 address";
              }
              uses SUBSCRIBER-SESSION-SUMMARY;
            }
          }

          container address-family-summaries {
            xr:xr-xml-map "iedge_session_oper:AddressFamilySummaryT"+
              "able";
            description
              "Summary information filtered by address
              family";

            list address-family-summary {
              xr:xr-xml-map "iedge_session_oper:AddressFamilySummar"+
                "y";
              key "address-family";
              description "Address family summary";
              leaf address-family {
                xr:xr-xml-map "iedge_session_oper:AddressFamily";
                type Subscriber-address-family-filter-flag;
                description "Address family";
              }
              uses SUBSCRIBER-SESSION-SUMMARY;
            }
          }

          container username-summaries {
            xr:xr-xml-map "iedge_session_oper:UsernameSummaryTable";
            description "Summary information filtered by username";

            list username-summary {
              xr:xr-xml-map "iedge_session_oper:UsernameSummary";
              key "username";
              description "Username summary";
              leaf username {
                xr:xr-xml-map "iedge_session_oper:Username";
                type xr:Cisco-ios-xr-string;
                description "Subscriber username";
              }
              uses SUBSCRIBER-SESSION-SUMMARY;
            }
          }

          container access-interface-summaries {
            xr:xr-xml-map "iedge_session_oper:AccessInterfaceSummar"+
              "yTable";
            description
              "Summary information filtered by access
              interface";

            list access-interface-summary {
              xr:xr-xml-map "iedge_session_oper:AccessInterfaceSumm"+
                "ary";
              key "interface-name";
              description "Access interface summary";
              leaf interface-name {
                xr:xr-xml-map "iedge_session_oper:InterfaceName";
                type xr:Interface-name;
                description "Interface name";
              }
              uses SUBSCRIBER-SESSION-SUMMARY;
            }
          }

          container ipv4-address-summaries {
            xr:xr-xml-map "iedge_session_oper:IPv4AddressSummaryTab"+
              "le";
            description
              "Summary information filtered by subscriber
              IPv4 address";

            list ipv4-address-summary {
              xr:xr-xml-map "iedge_session_oper:IPv4AddressSummary";
              key "address";
              description "IPv4 address summary";
              leaf address {
                xr:xr-xml-map "iedge_session_oper:Address";
                type inet:ipv4-address-no-zone;
                description "Subscriber IPv4 address";
              }
              uses SUBSCRIBER-SESSION-SUMMARY;
            }
          }

          container vrf-summaries {
            xr:xr-xml-map "iedge_session_oper:VRFSummaryTable";
            description "Summary information filtered by VRF";

            list vrf-summary {
              xr:xr-xml-map "iedge_session_oper:VRFSummary";
              key "vrf-name";
              description "VRF summary";
              leaf vrf-name {
                xr:xr-xml-map "iedge_session_oper:VRFName";
                type xr:Cisco-ios-xr-string;
                description "VRF name";
              }
              uses SUBSCRIBER-SESSION-SUMMARY;
            }
          }

          container sessions {
            xr:xr-xml-map "iedge_session_oper:SessionTable";
            description "IP subscriber sessions";

            list session {
              xr:xr-xml-map "iedge_session_oper:Session";
              key "session-id";
              description "Subscriber session information";
              leaf session-id {
                xr:xr-xml-map "iedge_session_oper:SessionID";
                type xr:Hex-integer;
                description "Session ID";
              }
              uses SUBSCRIBER-SESSION-DATA;
            }
          }
          leaf node-name {
            xr:xr-xml-map "iedge_session_oper:NodeName";
            type xr:Node-id;
            description "Node name";
          }
        }
      }
    }
  }

  container iedge-license-manager {
    xr:xr-xml-map "islm_show:iEdgeLicenseManager";
    config false;
    description "iedge license manager";

    container nodes {
      xr:xr-xml-map "islm_show:NodeTable";
      description
        "Session License Manager operational data for a
        location";

      list node {
        xr:xr-xml-map "islm_show:Node";
        key "nodeid";
        description "Location. For example, 0/1/CPU0";

        container iedge-license-manager-summary {
          xr:xr-xml-map "islm_show:iEdgeLicenseManagerSummary";
          description
            "Display Session License Manager summary data";
          uses ISLM-SUMMARY-DATA;
        }
        leaf nodeid {
          xr:xr-xml-map "islm_show:nodeid";
          type xr:Node-id;
          description
            "The node id to filter on. For example,
            0/1/CPU0";
        }
      }
    }
  }
}
