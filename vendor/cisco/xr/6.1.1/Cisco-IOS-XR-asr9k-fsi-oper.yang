module Cisco-IOS-XR-asr9k-fsi-oper {

  /*** NAMESPACE / PREFIX DEFINITION ***/

  namespace "http://cisco.com/ns/yang/Cisco-IOS-XR-asr9k-fsi-oper";


  prefix "asr9k-fsi-oper";

  /*** LINKAGE (IMPORTS / INCLUDES) ***/

  import Cisco-IOS-XR-types { prefix "xr"; }

  include Cisco-IOS-XR-asr9k-fsi-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR asr9k-fsi package operational data.

     This module contains definitions
     for the following management objects:
       fabric-stats: Fabric stats operational data

     Copyright (c) 2013-2016 by Cisco Systems, Inc.
     All rights reserved.";

  revision "2015-11-09" {
    description
      "IOS XR 6.0 revision.";
  }


  container fabric-stats {
    xr:xr-xml-map "fsi_oper:FabricStats";
    config false;
    description "Fabric stats operational data";

    container nodes {
      xr:xr-xml-map "fsi_oper:NodeTable";
      description "Table of Nodes";

      list node {
        xr:xr-xml-map "fsi_oper:Node";
        key "node-name";
        description "Information about a particular node";

        container statses {
          xr:xr-xml-map "fsi_oper:StatsTable";
          description "Table of stats information";

          list stats {
            xr:xr-xml-map "fsi_oper:Stats";
            key "type";
            description "Stats information for a particular type";
            leaf type {
              xr:xr-xml-map "fsi_oper:Type";
              type xr:Cisco-ios-xr-string;
              description "Fabric asic type";
            }
            uses FSI-SHOW-GENERIC-STATS;
          }
        }
        leaf node-name {
          xr:xr-xml-map "fsi_oper:NodeName";
          type xr:Node-id;
          description "Node name";
        }
      }
    }
  }
}
