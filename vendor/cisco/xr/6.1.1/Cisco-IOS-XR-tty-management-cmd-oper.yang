module Cisco-IOS-XR-tty-management-cmd-oper {

  /*** NAMESPACE / PREFIX DEFINITION ***/

  namespace "http://cisco.com/ns/yang"+
    "/Cisco-IOS-XR-tty-management-cmd-oper";


  prefix "tty-management-cmd-oper";

  /*** LINKAGE (IMPORTS / INCLUDES) ***/

  import Cisco-IOS-XR-types { prefix "xr"; }

  include Cisco-IOS-XR-tty-management-cmd-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR tty-management-cmd package operational data.

     This module contains definitions
     for the following management objects:
       show-users: Show users statistics

     Copyright (c) 2013-2016 by Cisco Systems, Inc.
     All rights reserved.";

  revision "2015-11-09" {
    description
      "IOS XR 6.0 revision.";
  }


  container show-users {
    xr:xr-xml-map "tty_show_users_oper:ShowUsers";
    config false;
    description "Show users statistics";

    container sessions {
      xr:xr-xml-map "tty_show_users_oper:Details";
      description "Show users statistics";

      list session {
        xr:xr-xml-map "tty_show_users_oper:Sessions";
        key "session-id";
        description "Show users statistics";
        leaf session-id {
          xr:xr-xml-map "tty_show_users_oper:SessionId";
          type int32;
          description "Session Id";
        }
        uses SHOWUSERS-ENTRY;
      }
    }
  }
}
