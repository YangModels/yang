submodule Cisco-IOS-XR-ncs1k-mxp-lldp-oper-sub1 {

  belongs-to Cisco-IOS-XR-ncs1k-mxp-lldp-oper {
    prefix Cisco-IOS-XR-ncs1k-mxp-lldp-oper;
  }

  /*** LINKAGE (IMPORTS / INCLUDES) ***/

  import ietf-inet-types { prefix "inet"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR ncs1k-mxp-lldp package operational data.

     Copyright (c) 2013-2016 by Cisco Systems, Inc.
     All rights reserved.";

  revision "2016-04-05" {
    description
      "Additional LLDP fields are added.";
  }

  revision "2015-11-09" {
    description
      "IOS XR 6.0 revision.";
  }

  typedef In6-addr {
    type inet:ipv6-address;
    description "In6 addr";
  }
  typedef Lldp-l3-addr-protocol {
    type enumeration {
      enum ipv4 {
        description "IPv4";
      }
      enum ipv6 {
        description "IPv6";
      }
    }
    description "Lldp l3 addr protocol";
  }

  grouping LLDP-L3-ADDR {
    description "LLDP L3 ADDR";
    leaf address-type {
      xr:xr-xml-map "mxp_show_lldp:AddressType";
      type Lldp-l3-addr-protocol;
      description "AddressType";
    }
    leaf ipv4-address {
      xr:xr-xml-map "mxp_show_lldp:IPv4Address";
      when "../address-type = 'ipv4'" {
        description "../AddressType = 'IPv4'";
      }
      type inet:ipv4-address;
      description "IPv4 address";
    }
    leaf ipv6-address {
      xr:xr-xml-map "mxp_show_lldp:IPv6Address";
      when "../address-type = 'ipv6'" {
        description "../AddressType = 'IPv6'";
      }
      type In6-addr;
      description "IPv6 address";
    }
  }

  grouping LLDP-ADDRESS-ENTRY {
    description "LLDP Address entry";

    container address {
      description "Network layer address";
      uses LLDP-L3-ADDR;
    }
    leaf ma-subtype {
      xr:xr-xml-map "mxp_show_lldp:MaSubtype";
      type uint8;
      description "MA sub type";
    }
    leaf if-num {
      xr:xr-xml-map "mxp_show_lldp:if_num";
      type uint32;
      description "Interface num";
    }
  }

  grouping MXP-LLDP-NEIGHBOR {
    description "LLDP neighbor info";

    container network-address {
      description "Management Address";
      uses LLDP-ADDRESS-ENTRY;
    }
    leaf source-mac {
      xr:xr-xml-map "mxp_show_lldp:SourceMac";
      type string;
      description "Mac address of the neighbor";
    }
    leaf chassis-id {
      xr:xr-xml-map "mxp_show_lldp:ChassisID";
      type string;
      description "Chassis id";
    }
    leaf port-id-detail {
      xr:xr-xml-map "mxp_show_lldp:PortIDDetail";
      type string;
      description "Outgoing port identifier";
    }
    leaf port-id-ckt {
      xr:xr-xml-map "mxp_show_lldp:PortIDCkt";
      type uint32;
      description "Outgoing port identifier circuit id";
    }
    leaf hold-time {
      xr:xr-xml-map "mxp_show_lldp:HoldTime";
      type uint16;
      description "Remaining hold time";
    }
    leaf port-description {
      xr:xr-xml-map "mxp_show_lldp:PortDescription";
      type string;
      description "Port Description";
    }
    leaf system-name {
      xr:xr-xml-map "mxp_show_lldp:SystemName";
      type string;
      description "System Name";
    }
    leaf system-description {
      xr:xr-xml-map "mxp_show_lldp:SystemDescription";
      type string;
      description "System Description";
    }
    leaf system-capabilities {
      xr:xr-xml-map "mxp_show_lldp:SystemCapabilities";
      type string;
      description "System Capabilities";
    }
    leaf enabled-capabilities {
      xr:xr-xml-map "mxp_show_lldp:EnabledCapabilities";
      type string;
      description "Enabled Capabilities";
    }
    leaf lldp-neighbor {
      xr:xr-xml-map "mxp_show_lldp:LldpNeighbor";
      type string {
        length "0..40";
      }
      description "LldpNeighbor";
    }
  }
}
