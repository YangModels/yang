module cisco-xr-openconfig-mpls-deviations {

  prefix  "mplsdevs";

  namespace "http://cisco.com/ns/yang/cisco-xr-openconfig-mpls-deviations";

  import openconfig-mpls { prefix mpls; }

  organization "Cisco Systems, Inc.";

  contact
    "Cisco Systems, Inc.
     Customer Service

     Postal: 170 West Tasman Drive
     San Jose, CA 95134

     Tel: +1 800 553-NETS

     E-mail: cs-yang@cisco.com";

  description
    "This module contains a set of deviations for 
 
     openconfig-mpls.yang@2015-11-05 

     on Cisco IOS-XR devices.

     Copyright (c) 2016 by Cisco Systems, Inc.
     All rights reserved.";

  revision "2016-05-16" {
    description
      "Initial revision applicable to IOS-XR 6.1.1";
  }


  deviation /mpls:mpls/mpls:global/mpls:config/mpls:null-label {
    deviate not-supported;
  }

  deviation /mpls:mpls/mpls:global/mpls:state/mpls:null-label {
    deviate not-supported;
  }

  deviation /mpls:mpls/mpls:global/mpls:mpls-interface-attributes/mpls:interface {
    deviate not-supported;
  }

  deviation /mpls:mpls/mpls:te-global-attributes/mpls:srlg/mpls:srlg/mpls:config/mpls:flooding-type {
    deviate not-supported;
  }

  deviation /mpls:mpls/mpls:te-global-attributes/mpls:srlg/mpls:srlg/mpls:state/mpls:flooding-type {
    deviate not-supported;
  }

  deviation /mpls:mpls/mpls:te-global-attributes/mpls:igp-flooding-bandwidth/mpls:config/mpls:threshold-type {
    deviate not-supported;
  }

  deviation /mpls:mpls/mpls:te-global-attributes/mpls:igp-flooding-bandwidth/mpls:config/mpls:threshold-specification {
    deviate not-supported;
  }

  deviation /mpls:mpls/mpls:te-global-attributes/mpls:igp-flooding-bandwidth/mpls:config/mpls:up-thresholds {
    deviate not-supported;
  }

  deviation /mpls:mpls/mpls:te-global-attributes/mpls:igp-flooding-bandwidth/mpls:config/mpls:down-thresholds {
    deviate not-supported;
  }

  deviation /mpls:mpls/mpls:te-global-attributes/mpls:igp-flooding-bandwidth/mpls:config/mpls:up-down-thresholds {
    deviate not-supported;
  }

  deviation /mpls:mpls/mpls:te-global-attributes/mpls:igp-flooding-bandwidth/mpls:state/mpls:threshold-type {
    deviate not-supported;
  }

  deviation /mpls:mpls/mpls:te-global-attributes/mpls:igp-flooding-bandwidth/mpls:state/mpls:threshold-specification {
    deviate not-supported;
  }

  deviation /mpls:mpls/mpls:te-global-attributes/mpls:igp-flooding-bandwidth/mpls:state/mpls:up-thresholds {
    deviate not-supported;
  }

  deviation /mpls:mpls/mpls:te-global-attributes/mpls:igp-flooding-bandwidth/mpls:state/mpls:down-thresholds {
    deviate not-supported;
  }

  deviation /mpls:mpls/mpls:te-global-attributes/mpls:igp-flooding-bandwidth/mpls:state/mpls:up-down-thresholds {
    deviate not-supported;
  }

  deviation /mpls:mpls/mpls:te-interface-attributes/mpls:interface/mpls:state/mpls:srlg-membership {
    deviate not-supported;
  }

  deviation /mpls:mpls/mpls:te-interface-attributes/mpls:interface/mpls:state/mpls:admin-group {
    deviate not-supported;
  }

  deviation /mpls:mpls/mpls:te-interface-attributes/mpls:interface/mpls:igp-flooding-bandwidth/mpls:config/mpls:threshold-type {
    deviate not-supported;
  }

  deviation /mpls:mpls/mpls:te-interface-attributes/mpls:interface/mpls:igp-flooding-bandwidth/mpls:config/mpls:delta-percentage {
    deviate not-supported;
  }

  deviation /mpls:mpls/mpls:te-interface-attributes/mpls:interface/mpls:igp-flooding-bandwidth/mpls:config/mpls:threshold-specification {
    deviate not-supported;
  }

  deviation /mpls:mpls/mpls:te-interface-attributes/mpls:interface/mpls:igp-flooding-bandwidth/mpls:config/mpls:up-down-thresholds {
    deviate not-supported;
  }

  deviation /mpls:mpls/mpls:te-interface-attributes/mpls:interface/mpls:igp-flooding-bandwidth/mpls:state/mpls:threshold-type {
    deviate not-supported;
  }

  deviation /mpls:mpls/mpls:te-interface-attributes/mpls:interface/mpls:igp-flooding-bandwidth/mpls:state/mpls:delta-percentage {
    deviate not-supported;
  }

  deviation /mpls:mpls/mpls:te-interface-attributes/mpls:interface/mpls:igp-flooding-bandwidth/mpls:state/mpls:threshold-specification {
    deviate not-supported;
  }

  deviation /mpls:mpls/mpls:te-interface-attributes/mpls:interface/mpls:igp-flooding-bandwidth/mpls:state/mpls:up-thresholds {
    deviate not-supported;
  }

  deviation /mpls:mpls/mpls:te-interface-attributes/mpls:interface/mpls:igp-flooding-bandwidth/mpls:state/mpls:down-thresholds {
    deviate not-supported;
  }

  deviation /mpls:mpls/mpls:te-interface-attributes/mpls:interface/mpls:igp-flooding-bandwidth/mpls:state/mpls:up-down-thresholds {
    deviate not-supported;
  }

  deviation /mpls:mpls/mpls:signaling-protocols/mpls:rsvp-te/mpls:sessions/mpls:state/mpls:session {
    deviate not-supported;
  }

  deviation /mpls:mpls/mpls:signaling-protocols/mpls:rsvp-te/mpls:neighbors/mpls:state/mpls:neighbor {
    deviate not-supported;
  }

  deviation /mpls:mpls/mpls:signaling-protocols/mpls:rsvp-te/mpls:global/mpls:hellos/mpls:config/mpls:refresh-reduction {
    deviate not-supported;
  }

  deviation /mpls:mpls/mpls:signaling-protocols/mpls:rsvp-te/mpls:global/mpls:hellos/mpls:state/mpls:refresh-reduction {
    deviate not-supported;
  }

  deviation /mpls:mpls/mpls:signaling-protocols/mpls:rsvp-te/mpls:interface-attributes/mpls:interface/mpls:state/mpls:bandwidth {
    deviate not-supported;
  }

  deviation /mpls:mpls/mpls:signaling-protocols/mpls:rsvp-te/mpls:interface-attributes/mpls:interface/mpls:state/mpls:highwater-mark {
    deviate not-supported;
  }

  deviation /mpls:mpls/mpls:signaling-protocols/mpls:rsvp-te/mpls:interface-attributes/mpls:interface/mpls:state/mpls:active-reservation-count {
    deviate not-supported;
  }

  deviation /mpls:mpls/mpls:signaling-protocols/mpls:rsvp-te/mpls:interface-attributes/mpls:interface/mpls:hellos/mpls:config/mpls:hello-interval {
    deviate not-supported;
  }

  deviation /mpls:mpls/mpls:signaling-protocols/mpls:rsvp-te/mpls:interface-attributes/mpls:interface/mpls:hellos/mpls:state/mpls:hello-interval {
    deviate not-supported;
  }

  deviation /mpls:mpls/mpls:signaling-protocols/mpls:rsvp-te/mpls:interface-attributes/mpls:interface/mpls:protection/mpls:config/mpls:bypass-optimize-interval {
    deviate not-supported;
  }

  deviation /mpls:mpls/mpls:signaling-protocols/mpls:rsvp-te/mpls:interface-attributes/mpls:interface/mpls:protection/mpls:state/mpls:bypass-optimize-interval {
    deviate not-supported;
  }

  deviation /mpls:mpls/mpls:signaling-protocols/mpls:segment-routing/mpls:srgb {
    deviate not-supported;
  }

  deviation /mpls:mpls/mpls:signaling-protocols/mpls:segment-routing/mpls:interfaces {
    deviate not-supported;
  }

  deviation /mpls:mpls/mpls:lsps/mpls:constrained-path/mpls:tunnel/mpls:config/mpls:signaling-protocol {
    deviate not-supported;
  }

  deviation /mpls:mpls/mpls:lsps/mpls:constrained-path/mpls:tunnel/mpls:config/mpls:description {
    deviate not-supported;
  }

  deviation /mpls:mpls/mpls:lsps/mpls:constrained-path/mpls:tunnel/mpls:config/mpls:preference {
    deviate not-supported;
  }

  deviation /mpls:mpls/mpls:lsps/mpls:constrained-path/mpls:tunnel/mpls:config/mpls:reoptimize-timer {
    deviate not-supported;
  }

  deviation /mpls:mpls/mpls:lsps/mpls:constrained-path/mpls:tunnel/mpls:config/mpls:source {
    deviate not-supported;
  }

  deviation /mpls:mpls/mpls:lsps/mpls:constrained-path/mpls:tunnel/mpls:state/mpls:preference {
    deviate not-supported;
  }

  deviation /mpls:mpls/mpls:lsps/mpls:constrained-path/mpls:tunnel/mpls:bandwidth/mpls:config/mpls:specification-type {
    deviate not-supported;
  }

  deviation /mpls:mpls/mpls:lsps/mpls:constrained-path/mpls:tunnel/mpls:bandwidth/mpls:state/mpls:specification-type {
    deviate not-supported;
  }

  deviation /mpls:mpls/mpls:lsps/mpls:constrained-path/mpls:tunnel/mpls:p2p-tunnel-attributes/mpls:p2p-primary-paths/mpls:config/mpls:use-cspf {
    deviate not-supported;
  }

  deviation /mpls:mpls/mpls:lsps/mpls:constrained-path/mpls:tunnel/mpls:p2p-tunnel-attributes/mpls:p2p-primary-paths/mpls:config/mpls:cspf-tiebreaker {
    deviate not-supported;
  }

  deviation /mpls:mpls/mpls:lsps/mpls:constrained-path/mpls:tunnel/mpls:p2p-tunnel-attributes/mpls:p2p-primary-paths/mpls:config/mpls:setup-priority {
    deviate not-supported;
  }

  deviation /mpls:mpls/mpls:lsps/mpls:constrained-path/mpls:tunnel/mpls:p2p-tunnel-attributes/mpls:p2p-primary-paths/mpls:config/mpls:hold-priority {
    deviate not-supported;
  }

  deviation /mpls:mpls/mpls:lsps/mpls:constrained-path/mpls:tunnel/mpls:p2p-tunnel-attributes/mpls:p2p-primary-paths/mpls:config/mpls:retry-timer {
    deviate not-supported;
  }

  deviation /mpls:mpls/mpls:lsps/mpls:constrained-path/mpls:tunnel/mpls:p2p-tunnel-attributes/mpls:p2p-primary-paths/mpls:state/mpls:use-cspf {
    deviate not-supported;
  }

  deviation /mpls:mpls/mpls:lsps/mpls:constrained-path/mpls:tunnel/mpls:p2p-tunnel-attributes/mpls:p2p-primary-paths/mpls:state/mpls:cspf-tiebreaker {
    deviate not-supported;
  }

  deviation /mpls:mpls/mpls:lsps/mpls:constrained-path/mpls:tunnel/mpls:p2p-tunnel-attributes/mpls:p2p-primary-paths/mpls:state/mpls:setup-priority {
    deviate not-supported;
  }

  deviation /mpls:mpls/mpls:lsps/mpls:constrained-path/mpls:tunnel/mpls:p2p-tunnel-attributes/mpls:p2p-primary-paths/mpls:state/mpls:hold-priority {
    deviate not-supported;
  }

  deviation /mpls:mpls/mpls:lsps/mpls:constrained-path/mpls:tunnel/mpls:p2p-tunnel-attributes/mpls:p2p-primary-paths/mpls:state/mpls:retry-timer {
    deviate not-supported;
  }

  deviation /mpls:mpls/mpls:lsps/mpls:constrained-path/mpls:tunnel/mpls:p2p-tunnel-attributes/mpls:p2p-primary-paths/mpls:candidate-secondary-paths/mpls:candidate-secondary-path {
    deviate not-supported;
  }

  deviation /mpls:mpls/mpls:lsps/mpls:constrained-path/mpls:tunnel/mpls:p2p-tunnel-attributes/mpls:p2p-primary-paths/mpls:admin-groups/mpls:state/mpls:exclude-group {
    deviate not-supported;
  }

  deviation /mpls:mpls/mpls:lsps/mpls:constrained-path/mpls:tunnel/mpls:p2p-tunnel-attributes/mpls:p2p-primary-paths/mpls:admin-groups/mpls:state/mpls:include-all-group {
    deviate not-supported;
  }

  deviation /mpls:mpls/mpls:lsps/mpls:constrained-path/mpls:tunnel/mpls:p2p-tunnel-attributes/mpls:p2p-primary-paths/mpls:admin-groups/mpls:state/mpls:include-any-group {
    deviate not-supported;
  }

  deviation /mpls:mpls/mpls:lsps/mpls:constrained-path/mpls:tunnel/mpls:p2p-tunnel-attributes/mpls:p2p-secondary-paths {
    deviate not-supported;
  }

  deviation /mpls:mpls/mpls:lsps/mpls:unconstrained-path/mpls:path-setup-protocol/mpls:ldp/mpls:tunnel/mpls:tunnel-type {
    deviate not-supported;
  }

  deviation /mpls:mpls/mpls:lsps/mpls:unconstrained-path/mpls:path-setup-protocol/mpls:ldp/mpls:tunnel/mpls:ldp-type {
    deviate not-supported;
  }

  deviation /mpls:mpls/mpls:lsps/mpls:unconstrained-path/mpls:path-setup-protocol/mpls:ldp/mpls:tunnel/mpls:p2p-lsp/mpls:fec-address {
    deviate not-supported;
  }

  deviation /mpls:mpls/mpls:lsps/mpls:unconstrained-path/mpls:path-setup-protocol/mpls:segment-routing/mpls:tunnel/mpls:tunnel-type {
    deviate not-supported;
  }

  deviation /mpls:mpls/mpls:lsps/mpls:unconstrained-path/mpls:path-setup-protocol/mpls:segment-routing/mpls:tunnel/mpls:p2p-lsp/mpls:fec {
    deviate not-supported;
  }


}
//total deviations:68
