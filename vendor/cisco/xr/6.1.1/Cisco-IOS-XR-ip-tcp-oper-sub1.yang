submodule Cisco-IOS-XR-ip-tcp-oper-sub1 {

  belongs-to Cisco-IOS-XR-ip-tcp-oper {
    prefix Cisco-IOS-XR-ip-tcp-oper;
  }

  /*** LINKAGE (IMPORTS / INCLUDES) ***/

  import ietf-inet-types { prefix "inet"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR ip-tcp package operational data.

     Copyright (c) 2013-2016 by Cisco Systems, Inc.
     All rights reserved.";

  revision "2016-02-26" {
    description
      "Descriptions updated.";
  }

  revision "2015-11-09" {
    description
      "IOS XR 6.0 revision.";
  }

  typedef Nsr-down-reason {
    type enumeration {
      enum none {
        description "None, i.e. NSR was never up";
      }
      enum init-sync-aborted {
        description "Initial sync was aborted";
      }
      enum client-disabled {
        description "Disabled by Active APP";
      }
      enum client-disconnect {
        description "Standby APP disconnected";
      }
      enum tcp-disconnect {
        description "Standby TCP disconnected";
      }
      enum failover {
        description "RP/DRP Failover occurred";
      }
      enum nsr-clear {
        description "Clear nsr command";
      }
      enum internal-error {
        description "Internal error occurred";
      }
      enum retransmit-threshold-exceed {
        description
          "Retransmission threshold exceededprobably
          becauseS-TCP was not healthy";
      }
      enum init-sync-failure-thresh-exceeded {
        description
          "Init-sync repeat failures have exceeded
          threshold";
      }
      enum audit-timeout {
        description "Audit operation timed out";
      }
      enum audit-failed {
        description "Audit operation failed";
      }
      enum standby-sscb-deleted {
        description "Standby SSCB deleted";
      }
      enum standby-session-close {
        description "Session was closed on standby";
      }
      enum standby-rxpath-frozen {
        description "RX-Path was frozen on standby";
      }
      enum partner-deleted {
        description "Partner was deleted from set";
      }
    }
    description "NSR-Down Reasons";
  }
  typedef Nsr-status {
    type enumeration {
      enum down {
        description "NSR Stream Down";
      }
      enum up {
        description "NSR Stream Up";
      }
      enum na {
        description "NSR Stream Not applicable";
      }
    }
    description "NSR Stream Status";
  }
  typedef Addr-family {
    type enumeration {
      enum internetwork {
        value 2;
        description "Internetwork: UDP, TCP, etc.";
      }
      enum ip-version6 {
        value 10;
        description "IP version 6";
      }
    }
    description "Address Family Types";
  }

  grouping TCP-NSR-PCB-STATS-BAG {
    description "SSO/NSR statistics of a TCP connection";

    container snd-counters {
      description "Send path counters for the PCB";
      uses TCP-NSR-SND-COUNTERS-NODE;
    }
    leaf pcb {
      xr:xr-xml-map "tcp_nsr:PCB";
      type uint64;
      description "PCB Address";
    }
    leaf number-of-times-nsr-up {
      xr:xr-xml-map "tcp_nsr:NumberOfTimesNSRUp";
      type uint32;
      description "no. of times nsr went up";
    }
    leaf number-of-timers-nsr-down {
      xr:xr-xml-map "tcp_nsr:NumberOfTimersNSRDown";
      type uint32;
      description "no. of times nsr went down";
    }
    leaf number-of-times-nsr-disabled {
      xr:xr-xml-map "tcp_nsr:NumberOfTimesNSRDisabled";
      type uint32;
      description "no. of times nsr was disabled";
    }
    leaf number-of-times-nsr-fail-over {
      xr:xr-xml-map "tcp_nsr:NumberOfTimesNSRFailOver";
      type uint32;
      description "no. of times fail-over occured";
    }
    leaf internal-ack-drops-not-replicated {
      xr:xr-xml-map "tcp_nsr:InternalAckDropsNotReplicated";
      type uint64;
      description
        "Number of iACKs dropped because session is not
        replicated";
    }
    leaf internal-ack-drops-initsync-first-phase {
      xr:xr-xml-map "tcp_nsr:InternalAckDropsInitsyncFirstPhase";
      type uint64;
      description
        "Number of iACKs dropped because 1st phase of
        init-sync is in progress";
    }
    leaf internal-ack-drops-stale {
      xr:xr-xml-map "tcp_nsr:InternalAckDropsStale";
      type uint64;
      description "Number of stale iACKs dropped";
    }
    leaf internal-ack-drops-immediate-match {
      xr:xr-xml-map "tcp_nsr:InternalAckDropsImmediateMatch";
      type uint64;
      description
        "Number of iACKs not held because of an immediate
        match";
    }
    leaf last-cleared-time {
      xr:xr-xml-map "tcp_nsr:LastClearedTime";
      type uint32;
      units "second";
      description
        "Time of last clear (in seconds since 1st Jan
        1970 00:00:00)";
    }
  }

  grouping TCP-NSR-SSCB-STATS-BAG {
    description "SSO/NSR statistics of a Session Set";
    leaf sscb {
      xr:xr-xml-map "tcp_nsr:SSCB";
      type uint64;
      description "SSCB Address";
    }
    leaf set-id {
      xr:xr-xml-map "tcp_nsr:SetID";
      type uint32;
      description "ID of this Session-set";
    }
    leaf number-of-attempted-init-sync {
      xr:xr-xml-map "tcp_nsr:NumberOfAttemptedInitSync";
      type uint32;
      description "no. of initial-sync attempts";
    }
    leaf number-of-succeeded-init-sync {
      xr:xr-xml-map "tcp_nsr:NumberOfSucceededInitSync";
      type uint32;
      description "no. of initial-sync successes";
    }
    leaf number-of-failed-init-sync {
      xr:xr-xml-map "tcp_nsr:NumberOfFailedInitSync";
      type uint32;
      description "no. of initial-sync failures";
    }
    leaf number-of-failover {
      xr:xr-xml-map "tcp_nsr:NumberOfFailover";
      type uint32;
      description "Number of Switch-overs";
    }
    leaf number-of-nsr-resets {
      xr:xr-xml-map "tcp_nsr:NumberOfNSRResets";
      type uint32;
      description "Number of times NSR was reset for the session";
    }
    leaf last-cleared-time {
      xr:xr-xml-map "tcp_nsr:LastClearedTime";
      type uint32;
      units "second";
      description
        "Time of last clear (in seconds since 1st Jan
        1970 00:00:00)";
    }
  }

  grouping TCP-NSR-CCB-STATS-BAG {
    description "SSO/NSR statistics of a Client";
    leaf ccb {
      xr:xr-xml-map "tcp_nsr:CCB";
      type uint64;
      description "Address of the Client Control Block";
    }
    leaf pid {
      xr:xr-xml-map "tcp_nsr:PID";
      type uint32;
      description "PID of the Client";
    }
    leaf process-name {
      xr:xr-xml-map "tcp_nsr:ProcessName";
      type string;
      description "Proc name of Clinet";
    }
    leaf job-id {
      xr:xr-xml-map "tcp_nsr:JobID";
      type int32;
      description "JOb ID of Client";
    }
    leaf instance {
      xr:xr-xml-map "tcp_nsr:Instance";
      type uint32;
      description "Instance of the Client";
    }
    leaf connected-at {
      xr:xr-xml-map "tcp_nsr:ConnectedAt";
      type uint32;
      units "second";
      description
        "Time of connect (in seconds since 1st Jan 1970
        00:00:00)";
    }
    leaf number-of-created-sscb {
      xr:xr-xml-map "tcp_nsr:NumberOfCreatedSSCB";
      type uint32;
      description "Num of created session sets";
    }
    leaf number-of-deleted-sscb {
      xr:xr-xml-map "tcp_nsr:NumberOfDeletedSSCB";
      type uint32;
      description "Num of deleted session sets";
    }
    leaf last-cleared-time {
      xr:xr-xml-map "tcp_nsr:LastClearedTime";
      type uint32;
      units "second";
      description
        "Time of last clear (in seconds since 1st Jan
        1970 00:00:00)";
    }

    list notification-statistic {
      description "Various types of notification stats";
      uses TSS-NOTIF-STATS;
    }
  }

  grouping TCP-NSR-AUDIT-COUNTERS-AGGR-ONLY-NODE {
    description "Aggregate-only counters for NSR audit";
    leaf mark-session-set-rcv-drop-aggr {
      xr:xr-xml-map "tcp_nsr:MarkSessionSetRcvDropAggr";
      type uint32;
      description
        "Number of session-set Mark messages dropped by
        standby";
    }
    leaf session-rcv-drop-aggr {
      xr:xr-xml-map "tcp_nsr:SessionRcvDropAggr";
      type uint32;
      description
        "Number of session audit messages dropped by
        standby";
    }
    leaf sweep-session-set-rcv-drop-aggr {
      xr:xr-xml-map "tcp_nsr:SweepSessionSetRcvDropAggr";
      type uint32;
      description
        "Number of session-set Sweep messages dropped by
        standby";
    }
    leaf session-set-response-rcv-drop-aggr {
      xr:xr-xml-map "tcp_nsr:SessionSetResponseRcvDropAggr";
      type uint32;
      description
        "Number of session-set response messages dropped
        by active";
    }
    leaf mark-session-set-ack-rcv-drop-aggr {
      xr:xr-xml-map "tcp_nsr:MarkSessionSetAckRcvDropAggr";
      type uint32;
      description
        "Number of session-set mark ack messages dropped
        by active";
    }
    leaf mark-session-set-nack-rcv-drop-aggr {
      xr:xr-xml-map "tcp_nsr:MarkSessionSetNackRcvDropAggr";
      type uint32;
      description
        "Number of session-set mark nack messages dropped
        by active";
    }
  }

  grouping TCP-NSR-AUDIT-COUNTERS-NODE {
    description "Audit counters";
    leaf mark-session-set-send {
      xr:xr-xml-map "tcp_nsr:MarkSessionSetSend";
      type uint32;
      description
        "Number of successful session-set Mark's sent by
        active";
    }
    leaf mark-session-set-send-drop {
      xr:xr-xml-map "tcp_nsr:MarkSessionSetSendDrop";
      type uint32;
      description "Number of failed session-set Mark's";
    }
    leaf mark-session-set-rcv {
      xr:xr-xml-map "tcp_nsr:MarkSessionSetRcv";
      type uint32;
      description
        "Number of successful session-set Mark's received
        by standby";
    }
    leaf mark-session-set-rcv-drop {
      xr:xr-xml-map "tcp_nsr:MarkSessionSetRcvDrop";
      type uint32;
      description "Number of session-set Mark's dropped by standby";
    }
    leaf session-send {
      xr:xr-xml-map "tcp_nsr:SessionSend";
      type uint32;
      description
        "Number of successful session audits sent by
        active";
    }
    leaf session-send-drop {
      xr:xr-xml-map "tcp_nsr:SessionSendDrop";
      type uint32;
      description
        "Number of session audits that couldn't be sent
        by active";
    }
    leaf session-rcv {
      xr:xr-xml-map "tcp_nsr:SessionRcv";
      type uint32;
      description "Number of session audits received by standby";
    }
    leaf session-rcv-drop {
      xr:xr-xml-map "tcp_nsr:SessionRcvDrop";
      type uint32;
      description "Number of session audits dropped by standby";
    }
    leaf sweep-session-set-send {
      xr:xr-xml-map "tcp_nsr:SweepSessionSetSend";
      type uint32;
      description
        "Number of successful session-set Sweep's sent by
        active";
    }
    leaf sweep-session-set-send-drop {
      xr:xr-xml-map "tcp_nsr:SweepSessionSetSendDrop";
      type uint32;
      description "Number of failed session-set Sweep's";
    }
    leaf sweep-session-set-rcv {
      xr:xr-xml-map "tcp_nsr:SweepSessionSetRcv";
      type uint32;
      description
        "Number of successful session-set Sweep's
        received by standby";
    }
    leaf sweep-session-set-rcv-drop {
      xr:xr-xml-map "tcp_nsr:SweepSessionSetRcvDrop";
      type uint32;
      description
        "Number of session-set Sweep's dropped by standby";
    }
    leaf session-set-response-send {
      xr:xr-xml-map "tcp_nsr:SessionSetResponseSend";
      type uint32;
      description
        "Number of successful audit responses sent by
        standby";
    }
    leaf session-set-response-send-drop {
      xr:xr-xml-map "tcp_nsr:SessionSetResponseSendDrop";
      type uint32;
      description
        "Number of audit responses that couldn't be sent
        by standby";
    }
    leaf session-set-response-rcv {
      xr:xr-xml-map "tcp_nsr:SessionSetResponseRcv";
      type uint32;
      description "Number of audit responses received by active";
    }
    leaf session-set-response-rcv-drop {
      xr:xr-xml-map "tcp_nsr:SessionSetResponseRcvDrop";
      type uint32;
      description "Number of audit responses dropped by active";
    }
    leaf mark-session-set-ack-send {
      xr:xr-xml-map "tcp_nsr:MarkSessionSetAckSend";
      type uint32;
      description
        "Number of successful audit mark acks sent by
        standby";
    }
    leaf mark-session-set-ack-send-drop {
      xr:xr-xml-map "tcp_nsr:MarkSessionSetAckSendDrop";
      type uint32;
      description
        "Number of audit mark acks that couldn't be sent
        by standby";
    }
    leaf mark-session-set-ack-rcv {
      xr:xr-xml-map "tcp_nsr:MarkSessionSetAckRcv";
      type uint32;
      description "Number of audit mark acks received by active";
    }
    leaf mark-session-set-ack-rcv-drop {
      xr:xr-xml-map "tcp_nsr:MarkSessionSetAckRcvDrop";
      type uint32;
      description "Number of audit mark acks dropped by active";
    }
    leaf mark-session-set-nack-send {
      xr:xr-xml-map "tcp_nsr:MarkSessionSetNackSend";
      type uint32;
      description
        "Number of successful audit mark nacks sent by
        standby";
    }
    leaf mark-session-set-nack-send-drop {
      xr:xr-xml-map "tcp_nsr:MarkSessionSetNackSendDrop";
      type uint32;
      description
        "Number of audit mark nacks that couldn't be sent
        by standby";
    }
    leaf mark-session-set-nack-rcv {
      xr:xr-xml-map "tcp_nsr:MarkSessionSetNackRcv";
      type uint32;
      description "Number of audit mark nacks received by active";
    }
    leaf mark-session-set-nack-rcv-drop {
      xr:xr-xml-map "tcp_nsr:MarkSessionSetNackRcvDrop";
      type uint32;
      description "Number of audit mark nacks dropped by active";
    }
    leaf abort {
      xr:xr-xml-map "tcp_nsr:Abort";
      type uint32;
      description
        "Number of times the active aborted an audit
        session";
    }
  }

  grouping TCP-NSR-AUDIT-COUNTERS-AGGR-NODE {
    description "Aggregate counters for NSR audit";

    container common {
      description "Common audit counters";
      uses TCP-NSR-AUDIT-COUNTERS-NODE;
    }

    container aggr-only {
      description "Aggregate only audit counters";
      uses TCP-NSR-AUDIT-COUNTERS-AGGR-ONLY-NODE;
    }
  }

  grouping TCP-NSR-SND-COUNTERS-AGGR-ONLY-NODE {
    description "Send path aggregate only counters";
    leaf data-xfer-rcv-drop-no-pcb {
      xr:xr-xml-map "tcp_nsr:DataXferRcvDropNoPcb";
      type uint32;
      description
        "Number of Data transfer messages dropped because
        PCB wasn't found";
    }
    leaf data-xfer-rcv-drop-no-scb-dp {
      xr:xr-xml-map "tcp_nsr:DataXferRcvDropNoScbDp";
      type uint32;
      description
        "Number of Data transfer messages dropped because
        SCB DP wasn't found";
    }
    leaf seg-instr-rcv-drop-no-pcb {
      xr:xr-xml-map "tcp_nsr:SegInstrRcvDropNoPcb";
      type uint32;
      description
        "Number of Segmentation instruction messages
        dropped because PCB wasn't found";
    }
    leaf seg-instr-rcv-drop-no-scb-dp {
      xr:xr-xml-map "tcp_nsr:SegInstrRcvDropNoScbDp";
      type uint32;
      description
        "Number of Segmentation instruction messages
        dropped because SCB DP wasn't found";
    }
    leaf nack-rcv-drop-no-pcb {
      xr:xr-xml-map "tcp_nsr:NackRcvDropNoPcb";
      type uint32;
      description
        "Number of NACK messages dropped because PCB
        wasn't found";
    }
    leaf nack-rcv-drop-no-scb-dp {
      xr:xr-xml-map "tcp_nsr:NackRcvDropNoScbDp";
      type uint32;
      description
        "Number of NACK messages dropped because SCB DP
        wasn't found";
    }
    leaf cleanup-rcv-drop-no-pcb {
      xr:xr-xml-map "tcp_nsr:CleanupRcvDropNoPcb";
      type uint32;
      description
        "Number of Cleanup messages dropped because PCB
        wasn't found";
    }
    leaf cleanup-rcv-drop-no-scb-dp {
      xr:xr-xml-map "tcp_nsr:CleanupRcvDropNoScbDp";
      type uint32;
      description
        "Number of Cleanup messages dropped because SCB
        DP wasn't found";
    }
  }

  grouping TCP-NSR-SND-COUNTERS-NODE {
    description "Send path counters";
    leaf data-xfer-send {
      xr:xr-xml-map "tcp_nsr:DataXferSend";
      type uint32;
      description "Number of successful DATA transfers";
    }
    leaf data-xfer-send-total {
      xr:xr-xml-map "tcp_nsr:DataXferSendTotal";
      type uint64;
      description "Amount of data transferred";
    }
    leaf data-xfer-send-drop {
      xr:xr-xml-map "tcp_nsr:DataXferSendDrop";
      type uint32;
      description "Number of failed DATA transfers";
    }
    leaf data-xfer-send-iov-alloc {
      xr:xr-xml-map "tcp_nsr:DataXferSendIOVAlloc";
      type uint32;
      description
        "Number of data transfer msgs., that required new
        IOV's to be allocated";
    }
    leaf data-xfer-rcv {
      xr:xr-xml-map "tcp_nsr:DataXferRcv";
      type uint32;
      description "Number of received DATA transfers";
    }
    leaf data-xfer-rcv-success {
      xr:xr-xml-map "tcp_nsr:DataXferRcvSuccess";
      type uint32;
      description "Number of successfully received DATA transfers";
    }
    leaf data-xfer-rcv-fail-buffer-trim {
      xr:xr-xml-map "tcp_nsr:DataXferRcvFailBufferTrim";
      type uint32;
      description
        "Number of received DATA transfers that had
        buffer trim failures";
    }
    leaf data-xfer-rcv-fail-snd-una-out-of-sync {
      xr:xr-xml-map "tcp_nsr:DataXferRcvFailSndUNAOutOfSync";
      type uint32;
      description
        "Number of received DATA transfers that had
        failures because the send path was out of sync";
    }
    leaf seg-instr-send {
      xr:xr-xml-map "tcp_nsr:SegInstrSend";
      type uint32;
      description
        "Number of successful Segmentation instruction
        messages";
    }
    leaf seg-instr-send-units {
      xr:xr-xml-map "tcp_nsr:SegInstrSendUnits";
      type uint32;
      description
        "Number of segement units transferred via the
        successful Segmentation instruction messages";
    }
    leaf seg-instr-send-drop {
      xr:xr-xml-map "tcp_nsr:SegInstrSendDrop";
      type uint32;
      description
        "Number of failed Segmentation instruction
        messages";
    }
    leaf seg-instr-rcv {
      xr:xr-xml-map "tcp_nsr:SegInstrRcv";
      type uint32;
      description
        "Number of received Segmentation instruction
        messages";
    }
    leaf seg-instr-rcv-success {
      xr:xr-xml-map "tcp_nsr:SegInstrRcvSuccess";
      type uint32;
      description
        "Number of successfully received Segmentation
        instruction messages";
    }
    leaf seg-instr-rcv-fail-buffer-trim {
      xr:xr-xml-map "tcp_nsr:SegInstrRcvFailBufferTrim";
      type uint32;
      description
        "Number of received Segmentation instructions
        that had buffer trim failures";
    }
    leaf seg-instr-rcv-fail-tcp-process {
      xr:xr-xml-map "tcp_nsr:SegInstrRcvFailTcpProcess";
      type uint32;
      description
        "Number of received Segmentation instructions
        that had failures during TCP processing";
    }
    leaf nack-send {
      xr:xr-xml-map "tcp_nsr:NackSend";
      type uint32;
      description "Number of successful NACK messages";
    }
    leaf nack-send-drop {
      xr:xr-xml-map "tcp_nsr:NackSendDrop";
      type uint32;
      description "Number of failed NACK messages";
    }
    leaf nack-rcv {
      xr:xr-xml-map "tcp_nsr:NackRcv";
      type uint32;
      description "Number of received NACK messages";
    }
    leaf nack-rcv-success {
      xr:xr-xml-map "tcp_nsr:NackRcvSuccess";
      type uint32;
      description "Number of successfully received NACK messages";
    }
    leaf nack-rcv-fail-data-send {
      xr:xr-xml-map "tcp_nsr:NackRcvFailDataSend";
      type uint32;
      description
        "Number of received NACK messages that had
        failures when sending data in response to the
        NACK";
    }
    leaf cleanup-send {
      xr:xr-xml-map "tcp_nsr:CleanupSend";
      type uint32;
      description "Number of successful Cleanup messages";
    }
    leaf cleanup-send-drop {
      xr:xr-xml-map "tcp_nsr:CleanupSendDrop";
      type uint32;
      description "Number of failed Cleanup messages";
    }
    leaf cleanup-rcv {
      xr:xr-xml-map "tcp_nsr:CleanupRcv";
      type uint32;
      description "Number of received Cleanup messages";
    }
    leaf cleanup-rcv-success {
      xr:xr-xml-map "tcp_nsr:CleanupRcvSuccess";
      type uint32;
      description
        "Number of successfully received Cleanup messages";
    }
    leaf cleanup-rcv-fail-buffer-trim {
      xr:xr-xml-map "tcp_nsr:CleanupRcvFailBufferTrim";
      type uint32;
      description
        "Number of Cleanup messages that had trim
        failures";
    }
  }

  grouping TCP-NSR-SND-COUNTERS-AGGR-NODE {
    description "Send path aggregate counters";

    container common {
      description "Common send path counters";
      uses TCP-NSR-SND-COUNTERS-NODE;
    }

    container aggr-only {
      description "Aggregate only send path counters";
      uses TCP-NSR-SND-COUNTERS-AGGR-ONLY-NODE;
    }
  }

  grouping TSS-NOTIF-STATS {
    description "notif stats structure used in ccb stats bag";
    leaf queued-count {
      xr:xr-xml-map "tcp_nsr:QueuedCount";
      type uint32;
      description "how many were queued";
    }
    leaf failed-count {
      xr:xr-xml-map "tcp_nsr:FailedCount";
      type uint32;
      description "Errors while queuing the notifs";
    }
    leaf delivered-count {
      xr:xr-xml-map "tcp_nsr:DeliveredCount";
      type uint32;
      description "How many were picked up by app?";
    }
    leaf dropped-count {
      xr:xr-xml-map "tcp_nsr:DroppedCount";
      type uint32;
      description "How many were dropped because of timeout";
    }
  }

  grouping TCP-NSR-SUMMARY-STATS-BAG {
    description "Summary SSO/NSR statistics";

    container snd-counters {
      description "Aggregate Send path counters";
      uses TCP-NSR-SND-COUNTERS-AGGR-NODE;
    }

    container audit-counters {
      description "Aggregate Audit counters";
      uses TCP-NSR-AUDIT-COUNTERS-AGGR-NODE;
    }
    leaf last-cleared-time {
      xr:xr-xml-map "tcp_nsr:LastClearedTime";
      type uint32;
      units "second";
      description
        "Time of last clear (in seconds since 1st Jan
        1970 00:00:00)";
    }
    leaf number-of-connected-clients {
      xr:xr-xml-map "tcp_nsr:NumberOfConnectedClients";
      type uint32;
      description "Number of disconnected clients";
    }
    leaf number-of-disconnected-clients {
      xr:xr-xml-map "tcp_nsr:NumberOfDisconnectedClients";
      type uint32;
      description "Number of disconnected clients";
    }
    leaf number-of-current-clients {
      xr:xr-xml-map "tcp_nsr:NumberOfCurrentClients";
      type uint32;
      description "Number of current  clients";
    }
    leaf number-of-created-session-sets {
      xr:xr-xml-map "tcp_nsr:NumberOfCreatedSessionSets";
      type uint32;
      description "Number of created session sets";
    }
    leaf number-of-destroyed-session-sets {
      xr:xr-xml-map "tcp_nsr:NumberOfDestroyedSessionSets";
      type uint32;
      description "Number of destroyed session sets";
    }
    leaf number-of-current-session-sets {
      xr:xr-xml-map "tcp_nsr:NumberOfCurrentSessionSets";
      type uint32;
      description "Number of current session sets";
    }
    leaf number-of-added-sessions {
      xr:xr-xml-map "tcp_nsr:NumberOfAddedSessions";
      type uint32;
      description "Number of added sessions";
    }
    leaf number-of-deleted-sessions {
      xr:xr-xml-map "tcp_nsr:NumberOfDeletedSessions";
      type uint32;
      description "Number of deleted sessions";
    }
    leaf number-of-current-sessions {
      xr:xr-xml-map "tcp_nsr:NumberOfCurrentSessions";
      type uint32;
      description "Number of current sessions";
    }
    leaf number-of-partner-node {
      xr:xr-xml-map "tcp_nsr:NumberOfPartnerNode";
      type uint32;
      description " Number of Parner Nodes";
    }
    leaf number-of-attempted-init-sync {
      xr:xr-xml-map "tcp_nsr:NumberOfAttemptedInitSync";
      type uint32;
      description "no. of initial-sync attempts";
    }
    leaf number-of-succeeded-init-sync {
      xr:xr-xml-map "tcp_nsr:NumberOfSucceededInitSync";
      type uint32;
      description "no. of initial-sync successes";
    }
    leaf number-of-failed-init-sync {
      xr:xr-xml-map "tcp_nsr:NumberOfFailedInitSync";
      type uint32;
      description "no. of initial-sync fails";
    }
    leaf number-of-held-packets {
      xr:xr-xml-map "tcp_nsr:NumberOfHeldPackets";
      type uint32;
      description "Number of Packets held by Active TCP";
    }
    leaf number-of-held-but-dropped-packets {
      xr:xr-xml-map "tcp_nsr:NumberOfHeldButDroppedPackets";
      type uint32;
      description "Number of held packets dropped by Active TCP";
    }
    leaf number-of-held-internal-acks {
      xr:xr-xml-map "tcp_nsr:NumberOfHeldInternalAcks";
      type uint32;
      description "Number of Internal Acks held by Active TCP";
    }
    leaf number-of-held-but-dropped-internal-acks {
      xr:xr-xml-map "tcp_nsr:NumberOfHeldButDroppedInternalAcks";
      type uint32;
      description
        "Number of held Internal Acks dropped by Active
        TCP";
    }
    leaf number-of-sent-internal-acks {
      xr:xr-xml-map "tcp_nsr:NumberOfSentInternalAcks";
      type uint32;
      description
        "Number of Internal Acks sent to Active TCP by
        Standby TCP";
    }
    leaf number-of-received-internal-acks {
      xr:xr-xml-map "tcp_nsr:NumberOfReceivedInternalAcks";
      type uint32;
      description "Number of Internal Acks received by Active TCP";
    }
    leaf number-of-qad-receive-messages-drops {
      xr:xr-xml-map "tcp_nsr:NumberOfQADReceiveMessagesDrops";
      type uint32;
      description
        "Number of dropped messages from partner TCP
        stack(s)";
    }
    leaf number-of-qad-receive-messages-unknowns {
      xr:xr-xml-map "tcp_nsr:NumberOfQADReceiveMessagesUnknowns";
      type uint32;
      description
        "Number of unknown messages from partner TCP
        stack(s)";
    }
    leaf number-of-qad-receive-messages-accepts {
      xr:xr-xml-map "tcp_nsr:NumberOfQADReceiveMessagesAccepts";
      type uint32;
      description
        "Number of messages accepted from partner TCP
        stack(s)";
    }
    leaf number-of-qad-stale-receive-messages-drops {
      xr:xr-xml-map "tcp_nsr:NumberOfQADStaleReceiveMessagesDrops";
      type uint32;
      description
        "Number of dropped messages from partner TCP
        stack(s) because they were out-of-order";
    }
    leaf number-of-qad-transfer-message-sent {
      xr:xr-xml-map "tcp_nsr:NumberOfQADTransferMessageSent";
      type uint32;
      description "Number of messages sent to partner TCP stack(s)";
    }
    leaf number-of-qad-transfer-message-drops {
      xr:xr-xml-map "tcp_nsr:NumberOfQADTransferMessageDrops";
      type uint32;
      description
        "Number of messages failed to be sent to partner
        TCP stack(s)";
    }
    leaf number-of-internal-ack-drops-no-pcb {
      xr:xr-xml-map "tcp_nsr:NumberOfInternalAckDropsNoPCB";
      type uint32;
      description "Number of iACKs dropped because there is no PCB";
    }
    leaf number-of-internal-ack-drops-no-scbdp {
      xr:xr-xml-map "tcp_nsr:NumberOfInternalAckDropsNoSCBDP";
      type uint32;
      description
        "Number of iACKs dropped because there is no
        datapath SCB";
    }
    leaf internal-ack-drops-not-replicated {
      xr:xr-xml-map "tcp_nsr:InternalAckDropsNotReplicated";
      type uint32;
      description
        "Number of iACKs dropped because session is not
        replicated";
    }
    leaf internal-ack-drops-initsync-first-phase {
      xr:xr-xml-map "tcp_nsr:InternalAckDropsInitsyncFirstPhase";
      type uint32;
      description
        "Number of iACKs dropped because init-sync is in
        1st phase";
    }
    leaf internal-ack-drops-stale {
      xr:xr-xml-map "tcp_nsr:InternalAckDropsStale";
      type uint32;
      description "Number of stale iACKs dropped";
    }
    leaf internal-ack-drops-immediate-match {
      xr:xr-xml-map "tcp_nsr:InternalAckDropsImmediateMatch";
      type uint32;
      description
        "Number of iACKs not held because of an immediate
        match";
    }
    leaf held-packet-drops {
      xr:xr-xml-map "tcp_nsr:HeldPacketDrops";
      type uint32;
      description
        "Number of held packets dropped because of errors";
    }

    list notification-statistic {
      description "Various types of notification stats";
      uses TSS-NOTIF-STATS;
    }
  }

  grouping TCP-NSR-SSCB-DETAILED-BAG {
    description "Detailed Information about an SSO/NSR Session-set";
    leaf sscb {
      xr:xr-xml-map "tcp_nsr:SSCB";
      type uint64;
      description "Address of the Session Set Control Block";
    }
    leaf pid {
      xr:xr-xml-map "tcp_nsr:PID";
      type uint32;
      description "PID of the Client that owns this Session-set";
    }
    leaf set-id {
      xr:xr-xml-map "tcp_nsr:SetID";
      type uint32;
      description "ID of this Session-set";
    }
    leaf sso-role {
      xr:xr-xml-map "tcp_nsr:SSORole";
      type uint32;
      description "TCP role for this set?";
    }
    leaf mode {
      xr:xr-xml-map "tcp_nsr:Mode";
      type uint32;
      description "Session-set mode";
    }
    leaf address-family {
      xr:xr-xml-map "tcp_nsr:AddressFamily";
      type Addr-family;
      description "Address Family of the sessions in this set";
    }
    leaf well-known-port {
      xr:xr-xml-map "tcp_nsr:WellKnownPort";
      type uint16;
      description "Well Known Port of the client";
    }
    leaf local-node {
      xr:xr-xml-map "tcp_nsr:LocalNode";
      type xr:Node-id;
      description "Local node of this set";
    }
    leaf local-instance {
      xr:xr-xml-map "tcp_nsr:LocalInstance";
      type uint32;
      description
        "Instance of the client application on the local
        node";
    }
    leaf protect-node {
      xr:xr-xml-map "tcp_nsr:ProtectNode";
      type xr:Node-id;
      description "The node protecting this set";
    }
    leaf protect-instance {
      xr:xr-xml-map "tcp_nsr:ProtectInstance";
      type uint32;
      description
        "Instance of the client application on the
        protection node";
    }
    leaf number-of-sessions {
      xr:xr-xml-map "tcp_nsr:NumberOfSessions";
      type uint32;
      description "Number of Sessions in the set";
    }
    leaf number-of-synced-sessions-up-stream {
      xr:xr-xml-map "tcp_nsr:NumberOfSyncedSessionsUpStream";
      type uint32;
      description
        "How many sessions are synced with upstream
        partner";
    }
    leaf number-of-synced-sessions-down-stream {
      xr:xr-xml-map "tcp_nsr:NumberOfSyncedSessionsDownStream";
      type uint32;
      description
        "How many sessions are synced with downstream
        partner";
    }
    leaf is-init-sync-in-progress {
      xr:xr-xml-map "tcp_nsr:IsInitSyncInProgress";
      type boolean;
      description "Is an initial sync in progress currently?";
    }
    leaf is-init-sync-second-phase {
      xr:xr-xml-map "tcp_nsr:IsInitSyncSecondPhase";
      type boolean;
      description "Is initial sync in the second phase?";
    }
    leaf sequence-number-of-init-sync {
      xr:xr-xml-map "tcp_nsr:SequenceNumberOfInitSync";
      type uint32;
      description
        "ID of the current or the last initial sync
        operation";
    }
    leaf init-sync-timer {
      xr:xr-xml-map "tcp_nsr:InitSyncTimer";
      type uint32;
      description "Time left on the initial sync timer";
    }
    leaf total-number-of-init-sync-sessions {
      xr:xr-xml-map "tcp_nsr:TotalNumberOfInitSyncSessions";
      type uint32;
      description
        "Number of sessions being synced as part of the
        current initial sync operation";
    }
    leaf number-of-init-synced-sessions {
      xr:xr-xml-map "tcp_nsr:NumberOfInitSyncedSessions";
      type uint32;
      description
        "Number of sessions that are synced as part of
        the current initial sync operation";
    }
    leaf number-of-sessions-init-sync-failed {
      xr:xr-xml-map "tcp_nsr:NumberOfSessionsInitSyncFailed";
      type uint32;
      description
        "Number of sessions that failed to sync as part
        of the current initial sync operation";
    }
    leaf init-sync-error {
      xr:xr-xml-map "tcp_nsr:InitSyncError";
      type string;
      description "Initial sync failure reason, if any";
    }
    leaf is-init-sync-error-local {
      xr:xr-xml-map "tcp_nsr:IsInitSyncErrorLocal";
      type boolean;
      description
        "Initial sync failed due to a local error or
        remote stack";
    }
    leaf init-sync-start-time {
      xr:xr-xml-map "tcp_nsr:InitSyncStartTime";
      type uint32;
      units "second";
      description
        "Time at which last or current initial sync
        operation was started (in seconds since 1st Jan
        1970 00:00:00)";
    }
    leaf init-sync-end-time {
      xr:xr-xml-map "tcp_nsr:InitSyncEndTime";
      type uint32;
      units "second";
      description
        "Time at which the last initial sync operation
        was ended (in seconds since 1st Jan 1970 00:00
        :00)";
    }
    leaf is-sscb-init-sync-ready {
      xr:xr-xml-map "tcp_nsr:IsSSCBInitSyncReady";
      type boolean;
      description "Is the SSCB ready for another initial sync?";
    }
    leaf init-sync-ready-start-time {
      xr:xr-xml-map "tcp_nsr:InitSyncReadyStartTime";
      type uint32;
      units "second";
      description
        "Time at which the session was ready for initial
        sync last (in seconds since 1st Jan 1970 00:00
        :00)";
    }
    leaf init-sync-ready-end-time {
      xr:xr-xml-map "tcp_nsr:InitSyncReadyEndTime";
      type uint32;
      units "second";
      description
        "Time at which the session set last went
        not-ready for initial sync (in seconds since 1st
        Jan 1970 00:00:00)";
    }
    leaf nsr-reset-time {
      xr:xr-xml-map "tcp_nsr:NSRResetTime";
      type uint32;
      units "second";
      description
        "Time at which NSR was last reset on the session
        set (in seconds since 1st Jan 1970 00:00:00)";
    }
    leaf is-audit-in-progress {
      xr:xr-xml-map "tcp_nsr:IsAuditInProgress";
      type boolean;
      description "Is an audit in progress currently?";
    }
    leaf audit-seq-number {
      xr:xr-xml-map "tcp_nsr:AuditSeqNumber";
      type uint32;
      description "ID of the current or the last audit operation";
    }
    leaf audit-start-time {
      xr:xr-xml-map "tcp_nsr:AuditStartTime";
      type uint32;
      units "second";
      description
        "Time at which last or current audit operation
        was started (in seconds since 1st Jan 1970 00:00
        :00)";
    }
    leaf audit-end-time {
      xr:xr-xml-map "tcp_nsr:AuditEndTime";
      type uint32;
      units "second";
      description
        "Time at which the last audit operation was ended
        (in seconds since 1st Jan 1970 00:00:00)";
    }
  }

  grouping TCP-NSR-CCB-BRIEF-BAG {
    description "Summary Information about an SSO/NSR Client";
    leaf ccb {
      xr:xr-xml-map "tcp_nsr:CCB";
      type uint64;
      description "Address of the Client Control Block";
    }
    leaf pid {
      xr:xr-xml-map "tcp_nsr:PID";
      type uint32;
      description "PID of the Client";
    }
    leaf process-name {
      xr:xr-xml-map "tcp_nsr:ProcessName";
      type string;
      description "Proc name of Clinet";
    }
    leaf job-id {
      xr:xr-xml-map "tcp_nsr:JobID";
      type int32;
      description "JOb ID of Client";
    }
    leaf instance {
      xr:xr-xml-map "tcp_nsr:Instance";
      type uint32;
      description "Instance of the Client";
    }
    leaf numberof-sets {
      xr:xr-xml-map "tcp_nsr:NumberofSets";
      type uint32;
      description "Number of Sets owned by this client ";
    }
    leaf number-of-sessions {
      xr:xr-xml-map "tcp_nsr:NumberOfSessions";
      type uint32;
      description "Number of sessions owned by this client ";
    }
    leaf number-of-up-sessions {
      xr:xr-xml-map "tcp_nsr:NumberOfUpSessions";
      type uint32;
      description "Number of sessions with NSR up ";
    }
  }

  grouping TCP-NSR-CCB-DETAILED-BAG {
    description "Detailed Information about an SSO/NSR Client";
    leaf ccb {
      xr:xr-xml-map "tcp_nsr:CCB";
      type uint64;
      description "Address of the Client Control Block";
    }
    leaf pid {
      xr:xr-xml-map "tcp_nsr:PID";
      type uint32;
      description "PID of the Client";
    }
    leaf process-name {
      xr:xr-xml-map "tcp_nsr:ProcessName";
      type string;
      description "Proc name of Clinet";
    }
    leaf job-id {
      xr:xr-xml-map "tcp_nsr:JobID";
      type int32;
      description "JOb ID of Client";
    }
    leaf instance {
      xr:xr-xml-map "tcp_nsr:Instance";
      type uint32;
      description "Instance of the Client";
    }
    leaf numberof-sets {
      xr:xr-xml-map "tcp_nsr:NumberofSets";
      type uint32;
      description "Number of Sets owned by this client ";
    }
    leaf number-of-sessions {
      xr:xr-xml-map "tcp_nsr:NumberOfSessions";
      type uint32;
      description "Number of sessions owned by this client ";
    }
    leaf number-of-up-sessions {
      xr:xr-xml-map "tcp_nsr:NumberOfUpSessions";
      type uint32;
      description "Number of sessions with NSR up";
    }
    leaf connected-at {
      xr:xr-xml-map "tcp_nsr:ConnectedAt";
      type uint32;
      units "second";
      description
        "Time of connect (in seconds since 1st Jan 1970
        00:00:00)";
    }
    leaf is-notification-registered {
      xr:xr-xml-map "tcp_nsr:IsNotificationRegistered";
      type boolean;
      description "Registered with TCP for notifications?";
    }
  }

  grouping TCP-NSR-HOLD-QUEUE-NODE {
    description "Info about the Packet or iACK held";
    leaf sequence-number {
      xr:xr-xml-map "tcp_nsr:SequenceNumber";
      type uint32;
      description "Sequence Number";
    }
    leaf data-length {
      xr:xr-xml-map "tcp_nsr:DataLength";
      type uint32;
      description "Data Length";
    }
    leaf acknoledgement-number {
      xr:xr-xml-map "tcp_nsr:AcknoledgementNumber";
      type uint32;
      description "Ack Number";
    }
  }

  grouping TCP-NSR-SSCB-BRIEF-BAG {
    description "Summary Information about an SSO/NSR Session-set";
    leaf sscb {
      xr:xr-xml-map "tcp_nsr:SSCB";
      type uint64;
      description "Address of the Session Set Control Block";
    }
    leaf pid {
      xr:xr-xml-map "tcp_nsr:PID";
      type uint32;
      description "PID of the Client that owns this Session-set";
    }
    leaf client-name {
      xr:xr-xml-map "tcp_nsr:ClientName";
      type string;
      description "the name of Clinet that owns this Session-set";
    }
    leaf client-instance {
      xr:xr-xml-map "tcp_nsr:ClientInstance";
      type uint32;
      description
        "Instance of the Client that owns this
        Session-set";
    }
    leaf set-id {
      xr:xr-xml-map "tcp_nsr:SetID";
      type uint32;
      description "ID of this Session-set";
    }
    leaf sso-role {
      xr:xr-xml-map "tcp_nsr:SSORole";
      type uint32;
      description "TCP role for this set?";
    }
    leaf mode {
      xr:xr-xml-map "tcp_nsr:Mode";
      type uint32;
      description "Session-set mode";
    }
    leaf address-family {
      xr:xr-xml-map "tcp_nsr:AddressFamily";
      type Addr-family;
      description "Address Family of the sessions in this set";
    }
    leaf well-known-port {
      xr:xr-xml-map "tcp_nsr:WellKnownPort";
      type uint16;
      description "Well Known Port of the client";
    }
    leaf local-node {
      xr:xr-xml-map "tcp_nsr:LocalNode";
      type xr:Node-id;
      description "Local node of this set";
    }
    leaf local-instance {
      xr:xr-xml-map "tcp_nsr:LocalInstance";
      type uint32;
      description
        "Instance of the client application on the local
        node";
    }
    leaf protect-node {
      xr:xr-xml-map "tcp_nsr:ProtectNode";
      type xr:Node-id;
      description "The node protecting this set";
    }
    leaf protect-instance {
      xr:xr-xml-map "tcp_nsr:ProtectInstance";
      type uint32;
      description
        "Instance of the client application on the
        protection node";
    }
    leaf number-of-sessions {
      xr:xr-xml-map "tcp_nsr:NumberOfSessions";
      type uint32;
      description "Number of Sessions in the set";
    }
    leaf number-of-synced-sessions-up-stream {
      xr:xr-xml-map "tcp_nsr:NumberOfSyncedSessionsUpStream";
      type uint32;
      description
        "How many sessions are synced with upstream
        partner";
    }
    leaf number-of-synced-sessions-down-stream {
      xr:xr-xml-map "tcp_nsr:NumberOfSyncedSessionsDownStream";
      type uint32;
      description
        "How many sessions are synced with downstream
        partner";
    }
    leaf is-init-sync-in-progress {
      xr:xr-xml-map "tcp_nsr:IsInitSyncInProgress";
      type boolean;
      description "Is an initial sync in progress currently?";
    }
    leaf is-sscb-init-sync-ready {
      xr:xr-xml-map "tcp_nsr:IsSSCBInitSyncReady";
      type boolean;
      description "Is the SSCB ready for another initial sync?";
    }
  }

  grouping TCP-NSR-PCB-DETAILED-BAG {
    description
      "Detailed SSO/NSR information about a TCP
      connection";

    container set-information {
      description "Sesson-set information";
      uses TCP-NSR-SSCB-BRIEF-BAG;
    }
    leaf address-family {
      xr:xr-xml-map "tcp_nsr:AddressFamily";
      type Addr-family;
      description "Address family";
    }
    leaf pcb {
      xr:xr-xml-map "tcp_nsr:PCB";
      type uint64;
      description "PCB Address";
    }
    leaf sscb {
      xr:xr-xml-map "tcp_nsr:SSCB";
      type uint64;
      description "SSCB Address";
    }
    leaf local-port {
      xr:xr-xml-map "tcp_nsr:LocalPort";
      type uint16;
      description "Local port";
    }
    leaf foreign-port {
      xr:xr-xml-map "tcp_nsr:ForeignPort";
      type uint16;
      description "Foreign port";
    }
    leaf vrf-id {
      xr:xr-xml-map "tcp_nsr:VRF_ID";
      type uint32;
      description "VRF Id";
    }
    leaf is-admin-configured-up {
      xr:xr-xml-map "tcp_nsr:IsAdminConfiguredUp";
      type boolean;
      description "Is NSR administratively configured?";
    }
    leaf is-us-operational-up {
      xr:xr-xml-map "tcp_nsr:IsUsOperationalUp";
      type Nsr-status;
      description "Is Upstream NSR operational?";
    }
    leaf is-ds-operational-up {
      xr:xr-xml-map "tcp_nsr:IsDsOperationalUp";
      type Nsr-status;
      description "Is Downstream NSR operational?";
    }
    leaf is-only-receive-path-replication {
      xr:xr-xml-map "tcp_nsr:IsOnlyReceivePathReplication";
      type boolean;
      description "Is replication limited to receive-path only";
    }
    leaf cookie {
      xr:xr-xml-map "tcp_nsr:Cookie";
      type uint64;
      description "Cookie provided by active APP";
    }
    leaf is-session-replicated {
      xr:xr-xml-map "tcp_nsr:IsSessionReplicated";
      type boolean;
      description "Has the session been replicated to standby?";
    }
    leaf is-session-synced {
      xr:xr-xml-map "tcp_nsr:IsSessionSynced";
      type boolean;
      description "Has the session completed initial-sync?";
    }
    leaf fist-standby-sequence-number {
      xr:xr-xml-map "tcp_nsr:FistStandbySequenceNumber";
      type uint32;
      description
        "If initial sync is completed, then the FSSN -
        First Standby Sequence Number";
    }
    leaf fssn-offset {
      xr:xr-xml-map "tcp_nsr:FSSNOffset";
      type uint32;
      description "Offset of FSSN in input stream";
    }
    leaf nsr-down-reason {
      xr:xr-xml-map "tcp_nsr:NSRDownReason";
      type Nsr-down-reason;
      description "If NSR is not up, the reason for it.";
    }
    leaf nsr-down-time {
      xr:xr-xml-map "tcp_nsr:NSRDownTime";
      type uint32;
      description "Time at which NSR went down";
    }
    leaf sequence-number-of-init-sync {
      xr:xr-xml-map "tcp_nsr:SequenceNumberOfInitSync";
      type uint32;
      description "ID of the Initial sync operation";
    }
    leaf is-init-sync-in-progress {
      xr:xr-xml-map "tcp_nsr:IsInitSyncInProgress";
      type boolean;
      description "Is initial-sync currently in progress?";
    }
    leaf is-init-sync-second-phase {
      xr:xr-xml-map "tcp_nsr:IsInitSyncSecondPhase";
      type boolean;
      description "Is initial sync in the second phase?";
    }
    leaf init-sync-error {
      xr:xr-xml-map "tcp_nsr:InitSyncError";
      type string;
      description "Initial sync failure reason, if any";
    }
    leaf is-init-sync-error-local {
      xr:xr-xml-map "tcp_nsr:IsInitSyncErrorLocal";
      type boolean;
      description
        "Initial sync failed due to a local error or
        remote stack";
    }
    leaf init-sync-start-time {
      xr:xr-xml-map "tcp_nsr:InitSyncStartTime";
      type uint32;
      units "second";
      description
        "Time at which the initial sync operation was
        started (in seconds since 1st Jan 1970 00:00:00)";
    }
    leaf init-sync-end-time {
      xr:xr-xml-map "tcp_nsr:InitSyncEndTime";
      type uint32;
      units "second";
      description
        "Time at which the initial sync operation was
        ended (in seconds since 1st Jan 1970 00:00:00)";
    }
    leaf init-sync-flags {
      xr:xr-xml-map "tcp_nsr:InitSyncFlags";
      type uint32;
      description "Init Sync flags for the session";
    }
    leaf sequence-number-of-init-sync-up-stream {
      xr:xr-xml-map "tcp_nsr:SequenceNumberOfInitSyncUpStream";
      type uint32;
      description "ID of the Initial sync operation";
    }
    leaf peer-endp-hdl-up-stream {
      xr:xr-xml-map "tcp_nsr:PeerEndpHdlUpStream";
      type uint64;
      description "Peer NCD endp handle";
    }
    leaf init-sync-start-time-up-stream {
      xr:xr-xml-map "tcp_nsr:InitSyncStartTimeUpStream";
      type uint32;
      units "second";
      description
        "Time at which the initial sync operation was
        started (in seconds since 1st Jan 1970 00:00:00)";
    }
    leaf init-sync-end-time-up-stream {
      xr:xr-xml-map "tcp_nsr:InitSyncEndTimeUpStream";
      type uint32;
      units "second";
      description
        "Time at which the initial sync operation was
        ended (in seconds since 1st Jan 1970 00:00:00)";
    }
    leaf fist-standby-sequence-number-up-stream {
      xr:xr-xml-map "tcp_nsr:FistStandbySequenceNumberUpStream";
      type uint32;
      description "FSSN for the upstream partner";
    }
    leaf nsr-down-reason-up-stream {
      xr:xr-xml-map "tcp_nsr:NSRDownReasonUpStream";
      type Nsr-down-reason;
      description
        "The reason NSR is not up towards the upstream
        partner";
    }
    leaf nsr-down-time-up-stream {
      xr:xr-xml-map "tcp_nsr:NSRDownTimeUpStream";
      type uint32;
      description "Time at which NSR went down";
    }
    leaf sequence-number-of-init-sync-down-stream {
      xr:xr-xml-map "tcp_nsr:SequenceNumberOfInitSyncDownStream";
      type uint32;
      description "ID of the Initial sync operation";
    }
    leaf peer-endp-hdl-down-stream {
      xr:xr-xml-map "tcp_nsr:PeerEndpHdlDownStream";
      type uint64;
      description "Peer NCD endp handle";
    }
    leaf init-sync-start-time-down-stream {
      xr:xr-xml-map "tcp_nsr:InitSyncStartTimeDownStream";
      type uint32;
      units "second";
      description
        "Time at which the initial sync operation was
        started (in seconds since 1st Jan 1970 00:00:00)";
    }
    leaf init-sync-end-time-down-stream {
      xr:xr-xml-map "tcp_nsr:InitSyncEndTimeDownStream";
      type uint32;
      units "second";
      description
        "Time at which the initial sync operation was
        ended (in seconds since 1st Jan 1970 00:00:00)";
    }
    leaf fist-standby-sequence-number-down-stream {
      xr:xr-xml-map "tcp_nsr:FistStandbySequenceNumberDownStream";
      type uint32;
      description "FSSN for the upstream partner";
    }
    leaf nsr-down-reason-down-stream {
      xr:xr-xml-map "tcp_nsr:NSRDownReasonDownStream";
      type Nsr-down-reason;
      description
        "The reason NSR is not up towards the upstream
        partner";
    }
    leaf nsr-down-time-down-stream {
      xr:xr-xml-map "tcp_nsr:NSRDownTimeDownStream";
      type uint32;
      description "Time at which NSR went down";
    }
    leaf max-number-of-held-packet {
      xr:xr-xml-map "tcp_nsr:MaxNumberOfHeldPacket";
      type int32;
      description "Max number of incoming packets have been held";
    }
    leaf max-number-of-held-packet-reach-time {
      xr:xr-xml-map "tcp_nsr:MaxNumberOfHeldPacketReachTime";
      type uint32;
      description "Max number of held incoming packets reaches at";
    }
    leaf max-number-of-held-internal-ack {
      xr:xr-xml-map "tcp_nsr:MaxNumberOfHeldInternalAck";
      type int32;
      description "Max number of internal acks have been held";
    }
    leaf max-number-of-held-internal-ack-reach-time {
      xr:xr-xml-map "tcp_nsr:MaxNumberOfHeldInternalAckReachTime";
      type uint32;
      description "Max number of held internal acks reaches at";
    }
    leaf-list local-address {
      xr:xr-xml-map "tcp_nsr:LocalAddress";
      type inet:ipv4-address;
      max-elements "4";
      description "Local address";
    }
    leaf-list foreign-address {
      xr:xr-xml-map "tcp_nsr:ForeignAddress";
      type inet:ipv4-address;
      max-elements "4";
      description "Foreign address";
    }

    list packet-hold-queue {
      description
        "Sequence Number and datalength of each node in
        hold_pakqueue";
      uses TCP-NSR-HOLD-QUEUE-NODE;
    }

    list internal-ack-hold-queue {
      description
        "Sequence Number and datalength of each node in
        hold_iackqueue";
      uses TCP-NSR-HOLD-QUEUE-NODE;
    }
  }

  grouping TCP-NSR-PCB-BRIEF-BAG {
    description "Summary NSR information about a TCP connection";
    leaf address-family {
      xr:xr-xml-map "tcp_nsr:AddressFamily";
      type Addr-family;
      description "Address family";
    }
    leaf pcb {
      xr:xr-xml-map "tcp_nsr:PCB";
      type uint64;
      description "PCB Address";
    }
    leaf sscb {
      xr:xr-xml-map "tcp_nsr:SSCB";
      type uint64;
      description "SSCB Address";
    }
    leaf local-port {
      xr:xr-xml-map "tcp_nsr:LocalPort";
      type uint16;
      description "Local port";
    }
    leaf foreign-port {
      xr:xr-xml-map "tcp_nsr:ForeignPort";
      type uint16;
      description "Foreign port";
    }
    leaf vrf-id {
      xr:xr-xml-map "tcp_nsr:VRF_ID";
      type uint32;
      description "VRF Id";
    }
    leaf is-admin-configured-up {
      xr:xr-xml-map "tcp_nsr:IsAdminConfiguredUp";
      type boolean;
      description "Is NSR administratively configured?";
    }
    leaf is-us-operational-up {
      xr:xr-xml-map "tcp_nsr:IsUsOperationalUp";
      type Nsr-status;
      description "Is Upstream NSR operational?";
    }
    leaf is-ds-operational-up {
      xr:xr-xml-map "tcp_nsr:IsDsOperationalUp";
      type Nsr-status;
      description "Is Downstream NSR operational?";
    }
    leaf is-only-receive-path-replication {
      xr:xr-xml-map "tcp_nsr:IsOnlyReceivePathReplication";
      type boolean;
      description "Is replication limited to receive-path only";
    }
    leaf-list local-address {
      xr:xr-xml-map "tcp_nsr:LocalAddress";
      type inet:ipv4-address;
      max-elements "4";
      description "Local address";
    }
    leaf-list foreign-address {
      xr:xr-xml-map "tcp_nsr:ForeignAddress";
      type inet:ipv4-address;
      max-elements "4";
      description "Foreign address";
    }
  }
}
