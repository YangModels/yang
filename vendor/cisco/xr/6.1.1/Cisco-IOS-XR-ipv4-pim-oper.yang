module Cisco-IOS-XR-ipv4-pim-oper {

  /*** NAMESPACE / PREFIX DEFINITION ***/

  namespace "http://cisco.com/ns/yang/Cisco-IOS-XR-ipv4-pim-oper";


  prefix "ipv4-pim-oper";

  /*** LINKAGE (IMPORTS / INCLUDES) ***/

  import ietf-inet-types { prefix "inet"; }

  import Cisco-IOS-XR-types { prefix "xr"; }

  include Cisco-IOS-XR-ipv4-pim-oper-sub2 {
    revision-date 2015-11-09;
  }

  include Cisco-IOS-XR-ipv4-pim-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ipv4-pim package operational data.

     This module contains definitions
     for the following management objects:
       pim-ma: PIM MA operational data
       pim: pim
       ipv6-pim: ipv6 pim
       pim6-ma: pim6 ma

     Copyright (c) 2013-2016 by Cisco Systems, Inc.
     All rights reserved.";

  revision "2015-11-09" {
    description
      "IOS XR 6.0 revision.";
  }

  typedef Pim-topology-interface-flag {
    type enumeration {
      enum lh {
        value 0;
        description "LH";
      }
      enum ld {
        value 1;
        description "LD";
      }
      enum li {
        value 2;
        description "LI";
      }
      enum ii {
        value 3;
        description "II";
      }
      enum id {
        value 4;
        description "ID";
      }
      enum as {
        value 5;
        description "AS";
      }
      enum ab {
        value 6;
        description "AB";
      }
      enum ex {
        value 7;
        description "EX";
      }
    }
    description "Pim topology interface flag";
  }
  typedef Pim-safi {
    type enumeration {
      enum unicast {
        value 1;
        description "SAFI unicast";
      }
      enum multicast {
        value 2;
        description "SAFI Multicast";
      }
      enum all {
        value 3;
        description "SAFI all";
      }
      enum default {
        value 4;
        description "SAFI default";
      }
    }
    description "Pim safi";
  }
  typedef Pim-client {
    type enumeration {
      enum none {
        value 0;
        description "No Client";
      }
      enum configured-embedded-rp {
        value 1;
        description "Embedded RP from configuration";
      }
      enum embedded {
        value 2;
        description "Embedded RP learnt from the Group addr";
      }
      enum permanent {
        value 3;
        description "Permanent";
      }
      enum auto-rp {
        value 4;
        description "AutoRP";
      }
      enum bsr {
        value 5;
        description "BSR";
      }
      enum configured {
        value 6;
        description "Configured";
      }
      enum static {
        value 7;
        description "Static";
      }
    }
    description "Pim client";
  }
  typedef Pim-topology-entry-flag {
    type enumeration {
      enum kat {
        value 0;
        description "KAT";
      }
      enum aa {
        value 1;
        description "AA";
      }
      enum pa {
        value 2;
        description "PA";
      }
      enum ra {
        value 3;
        description "RA";
      }
      enum ia {
        value 4;
        description "IA";
      }
      enum rr {
        value 5;
        description "RR";
      }
      enum lh {
        value 6;
        description "LH";
      }
      enum dss {
        value 7;
        description "DSS";
      }
      enum dcc {
        value 8;
        description "DCC";
      }
      enum sr {
        value 9;
        description "SR";
      }
      enum e {
        value 10;
        description "E";
      }
      enum ex {
        value 11;
        description "EX";
      }
      enum ma {
        value 12;
        description "MA";
      }
      enum mt {
        value 13;
        description "MT";
      }
      enum mfa {
        value 14;
        description "MFA";
      }
      enum mfp {
        value 15;
        description "MFP";
      }
      enum mfb {
        value 16;
        description "MFB";
      }
    }
    description "Pim topology entry flag";
  }
  typedef Pim-protocol {
    type enumeration {
      enum non-routable {
        value 0;
        description "Non Routable";
      }
      enum sparse-mode {
        value 1;
        description "Sparse Mode";
      }
      enum dense-mode {
        value 2;
        description "Dense Mode";
      }
      enum bidir {
        value 3;
        description "Bidirectional Mode";
      }
      enum ssm {
        value 4;
        description "Source Specific Multicast Mode";
      }
      enum maximum {
        value 5;
        description "Maximum";
      }
      enum any {
        value 6;
        description "Any";
      }
    }
    description "Pim protocol";
  }

  grouping AUTO-RP {
    description "Common node of vrf, default-context";

    container auto-rp {
      xr:xr-xml-map "ipv4_pim_common_oper:AutoRP";
      description "PIM Auto-RP information";
    }
  }

  grouping ROUTE-POLICY {
    description "Common node of vrf, default-context";

    container route-policy {
      xr:xr-xml-map "ipv4_pim_common_oper:RoutePolicy";
      description "PIM route policy";

      container route-policy-statistics {
        xr:xr-xml-map "ipv4_pim_common_oper:RoutePolicyStatistics";
        description "PIM route policy statistics";
        uses PIM-RPF-POLICY-STATS-BAG;
      }

      container route-policy-tests {
        xr:xr-xml-map "ipv4_pim_common_oper:RoutePolicyTestTable";
        description "PIM route policy test run table";

        list route-policy-test {
          xr:xr-xml-map "ipv4_pim_common_oper:RoutePolicyTest";
          description "PIM route policy test run";
          leaf source-address {
            xr:xr-xml-map "ipv4_pim_common_oper:SourceAddress";
            type inet:ip-address-no-zone;
            description "Source IP address";
          }
          leaf group-address {
            xr:xr-xml-map "ipv4_pim_common_oper:GroupAddress";
            type inet:ip-address-no-zone;
            description "Group IP address";
          }
          leaf ext-comm {
            xr:xr-xml-map "ipv4_pim_common_oper:ExtComm";
            type xr:Cisco-ios-xr-string;
            description "Extended Community";
          }
          uses PIM-RPF-POLICY-TEST-BAG;
        }
      }
    }
  }

  grouping GROUP-MAP-SOURCE-TABLE {
    description "Common node of vrf, default-context";

    container group-map-sources {
      xr:xr-xml-map "ipv4_pim_common_oper:GroupMapSourceTable";
      description "PIM group-mapping with source information";

      list group-map-source {
        xr:xr-xml-map "ipv4_pim_common_oper:GroupMapSource";
        description
          "PIM Group Mapping Entry with source information";
        leaf prefix {
          xr:xr-xml-map "ipv4_pim_common_oper:Prefix";
          type inet:ip-address-no-zone;
          description "Prefix";
        }
        leaf prefix-length {
          xr:xr-xml-map "ipv4_pim_common_oper:PrefixLength";
          type int32;
          description "Prefix length";
        }
        leaf client {
          xr:xr-xml-map "ipv4_pim_common_oper:Client";
          type Pim-client;
          description "Client";
        }
        leaf protocol {
          xr:xr-xml-map "ipv4_pim_common_oper:Protocol";
          type Pim-protocol;
          description "Protocol";
        }
        leaf rp-address {
          xr:xr-xml-map "ipv4_pim_common_oper:RPAddress";
          type inet:ip-address-no-zone;
          description "RP address";
        }
        leaf priority {
          xr:xr-xml-map "ipv4_pim_common_oper:Priority";
          type int32;
          description "RP Priority";
        }
        uses PIM-GRP-MAP-INFOSRC-BAG;
      }
    }
  }

  grouping BIDIR-DF-STATE-TABLE {
    description "Common node of vrf, default-context";

    container bidir-df-states {
      xr:xr-xml-map "ipv4_pim_common_oper:BidirDFStateTable";
      description "Bidirectional PIM DF election state table";

      list bidir-df-state {
        xr:xr-xml-map "ipv4_pim_common_oper:BidirDFState";
        description "Bidirectional PIM DF Election Table Entry";
        leaf rp-address {
          xr:xr-xml-map "ipv4_pim_common_oper:RPAddress";
          type inet:ip-address-no-zone;
          description "RP address";
        }
        leaf interface-name {
          xr:xr-xml-map "ipv4_pim_common_oper:InterfaceName";
          type xr:Interface-name;
          description "Interface name";
        }
        uses PIM-BIDIR-DF-STATE-BAG;
      }
    }
  }

  grouping MIB-DATABASE-TABLE {
    description "Common node of vrf, default-context";

    container mib-databases {
      xr:xr-xml-map "ipv4_pim_common_oper:MIBDatabaseTable";
      description "PIM group database for mroute mibs table";

      list mib-database {
        xr:xr-xml-map "ipv4_pim_common_oper:MIBDatabase";
        description "PIM multicast static route information";
        leaf source-address {
          xr:xr-xml-map "ipv4_pim_common_oper:SourceAddress";
          type inet:ip-address-no-zone;
          description "Multicast static route source address";
        }
        leaf group-address {
          xr:xr-xml-map "ipv4_pim_common_oper:GroupAddress";
          type inet:ip-address-no-zone;
          description "Multicast satic route group address";
        }
        leaf source-netmask {
          xr:xr-xml-map "ipv4_pim_common_oper:SourceNetmask";
          type int32;
          description "Source mask";
        }
        uses PIM-MROUTE-BAG;
      }
    }
  }

  grouping BGP-AF-TABLE {
    description "Common node of vrf, default-context";

    container bgp-afs {
      xr:xr-xml-map "ipv4_pim_common_oper:BGP_AFTable";
      description "PIM BGP SAFI table";

      list bgp-af {
        xr:xr-xml-map "ipv4_pim_common_oper:BGP_AF";
        description "PIM BGP SAFI information";
        leaf source-address {
          xr:xr-xml-map "ipv4_pim_common_oper:SourceAddress";
          type inet:ip-address-no-zone;
          description "Source IP address";
        }
        leaf group-address {
          xr:xr-xml-map "ipv4_pim_common_oper:GroupAddress";
          type inet:ip-address-no-zone;
          description "Group IP address";
        }
        uses PIM-BGP-SAFI-BAG;
      }
    }
  }

  grouping TOPOLOGY-ENTRY-FLAG-ROUTE-COUNT-TABLE {
    description "Common node of vrf, default-context";

    container topology-entry-flag-route-counts {
      xr:xr-xml-map "ipv4_pim_common_oper:TopologyEntryFlagRouteCou"+
        "ntTable";
      description "Route count for topology with entry flag set";

      list topology-entry-flag-route-count {
        xr:xr-xml-map "ipv4_pim_common_oper:TopologyEntryFlagRouteC"+
          "ount";
        key "entry-flag";
        description "Route count for topology with entry flag set";
        leaf entry-flag {
          xr:xr-xml-map "ipv4_pim_common_oper:EntryFlag";
          type Pim-topology-entry-flag;
          description "entry flag";
        }
        uses PIM-TT-SUMM-BAG;
      }
    }
  }

  grouping BIDIR-DF-WINNER-TABLE {
    description "Common node of vrf, default-context";

    container bidir-df-winners {
      xr:xr-xml-map "ipv4_pim_common_oper:BidirDFWinnerTable";
      description "Bidirectional PIM DF election winner table";

      list bidir-df-winner {
        xr:xr-xml-map "ipv4_pim_common_oper:BidirDFWinner";
        description "Bidirectional PIM DF election table entry";
        leaf rp-address {
          xr:xr-xml-map "ipv4_pim_common_oper:RPAddress";
          type inet:ip-address-no-zone;
          description "RP address";
        }
        leaf interface-name {
          xr:xr-xml-map "ipv4_pim_common_oper:InterfaceName";
          type xr:Interface-name;
          description "Interface name";
        }
        uses PIM-BIDIR-DF-BAG;
      }
    }
  }

  grouping TABLE-CONTEXT-TABLE {
    description "Common node of vrf, default-context";

    container table-contexts {
      xr:xr-xml-map "ipv4_pim_common_oper:TableContextTable";
      description "PIM table context list";

      list table-context {
        xr:xr-xml-map "ipv4_pim_common_oper:TableContext";
        description "PIM table context information";
        leaf saf-name {
          xr:xr-xml-map "ipv4_pim_common_oper:SAFName";
          type Pim-safi;
          description "SAF name";
        }
        leaf topology-name {
          xr:xr-xml-map "ipv4_pim_common_oper:TopologyName";
          type xr:Cisco-ios-xr-string;
          description "Topology name";
        }
        uses PIM-TABLE-CTX-BAG;
      }
    }
  }

  grouping VRF-TABLE {
    description "Common node of active, standby";

    container vrfs {
      xr:xr-xml-map "ipv4_pim_common_oper:VRFTable";
      description "VRF Table";

      list vrf {
        xr:xr-xml-map "ipv4_pim_common_oper:VRF";
        key "vrf-name";
        description "VRF name";
        leaf vrf-name {
          xr:xr-xml-map "ipv4_pim_common_oper:VRFName";
          type xr:Cisco-ios-xr-string;
          description "VRF name ";
        }
        uses IFRS-INTERFACE-TABLE;
        uses SAF-TABLE;
        uses INTERFACE-STATISTICS-TABLE;
        uses TOPOLOGY-ROUTE-COUNT;
        uses JP-STATISTICS-TABLE;
        uses MIB-DATABASE-TABLE;
        uses GROUP-MAP-MATCH-RPF-TABLE;
        uses NEIGHBOR-OLD-FORMAT-TABLE;
        uses IFRS-SUMMARY;
        uses RANGE-LIST-TABLE;
        uses INTERFACE-OLD-FORMAT-TABLE;
        uses BSR;
        uses ROUTE-POLICY;
        uses RPF-SUMMARY;
        uses IPV4-PIM-COMMON-OPER-INTERFACE-TABLE;
        uses NET-IO-TUNNEL-TABLE;
        uses BIDIR-DF-STATE-TABLE;
        uses TOPOLOGY-TABLE;
        uses BGP-AF-TABLE;
        uses AUTO-RP;
        uses TOPOLOGY-INTERFACE-FLAG-ROUTE-COUNT-TABLE;
        uses GROUP-MAP-SOURCE-TABLE;
        uses TRAFFIC-COUNTERS;
        uses GROUP-MAP-RPF-TABLE;
        uses SUMMARY;
        uses GRE;
        uses BIDIR-DF-WINNER-TABLE;
        uses TABLE-CONTEXT-TABLE;
        uses GLOBAL-INTERFACE-TABLE;
        uses NEIGHBOR-SUMMARY-TABLE;
        uses CONTEXT;
        uses TOPOLOGY-ENTRY-FLAG-ROUTE-COUNT-TABLE;
        uses RPF-REDIRECT;
        uses TUNNEL-TABLE;
        uses MULTICAST-STATIC-ROUTE-TABLE;
        uses GROUP-MAP-MATCH-SOURCE-TABLE;
        uses NEIGHBOR-TABLE;
      }
    }
  }

  grouping BSR {
    description "Common node of vrf, default-context";

    container bsr {
      xr:xr-xml-map "ipv4_pim_common_oper:BSR";
      description "PIM BSR information";

      container rp-caches {
        xr:xr-xml-map "ipv4_pim_common_oper:RPCacheTable";
        description "PIM BSR RP cache table";

        list rp-cache {
          xr:xr-xml-map "ipv4_pim_common_oper:RPCache";
          key "group-prefix";
          description "PIM BSR RP cache";
          leaf group-prefix {
            xr:xr-xml-map "ipv4_pim_common_oper:GroupPrefix";
            type inet:ip-address-no-zone;
            description "Group prefix";
          }
          uses PIM-BSR-RP-CACHE-BAG;
        }
      }

      container candidate-rps {
        xr:xr-xml-map "ipv4_pim_common_oper:CandidateRPTable";
        description "PIM candidate-RP";

        list candidate-rp {
          xr:xr-xml-map "ipv4_pim_common_oper:CandidateRP";
          key "rp-address";
          description "PIM BSR candidate RP information";
          leaf rp-address {
            xr:xr-xml-map "ipv4_pim_common_oper:RPAddress";
            type inet:ip-address-no-zone;
            description "Candidate-RP address";
          }
          uses PIM-BSR-CANDIDATE-RP-BAG;
        }
      }

      container bsr-elections {
        xr:xr-xml-map "ipv4_pim_common_oper:BSRElectionTable";
        description "PIM BSR election state";

        list bsr-election {
          xr:xr-xml-map "ipv4_pim_common_oper:BSRElection";
          key "pim-scope";
          description "PIM BSR information";
          leaf pim-scope {
            xr:xr-xml-map "ipv4_pim_common_oper:PIMScope";
            type int32;
            description "BSR information";
          }
          uses PIM-BSR-ELECTION-BAG;
        }
      }
    }
  }

  grouping NET-IO-TUNNEL-TABLE {
    description "Common node of vrf, default-context";

    container net-io-tunnels {
      xr:xr-xml-map "ipv4_pim_common_oper:NetIOTunnelTable";
      description "Tunnel information that NETIO has ";

      list net-io-tunnel {
        xr:xr-xml-map "ipv4_pim_common_oper:NetIOTunnel";
        key "tunnel-name";
        description "PIM netio tunnel information";
        leaf tunnel-name {
          xr:xr-xml-map "ipv4_pim_common_oper:TunnelName";
          type xr:Cisco-ios-xr-string;
          description "Tunnel name";
        }
        uses PIM-TUNNEL-INFO-BAG;
      }
    }
  }

  grouping RPF-SUMMARY {
    description "Common node of vrf, default-context";

    container rpf-summary {
      xr:xr-xml-map "ipv4_pim_common_oper:RPFSummary";
      description "PIM RPF registration summary";
      uses PIM-RPF-SUMMARY-BAG;
    }
  }

  grouping IFRS-INTERFACE-TABLE {
    description "Common node of vrf, default-context";

    container ifrs-interfaces {
      xr:xr-xml-map "ipv4_pim_common_oper:IFRSInterfaceTable";
      description "PIM interfaces in forward reference store table";

      list ifrs-interface {
        xr:xr-xml-map "ipv4_pim_common_oper:IFRSInterface";
        key "interface-name";
        description "PIM IFRS interface information";
        leaf interface-name {
          xr:xr-xml-map "ipv4_pim_common_oper:InterfaceName";
          type xr:Interface-name;
          description "Interface name";
        }
        uses PIM-IDB-BAG;
      }
    }
  }

  grouping PROCESS {
    description "Common node of active, standby";

    container process {
      xr:xr-xml-map "ipv4_pim_role_lvl_oper:Process";
      description "Process";

      container checkpoint-statistics {
        xr:xr-xml-map "ipv4_pim_common_oper:CheckpointStatistics";
        description "Checkpoint Statistics";
        uses PIM-CHKPT-STATS;
      }

      container nsr {
        xr:xr-xml-map "ipv4_pim_common_oper:NSR";
        description "NSR Information";
        uses PIM-NSR-BAG;
      }

      container summary {
        xr:xr-xml-map "ipv4_pim_common_oper:Summary";
        description "PIM Global Summary";
        uses PIM-SUMMARY-BAG;
      }

      container nsf {
        xr:xr-xml-map "ipv4_pim_common_oper:NSF";
        description "PIM NSF information";
        uses PIM-NSF-BAG;
      }

      container issu {
        xr:xr-xml-map "ipv4_pim_common_oper:ISSU";
        description "ISSU Information";
        uses PIM-ISSU-BAG;
      }
    }
  }

  grouping JP-STATISTICS-TABLE {
    description "Common node of vrf, default-context";

    container jp-statistics {
      xr:xr-xml-map "ipv4_pim_common_oper:JPStatisticsTable";
      description "PIM join prune statistics table";

      list jp-statistic {
        xr:xr-xml-map "ipv4_pim_common_oper:JPStatistics";
        key "interface-name";
        description "PIM Join Prune Statistics";
        leaf interface-name {
          xr:xr-xml-map "ipv4_pim_common_oper:InterfaceName";
          type xr:Interface-name;
          description "Interface name";
        }
        uses PIM-JPSTATS-BAG;
      }
    }
  }

  grouping TOPOLOGY-TABLE {
    description "Common node of vrf, default-context";

    container topologies {
      xr:xr-xml-map "ipv4_pim_common_oper:TopologyTable";
      description "PIM topology table";

      list topology {
        xr:xr-xml-map "ipv4_pim_common_oper:Topology";
        description "PIM topology information";
        leaf source-address {
          xr:xr-xml-map "ipv4_pim_common_oper:SourceAddress";
          type inet:ip-address-no-zone;
          description "Source address";
        }
        leaf group-address {
          xr:xr-xml-map "ipv4_pim_common_oper:GroupAddress";
          type inet:ip-address-no-zone;
          description "Group address";
        }
        leaf rpt {
          xr:xr-xml-map "ipv4_pim_common_oper:RPT";
          type int32;
          description "RPT bit";
        }
        uses PIM-TT-ROUTE-BAG;
      }
    }
  }

  grouping NEIGHBOR-SUMMARY-TABLE {
    description "Common node of vrf, default-context";

    container neighbor-summaries {
      xr:xr-xml-map "ipv4_pim_common_oper:NeighborSummaryTable";
      description "PIM neighbor summary table";

      list neighbor-summary {
        xr:xr-xml-map "ipv4_pim_common_oper:NeighborSummary";
        key "interface-name";
        description "PIM neighbor summary information";
        leaf interface-name {
          xr:xr-xml-map "ipv4_pim_common_oper:InterfaceName";
          type xr:Interface-name;
          description "Interface name";
        }
        uses PIM-NBR-SUMM-BAG;
      }
    }
  }

  grouping TRAFFIC-COUNTERS {
    description "Common node of vrf, default-context";

    container traffic-counters {
      xr:xr-xml-map "ipv4_pim_common_oper:TrafficCounters";
      description "PIM message traffic counters";
      uses PIM-TRAFFIC-BAG;
    }
  }

  grouping TOPOLOGY-ROUTE-COUNT {
    description "Common node of vrf, default-context";

    container topology-route-count {
      xr:xr-xml-map "ipv4_pim_common_oper:TopologyRouteCount";
      description
        "Topology route count information from PIM
        topology table";
      uses PIM-TT-SUMM-BAG;
    }
  }

  grouping GLOBAL-INTERFACE-TABLE {
    description "Common node of vrf, default-context";

    container global-interfaces {
      xr:xr-xml-map "ipv4_pim_common_oper:GlobalInterfaceTable";
      description "PIM global interface table";

      list global-interface {
        xr:xr-xml-map "ipv4_pim_common_oper:GlobalInterface";
        key "interface-name";
        description "PIM interface name";
        leaf interface-name {
          xr:xr-xml-map "ipv4_pim_common_oper:InterfaceName";
          type xr:Interface-name;
          description "Interface name";
        }
        uses PIM-IDB-BAG;
      }
    }
  }

  grouping TUNNEL-TABLE {
    description "Common node of vrf, default-context";

    container tunnels {
      xr:xr-xml-map "ipv4_pim_common_oper:TunnelTable";
      description "Tunnels information that PIM has";

      list tunnel {
        xr:xr-xml-map "ipv4_pim_common_oper:Tunnel";
        key "tunnel-name";
        description "PIM tunnel information";
        leaf tunnel-name {
          xr:xr-xml-map "ipv4_pim_common_oper:TunnelName";
          type xr:Cisco-ios-xr-string;
          description "Tunnel name";
        }
        uses PIM-TUNNEL-INFO-BAG;
      }
    }
  }

  grouping PIM-MA-COMMON-OPER-PIM-MA-SUMMARY-MP {
    description "Common node of active, standby";

    container pim-ma-summary {
      xr:xr-xml-map "pim_ma_common_oper:PIM_MASummary";
      description "PIM MA summary";
      uses PIM-MA-SUMMARY;
    }
  }

  grouping ACTIVE {
    description "Common node of pim-ma, pim6-ma";

    container active {
      xr:xr-xml-map "pim_ma_role_lvl_oper:Active";
      description "Active Process";
      uses INTERFACE-TABLE;
      uses PIM-MA-COMMON-OPER-PIM-MA-SUMMARY-MP;
    }
  }

  grouping IPV4-PIM-ROLE-LVL-OPER-ACTIVE {
    description
      "Common node of pim-ma, pim6-maCommon node of pim,
      ipv6-pim";

    container active {
      xr:xr-xml-map "ipv4_pim_role_lvl_oper:Active";
      description "Active Process";
      uses DEFAULT-CONTEXT;
      uses PROCESS;
      uses VRF-TABLE;
    }
  }

  grouping GROUP-MAP-RPF-TABLE {
    description "Common node of vrf, default-context";

    container group-map-rpfs {
      xr:xr-xml-map "ipv4_pim_common_oper:GroupMapRPFTable";
      description "PIM group mapping information";

      list group-map-rpf {
        xr:xr-xml-map "ipv4_pim_common_oper:GroupMapRPF";
        description "PIM group mapping entry";
        leaf prefix {
          xr:xr-xml-map "ipv4_pim_common_oper:Prefix";
          type inet:ip-address-no-zone;
          description "Prefix";
        }
        leaf prefix-length {
          xr:xr-xml-map "ipv4_pim_common_oper:PrefixLength";
          type int32;
          description "Prefix length";
        }
        leaf client {
          xr:xr-xml-map "ipv4_pim_common_oper:Client";
          type Pim-client;
          description "Client";
        }
        leaf protocol {
          xr:xr-xml-map "ipv4_pim_common_oper:Protocol";
          type Pim-protocol;
          description "Protocol";
        }
        leaf rp-address {
          xr:xr-xml-map "ipv4_pim_common_oper:RPAddress";
          type inet:ip-address-no-zone;
          description "RP address";
        }
        leaf rp-priority {
          xr:xr-xml-map "ipv4_pim_common_oper:RPPriority";
          type int32;
          description "RP priority";
        }
        uses PIM-GRP-MAP-INFORPF-BAG;
      }
    }
  }

  grouping INTERFACE-OLD-FORMAT-TABLE {
    description "Common node of vrf, default-context";

    container interface-old-formats {
      xr:xr-xml-map "ipv4_pim_common_oper:InterfaceOldFormatTable";
      description "PIM interfaces in old format";

      list interface-old-format {
        xr:xr-xml-map "ipv4_pim_common_oper:InterfaceOldFormat";
        key "interface-name";
        description "PIM interface name";
        leaf interface-name {
          xr:xr-xml-map "ipv4_pim_common_oper:InterfaceName";
          type xr:Interface-name;
          description "Interface name";
        }
        uses PIM-IDB-BAG;
      }
    }
  }

  grouping RPF-REDIRECT {
    description "Common node of vrf, default-context";

    container rpf-redirect {
      xr:xr-xml-map "ipv4_pim_common_oper:RPFRedirect";
      description "PIM ECMP RPF-redirect bundle";

      container redirect-route-databases {
        xr:xr-xml-map "ipv4_pim_common_oper:RedirectRouteDatabaseTa"+
          "ble";
        description "PIM ECMP RPF-redirect route database";

        list redirect-route-database {
          xr:xr-xml-map "ipv4_pim_common_oper:RedirectRouteDatabase";
          description "PIM ECMP RPF-redirect route information";
          leaf source-address {
            xr:xr-xml-map "ipv4_pim_common_oper:SourceAddress";
            type inet:ip-address-no-zone;
            description "Source address";
          }
          leaf group-address {
            xr:xr-xml-map "ipv4_pim_common_oper:GroupAddress";
            type inet:ip-address-no-zone;
            description "Group address";
          }
          uses PIM-RPF-RDRCT-ROUTE-BAG;
        }
      }

      container bundle-interfaces {
        xr:xr-xml-map "ipv4_pim_common_oper:BundleInterfaceTable";
        description "PIM ECMP RPF-redirect bundle information";

        list bundle-interface {
          xr:xr-xml-map "ipv4_pim_common_oper:BundleInterface";
          description
            "PIM ECMP RPF-redirect bundle interface
            information";
          leaf bundle-name {
            xr:xr-xml-map "ipv4_pim_common_oper:BundleName";
            type xr:Cisco-ios-xr-string;
            description "Bundle name";
          }
          leaf interface-name {
            xr:xr-xml-map "ipv4_pim_common_oper:InterfaceName";
            type xr:Interface-name;
            description "Bundle interface name";
          }
          uses PIM-RPF-RDRCT-BNDL-BAG;
        }
      }
    }
  }

  grouping CONTEXT {
    description "Common node of vrf, default-context";

    container context {
      xr:xr-xml-map "ipv4_pim_common_oper:Context";
      description "PIM context information";
      uses PIM-CONTEXT-BAG;
    }
  }

  grouping INTERFACE-TABLE {
    description "Common node of active, standby";

    container interface-table {
      xr:xr-xml-map "pim_ma_role_lvl_oper:InterfaceTable";
      description "Interface Table";

      container interface-by-handles {
        xr:xr-xml-map "pim_ma_common_oper:InterfaceByHandleTable";
        description "Table of PIM MA interfaces indexed by handle";

        list interface-by-handle {
          xr:xr-xml-map "pim_ma_common_oper:InterfaceByHandle";
          key "interface-handle";
          description "PIM MA interface referenced by handle";
          leaf interface-handle {
            xr:xr-xml-map "pim_ma_common_oper:InterfaceHandle";
            type int32;
            description "Interface handle";
          }
          uses PIM-MA-IDB;
        }
      }

      container interface-by-names {
        xr:xr-xml-map "pim_ma_common_oper:InterfaceByNameTable";
        description "Table of PIM MA interfaces indexed by name";

        list interface-by-name {
          xr:xr-xml-map "pim_ma_common_oper:InterfaceByName";
          key "interface-name";
          description "PIM MA interface referenced by name";
          leaf interface-name {
            xr:xr-xml-map "pim_ma_common_oper:InterfaceName";
            type xr:Cisco-ios-xr-string;
            description "Interface name";
          }
          uses PIM-MA-IDB;
        }
      }
    }
  }

  grouping IPV4-PIM-COMMON-OPER-INTERFACE-TABLE {
    description
      "Common node of active, standbyCommon node of vrf,
      default-context";

    container interfaces {
      xr:xr-xml-map "ipv4_pim_common_oper:InterfaceTable";
      description "PIM interfaces";

      list interface {
        xr:xr-xml-map "ipv4_pim_common_oper:Interface";
        key "interface-name";
        description "PIM interface name";
        leaf interface-name {
          xr:xr-xml-map "ipv4_pim_common_oper:InterfaceName";
          type xr:Interface-name;
          description "Interface name";
        }
        uses PIM-IDB-BAG;
      }
    }
  }

  grouping SUMMARY {
    description "Common node of vrf, default-context";

    container summary {
      xr:xr-xml-map "ipv4_pim_common_oper:Summary";
      description "PIM summary";
      uses PIM-SUMMARY-BAG;
    }
  }

  grouping TOPOLOGY-INTERFACE-FLAG-ROUTE-COUNT-TABLE {
    description "Common node of vrf, default-context";

    container topology-interface-flag-route-counts {
      xr:xr-xml-map "ipv4_pim_common_oper:TopologyInterfaceFlagRout"+
        "eCountTable";
      description
        "Route count for topology with interface flag set";

      list topology-interface-flag-route-count {
        xr:xr-xml-map "ipv4_pim_common_oper:TopologyInterfaceFlagRo"+
          "uteCount";
        key "interface-flag";
        description
          "Route count for topology with interface flag
          set";
        leaf interface-flag {
          xr:xr-xml-map "ipv4_pim_common_oper:InterfaceFlag";
          type Pim-topology-interface-flag;
          description "Interface flag";
        }
        uses PIM-TT-SUMM-BAG;
      }
    }
  }

  grouping INTERFACE-STATISTICS-TABLE {
    description "Common node of vrf, default-context";

    container interface-statistics {
      xr:xr-xml-map "ipv4_pim_common_oper:InterfaceStatisticsTable";
      description "PIM interface statistics";

      list interface-statistic {
        xr:xr-xml-map "ipv4_pim_common_oper:InterfaceStatistics";
        key "interface-name";
        description "PIM interface statistics";
        leaf interface-name {
          xr:xr-xml-map "ipv4_pim_common_oper:InterfaceName";
          type xr:Interface-name;
          description "Interface name";
        }
        uses PIM-IFSTATS-BAG;
      }
    }
  }

  grouping GRE {
    description "Common node of vrf, default-context";

    container gre {
      xr:xr-xml-map "ipv4_pim_common_oper:GRE";
      description "GRE information";

      container gre-hashes {
        xr:xr-xml-map "ipv4_pim_common_oper:GREHashTable";
        description "GRE hash";

        list gre-hash {
          xr:xr-xml-map "ipv4_pim_common_oper:GREHash";
          key "source-address destination-address ifname";
          description "PIM GRE Hashed Underlying Interface";
          leaf source-address {
            xr:xr-xml-map "ipv4_pim_common_oper:SourceAddress";
            type inet:ip-address-no-zone;
            description "Source address";
          }
          leaf destination-address {
            xr:xr-xml-map "ipv4_pim_common_oper:DestinationAddress";
            type inet:ip-address-no-zone;
            description "Destination address";
          }
          leaf ifname {
            xr:xr-xml-map "ipv4_pim_common_oper:Ifname";
            type xr:Interface-name;
            description "GRE Tunnel Interface";
          }
          uses PIM-GRE-HASH-BAG;
        }
      }

      container gre-next-hops {
        xr:xr-xml-map "ipv4_pim_common_oper:GRENextHopTable";
        description "GRE destination neighbor table";

        list gre-next-hop {
          xr:xr-xml-map "ipv4_pim_common_oper:GRENextHop";
          key "destination-address";
          description "PIM GRE address next-hop information";
          leaf destination-address {
            xr:xr-xml-map "ipv4_pim_common_oper:DestinationAddress";
            type inet:ip-address-no-zone;
            description "GRE destination address";
          }
          uses PIM-GRE-INFO-BAG;
        }
      }
    }
  }

  grouping NEIGHBOR-OLD-FORMAT-TABLE {
    description "Common node of vrf, default-context";

    container neighbor-old-formats {
      xr:xr-xml-map "ipv4_pim_common_oper:NeighborOldFormatTable";
      description "PIM neighbor table old format";

      list neighbor-old-format {
        xr:xr-xml-map "ipv4_pim_common_oper:NeighborOldFormat";
        description "PIM neighbor information";
        leaf interface-name {
          xr:xr-xml-map "ipv4_pim_common_oper:InterfaceName";
          type xr:Interface-name;
          description "Interface name";
        }
        leaf neighbor-address {
          xr:xr-xml-map "ipv4_pim_common_oper:NeighborAddress";
          type inet:ip-address-no-zone;
          description "Neighbor address";
        }
        uses PIM-NBR-BAG;
      }
    }
  }

  grouping IFRS-SUMMARY {
    description "Common node of vrf, default-context";

    container ifrs-summary {
      xr:xr-xml-map "ipv4_pim_common_oper:IFRSSummary";
      description
        "PIM interfaces in forward reference store
        summary";
      uses PIM-IDB-SUMM-BAG;
    }
  }

  grouping DEFAULT-CONTEXT {
    description "Common node of active, standby";

    container default-context {
      xr:xr-xml-map "ipv4_pim_common_oper:DefaultContext";
      description "Default Context";
      uses IFRS-INTERFACE-TABLE;
      uses SAF-TABLE;
      uses INTERFACE-STATISTICS-TABLE;
      uses TOPOLOGY-ROUTE-COUNT;
      uses JP-STATISTICS-TABLE;
      uses MIB-DATABASE-TABLE;
      uses GROUP-MAP-MATCH-RPF-TABLE;
      uses NEIGHBOR-OLD-FORMAT-TABLE;
      uses IFRS-SUMMARY;
      uses RANGE-LIST-TABLE;
      uses INTERFACE-OLD-FORMAT-TABLE;
      uses BSR;
      uses ROUTE-POLICY;
      uses RPF-SUMMARY;
      uses IPV4-PIM-COMMON-OPER-INTERFACE-TABLE;
      uses NET-IO-TUNNEL-TABLE;
      uses BIDIR-DF-STATE-TABLE;
      uses TOPOLOGY-TABLE;
      uses BGP-AF-TABLE;
      uses AUTO-RP;
      uses TOPOLOGY-INTERFACE-FLAG-ROUTE-COUNT-TABLE;
      uses GROUP-MAP-SOURCE-TABLE;
      uses TRAFFIC-COUNTERS;
      uses GROUP-MAP-RPF-TABLE;
      uses SUMMARY;
      uses GRE;
      uses BIDIR-DF-WINNER-TABLE;
      uses TABLE-CONTEXT-TABLE;
      uses GLOBAL-INTERFACE-TABLE;
      uses NEIGHBOR-SUMMARY-TABLE;
      uses CONTEXT;
      uses TOPOLOGY-ENTRY-FLAG-ROUTE-COUNT-TABLE;
      uses RPF-REDIRECT;
      uses TUNNEL-TABLE;
      uses MULTICAST-STATIC-ROUTE-TABLE;
      uses GROUP-MAP-MATCH-SOURCE-TABLE;
      uses NEIGHBOR-TABLE;
    }
  }

  grouping GROUP-MAP-MATCH-SOURCE-TABLE {
    description "Common node of vrf, default-context";

    container group-map-match-sources {
      xr:xr-xml-map "ipv4_pim_common_oper:GroupMapMatchSourceTable";
      description
        "Find the matching group-mapping with source
        information on specified group address";

      list group-map-match-source {
        xr:xr-xml-map "ipv4_pim_common_oper:GroupMapMatchSource";
        key "group-address";
        description
          "PIM group-matching mapping entry with source
          information";
        leaf group-address {
          xr:xr-xml-map "ipv4_pim_common_oper:GroupAddress";
          type inet:ip-address-no-zone;
          description "Group address";
        }
        uses PIM-GRP-MAP-INFOSRC-BAG;
      }
    }
  }

  grouping NEIGHBOR-TABLE {
    description "Common node of vrf, default-context";

    container neighbors {
      xr:xr-xml-map "ipv4_pim_common_oper:NeighborTable";
      description "PIM neighbor table";

      list neighbor {
        xr:xr-xml-map "ipv4_pim_common_oper:Neighbor";
        description "PIM neighbor information";
        leaf interface-name {
          xr:xr-xml-map "ipv4_pim_common_oper:InterfaceName";
          type xr:Interface-name;
          description "Interface name";
        }
        leaf neighbor-address {
          xr:xr-xml-map "ipv4_pim_common_oper:NeighborAddress";
          type inet:ip-address-no-zone;
          description "Neighbor address";
        }
        uses PIM-NBR-BAG;
      }
    }
  }

  grouping SAF-TABLE {
    description "Common node of vrf, default-context";

    container safs {
      xr:xr-xml-map "ipv4_pim_common_oper:SAFTable";
      description "SAFI table and type";

      list saf {
        xr:xr-xml-map "ipv4_pim_common_oper:SAF";
        description "SAF name ";

        container rpf-hash-source-groups {
          xr:xr-xml-map "ipv4_pim_common_oper:RPFHashSourceGroupTab"+
            "le";
          description "PIM RPF multipath hash outcome";

          list rpf-hash-source-group {
            xr:xr-xml-map "ipv4_pim_common_oper:RPFHashSourceGroup";
            description "PIM RPF hash outcome for S,G";
            leaf source-address {
              xr:xr-xml-map "ipv4_pim_common_oper:SourceAddress";
              type inet:ip-address-no-zone;
              description "Source address";
            }
            leaf group-address {
              xr:xr-xml-map "ipv4_pim_common_oper:GroupAddress";
              type inet:ip-address-no-zone;
              description "Group address";
            }
            leaf mask-length {
              xr:xr-xml-map "ipv4_pim_common_oper:MaskLength";
              type int32;
              description "Hash mask length";
            }
            leaf mofrr {
              xr:xr-xml-map "ipv4_pim_common_oper:MOFRR";
              type int32;
              description "MOFRR";
            }
            uses PIM-RPF-HASH-BAG;
          }
        }

        container rpf-neighbors {
          xr:xr-xml-map "ipv4_pim_common_oper:RPFNeighborTable";
          description "PIM RPF neighbor table";

          list rpf-neighbor {
            xr:xr-xml-map "ipv4_pim_common_oper:RPFNeighbor";
            description "PIM RPF RIB neighbor";
            leaf interface-name {
              xr:xr-xml-map "ipv4_pim_common_oper:InterfaceName";
              type xr:Interface-name;
              description "Interface name";
            }
            leaf neighbor-address {
              xr:xr-xml-map "ipv4_pim_common_oper:NeighborAddress";
              type inet:ip-address-no-zone;
              description "RPF neighbor  address to lookup";
            }
            uses PIM-RPF-NBR-BAG;
          }
        }

        container rpf-hash-sources {
          xr:xr-xml-map "ipv4_pim_common_oper:RPFHashSourceTable";
          description "PIM RPF multipath hash outcome";

          list rpf-hash-source {
            xr:xr-xml-map "ipv4_pim_common_oper:RPFHashSource";
            description "PIM RPF hash outcome for S,G";
            leaf source-address {
              xr:xr-xml-map "ipv4_pim_common_oper:SourceAddress";
              type inet:ip-address-no-zone;
              description "Source address";
            }
            leaf mofrr {
              xr:xr-xml-map "ipv4_pim_common_oper:MOFRR";
              type int32;
              description "MOFRR";
            }
            uses PIM-RPF-HASH-BAG;
          }
        }

        container rpfs {
          xr:xr-xml-map "ipv4_pim_common_oper:RPFTable";
          description "PIM RPF information table";

          list rpf {
            xr:xr-xml-map "ipv4_pim_common_oper:RPF";
            key "registered-address";
            description "PIM RPF information";
            leaf registered-address {
              xr:xr-xml-map "ipv4_pim_common_oper:RegisteredAddress";
              type inet:ip-address-no-zone;
              description "Address for which RPF lookup";
            }
            uses PIM-RPF-INFO-BAG;
          }
        }
        leaf saf-name {
          xr:xr-xml-map "ipv4_pim_common_oper:SAFName";
          type Pim-safi;
          description "SAF name ";
        }
        leaf topology-name {
          xr:xr-xml-map "ipv4_pim_common_oper:TopologyName";
          type xr:Cisco-ios-xr-string;
          description "Topology name ";
        }
      }
    }
  }

  grouping MULTICAST-STATIC-ROUTE-TABLE {
    description
      "Common node of vrf, default-contextCommon node of
      vrf, default-context";

    container multicast-static-routes {
      xr:xr-xml-map "ipv4_pim_common_oper:MulticastStaticRouteTable";
      description "PIM multicast static route table";

      list multicast-static-route {
        xr:xr-xml-map "ipv4_pim_common_oper:MulticastStaticRoute";
        description "PIM multicast static route information";
        leaf address {
          xr:xr-xml-map "ipv4_pim_common_oper:Address";
          type inet:ip-address-no-zone;
          description "Network address";
        }
        leaf prefix-length {
          xr:xr-xml-map "ipv4_pim_common_oper:PrefixLength";
          type int32;
          description "Prefix length";
        }
        uses PIM-MSTATIC-BAG;
      }
    }
  }

  grouping RANGE-LIST-TABLE {
    description "Common node of vrf, default-context";

    container ranges {
      xr:xr-xml-map "ipv4_pim_common_oper:RangeListTable";
      description "PIM range list information";

      list range {
        xr:xr-xml-map "ipv4_pim_common_oper:RangeList";
        description "PIM range list information";
        leaf rp-address {
          xr:xr-xml-map "ipv4_pim_common_oper:RPAddress";
          type inet:ip-address-no-zone;
          description "RP address";
        }
        leaf client {
          xr:xr-xml-map "ipv4_pim_common_oper:Client";
          type Pim-client;
          description "Client";
        }
        uses PIM-RL-BAG;
      }
    }
  }

  grouping STANDBY {
    description "Common node of pim-ma, pim6-ma";

    container standby {
      xr:xr-xml-map "pim_ma_role_lvl_oper:Standby";
      description "Standby Process";
      uses INTERFACE-TABLE;
      uses PIM-MA-COMMON-OPER-PIM-MA-SUMMARY-MP;
    }
  }

  grouping IPV4-PIM-ROLE-LVL-OPER-STANDBY {
    description
      "Common node of pim-ma, pim6-maCommon node of pim,
      ipv6-pim";

    container standby {
      xr:xr-xml-map "ipv4_pim_role_lvl_oper:Standby";
      description "Standby Process";
      uses DEFAULT-CONTEXT;
      uses PROCESS;
      uses VRF-TABLE;
    }
  }

  grouping GROUP-MAP-MATCH-RPF-TABLE {
    description "Common node of vrf, default-context";

    container group-map-match-rpfs {
      xr:xr-xml-map "ipv4_pim_common_oper:GroupMapMatchRPFTable";
      description
        "Find matching group-mapping for the specified
        group address";

      list group-map-match-rpf {
        xr:xr-xml-map "ipv4_pim_common_oper:GroupMapMatchRPF";
        key "group-address";
        description "PIM group matching mapping entry";
        leaf group-address {
          xr:xr-xml-map "ipv4_pim_common_oper:GroupAddress";
          type inet:ip-address-no-zone;
          description "Group address";
        }
        uses PIM-GRP-MAP-INFORPF-BAG;
      }
    }
  }

  container pim-ma {
    xr:xr-xml-map "pim_ma_oper:PIM_MA";
    config false;
    description "PIM MA operational data";
    uses ACTIVE;
    uses STANDBY;
  }

  container pim {
    xr:xr-xml-map "ipv4_pim_oper:PIM";
    config false;
    description "pim";
    uses IPV4-PIM-ROLE-LVL-OPER-STANDBY;
    uses IPV4-PIM-ROLE-LVL-OPER-ACTIVE;
  }

  container ipv6-pim {
    xr:xr-xml-map "ipv6_pim_oper:IPV6_PIM";
    config false;
    description "ipv6 pim";
    uses IPV4-PIM-ROLE-LVL-OPER-STANDBY;
    uses IPV4-PIM-ROLE-LVL-OPER-ACTIVE;
  }

  container pim6-ma {
    xr:xr-xml-map "pim6_ma_oper:PIM6_MA";
    config false;
    description "pim6 ma";
    uses ACTIVE;
    uses STANDBY;
  }
}
