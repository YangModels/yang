module Cisco-IOS-XR-pbr-vservice-ea-oper {

  /*** NAMESPACE / PREFIX DEFINITION ***/

  namespace "http://cisco.com/ns/yang"+
    "/Cisco-IOS-XR-pbr-vservice-ea-oper";


  prefix "pbr-vservice-ea-oper";

  /*** LINKAGE (IMPORTS / INCLUDES) ***/

  import Cisco-IOS-XR-types { prefix "xr"; }

  import Cisco-IOS-XR-pbr-datatypes { prefix "dt1"; }

  include Cisco-IOS-XR-pbr-vservice-ea-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR pbr-vservice-ea package operational data.

     This module contains definitions
     for the following management objects:
       service-function-chaining: NSH Service Function Chaining
         operational data

     Copyright (c) 2013-2016 by Cisco Systems, Inc.
     All rights reserved.";

  revision "2015-11-09" {
    description
      "IOS XR 6.0 revision.";
  }


  container service-function-chaining {
    xr:xr-xml-map "vservice_ea_nsh_oper:ServiceFunctionChaining";
    config false;
    description "NSH Service Function Chaining operational data";

    container nodes {
      xr:xr-xml-map "vservice_ea_nsh_oper:NodeTable";
      description
        "Node-specific NSH Service Function Chaining
        operational data";

      list node {
        xr:xr-xml-map "vservice_ea_nsh_oper:Node";
        key "node-name";
        description "NSH operational data for a particular node";

        container process {
          xr:xr-xml-map "vservice_ea_nsh_oper:Process";
          description "Client Process";

          container service-function-path {
            xr:xr-xml-map "vservice_ea_nsh_oper:ServiceFunctionPath";
            description "Service Function Path operational data";

            container path-ids {
              xr:xr-xml-map "vservice_ea_nsh_oper:PathIdTable";
              description "Service Function Path Id ";

              list path-id {
                xr:xr-xml-map "vservice_ea_nsh_oper:PathId";
                key "id";
                description
                  "Specific Service-Function-Path identifier ";

                container service-indexes {
                  xr:xr-xml-map "vservice_ea_nsh_oper:ServiceIndexT"+
                    "able";
                  description "Service Index Belonging to Path";

                  list service-index {
                    xr:xr-xml-map "vservice_ea_nsh_oper:ServiceInde"+
                      "x";
                    key "index";
                    description
                      "Service index operational data belonging
                      to this path";
                    leaf index {
                      xr:xr-xml-map "vservice_ea_nsh_oper:Index";
                      type dt1:Vservice-nsh-service-index-range;
                      description "Service Index";
                    }
                    uses VSERVICE-EDM-NSH-STATS-INFO;
                  }
                }

                container stats {
                  xr:xr-xml-map "vservice_ea_nsh_oper:Stats";
                  description "SFP Statistics";

                  container detail {
                    xr:xr-xml-map "vservice_ea_nsh_oper:Detail";
                    description
                      "Detail statistics per service index ";
                    uses VSERVICE-EDM-NSH-STATS-INFO;
                  }

                  container summarized {
                    xr:xr-xml-map "vservice_ea_nsh_oper:Summarized";
                    description
                      "Combined statistics of all service index
                      in service functionpath";
                    uses VSERVICE-EDM-NSH-STATS-INFO;
                  }
                }
                leaf id {
                  xr:xr-xml-map "vservice_ea_nsh_oper:Id";
                  type dt1:Vservice-nsh-path-id-range;
                  description
                    "Specific Service-Function-Path identifier";
                }
              }
            }
          }

          container service-function {
            xr:xr-xml-map "vservice_ea_nsh_oper:ServiceFunction";
            description "Service Function operational data";

            container sf-names {
              xr:xr-xml-map "vservice_ea_nsh_oper:SFNameListTable";
              description "List of Service Function Names";

              list sf-name {
                xr:xr-xml-map "vservice_ea_nsh_oper:SFName";
                key "name";
                description "Name of Service Function";
                leaf name {
                  xr:xr-xml-map "vservice_ea_nsh_oper:Name";
                  type xr:Cisco-ios-xr-string {
                    length "0..32";
                  }
                  description "Name";
                }
                uses VSERVICE-EDM-NSH-STATS-INFO;
              }
            }
          }

          container service-function-forwarder {
            xr:xr-xml-map "vservice_ea_nsh_oper:ServiceFunctionForw"+
              "arder";
            description
              "Service Function Forwarder operational data";

            container local {
              xr:xr-xml-map "vservice_ea_nsh_oper:Local";
              description
                "Local Service Function Forwarder operational
                data";

              container error {
                xr:xr-xml-map "vservice_ea_nsh_oper:Error";
                description
                  "Error Statistics for local service function
                  forwarder";
                uses VSERVICE-EDM-NSH-STATS-INFO;
              }
            }

            container sff-names {
              xr:xr-xml-map "vservice_ea_nsh_oper:SFFNameListTable";
              description
                "List of Service Function Forwarder Names";

              list sff-name {
                xr:xr-xml-map "vservice_ea_nsh_oper:SFFName";
                key "name";
                description "Name of Service Function Forwarder";
                leaf name {
                  xr:xr-xml-map "vservice_ea_nsh_oper:Name";
                  type xr:Cisco-ios-xr-string {
                    length "0..32";
                  }
                  description "Name";
                }
                uses VSERVICE-EDM-NSH-STATS-INFO;
              }
            }
          }
        }
        leaf node-name {
          xr:xr-xml-map "vservice_ea_nsh_oper:NodeName";
          type xr:Node-id;
          description "Node to collect statistics from";
        }
      }
    }
  }
}
