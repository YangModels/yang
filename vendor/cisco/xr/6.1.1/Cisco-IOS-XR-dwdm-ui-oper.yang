module Cisco-IOS-XR-dwdm-ui-oper {

  /*** NAMESPACE / PREFIX DEFINITION ***/

  namespace "http://cisco.com/ns/yang/Cisco-IOS-XR-dwdm-ui-oper";


  prefix "dwdm-ui-oper";

  /*** LINKAGE (IMPORTS / INCLUDES) ***/

  import Cisco-IOS-XR-types { prefix "xr"; }

  include Cisco-IOS-XR-dwdm-ui-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR dwdm-ui package operational data.

     This module contains definitions
     for the following management objects:
       dwdm: DWDM operational data
       vtxp: vtxp

     Copyright (c) 2013-2016 by Cisco Systems, Inc.
     All rights reserved.";

  revision "2015-11-09" {
    description
      "IOS XR 6.0 revision.";
  }


  container dwdm {
    xr:xr-xml-map "dwdm_ui_oper:DWDM";
    config false;
    description "DWDM operational data";

    container ports {
      xr:xr-xml-map "dwdm_ui_oper:PortTable";
      description "All DWDM Port operational data";

      list port {
        xr:xr-xml-map "dwdm_ui_oper:Port";
        key "name";
        description "DWDM Port operational data";

        container prbs {
          xr:xr-xml-map "dwdm_ui_oper:PRBS";
          description "DWDM Port PRBS related data";

          container twenty-four-hours-bucket {
            xr:xr-xml-map "dwdm_ui_oper:TwentyFourHoursBucket";
            description "Port 24-hour PRBS statistics table";

            container twenty-four-hours-statistics {
              xr:xr-xml-map "dwdm_ui_oper:TwentyFourHoursStatistics";
              description "Port 24-hour PRBS statistics data";
              uses DWDM-EDM-PRBS-INFO;
            }
          }

          container fifteen-minutes-bucket {
            xr:xr-xml-map "dwdm_ui_oper:FifteenMinutesBucket";
            description "Port 15-minute PRBS statistics table";

            container fifteen-minutes-statistics {
              xr:xr-xml-map "dwdm_ui_oper:FifteenMinutesStatistics";
              description "Port 15-minute PRBS statistics data";
              uses DWDM-EDM-PRBS-INFO;
            }
          }
        }

        container optics {
          xr:xr-xml-map "dwdm_ui_oper:Optics";
          description "DWDM Port optics operational data";

          container wave-info {
            xr:xr-xml-map "dwdm_ui_oper:WaveInfo";
            description "DWDM port wavelength information data";
            uses DWDM-EDM-WAVE-INFO;
          }
        }

        container info {
          xr:xr-xml-map "dwdm_ui_oper:Info";
          description "DWDM port operational data";
          uses DWDM-EDM-PORT-INFO;
        }
        leaf name {
          xr:xr-xml-map "dwdm_ui_oper:Name";
          type xr:Interface-name;
          description "Port name";
        }
      }
    }
  }

  container vtxp {
    xr:xr-xml-map "dwdm_ui_oper:VTXP";
    config false;
    description "vtxp";

    container dwdm-vtxp {
      xr:xr-xml-map "dwdm_ui_oper:DWDM_VTXP";
      description "DWDM operational data";

      container port-vtxps {
        xr:xr-xml-map "dwdm_ui_oper:PortTableVTXP";
        description "All DWDM Port operational data";

        list port-vtxp {
          xr:xr-xml-map "dwdm_ui_oper:PortVTXP";
          key "name";
          description "DWDM Port operational data";

          container info {
            xr:xr-xml-map "dwdm_ui_oper:Info";
            description "DWDM port operational data";
            uses DWDM-EDM-VTXP-INFO;
          }
          leaf name {
            xr:xr-xml-map "dwdm_ui_oper:Name";
            type xr:Interface-name;
            description "Port name";
          }
        }
      }
    }
  }
}
