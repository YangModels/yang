submodule Cisco-IOS-XR-asr9k-lc-ethctrl-oper-sub1 {

  belongs-to Cisco-IOS-XR-asr9k-lc-ethctrl-oper {
    prefix Cisco-IOS-XR-asr9k-lc-ethctrl-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR asr9k-lc-ethctrl package operational data.

     Copyright (c) 2013-2016 by Cisco Systems, Inc.
     All rights reserved.";

  revision "2015-11-09" {
    description
      "IOS XR 6.0 revision.";
  }


  grouping MLAN-ATU {
    description "MLAN ATU";
    leaf db-num {
      xr:xr-xml-map "mlan_edm_defs:dbNum";
      type uint16;
      description "dbNum";
    }
    leaf priority {
      xr:xr-xml-map "mlan_edm_defs:priority";
      type uint8;
      description "priority";
    }
    leaf trunk {
      xr:xr-xml-map "mlan_edm_defs:trunk";
      type boolean;
      description "trunk";
    }
    leaf dpv {
      xr:xr-xml-map "mlan_edm_defs:dpv";
      type uint8;
      description "dpv";
    }
    leaf es {
      xr:xr-xml-map "mlan_edm_defs:es";
      type uint8;
      description "es";
    }
    leaf-list macaddr {
      xr:xr-xml-map "mlan_edm_defs:macaddr";
      type uint16;
      max-elements "3";
      description "macaddr";
    }
  }

  grouping MLAN-SWITCH-ATU-DATA {
    description "";

    container atu {
      description "Switch ATU Data";
      uses MLAN-ATU;
    }
    leaf entry-num {
      xr:xr-xml-map "mlan_edm_defs:entry_num";
      type uint32;
      description "Index of ATU Entry";
    }
  }

  grouping MLAN-PORT-COUNTER {
    description "MLAN PORT COUNTER";
    leaf in-good-octets-hi {
      xr:xr-xml-map "mlan_edm_defs:inGoodOctets_hi";
      type uint32;
      description "inGoodOctets hi";
    }
    leaf in-good-octets {
      xr:xr-xml-map "mlan_edm_defs:inGoodOctets";
      type uint32;
      description "inGoodOctets";
    }
    leaf in-bad-octets {
      xr:xr-xml-map "mlan_edm_defs:inBadOctets";
      type uint32;
      description "inBadOctets";
    }
    leaf in-unicast-pkt {
      xr:xr-xml-map "mlan_edm_defs:inUnicastPkt";
      type uint32;
      description "inUnicastPkt";
    }
    leaf in-bcast-pkt {
      xr:xr-xml-map "mlan_edm_defs:inBcastPkt";
      type uint32;
      description "inBcastPkt";
    }
    leaf in-mcast-pkt {
      xr:xr-xml-map "mlan_edm_defs:inMcastPkt";
      type uint32;
      description "inMcastPkt";
    }
    leaf in-pause-pkt {
      xr:xr-xml-map "mlan_edm_defs:inPausePkt";
      type uint32;
      description "inPausePkt";
    }
    leaf in-undersize-pkt {
      xr:xr-xml-map "mlan_edm_defs:inUndersizePkt";
      type uint32;
      description "inUndersizePkt";
    }
    leaf in-fragments {
      xr:xr-xml-map "mlan_edm_defs:inFragments";
      type uint32;
      description "inFragments";
    }
    leaf in-oversize {
      xr:xr-xml-map "mlan_edm_defs:inOversize";
      type uint32;
      description "inOversize";
    }
    leaf in-jabber {
      xr:xr-xml-map "mlan_edm_defs:inJabber";
      type uint32;
      description "inJabber";
    }
    leaf in-rx-err {
      xr:xr-xml-map "mlan_edm_defs:inRxErr";
      type uint32;
      description "inRxErr";
    }
    leaf in-fcs-err {
      xr:xr-xml-map "mlan_edm_defs:inFcsErr";
      type uint32;
      description "inFcsErr";
    }
    leaf out-octets-hi {
      xr:xr-xml-map "mlan_edm_defs:outOctets_hi";
      type uint32;
      description "outOctets hi";
    }
    leaf out-octets {
      xr:xr-xml-map "mlan_edm_defs:outOctets";
      type uint32;
      description "outOctets";
    }
    leaf out-unicast-pkt {
      xr:xr-xml-map "mlan_edm_defs:outUnicastPkt";
      type uint32;
      description "outUnicastPkt";
    }
    leaf out-bcast-pkt {
      xr:xr-xml-map "mlan_edm_defs:outBcastPkt";
      type uint32;
      description "outBcastPkt";
    }
    leaf out-mcast-pkt {
      xr:xr-xml-map "mlan_edm_defs:outMcastPkt";
      type uint32;
      description "outMcastPkt";
    }
    leaf out-pause-pkt {
      xr:xr-xml-map "mlan_edm_defs:outPausePkt";
      type uint32;
      description "outPausePkt";
    }
    leaf excessive {
      xr:xr-xml-map "mlan_edm_defs:excessive";
      type uint32;
      description "excessive";
    }
    leaf collisions {
      xr:xr-xml-map "mlan_edm_defs:collisions";
      type uint32;
      description "collisions";
    }
    leaf deferred {
      xr:xr-xml-map "mlan_edm_defs:deferred";
      type uint32;
      description "deferred";
    }
    leaf single {
      xr:xr-xml-map "mlan_edm_defs:single";
      type uint32;
      description "single";
    }
    leaf multiple {
      xr:xr-xml-map "mlan_edm_defs:multiple";
      type uint32;
      description "multiple";
    }
    leaf out-fcs-err {
      xr:xr-xml-map "mlan_edm_defs:outFcsErr";
      type uint32;
      description "outFcsErr";
    }
    leaf late {
      xr:xr-xml-map "mlan_edm_defs:late";
      type uint32;
      description "late";
    }
    leaf rx-tx-64-octets {
      xr:xr-xml-map "mlan_edm_defs:rx_tx_64_Octets";
      type uint32;
      description "rx tx 64 Octets";
    }
    leaf rx-tx-65-127-octets {
      xr:xr-xml-map "mlan_edm_defs:rx_tx_65_127_Octets";
      type uint32;
      description "rx tx 65 127 Octets";
    }
    leaf rx-tx-128-255-octets {
      xr:xr-xml-map "mlan_edm_defs:rx_tx_128_255_Octets";
      type uint32;
      description "rx tx 128 255 Octets";
    }
    leaf rx-tx-256-511-octets {
      xr:xr-xml-map "mlan_edm_defs:rx_tx_256_511_Octets";
      type uint32;
      description "rx tx 256 511 Octets";
    }
    leaf rx-tx-512-1023-octets {
      xr:xr-xml-map "mlan_edm_defs:rx_tx_512_1023_Octets";
      type uint32;
      description "rx tx 512 1023 Octets";
    }
    leaf rx-tx-1024-max-octets {
      xr:xr-xml-map "mlan_edm_defs:rx_tx_1024_Max_Octets";
      type uint32;
      description "rx tx 1024 Max Octets";
    }
    leaf in-discards {
      xr:xr-xml-map "mlan_edm_defs:inDiscards";
      type uint32;
      description "inDiscards";
    }
    leaf in-filtered {
      xr:xr-xml-map "mlan_edm_defs:inFiltered";
      type uint32;
      description "inFiltered";
    }
    leaf out-filtered {
      xr:xr-xml-map "mlan_edm_defs:outFiltered";
      type uint32;
      description "outFiltered";
    }
  }

  grouping MLAN-PORT-COUNTERS {
    description "";

    container mlan-stats {
      description "Switch Port Statistics";
      uses MLAN-PORT-COUNTER;
    }
    leaf port-num {
      xr:xr-xml-map "mlan_edm_defs:port_num";
      type uint32;
      description "Port Number";
    }
  }

  grouping MLAN-SWITCH-STATUS {
    description "MLAN SWITCH STATUS";
    leaf ppu {
      xr:xr-xml-map "mlan_edm_defs:ppu";
      type uint32;
      description "ppu";
    }
    leaf mtu {
      xr:xr-xml-map "mlan_edm_defs:mtu";
      type uint32;
      description "mtu";
    }
    leaf mac {
      xr:xr-xml-map "mlan_edm_defs:mac";
      type string {
        length "0..6";
      }
      description "mac";
    }
    leaf cpu-port {
      xr:xr-xml-map "mlan_edm_defs:cpu_port";
      type uint16;
      description "cpu port";
    }
    leaf cpu-mac {
      xr:xr-xml-map "mlan_edm_defs:cpu_mac";
      type uint16;
      description "cpu mac";
    }
    leaf initialized {
      xr:xr-xml-map "mlan_edm_defs:initialized";
      type uint16;
      description "initialized";
    }
    leaf restarted {
      xr:xr-xml-map "mlan_edm_defs:restarted";
      type uint16;
      description "restarted";
    }
  }

  grouping MLAN-SWITCH-STATUS-DATA {
    description "";

    container sw-reg-1 {
      description "Switch Global Registers";
      uses MLAN-SWITCH-REG-BANK;
    }

    container sw-reg-2 {
      description "Switch Global Registers";
      uses MLAN-SWITCH-REG-BANK;
    }

    container sw-status {
      description "Switch Status Data";
      uses MLAN-SWITCH-STATUS;
    }
    leaf rate-limit {
      xr:xr-xml-map "mlan_edm_defs:rate_limit";
      type int32;
      description "CPU Interface Rate Limit";
    }
  }

  grouping MLAN-SWITCH-REG-BANK {
    description "MLAN SWITCH REG BANK";
    leaf-list reg {
      xr:xr-xml-map "mlan_edm_defs:reg";
      type uint16;
      max-elements "32";
      description "reg";
    }
  }

  grouping MLAN-PORT-CONFIG {
    description "MLAN PORT CONFIG";
    leaf speed {
      xr:xr-xml-map "mlan_edm_defs:speed";
      type uint32;
      description "speed";
    }
    leaf duplex {
      xr:xr-xml-map "mlan_edm_defs:duplex";
      type uint32;
      description "duplex";
    }
    leaf pause {
      xr:xr-xml-map "mlan_edm_defs:pauseEn";
      type uint16;
      description "pauseEn";
    }
    leaf my-pause {
      xr:xr-xml-map "mlan_edm_defs:myPause";
      type uint16;
      description "myPause";
    }
    leaf loopback {
      xr:xr-xml-map "mlan_edm_defs:loopback";
      type uint32;
      description "loopback";
    }
  }

  grouping MLAN-PORT-STATUS {
    description "";

    container config {
      description "Configuration Data";
      uses MLAN-PORT-CONFIG;
    }

    container phy {
      description "PHY Registers";
      uses MLAN-SWITCH-REG-BANK;
    }

    container serdes {
      description "SERDES Registers";
      uses MLAN-SWITCH-REG-BANK;
    }

    container mac {
      description "MAC Registers";
      uses MLAN-SWITCH-REG-BANK;
    }
    leaf port-num {
      xr:xr-xml-map "mlan_edm_defs:port_num";
      type uint32;
      description "Port Number";
    }
    leaf phy-valid {
      xr:xr-xml-map "mlan_edm_defs:phy_valid";
      type uint32;
      description "PHY data valid";
    }
    leaf serdes-valid {
      xr:xr-xml-map "mlan_edm_defs:serdes_valid";
      type uint32;
      description "SERDES data valid";
    }
    leaf mac-valid {
      xr:xr-xml-map "mlan_edm_defs:mac_valid";
      type uint32;
      description "MAC data valid";
    }
  }
}
