module Cisco-IOS-XR-infra-correlator-oper {

  /*** NAMESPACE / PREFIX DEFINITION ***/

  namespace "http://cisco.com/ns/yang"+
    "/Cisco-IOS-XR-infra-correlator-oper";


  prefix "infra-correlator-oper";

  /*** LINKAGE (IMPORTS / INCLUDES) ***/

  import Cisco-IOS-XR-types { prefix "xr"; }

  include Cisco-IOS-XR-infra-correlator-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR infra-correlator package operational data.

     This module contains definitions
     for the following management objects:
       suppression: Suppression operational data
       correlator: correlator

     Copyright (c) 2013-2016 by Cisco Systems, Inc.
     All rights reserved.";

  revision "2015-11-09" {
    description
      "IOS XR 6.0 revision.";
  }


  container suppression {
    xr:xr-xml-map "infra_correlator_suppress_oper:Suppression";
    config false;
    description "Suppression operational data";

    container rule-summaries {
      xr:xr-xml-map "infra_correlator_suppress_oper:RuleSummaryTabl"+
        "e";
      description
        "Table that contains the database of suppression
        rule summary";

      list rule-summary {
        xr:xr-xml-map "infra_correlator_suppress_oper:RuleSummary";
        key "rule-name";
        description "One of the suppression rules";
        leaf rule-name {
          xr:xr-xml-map "infra_correlator_suppress_oper:RuleName";
          type string {
            length "0..32";
          }
          description "Suppression Rule Name";
        }
        uses AC-SUPPR-RULE-SUMMARY-BAG;
      }
    }

    container rule-details {
      xr:xr-xml-map "infra_correlator_suppress_oper:RuleDetailTable";
      description
        "Table that contains the database of suppression
        rule details";

      list rule-detail {
        xr:xr-xml-map "infra_correlator_suppress_oper:RuleDetail";
        key "rule-name";
        description "Details of one of the suppression rules";
        leaf rule-name {
          xr:xr-xml-map "infra_correlator_suppress_oper:RuleName";
          type string {
            length "0..32";
          }
          description "Suppression Rule Name";
        }
        uses AC-SUPPR-RULE-DETAIL-BAG;
      }
    }
  }

  container correlator {
    xr:xr-xml-map "infra_correlator_oper:Correlator";
    config false;
    description "correlator";

    container rules {
      xr:xr-xml-map "infra_correlator_oper:RuleTable";
      description
        "Table that contains the database of correlation
        rules";

      list rule {
        xr:xr-xml-map "infra_correlator_oper:Rule";
        key "rule-name";
        description "One of the correlation rules";
        leaf rule-name {
          xr:xr-xml-map "infra_correlator_oper:RuleName";
          type string {
            length "0..32";
          }
          description "Correlation Rule Name";
        }
        uses AC-RULE-INFO-BAG;
      }
    }

    container buffer-status {
      xr:xr-xml-map "infra_correlator_oper:BufferStatus";
      description
        "Describes buffer utilization and parameters
        configured";
      uses AC-BUFFER-INFO-BAG;
    }

    container alarms {
      xr:xr-xml-map "infra_correlator_oper:AlarmTable";
      description "Correlated alarms Table";

      list alarm {
        xr:xr-xml-map "infra_correlator_oper:Alarm";
        key "alarm-id";
        description "One of the correlated alarms";
        leaf alarm-id {
          xr:xr-xml-map "infra_correlator_oper:AlarmID";
          type int32;
          description "Alarm ID";
        }
        uses AC-ALDEMS-ALARM-BAG;
      }
    }

    container rule-set-summaries {
      xr:xr-xml-map "infra_correlator_oper:RulesetSummaryTable";
      description "Table that contains the ruleset summary info";

      list rule-set-summary {
        xr:xr-xml-map "infra_correlator_oper:RulesetSummary";
        key "rule-set-name";
        description "Summary of one of the correlation rulesets";
        leaf rule-set-name {
          xr:xr-xml-map "infra_correlator_oper:RulesetName";
          type string {
            length "0..32";
          }
          description "Ruleset Name";
        }
        uses AC-RULESET-SUMMARY-BAG;
      }
    }

    container rule-set-details {
      xr:xr-xml-map "infra_correlator_oper:RulesetDetailTable";
      description "Table that contains the ruleset detail info";

      list rule-set-detail {
        xr:xr-xml-map "infra_correlator_oper:RulesetDetail";
        key "rule-set-name";
        description "Detail of one of the correlation rulesets";
        leaf rule-set-name {
          xr:xr-xml-map "infra_correlator_oper:RulesetName";
          type string {
            length "0..32";
          }
          description "Ruleset Name";
        }
        uses AC-RULESET-DETAIL-BAG;
      }
    }

    container rule-details {
      xr:xr-xml-map "infra_correlator_oper:RuleDetailTable";
      description
        "Table that contains the database of correlation
        rule details";

      list rule-detail {
        xr:xr-xml-map "infra_correlator_oper:RuleDetail";
        key "rule-name";
        description "Details of one of the correlation rules";
        leaf rule-name {
          xr:xr-xml-map "infra_correlator_oper:RuleName";
          type string {
            length "0..32";
          }
          description "Correlation Rule Name";
        }
        uses AC-RULE-DETAIL-BAG;
      }
    }

    container rule-summaries {
      xr:xr-xml-map "infra_correlator_oper:RuleSummaryTable";
      description
        "Table that contains the database of correlation
        rule summary";

      list rule-summary {
        xr:xr-xml-map "infra_correlator_oper:RuleSummary";
        key "rule-name";
        description "One of the correlation rules";
        leaf rule-name {
          xr:xr-xml-map "infra_correlator_oper:RuleName";
          type string {
            length "0..32";
          }
          description "Correlation Rule Name";
        }
        uses AC-RULE-SUMMARY-BAG;
      }
    }
  }
}
