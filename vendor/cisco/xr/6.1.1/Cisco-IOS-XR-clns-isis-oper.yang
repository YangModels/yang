module Cisco-IOS-XR-clns-isis-oper {

  /*** NAMESPACE / PREFIX DEFINITION ***/

  namespace "http://cisco.com/ns/yang/Cisco-IOS-XR-clns-isis-oper";


  prefix "clns-isis-oper";

  /*** LINKAGE (IMPORTS / INCLUDES) ***/

  import ietf-inet-types { prefix "inet"; }

  import Cisco-IOS-XR-types { prefix "xr"; }

  import Cisco-IOS-XR-clns-isis-datatypes { prefix "dt1"; }

  include Cisco-IOS-XR-clns-isis-oper-sub2 {
    revision-date 2015-11-09;
  }

  include Cisco-IOS-XR-clns-isis-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR clns-isis package operational data.

     This module contains definitions
     for the following management objects:
       isis: IS-IS operational data

     Copyright (c) 2013-2016 by Cisco Systems, Inc.
     All rights reserved.";

  revision "2015-11-09" {
    description
      "IOS XR 6.0 revision.";
  }


  grouping POLICY-MI {
    description
      "Common node of policy-ipv4-active,
      policy-ipv4-backup, policy-ipv6-active,
      policy-ipv6-backup";

    list policy-mi {
      xr:xr-xml-map "isis_oper:PolicyMi";
      key "mi-id";
      description "Mapping Item";
      leaf mi-id {
        xr:xr-xml-map "isis_oper:MiId";
        type xr:Cisco-ios-xr-string;
        description "Mapping Item ID (0, 1, 2, ...)";
      }
      uses SRMS-MI-T-B;
    }
  }

  container isis {
    xr:xr-xml-map "isis_oper:ISIS";
    config false;
    description "IS-IS operational data";

    container instances {
      xr:xr-xml-map "isis_oper:InstanceTable";
      description "Per-instance operational data";

      list instance {
        xr:xr-xml-map "isis_oper:Instance";
        key "instance-name";
        description "IS-IS instance";

        container neighbors {
          xr:xr-xml-map "isis_oper:NeighborTable";
          description "Neighbor table";

          list neighbor {
            xr:xr-xml-map "isis_oper:Neighbor";
            description "A single neighbor router";
            leaf system-id {
              xr:xr-xml-map "isis_oper:SystemID";
              type xr:Osi-system-id;
              description "System ID";
            }
            leaf interface-name {
              xr:xr-xml-map "isis_oper:InterfaceName";
              type xr:Interface-name;
              description "Interface name";
            }
            uses ISIS-SH-NBR;
          }
        }

        container host-names {
          xr:xr-xml-map "isis_oper:HostnameTable";
          description "Hostname table";

          list host-name {
            xr:xr-xml-map "isis_oper:Hostname";
            key "system-id";
            description "Hostname table entry";
            leaf system-id {
              xr:xr-xml-map "isis_oper:SystemID";
              type xr:Osi-system-id;
              description "System ID";
            }
            uses ISIS-SH-HOST;
          }
        }

        container statistics-global {
          xr:xr-xml-map "isis_oper:StatisticsGlobal";
          description "Per-instance statistics";
          uses ISIS-SH-TRAFFIC-GLOBAL;
        }

        container levels {
          xr:xr-xml-map "isis_oper:LevelTable";
          description "Level table";

          list level {
            xr:xr-xml-map "isis_oper:Level";
            key "level";
            description "Per-level operational data";

            container adjacency-log {
              xr:xr-xml-map "isis_oper:AdjacencyLog";
              description
                "Log of adjacency changes within a single
                level";
              uses ISIS-SH-ADJ-LOG-STRUC;
            }

            container lsp-table-summary {
              xr:xr-xml-map "isis_oper:LSPTableSummary";
              description
                "Summary information for one level's LSP
                database";
              uses ISIS-SH-LSP-DB-SUMMARY;
            }

            container adjacencies {
              xr:xr-xml-map "isis_oper:AdjacencyTable";
              description "Adjacency table";

              list adjacency {
                xr:xr-xml-map "isis_oper:Adjacency";
                description "A single IS-IS adjacency";
                leaf system-id {
                  xr:xr-xml-map "isis_oper:SystemID";
                  type xr:Osi-system-id;
                  description "System ID";
                }
                leaf interface-name {
                  xr:xr-xml-map "isis_oper:InterfaceName";
                  type xr:Interface-name;
                  description "Interface name";
                }
                uses ISIS-SH-ADJ;
              }
            }

            container detailed-lsps {
              xr:xr-xml-map "isis_oper:DetailedLSPTable";
              description
                "Detailed LSP table. Use to retrieve LSPs
                with TLV content.";

              list detailed-lsp {
                xr:xr-xml-map "isis_oper:DetailedLSP";
                key "lsp-id";
                description
                  "An IS-IS LSP with detailed TLV data
                  included";
                leaf lsp-id {
                  xr:xr-xml-map "isis_oper:LSP_ID";
                  type xr:Isis-lsp-id;
                  description "LSP ID";
                }
                uses ISIS-SH-LSP;
              }
            }

            container lsps {
              xr:xr-xml-map "isis_oper:LSPTable";
              description "LSP table";

              list lsp {
                xr:xr-xml-map "isis_oper:LSP";
                key "lsp-id";
                description
                  "An IS-IS LSP (header information only)";
                leaf lsp-id {
                  xr:xr-xml-map "isis_oper:LSP_ID";
                  type xr:Isis-lsp-id;
                  description "LSP ID";
                }
                uses ISIS-SH-LSP;
              }
            }

            container lsp-log {
              xr:xr-xml-map "isis_oper:LSPLog";
              description "LSP-log for a single level";
              uses ISIS-SH-LSP-LOG-STRUC;
            }

            container database-log {
              xr:xr-xml-map "isis_oper:DatabaseLog";
              description "Database-log for a single level";
              uses ISIS-SH-LSP-DB-LOG-STRUC;
            }
            leaf level {
              xr:xr-xml-map "isis_oper:Level";
              type dt1:Isis-internal-level;
              description "Level";
            }
          }
        }

        container topologies {
          xr:xr-xml-map "isis_oper:TopologyTable";
          description "Topology table";

          list topology {
            xr:xr-xml-map "isis_oper:Topology";
            description "Per-topology data";

            container frr-summary {
              xr:xr-xml-map "isis_oper:FRRSummary";
              description
                "FRR summary information for a particular
                IS-IS topology";
              uses ISIS-SH-FRR-SUMMARY;
            }

            container topology-levels {
              xr:xr-xml-map "isis_oper:TopologyLevelTable";
              description "Per-topology level table";

              list topology-level {
                xr:xr-xml-map "isis_oper:TopologyLevel";
                key "level";
                description "Per-level topology operational data";

                container te-advertisements {
                  xr:xr-xml-map "isis_oper:TEAdvertisements";
                  description
                    "TE advertisements for a single level and
                    topology. Only available within the IPv4
                    Unicast topology.";
                  uses ISIS-SH-TE-ADV;
                }

                container te-adjacency-log {
                  xr:xr-xml-map "isis_oper:TEAdjacencyLog";
                  description
                    "TE adjacency-log for a single level and
                    topology. Only available within the IPv4
                    Unicast topology.";
                  uses ISIS-SH-TE-LOG-STRUC;
                }

                container spf-log {
                  xr:xr-xml-map "isis_oper:SPFLog";
                  description
                    "Log of route calculations for a single
                    level and topology";
                  uses ISIS-SH-SPF-LOG-STRUC;
                }

                container te-tunnels {
                  xr:xr-xml-map "isis_oper:TETunnelTable";
                  description
                    "TE tunnels table. Only available within
                    the IPv4 Unicast topology.";

                  list te-tunnel {
                    xr:xr-xml-map "isis_oper:TETunnel";
                    description
                      "A single TE tunnel advertized by IS-IS";
                    leaf system-id {
                      xr:xr-xml-map "isis_oper:SystemID";
                      type xr:Osi-system-id;
                      description "System ID";
                    }
                    leaf interface-name {
                      xr:xr-xml-map "isis_oper:InterfaceName";
                      type xr:Interface-name;
                      description "Interface name";
                    }
                    uses ISIS-SH-TE-TUNNEL;
                  }
                }

                container ipv4-link-topologies {
                  xr:xr-xml-map "isis_oper:IPV4LinkTopologyTable";
                  description "IPv4 IS Topology table";

                  list ipv4-link-topology {
                    xr:xr-xml-map "isis_oper:IPV4LinkTopology";
                    key "system-id";
                    description "An IS in an IPv4 Link Topology";
                    leaf system-id {
                      xr:xr-xml-map "isis_oper:SystemID";
                      type xr:Osi-system-id;
                      description "System ID";
                    }
                    uses ISIS-SH-IPV4-TOPO-ENTRY;
                  }
                }

                container topology-summary {
                  xr:xr-xml-map "isis_oper:TopologySummary";
                  description
                    "Summary information for a particular IS
                    Topology";
                  uses ISIS-SH-TOPO-SUMMARY;
                }

                container ipv6-link-topologies {
                  xr:xr-xml-map "isis_oper:IPV6LinkTopologyTable";
                  description "IPv6 IS Topology table";

                  list ipv6-link-topology {
                    xr:xr-xml-map "isis_oper:IPV6LinkTopology";
                    key "system-id";
                    description "An IS in an IPv6 Link Topology";
                    leaf system-id {
                      xr:xr-xml-map "isis_oper:SystemID";
                      type xr:Osi-system-id;
                      description "System ID";
                    }
                    uses ISIS-SH-IPV6-TOPO-ENTRY;
                  }
                }
                leaf level {
                  xr:xr-xml-map "isis_oper:Level";
                  type dt1:Isis-internal-level;
                  description "Level";
                }
              }
            }

            container ipv6-routes {
              xr:xr-xml-map "isis_oper:IPV6RouteTable";
              description "IPv6 local route";

              list ipv6-route {
                xr:xr-xml-map "isis_oper:IPv6Route";
                description "An IPv6 route known to IS-IS";
                leaf prefix {
                  xr:xr-xml-map "isis_oper:Prefix";
                  type inet:ipv6-address-no-zone;
                  description "Prefix";
                }
                leaf prefix-length {
                  xr:xr-xml-map "isis_oper:PrefixLength";
                  type dt1:Isis-ipv6-prefix-length;
                  description "Prefix Length";
                }
                uses ISIS-SH-IPV6-ROUTE;
              }
            }

            container ipv6frr-backups {
              xr:xr-xml-map "isis_oper:IPV6FRRTable";
              description "IPv6 FRR table";

              list ipv6frr-backup {
                xr:xr-xml-map "isis_oper:IPv6FRRBackup";
                description "FRR backup for an IPv6 network";
                leaf prefix {
                  xr:xr-xml-map "isis_oper:Prefix";
                  type inet:ipv6-address-no-zone;
                  description "Prefix";
                }
                leaf prefix-length {
                  xr:xr-xml-map "isis_oper:PrefixLength";
                  type dt1:Isis-ipv6-prefix-length;
                  description "Prefix Length";
                }
                uses ISIS-SH-IPV6-ROUTE;
              }
            }

            container ipv4frr-backups {
              xr:xr-xml-map "isis_oper:IPV4FRRTable";
              description "IPv4 FRR table";

              list ipv4frr-backup {
                xr:xr-xml-map "isis_oper:IPV4FRRBackup";
                description "FRR backup for an IPv4 network";
                leaf prefix {
                  xr:xr-xml-map "isis_oper:Prefix";
                  type inet:ipv4-address-no-zone;
                  description "Prefix";
                }
                leaf prefix-length {
                  xr:xr-xml-map "isis_oper:PrefixLength";
                  type dt1:Isis-ipv4-prefix-length;
                  description "Prefix Length";
                }
                uses ISIS-SH-IPV4-ROUTE;
              }
            }

            container ipv4-routes {
              xr:xr-xml-map "isis_oper:IPV4RouteTable";
              description "IPv4 local route table";

              list ipv4-route {
                xr:xr-xml-map "isis_oper:IPV4Route";
                description "An IPv4 route known to IS-IS";
                leaf prefix {
                  xr:xr-xml-map "isis_oper:Prefix";
                  type inet:ipv4-address-no-zone;
                  description "Prefix";
                }
                leaf prefix-length {
                  xr:xr-xml-map "isis_oper:PrefixLength";
                  type dt1:Isis-ipv4-prefix-length;
                  description "Prefix Length";
                }
                uses ISIS-SH-IPV4-ROUTE;
              }
            }
            leaf af-name {
              xr:xr-xml-map "isis_oper:AFName";
              type dt1:Isis-address-family;
              description "Address family";
            }
            leaf saf-name {
              xr:xr-xml-map "isis_oper:SAFName";
              type dt1:Isis-sub-address-family;
              description "Sub address family";
            }
            leaf topology-name {
              xr:xr-xml-map "isis_oper:TopologyName";
              type dt1:Isis-topology-name;
              description "Topology Name";
            }
          }
        }

        container nsr-status {
          xr:xr-xml-map "isis_oper:NSRStatus";
          description "NSR Status information";
          uses ISIS-SH-NSR-STATUS-GLOBAL;
        }

        container interfaces {
          xr:xr-xml-map "isis_oper:InterfaceTable";
          description "Interface table";

          list interface {
            xr:xr-xml-map "isis_oper:Interface";
            key "interface-name";
            description "Information about one IS-IS interface";
            leaf interface-name {
              xr:xr-xml-map "isis_oper:InterfaceName";
              type xr:Interface-name;
              description "Interface name";
            }
            uses ISIS-SH-IF;
          }
        }

        container checkpoint-adjacencies {
          xr:xr-xml-map "isis_oper:CheckpointAdjacencyTable";
          description "Checkpointed adjacency table";

          list checkpoint-adjacency {
            xr:xr-xml-map "isis_oper:CheckpointAdjacency";
            description "A checkpointed IS-IS adjacency";
            leaf level {
              xr:xr-xml-map "isis_oper:Level";
              type dt1:Isis-internal-level;
              description "Level";
            }
            leaf system-id {
              xr:xr-xml-map "isis_oper:SystemID";
              type xr:Osi-system-id;
              description "System ID";
            }
            leaf interface-name {
              xr:xr-xml-map "isis_oper:InterfaceName";
              type xr:Interface-name;
              description "Interface name";
            }
            uses ISIS-SH-CHKPT-ADJ;
          }
        }

        container srms {
          xr:xr-xml-map "isis_oper:SRMS";
          description
            "Segment Routing Mapping Server operational
            data";

          container policy {
            xr:xr-xml-map "isis_oper:Policy";
            description "Policy operational data";

            container policy-ipv4 {
              xr:xr-xml-map "isis_oper:PolicyIpv4";
              description "IPv4 policy operational data";

              container policy-ipv4-active {
                xr:xr-xml-map "isis_oper:PolicyIpv4Active";
                description "IPv4 active policy operational data";
                uses POLICY-MI;
              }

              container policy-ipv4-backup {
                xr:xr-xml-map "isis_oper:PolicyIpv4Backup";
                description "IPv4 backup policy operational data";
                uses POLICY-MI;
              }
            }

            container policy-ipv6 {
              xr:xr-xml-map "isis_oper:PolicyIpv6";
              description "IPv6 policy operational data";

              container policy-ipv6-backup {
                xr:xr-xml-map "isis_oper:PolicyIpv6Backup";
                description "IPv6 backup policy operational data";
                uses POLICY-MI;
              }

              container policy-ipv6-active {
                xr:xr-xml-map "isis_oper:PolicyIpv6Active";
                description "IPv6 active policy operational data";
                uses POLICY-MI;
              }
            }
          }
        }

        container error-log {
          xr:xr-xml-map "isis_oper:ErrorLog";
          description "Log of errors and warnings";
          uses ISIS-SH-ERR-LOG-STRUC;
        }

        container checkpoint-interfaces {
          xr:xr-xml-map "isis_oper:CheckpointInterfaceTable";
          description "Checkpointed interface table";

          list checkpoint-interface {
            xr:xr-xml-map "isis_oper:CheckpointInterface";
            key "interface-name";
            description
              "Checkpointed information about one IS-IS
              interface";
            leaf interface-name {
              xr:xr-xml-map "isis_oper:InterfaceName";
              type xr:Interface-name;
              description "Interface name";
            }
            uses ISIS-SH-CHKPT-IDB;
          }
        }

        container interface-statistics {
          xr:xr-xml-map "isis_oper:InterfaceStatisticsTable";
          description "Interface statistics table";

          list interface-statistic {
            xr:xr-xml-map "isis_oper:InterfaceStatistics";
            key "interface-name";
            description "Statistics data for one IS-IS interface";
            leaf interface-name {
              xr:xr-xml-map "isis_oper:InterfaceName";
              type xr:Interface-name;
              description "Interface name";
            }
            uses ISIS-SH-TRAFFIC-INTF;
          }
        }

        container protocol {
          xr:xr-xml-map "isis_oper:Protocol";
          description
            "Basic protocol information about an IS-IS
            instance";
          uses ISIS-SH-PROTO;
        }

        container neighbor-summaries {
          xr:xr-xml-map "isis_oper:NeighborSummaryTable";
          description "Neighbor-summary table";

          list neighbor-summary {
            xr:xr-xml-map "isis_oper:NeighborSummary";
            key "interface-name";
            description
              "Neighbor-summary data for a single interface";
            leaf interface-name {
              xr:xr-xml-map "isis_oper:InterfaceName";
              type xr:Interface-name;
              description "Interface name";
            }
            uses ISIS-SH-NBR-SUMM;
          }
        }

        container checkpoint-lsps {
          xr:xr-xml-map "isis_oper:CheckpointLSPTable";
          description "Checkpointed LSP table";

          list checkpoint-lsp {
            xr:xr-xml-map "isis_oper:CheckpointLSP";
            description "A checkpointed IS-IS LSP";
            leaf level {
              xr:xr-xml-map "isis_oper:Level";
              type dt1:Isis-internal-level;
              description "Level";
            }
            leaf lsp-id {
              xr:xr-xml-map "isis_oper:LSP_ID";
              type xr:Isis-lsp-id;
              description "LSP ID";
            }
            uses ISIS-SH-CHKPT-LSP;
          }
        }

        container mesh-groups {
          xr:xr-xml-map "isis_oper:MeshGroups";
          description "Mesh-group information";
          uses ISIS-SH-MESH-GROUPS;
        }

        container nsr-statistics {
          xr:xr-xml-map "isis_oper:NSRStatistics";
          description "NSR Statistics information";
          uses ISIS-SH-NSR-STATS-GLOBAL;
        }

        container checkpoint-te-tunnels {
          xr:xr-xml-map "isis_oper:CheckpointTETunnelTable";
          description "Checkpointed TE tunnel table";

          list checkpoint-te-tunnel {
            xr:xr-xml-map "isis_oper:CheckpointTETunnel";
            description "A checkpointed TE tunnel";
            leaf level {
              xr:xr-xml-map "isis_oper:Level";
              type dt1:Isis-internal-level;
              description "Level";
            }
            leaf interface-name {
              xr:xr-xml-map "isis_oper:InterfaceName";
              type xr:Interface-name;
              description "Interface name";
            }
            uses ISIS-SH-CHKPT-TE-TUNNEL;
          }
        }
        leaf instance-name {
          xr:xr-xml-map "isis_oper:InstanceName";
          type dt1:Isis-instance-name;
          description "Instance identifier";
        }
      }
    }
  }
}
