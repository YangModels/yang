submodule Cisco-IOS-XR-man-ems-oper-sub1 {

  belongs-to Cisco-IOS-XR-man-ems-oper {
    prefix Cisco-IOS-XR-man-ems-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR man-ems package operational data.

     Copyright (c) 2013-2016 by Cisco Systems, Inc.
     All rights reserved.";

  revision "2015-11-09" {
    description
      "IOS XR 6.0 revision.";
  }


  grouping GRPC-CONFIGURATION-INFO {
    description "gRPC Configuration Info";
    leaf ct-show-cmd-txt-req-recv {
      xr:xr-xml-map "ems_status:CtShowCmdTxtReqRecv";
      type uint64;
      description "CounterShowCmdTxtReqRecv";
    }
    leaf ct-show-cmd-txt-res-sent {
      xr:xr-xml-map "ems_status:CtShowCmdTxtResSent";
      type uint64;
      description "CounterShowCmdTxtResSent";
    }
    leaf ct-get-config-req-recv {
      xr:xr-xml-map "ems_status:CtGetConfigReqRecv";
      type uint64;
      description "CounterGetConfigReqRecv";
    }
    leaf ct-get-config-res-sent {
      xr:xr-xml-map "ems_status:CtGetConfigResSent";
      type uint64;
      description "CounterGetConfigResSent";
    }
    leaf ct-cli-config-req-recv {
      xr:xr-xml-map "ems_status:CtCliConfigReqRecv";
      type uint64;
      description "CounterCliConfigReqRecv";
    }
    leaf ct-cli-config-res-sent {
      xr:xr-xml-map "ems_status:CtCliConfigResSent";
      type uint64;
      description "CounterCliConfigResSent";
    }
    leaf ct-merge-config-req-recv {
      xr:xr-xml-map "ems_status:CtMergeConfigReqRecv";
      type uint64;
      description "CounterMergeConfigReq";
    }
    leaf ct-merge-config-res-sent {
      xr:xr-xml-map "ems_status:CtMergeConfigResSent";
      type uint64;
      description "CounterMergeConfigRes";
    }
    leaf ct-commit-replace-req-recv {
      xr:xr-xml-map "ems_status:CtCommitReplaceReqRecv";
      type uint64;
      description "CounterCommitReplaceReq";
    }
    leaf ct-commit-replace-res-sent {
      xr:xr-xml-map "ems_status:CtCommitReplaceResSent";
      type uint64;
      description "CounterCommitReplaceRes";
    }
    leaf ct-delete-config-req-recv {
      xr:xr-xml-map "ems_status:CtDeleteConfigReqRecv";
      type uint64;
      description "CounterDeleteConfigReq";
    }
    leaf ct-delete-config-res-sent {
      xr:xr-xml-map "ems_status:CtDeleteConfigResSent";
      type uint64;
      description "CounterDeleteConfigRes";
    }
    leaf ct-replace-config-req-recv {
      xr:xr-xml-map "ems_status:CtReplaceConfigReqRecv";
      type uint64;
      description "CounterReplaceConfigReq";
    }
    leaf ct-replace-config-res-sent {
      xr:xr-xml-map "ems_status:CtReplaceConfigResSent";
      type uint64;
      description "CounterReplaceConfigSent";
    }
    leaf ct-get-oper-req-recv {
      xr:xr-xml-map "ems_status:CtGetOperReqRecv";
      type uint64;
      description "CounterGetOperReqRecv";
    }
    leaf ct-get-oper-res-sent {
      xr:xr-xml-map "ems_status:CtGetOperResSent";
      type uint64;
      description "CounterGetOperResSent";
    }
    leaf ct-get-current-session {
      xr:xr-xml-map "ems_status:CtGetCurrentSession";
      type uint32;
      description "CounterGetCurrentSession";
    }
    leaf transport {
      xr:xr-xml-map "ems_status:Transport";
      type string;
      description "GRPCTransport";
    }
    leaf address-family {
      xr:xr-xml-map "ems_status:AddressFamily";
      type string;
      description "AddressFamily";
    }
    leaf tls {
      xr:xr-xml-map "ems_status:TLS";
      type string;
      description "GRPCTLS";
    }
    leaf trustpoint {
      xr:xr-xml-map "ems_status:Trustpoint";
      type string;
      description "GRPCTrustpoint";
    }
    leaf listening-port {
      xr:xr-xml-map "ems_status:ListeningPort";
      type int32;
      description "ListeningPort";
    }
    leaf max-req-per-user {
      xr:xr-xml-map "ems_status:MaxReqPerUser";
      type uint32;
      description "MaxReqPerUser";
    }
    leaf max-req-total {
      xr:xr-xml-map "ems_status:MaxReqTotal";
      type uint32;
      description "MaxReqTotal";
    }
  }
}
