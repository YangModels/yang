submodule Cisco-IOS-XR-ipv4-ospf-oper-sub1 {

  belongs-to Cisco-IOS-XR-ipv4-ospf-oper {
    prefix Cisco-IOS-XR-ipv4-ospf-oper;
  }

  /*** LINKAGE (IMPORTS / INCLUDES) ***/

  import ietf-inet-types { prefix "inet"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR ipv4-ospf package operational data.

     Copyright (c) 2013-2016 by Cisco Systems, Inc.
     All rights reserved.";

  revision "2015-11-09" {
    description
      "IOS XR 6.0 revision.";
  }

  typedef Srms-mi-flag-e-b {
    type enumeration {
      enum false {
        value 0;
        description "False";
      }
      enum true {
        value 1;
        description "True";
      }
    }
    description "Srms mi flag e b";
  }
  typedef In6-addr-t-b {
    type inet:ipv6-address;
    description "In6 addr t b";
  }
  typedef Srms-mi-af-e-b {
    type enumeration {
      enum none {
        value 0;
        description "None";
      }
      enum ipv4 {
        value 1;
        description "IPv4";
      }
      enum ipv6 {
        value 2;
        description "IPv6";
      }
    }
    description "Srms mi af e b";
  }
  typedef Srms-mi-src-e-b {
    type enumeration {
      enum none {
        value 0;
        description "None";
      }
      enum local {
        value 1;
        description "Local";
      }
      enum remote {
        value 2;
        description "Remote";
      }
    }
    description "Srms mi src e b";
  }

  grouping ADDR {
    description "ADDR";
    leaf af {
      xr:xr-xml-map "srms_show:AF";
      type Srms-mi-af-e-b;
      description "AF";
    }
    leaf ipv4 {
      xr:xr-xml-map "srms_show:IPv4";
      when "../af = 'ipv4'" {
        description "../AF = 'IPv4'";
      }
      type inet:ipv4-address;
      description "IPv4";
    }
    leaf ipv6 {
      xr:xr-xml-map "srms_show:IPv6";
      when "../af = 'ipv6'" {
        description "../AF = 'IPv6'";
      }
      type In6-addr-t-b;
      description "IPv6";
    }
  }

  grouping SRMS-MI-T-B {
    description "SRMS show bag";

    container addr {
      description "addr";
      uses ADDR;
    }
    leaf src {
      xr:xr-xml-map "srms_show:src";
      type Srms-mi-src-e-b;
      description "src";
    }
    leaf router {
      xr:xr-xml-map "srms_show:router";
      type string {
        length "0..30";
      }
      description "Router ID";
    }
    leaf area {
      xr:xr-xml-map "srms_show:area";
      type string {
        length "0..30";
      }
      description "Area (OSPF) or Level (ISIS)";
    }
    leaf prefix {
      xr:xr-xml-map "srms_show:prefix";
      type uint8;
      description "Prefix length";
    }
    leaf sid-start {
      xr:xr-xml-map "srms_show:sid_start";
      type uint32;
      description "Starting SID";
    }
    leaf sid-count {
      xr:xr-xml-map "srms_show:sid_count";
      type uint32;
      description "SID range";
    }
    leaf last-prefix {
      xr:xr-xml-map "srms_show:last_prefix";
      type string {
        length "0..50";
      }
      description "Last IP Prefix";
    }
    leaf last-sid-index {
      xr:xr-xml-map "srms_show:last_sid_index";
      type uint32;
      description "Last SID Index";
    }
    leaf flag-attached {
      xr:xr-xml-map "srms_show:flag_attached";
      type Srms-mi-flag-e-b;
      description "Attached flag";
    }
  }
}
