module Cisco-IOS-XR-linux-os-reboot-history-oper {

  /*** NAMESPACE / PREFIX DEFINITION ***/

  namespace "http://cisco.com/ns/yang"+
    "/Cisco-IOS-XR-linux-os-reboot-history-oper";


  prefix "linux-os-reboot-history-oper";

  /*** LINKAGE (IMPORTS / INCLUDES) ***/

  import Cisco-IOS-XR-types { prefix "xr"; }

  include Cisco-IOS-XR-linux-os-reboot-history-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR linux-os-reboot-history package operational data.

     This module contains definitions
     for the following management objects:
       reboot-history: Reboot History information

     Copyright (c) 2013-2016 by Cisco Systems, Inc.
     All rights reserved.";

  revision "2015-11-09" {
    description
      "IOS XR 6.0 revision.";
  }


  container reboot-history {
    xr:xr-xml-map "linux_os_reboot_history_oper:RebootHistory";
    config false;
    description "Reboot History information";

    list node {
      xr:xr-xml-map "linux_os_reboot_history_oper:Node";
      key "node-name";
      description "Node ID";
      leaf node-name {
        xr:xr-xml-map "linux_os_reboot_history_oper:NodeName";
        type xr:Node-id;
        description "Node name";
      }
      uses HISTORY;
    }
  }
}
