submodule Cisco-IOS-XR-infra-policymgr-oper-sub2 {

  belongs-to Cisco-IOS-XR-infra-policymgr-oper {
    prefix Cisco-IOS-XR-infra-policymgr-oper;
  }

  /*** LINKAGE (IMPORTS / INCLUDES) ***/

  import ietf-inet-types { prefix "inet"; }

  import ietf-yang-types { prefix "yang"; }

  import Cisco-IOS-XR-types { prefix "xr"; }

  include Cisco-IOS-XR-infra-policymgr-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR infra-policymgr package operational data.

     Copyright (c) 2013-2016 by Cisco Systems, Inc.
     All rights reserved.";

  revision "2015-11-09" {
    description
      "IOS XR 6.0 revision.";
  }

  typedef Pclass-diff-inbag {
    type uint64;
    description "Pclass diff inbag";
  }
  typedef Pclass-data-avl-inbag {
    type uint64;
    description "Pclass data avl inbag";
  }
  typedef Cac-flow-actn {
    type uint8;
    description "Cac flow actn";
  }
  typedef Policy-map-hd-inbag {
    type uint64;
    description "Policy map hd inbag";
  }
  typedef Shared-bucket-name {
    type string {
      length "0..65";
    }
    description "Shared bucket name";
  }
  typedef Police-action {
    type enumeration {
      enum police-action-none {
        value 0;
        description "Policer Action None";
      }
      enum police-action-transmit {
        value 1;
        description "Policer Action Transmit";
      }
      enum police-action-drop {
        value 2;
        description "Policer Action Drop";
      }
      enum police-action-mark {
        value 3;
        description "Policer Action Mark";
      }
      enum police-action-max {
        value 4;
        description "Policer Action Max";
      }
    }
    description "Policer Action Type";
  }
  typedef Redirect {
    type uint8;
    description "Redirect";
  }
  typedef Dpss-snid {
    type enumeration {
      enum dpss-snid-invalid {
        value 0;
        description "dpss snid invalid";
      }
      enum dpss-snid-index {
        value 1;
        description "dpss snid index";
      }
      enum dpss-snid-name {
        value 2;
        description "dpss snid name";
      }
      enum dpss-snid-type-max {
        value 3;
        description "dpss snid type max";
      }
    }
    description "Dpss snid";
  }
  typedef Acct {
    type enumeration {
      enum policy-acct-evt-unspecified {
        value 0;
        description "policy acct evt unspecified";
      }
      enum policy-acct-evt-start {
        value 1;
        description "policy acct evt start";
      }
      enum policy-acct-evt-stop {
        value 2;
        description "policy acct evt stop";
      }
      enum policy-acct-evt-update {
        value 3;
        description "policy acct evt update";
      }
    }
    description "Acct";
  }
  typedef Qlimit {
    type enumeration {
      enum qlimit-cmd {
        value 0;
        description "Queue Limit";
      }
      enum qlimit-discard-class {
        value 1;
        description "Queue Limit based on Discard Class";
      }
      enum qlimit-qos-group {
        value 2;
        description "Queue Limit based on Qos Group";
      }
      enum qlimit-precedence {
        value 3;
        description "Queue Limit based on Precedence";
      }
      enum qlimit-mpls-exp {
        value 4;
        description "Queue Limit based on Mpls Exp";
      }
      enum qlimit-dscp {
        value 5;
        description "Queue Limit based on Dscp";
      }
      enum qlimit-max {
        value 6;
        description "Queue Limit Max (Invalid)";
      }
    }
    description "Queue Limit Types";
  }
  typedef Decode-identifier {
    type enumeration {
      enum policy-decid-unspecified {
        value 0;
        description "policy decid unspecified";
      }
      enum policy-decid-remote-id {
        value 1;
        description "policy decid remote id";
      }
      enum policy-decid-circuit-id {
        value 2;
        description "policy decid circuit id";
      }
      enum policy-decid-user-name {
        value 3;
        description "policy decid user name";
      }
      enum policy-decid-max {
        value 4;
        description "policy decid max";
      }
    }
    description "Decode identifier";
  }
  typedef Identifier {
    type enumeration {
      enum policy-ident-unspecified {
        value 0;
        description "policy ident unspecified";
      }
      enum policy-ident-authen-status {
        value 1;
        description "policy ident authen status";
      }
      enum policy-ident-dnis {
        value 2;
        description "policy ident dnis";
      }
      enum policy-ident-media {
        value 3;
        description "policy ident media";
      }
      enum policy-ident-mlp-negotiated {
        value 4;
        description "policy ident mlp negotiated";
      }
      enum policy-ident-nas-port {
        value 5;
        description "policy ident nas port";
      }
      enum policy-ident-no-user-name {
        value 6;
        description "policy ident no user name";
      }
      enum policy-ident-protocol {
        value 7;
        description "policy ident protocol";
      }
      enum policy-ident-service-name {
        value 8;
        description "policy ident service name";
      }
      enum policy-ident-source-address-ipv4 {
        value 9;
        description "policy ident source address ipv4";
      }
      enum policy-ident-source-address-ipv6 {
        value 10;
        description "policy ident source address ipv6";
      }
      enum policy-ident-source-address-mac {
        value 11;
        description "policy ident source address mac";
      }
      enum policy-ident-timer {
        value 12;
        description "policy ident timer";
      }
      enum policy-ident-tunnel-name {
        value 13;
        description "policy ident tunnel name";
      }
      enum policy-ident-auth-domain {
        value 14;
        description "policy ident auth domain";
      }
      enum policy-ident-auth-user-name {
        value 15;
        description "policy ident auth user name";
      }
      enum policy-ident-unauth-domain {
        value 16;
        description "policy ident unauth domain";
      }
      enum policy-ident-unauth-user-name {
        value 17;
        description "policy ident unauth user name";
      }
      enum policy-ident-max {
        value 18;
        description "policy ident max";
      }
    }
    description "Identifier";
  }
  typedef Mark1 {
    type uint8;
    description "Mark1";
  }
  typedef Mark {
    type enumeration {
      enum mark-type-none {
        value 0;
        description "Mark None";
      }
      enum mark-type-dscp {
        value 1;
        description "Mark DSCP";
      }
      enum mark-type-prec {
        value 2;
        description "Mark Precedence";
      }
      enum mark-type-mpls-exp-topmost {
        value 3;
        description "Mark MPLS EXP on topmost header";
      }
      enum mark-type-mpls-exp-imposition {
        value 4;
        description "Mark MPLS EXP on imposition header";
      }
      enum mark-type-qos-group {
        value 5;
        description "Mark QoS Group";
      }
      enum mark-type-discard-class {
        value 6;
        description "Mark Discard Class";
      }
      enum mark-type-cos {
        value 7;
        description "Mark CoS";
      }
      enum mark-type-cos-inner {
        value 8;
        description "Mark COS Inner";
      }
      enum mark-type-srp-priority {
        value 9;
        description "Mark Priority";
      }
      enum mark-type-atm-clp {
        value 10;
        description "Mark ATM CLP";
      }
      enum mark-type-fr-de {
        value 11;
        description "Mark FR DE";
      }
      enum mark-type-dscp-tunnel {
        value 12;
        description "Mark DSCP in Tunnel Header";
      }
      enum mark-type-prec-tunnel {
        value 13;
        description "Mark Precedence in Tunnel Header";
      }
      enum mark-type-dei {
        value 14;
        description "Mark DEI";
      }
      enum mark-type-dei-imposition {
        value 15;
        description "Mark DEI on imposition header";
      }
      enum mark-type-forward-class {
        value 16;
        description "Mark forward class";
      }
      enum mark-type-df {
        value 17;
        description "Mark DF bit";
      }
      enum mark-type-traffic-class {
        value 18;
        description "Mark Traffic Class";
      }
      enum mark-type-src-mac {
        value 19;
        description "Mark source mac";
      }
      enum mark-type-dst-mac {
        value 20;
        description "Mark destination mac";
      }
      enum mark-type-ipv4-src-addr {
        value 21;
        description "Mark ipv4 source address";
      }
      enum mark-type-ipv4-dst-addr {
        value 22;
        description "Mark ipv4 destination address";
      }
      enum mark-type-vlan-id {
        value 23;
        description "Mark vlan id";
      }
      enum mark-type-udp-src-port {
        value 24;
        description "Mark type udp source port";
      }
      enum mark-type-udp-dst-port {
        value 25;
        description "Mark type udp destination port";
      }
      enum mark-type-tcp-src-port {
        value 26;
        description "Mark type tcp source port";
      }
      enum mark-type-tcp-dst-port {
        value 27;
        description "Mark type tcp destination port";
      }
      enum mark-type-sctp-src-port {
        value 28;
        description "Mark type sctp source port";
      }
      enum mark-type-sctp-dst-port {
        value 29;
        description "Mark type sctp destination port";
      }
      enum mark-type-max {
        value 30;
        description "Mark Type Max (Invalid)";
      }
    }
    description "Mark Type Enumeration";
  }
  typedef Policy-action {
    type enumeration {
      enum policy-action-none {
        value 0;
        description "Policy Action None";
      }
      enum policy-action-unspecified {
        value 1;
        description "Policy Action is not specified";
      }
      enum policy-action-mark {
        value 2;
        description "Policy Action Mark";
      }
      enum policy-action-mark2 {
        value 3;
        description "Policy Action Mark2";
      }
      enum policy-action-wred {
        value 4;
        description "Policy Action WRED";
      }
      enum policy-action-encap-seq {
        value 5;
        description "Policy action encap-sequence number";
      }
      enum policy-action-priority {
        value 6;
        description "Policy Action Priority Queue";
      }
      enum policy-action-iphc {
        value 7;
        description "Policy Action IP Header Compression";
      }
      enum policy-action-bw-remaining {
        value 8;
        description "Policy Action Bandwidth Remaining Queue";
      }
      enum policy-action-min-bw {
        value 9;
        description "Policy Action Minimum Bandwidth Queue";
      }
      enum policy-action-authenticate-aaa {
        value 10;
        description "Policy Action authenticate";
      }
      enum policy-action-collect-id {
        value 11;
        description "Policy Action collect identifier";
      }
      enum policy-action-disconnect {
        value 12;
        description "Policy Action disconnect session";
      }
      enum policy-action-set-timer {
        value 13;
        description "Policy Action set timer";
      }
      enum policy-action-stop-timer {
        value 14;
        description "Policy Action stop timer";
      }
      enum policy-action-query-ancp {
        value 15;
        description "Policy Action query ancp";
      }
      enum policy-action-accounting-aaa-list {
        value 16;
        description "Policy Action accounting aaa";
      }
      enum policy-action-prepaid-config {
        value 17;
        description "Policy Action prepaid config";
      }
      enum policy-action-timeout-idle {
        value 18;
        description "Policy Action timeout idle";
      }
      enum policy-action-proxy-aaa {
        value 19;
        description "Policy Action proxy aaa";
      }
      enum policy-action-template-activate {
        value 20;
        description "Policy Action activate template";
      }
      enum policy-action-template-deactivate {
        value 21;
        description "Policy Action deactivate template";
      }
      enum policy-action-decode-identifier {
        value 22;
        description "Policy Action decode identifier";
      }
      enum policy-action-q-limit {
        value 23;
        description "Policy Action Queue Limit";
      }
      enum policy-action-authorize-id {
        value 24;
        description "Policy Action authorize idetifier";
      }
      enum policy-action-accounting-event-aaa-list {
        value 25;
        description "Policy Action accounting event";
      }
      enum policy-action-afmon-react {
        value 26;
        description "Policy Action React (afmon)";
      }
      enum policy-action-httpr {
        value 27;
        description "Policy Action httpr (pbr)";
      }
      enum policy-action-pbr-transmit {
        value 28;
        description "Policy Action pbr transmit";
      }
      enum policy-action-pbr-drop {
        value 29;
        description "Policy Action pbr drop";
      }
      enum policy-action-punt {
        value 30;
        description "Policy Action pbr punt";
      }
      enum policy-action-copy {
        value 31;
        description "Policy Action pbr copy";
      }
      enum policy-action-sfrag {
        value 32;
        description "Policy Action Service fragment";
      }
      enum policy-action-monitor {
        value 33;
        description "Policy Action Monitor";
      }
      enum policy-action-redirect {
        value 34;
        description "Policy Action redirect";
      }
      enum policy-action-ipv4-nh {
        value 35;
        description "Policy Action ipv4 next hop";
      }
      enum policy-action-ipv6-nh {
        value 36;
        description "Policy Action ipv6 next hop";
      }
      enum policy-action-vlan-pop {
        value 37;
        description "Policy Action pop";
      }
      enum policy-action-pbr-next-hop {
        value 38;
        description "Policy Action PBR Forward";
      }
      enum policy-action-decap-gre {
        value 39;
        description "Policy Action decapsule GRE";
      }
      enum policy-action-output-interface {
        value 40;
        description "Policy Action PBR redirect interface";
      }
      enum policy-action-service-function-path {
        value 41;
        description "Policy Action PBR service chaining";
      }
      enum policy-action-ptrs {
        value 42;
        description "Dummy action for internal use";
      }
      enum policy-action-police {
        value 43;
        description "Policy Action Police";
      }
      enum policy-action-shape {
        value 44;
        description "Policy Action Shape";
      }
      enum policy-action-serv-pol {
        value 45;
        description "Policy Action Service Policy";
      }
      enum policy-action-cac {
        value 46;
        description "Policy Action CAC";
      }
      enum policy-action-afmon-flow-parm {
        value 47;
        description "Policy Action Flow params (afmon)";
      }
      enum policy-action-afmon-ipcbr-metric {
        value 48;
        description "Policy Action IP-CBR Metric (afmon)";
      }
      enum policy-action-afmon-rtp-metric {
        value 49;
        description "Policy Action RTP-Custom Metric (afmon)";
      }
      enum policy-action-afmon-rtp-mmr-metric {
        value 50;
        description "Policy Action RTP-MMR Metric (afmon)";
      }
      enum policy-action-afmon-rtp-j2k-metric {
        value 51;
        description "Policy Action RTP-J2K Metric (afmon)";
      }
      enum policy-action-afmon-rtp-voice-metric {
        value 52;
        description "Policy Action RTP-Voice Metric (afmon)";
      }
      enum policy-action-afmon-mdi-metric {
        value 53;
        description "Policy Action MDI Metric (afmon)";
      }
      enum policy-action-afmon-mdi-rtp-metric {
        value 54;
        description "Policy Action MDI RTP Metric (afmon)";
      }
      enum policy-action-afmon-fmm {
        value 55;
        description "Policy Action flow monitor (afmon)";
      }
      enum policy-action-pfc {
        value 56;
        description "Policy Action PFC";
      }
      enum policy-action-max {
        value 57;
        description "Policy Action Max (Invalid)";
      }
    }
    description "Policy Actions Enumeration";
  }
  typedef Pclass-exec-strat {
    type enumeration {
      enum pclass-exe-strat-unspecified {
        description "Unspecified";
      }
      enum pclass-exe-strat-do-all {
        description "Exec all actions";
      }
      enum pclass-exe-strat-do-until-success {
        description "Exec until one of actions succeeds";
      }
      enum pclass-exe-strat-do-until-failure {
        description "Exec until there is a failure";
      }
      enum pclass-exe-strat-max {
        description "Invalid";
      }
    }
    description "Policy class execution strategy";
  }
  typedef Policy-chk-sum {
    type string {
      length "0..16";
    }
    description "Policy chk sum";
  }
  typedef Match-logical-operator {
    type enumeration {
      enum match-operator-unspecified {
        value 0;
        description "match operator unspecified";
      }
      enum match-equal-to {
        value 1;
        description "match equal to";
      }
      enum match-greater-than {
        value 2;
        description "match greater than";
      }
      enum match-greater-than-or-equal {
        value 3;
        description "match greater than or equal";
      }
      enum match-less-than {
        value 4;
        description "match less than";
      }
      enum match-less-than-or-equal {
        value 5;
        description "match less than or equal";
      }
      enum match-operator-max {
        value 6;
        description "match operator max";
      }
    }
    description "Logical Operators";
  }
  typedef String1 {
    type string;
    description "String1";
  }
  typedef Match {
    type enumeration {
      enum match-type-none {
        description "Match Type None";
      }
      enum match-type-ipv4-dscp {
        description "Match Type IPv4 DSCP";
      }
      enum match-type-ipv4-prec {
        description "Match Type IPv4 Precedence";
      }
      enum match-type-ipv6-dscp {
        description "Match Type IPv6 DSCP";
      }
      enum match-type-packet-length {
        description "Match Type Packet length";
      }
      enum match-type-ipv4-packet-length {
        description "Match Type IPv4 Packet length";
      }
      enum match-type-ipv6-packet-length {
        description "Match Type IPv6 Packet length";
      }
      enum match-type-flow-tag {
        description "Match Type Flow Tag";
      }
      enum match-type-icmpv4-type {
        description "Match Type IPv4 icmp-type";
      }
      enum match-type-icmpv4-code {
        description "Match Type IPv4 icmp-code";
      }
      enum match-type-icmpv6-type {
        description "Match Type IPv6 icmp-type";
      }
      enum match-type-icmpv6-code {
        description "Match Type IPv6 icmp-code";
      }
      enum match-type-ipv6-prec {
        description "Match Type IPv6 Precedence";
      }
      enum match-type-fragment-type {
        description "Match type fragment-type";
      }
      enum match-type-tcp-flag {
        description "Match type TCP flag";
      }
      enum match-type-dscp {
        description "Match Type DSCP";
      }
      enum match-type-prec {
        description "Match Type Precedence";
      }
      enum match-type-proto {
        description "Match Type Protocol";
      }
      enum match-type-proto-icmpv4 {
        description "Match Type protocol ICMPv4";
      }
      enum match-type-proto-icmpv6 {
        description "Match Type protocol ICMPv6";
      }
      enum match-type-mpls-exp-top {
        description "Match Type MPLS EXP Topmost";
      }
      enum match-type-mpls-exp-imp {
        description "Match Type MPLS EXP Imposition";
      }
      enum match-type-mpls-disp-ipv4-acl {
        description "Match Type MPLS DISP IPv4 ACL";
      }
      enum match-type-mpls-disp-ipv6-acl {
        description "Match Type MPLS DISP IPv6 ACL";
      }
      enum match-type-mpls-topmost-eos {
        description "Match Type MPLS TOPMOST EOS";
      }
      enum match-type-mpls-topmost-label {
        description "Match Type MPLS TOPMOST LABEL";
      }
      enum match-type-cos {
        description "Match Type COS";
      }
      enum match-type-cos-inner {
        description "Match Type inner COS";
      }
      enum match-type-dei {
        description "Match Type DEI";
      }
      enum match-type-dei-inner {
        description "Match Type inner DEI";
      }
      enum match-type-vlan {
        description "Match Type VLAN";
      }
      enum match-type-vlan-inner {
        description "Match Type inner VLAN";
      }
      enum match-type-fr-dlci {
        description "Match Type  FR DLCI";
      }
      enum match-type-src-mac {
        description "Match Type Source MAC Address";
      }
      enum match-type-dst-mac {
        description "Match Type Destination MAC Address";
      }
      enum match-type-atm-oam {
        description "Match Type ATM OAM";
      }
      enum match-type-atm-clp {
        description "Match Type ATM CLP";
      }
      enum match-type-fr-de {
        description "Match Type FR DE";
      }
      enum match-type-qos-grp {
        description "Match Type QoS Group";
      }
      enum match-type-traffic-class {
        description "Match Type Traffic Class";
      }
      enum match-type-disc-cls {
        description "Match Type Discard Class";
      }
      enum match-type-vpls-known {
        description "Match Type VPLS Known";
      }
      enum match-type-vpls-unknown {
        description "Match Type VPLS Unknown";
      }
      enum match-type-vpls-mcast {
        description "Match Type VPLS Multicast";
      }
      enum match-type-vpls-bcast {
        description "Match Type VPLS Broadcast";
      }
      enum match-type-vpls-control {
        description "Match Type VPLS Control";
      }
      enum match-type-ipv4-acl {
        description "Match Type IPv4 ACL";
      }
      enum match-type-ipv6-acl {
        description "Match Type IPv6 ACL";
      }
      enum match-type-flow-key {
        description "Match Type Flow Key";
      }
      enum match-type-avail-id {
        description "Match Type Available Identifier";
      }
      enum match-type-authen-status {
        description "Match Type Authentication Status";
      }
      enum match-type-media {
        description "Match Type Media";
      }
      enum match-type-mlp-negotiated {
        description "Match Type MLP Negotiated";
      }
      enum match-type-subs-protocol {
        description "Match Type Protocol";
      }
      enum match-type-dnis {
        description "Match Type DNIS";
      }
      enum match-type-dnis-regexp {
        description "Match Type DNIS Regular Exp";
      }
      enum match-type-domain {
        description "Match Type Domain";
      }
      enum match-type-domain-regexp {
        description "Match Type Domain Regular Exp";
      }
      enum match-type-nas-port {
        description "Match Type NAS Port";
      }
      enum match-type-service-name {
        description "Match Type Service Name";
      }
      enum match-type-service-name-regexp {
        description "Match Type Service Name Regular Exp";
      }
      enum match-type-src-addr-ipv4 {
        description "Match Type Source Address IPV4";
      }
      enum match-type-dst-addr-ipv4 {
        description "Match Type Source Address IPV4";
      }
      enum match-type-src-addr-ipv6 {
        description "Match Type Source Address IPV6";
      }
      enum match-type-dst-addr-ipv6 {
        description "Match Type Source Address IPV6";
      }
      enum match-type-src-addr-mac {
        description "Match Type Source Address Mac";
      }
      enum match-type-src-port {
        description "Match Type Source Port";
      }
      enum match-type-dst-port {
        description "Match Type Source Port";
      }
      enum match-type-timer {
        description "Match Type Timer";
      }
      enum match-type-timer-regexp {
        description "Match Type Timer Regular Exp";
      }
      enum match-type-tunnel-name {
        description "Match Type Tunnel Name";
      }
      enum match-type-tunnel-name-regexp {
        description "Match Type Tunnel Name Regular Exp";
      }
      enum match-type-user-name {
        description "Match Type User Name";
      }
      enum match-type-user-name-regexp {
        description "Match Type User Name Regular Exp";
      }
      enum match-type-auth-user-name {
        description "Match Type Authenticated User Name";
      }
      enum match-type-auth-user-name-regexp {
        description "Match Type Authenticated Userame Reg Exp";
      }
      enum match-type-unauth-user-name {
        description "Match Type Unauthenticated Username";
      }
      enum match-type-unauth-user-name-regexp {
        description "Match Type Unauthenicated Username RegEx";
      }
      enum match-type-no-user-name {
        description "Match Type No Username";
      }
      enum match-type-auth-domain {
        description "Match Type Authenticated Domain";
      }
      enum match-type-auth-domain-regexp {
        description "Match Type Authenticated Domain RegEx";
      }
      enum match-type-unauth-domain {
        description "Match Type Unauthenticated Domain";
      }
      enum match-type-unauth-domain-regexp {
        description "Match Type Unauthenticated Domain RegEx";
      }
      enum match-type-vendor-id {
        description "Match Type Vendor ID";
      }
      enum match-type-vendor-id-regexp {
        description "Match Type Vendor ID RegEx";
      }
      enum match-type-access-interface {
        description "Match Type Access Interface";
      }
      enum match-type-input-interface {
        description "Match Type Input Interface";
      }
      enum match-type-input-interface-hdl {
        description "Match Type Input Interface handle";
      }
      enum match-type-ether-type {
        description "Match Type Ethernet Type";
      }
      enum match-type-dhcp-client-id {
        description "Match DHCP Client ID";
      }
      enum match-type-dhcp-client-id-regexp {
        description "Match DHCP Client ID RegEx";
      }
      enum match-type-circuit-id {
        description "Match Type Circuit ID";
      }
      enum match-type-circuit-id-regexp {
        description "Match Type Circuit ID RegEx";
      }
      enum match-type-remote-id {
        description "Match Type Remote ID";
      }
      enum match-type-remote-id-regexp {
        description "Match Type Remote ID RegEx";
      }
      enum match-type-cac-admit-local {
        description "Match Type CAC admitted";
      }
      enum match-type-cac-unadmit-local {
        description "Match Type CAC unadmitted";
      }
      enum match-type-any-internal {
        description "Match Type Any (Used only for class-default)";
      }
      enum match-type-ethernet-service-s-acl {
        description "Match Type Ethernet-Services ACL";
      }
      enum match-type-ptrs {
        description "Dummy match type for internal use";
      }
      enum match-type-max {
        description "Match Type Max (Invalid)";
      }
    }
    description "Match Type";
  }
  typedef Class-map-mode {
    type enumeration {
      enum class-map-mode-match-any {
        value 0;
        description "Type Match-Any";
      }
      enum class-map-mode-match-all {
        value 1;
        description "Type Match-All";
      }
      enum class-map-mode-max {
        value 2;
        description "Not a valid mode";
      }
      enum class-map-mode-usr-def {
        value 1073741824;
        description "User defined match type";
      }
    }
    description "Class-Map Mode";
  }
  typedef Class-map-hd-inbag {
    type uint64;
    description "Class map hd inbag";
  }
  typedef Class-map-name {
    type string {
      length "0..65";
    }
    description "Class map name";
  }
  typedef Policy-obj-enc {
    type enumeration {
      enum policy-obj-enc-name {
        description "Name of the Policy";
      }
      enum policy-obj-enc-hdl {
        description "Policy Handle";
      }
      enum policy-obj-enc-var-idx {
        description "Policy Variable Index";
      }
      enum policy-obj-enc-in-line {
        description "Inline Class";
      }
    }
    description "Child policy related encoding information";
  }
  typedef Pevent-cond-eval {
    type enumeration {
      enum pevent-cond-eval-unspecified {
        description "Unspecified execution strategy";
      }
      enum pevent-cond-eval-match-first {
        description "Match-first execution strategy";
      }
      enum pevent-cond-eval-match-all {
        description "Match-all execution strategy";
      }
      enum pevent-cond-eval-max {
        description "Internal use only";
      }
    }
    description "Policy event execution strategy enumeration";
  }
  typedef Pevent {
    type enumeration {
      enum pevent-type-unspecified {
        description "Unspecified event";
      }
      enum pevent-type-acct-logon {
        description "Log on event";
      }
      enum pevent-type-acct-logoff {
        description "Log off event";
      }
      enum pevent-type-credit-exhausted {
        description "Credit exhausted event";
      }
      enum pevent-type-idle-timeout {
        description "Idle timeout event";
      }
      enum pevent-type-absolute-timeout {
        description "Absolute timeout event";
      }
      enum pevent-type-quota-depleted {
        description "Quota depletion event";
      }
      enum pevent-type-service-start {
        description "Service start event";
      }
      enum pevent-type-service-stop {
        description "Service stop event";
      }
      enum pevent-type-session-start {
        description "Session start event";
      }
      enum pevent-type-session-activate {
        description "Session activate event";
      }
      enum pevent-type-session-restart {
        description "Session restart event";
      }
      enum pevent-type-session-stop {
        description "Session stop event";
      }
      enum pevent-type-session-disconnect {
        description "Session disconnect event";
      }
      enum pevent-type-session-update {
        description "Session update event";
      }
      enum pevent-type-flow-start {
        description "Flow start event";
      }
      enum pevent-type-flow-stop {
        description "Flow stop event";
      }
      enum pevent-type-accouting-start {
        description "Accounting start event";
      }
      enum pevent-type-acountng-g-stop {
        description "Accounting stop event";
      }
      enum pevent-type-acountng-g-update {
        description "Accounting update event";
      }
      enum pevent-type-timer-expiry {
        description "Timer expierd event";
      }
      enum pevent-type-threshold-reached {
        description "Threshold reached event";
      }
      enum pevent-type-ka-success {
        description "Keep alive success event";
      }
      enum pevent-type-ka-failure {
        description "Keep alive failure event";
      }
      enum pevent-type-link-up {
        description "Link up event";
      }
      enum pevent-type-link-down {
        description "Link down event";
      }
      enum pevent-type-authorization-failure {
        description "Authorization failure event";
      }
      enum pevent-type-authorization-no-response {
        description "Authorization no response event";
      }
      enum pevent-type-authentication-failure {
        description "Authentication failure event";
      }
      enum pevent-type-authentication-no-response {
        description "Authentication no response event";
      }
      enum pevent-type-exception {
        description "Exception event";
      }
      enum pevent-type-session-ident-chg {
        description "Session identity change event";
      }
      enum pevent-type-max {
        description "Internal use only";
      }
    }
    description "Policy event enumeration";
  }
  typedef Var-cmap-name {
    type string {
      length "0..65";
    }
    description "Var cmap name";
  }
  typedef Plmgr-var {
    type enumeration {
      enum plmgr-var-type-class-name {
        description "plmgr var type class name";
      }
      enum plmgr-var-type-uint8 {
        description "plmgr var type uint8";
      }
      enum plmgr-var-type-uint16 {
        description "plmgr var type uint16";
      }
      enum plmgr-var-type-uint32 {
        description "plmgr var type uint32";
      }
      enum plmgr-var-type-param-uint32 {
        description "plmgr var type param uint32";
      }
      enum plmgr-var-type-dscp {
        description "plmgr var type dscp";
      }
      enum plmgr-var-type-prec {
        description "plmgr var type prec";
      }
      enum plmgr-var-type-max {
        description "plmgr var type max";
      }
    }
    description "Type of default variable values";
  }
  typedef Policy-map-name {
    type string {
      length "0..65";
    }
    description "Policy map name";
  }

  grouping PLMGR-APPLIED-VARLIST-BG {
    description "Policy-map applied variable list";

    list var {
      description "var";
      uses PLMGR-VAR-VAL-UN;
    }
  }

  grouping ACTION-IPV6-NH-INFO-ST {
    description "ipv6 next hop action";
    leaf nh-addr {
      xr:xr-xml-map "policymgr:nh_addr";
      type inet:ipv6-address;
      description "IPV6 Address";
    }
    leaf vrf-name {
      xr:xr-xml-map "policymgr:vrf_name";
      type string;
      description "Vrf name";
    }
  }

  grouping ACTION-IPV6-NH-INFO-ARRAY {
    description "ACTION IPV6 NH INFO ARRAY";

    list action-ipv6-nh-info-array {
      description "action ipv6 nh info array";
      uses ACTION-IPV6-NH-INFO-ST;
    }
  }

  grouping ACTION-IPV4-NH-INFO-ST {
    description "ipv4 next hop action";
    leaf nh-addr {
      xr:xr-xml-map "policymgr:nh_addr";
      type inet:ipv4-address;
      description "nh addr";
    }
    leaf vrf-name {
      xr:xr-xml-map "policymgr:vrf_name";
      type string;
      description "Vrf name";
    }
  }

  grouping ACTION-IPV4-NH-INFO-ARRAY {
    description "ACTION IPV4 NH INFO ARRAY";

    list action-ipv4-nh-info-array {
      description "action ipv4 nh info array";
      uses ACTION-IPV4-NH-INFO-ST;
    }
  }

  grouping ACTION-PBF-INFO-ST {
    description "action pbr pbf";
    leaf addr {
      xr:xr-xml-map "policymgr:addr";
      type inet:ipv6-address;
      description "v4 or v6 address";
    }
    leaf vrf {
      xr:xr-xml-map "policymgr:vrf";
      type String1;
      description "vrf name";
    }
    leaf rt-type {
      xr:xr-xml-map "policymgr:rt_type";
      type uint8;
      description "route target type";
    }
    leaf rt {
      xr:xr-xml-map "policymgr:rt";
      type yang:hex-string;
      description "route target";
    }
  }

  grouping ACTION-PBF-INFO-ARRAY {
    description "ACTION PBF INFO ARRAY";

    list action-pbf-info-array {
      description "action pbf info array";
      uses ACTION-PBF-INFO-ST;
    }
  }

  grouping ACTION-AFMON-FMM-INFO-ST {
    description "AFMon flow monitor configuration";
    leaf fmm-name {
      xr:xr-xml-map "policymgr:fmm_name";
      type string {
        length "0..33";
      }
      description "flow monitor name";
    }
  }

  grouping ACTION-AFMON-MDI-INFO-ST {
    description "AFMon MDI Configuration";

    container ip-bit-rate {
      description "data rate in bps";
      uses POLICY-PARAM-UINT32-ST;
    }
    leaf action-metric-type {
      xr:xr-xml-map "policymgr:action_metric_type";
      type Policy-action;
      description "metric type";
    }
    leaf filtered-pkt-rate {
      xr:xr-xml-map "policymgr:filtered_pkt_rate";
      type uint32;
      description "filtered packet rate";
    }
    leaf ip-pkt-rate {
      xr:xr-xml-map "policymgr:ip_pkt_rate";
      type uint32;
      description "packet rate in pps";
    }
    leaf-list pids {
      xr:xr-xml-map "policymgr:pids";
      type uint32;
      description "array of monitoredcd  pids";
    }
  }

  grouping AFMON-RTP-CLOCK-RATE-ST {
    description "AFMon RTP clock rate params";
    leaf pt {
      xr:xr-xml-map "policymgr:pt";
      type uint32;
      description "pt";
    }
    leaf frequency {
      xr:xr-xml-map "policymgr:frequency";
      type uint32;
      description "frequency";
    }
  }

  grouping ACTION-AFMON-RTP-INFO-ST {
    description "AFMon RTP Configuration";
    leaf action-metric-type {
      xr:xr-xml-map "policymgr:action_metric_type";
      type Policy-action;
      description "metric type";
    }
    leaf min-sequential {
      xr:xr-xml-map "policymgr:min_sequential";
      type uint32;
      description "min sequential";
    }
    leaf max-dropout {
      xr:xr-xml-map "policymgr:max_dropout";
      type uint32;
      description "max dropout";
    }
    leaf max-misorder {
      xr:xr-xml-map "policymgr:max_misorder";
      type uint32;
      description "max misorder";
    }
    leaf seq-ext-cop4 {
      xr:xr-xml-map "policymgr:seq_ext_cop4_en";
      type uint32;
      description "enable seq extension cop4";
    }

    list clock-rate {
      description "clock rate";
      uses AFMON-RTP-CLOCK-RATE-ST;
    }
  }

  grouping ACTION-AFMON-IPCBR-INFO-ST {
    description "AFMon IP-CBR Configuration";

    container ip-bit-rate {
      description "data rate in bps";
      uses POLICY-PARAM-UINT32-ST;
    }

    container media-bit-rate {
      description "media data rate in bps";
      uses POLICY-PARAM-UINT32-ST;
    }
    leaf action-metric-type {
      xr:xr-xml-map "policymgr:action_metric_type";
      type Policy-action;
      description "metric type";
    }
    leaf ip-pkt-rate {
      xr:xr-xml-map "policymgr:ip_pkt_rate";
      type uint32;
      description "packet rate in pps";
    }
    leaf media-pkt-size {
      xr:xr-xml-map "policymgr:media_pkt_size";
      type uint32;
      units "byte";
      description "media packet size in bytes";
    }
    leaf media-pkts-per-ip {
      xr:xr-xml-map "policymgr:media_pkts_per_ip";
      type uint32;
      description "media packets per ip pkt";
    }
  }

  grouping ACTION-AFMON-FLOW-PARM-INFO-ST {
    description "(afmon) flow-parm submode action";
    leaf max-mon-flows {
      xr:xr-xml-map "policymgr:max_mon_flows";
      type uint32;
      description "max simult flows monitored per policy class";
    }
    leaf mon-interval {
      xr:xr-xml-map "policymgr:mon_interval";
      type uint32;
      units "second";
      description "monitored interval duration in secs";
    }
    leaf intvl-hist {
      xr:xr-xml-map "policymgr:intvl_hist";
      type uint32;
      description "num intervals of data stored on rtr";
    }
    leaf flow-timeout {
      xr:xr-xml-map "policymgr:flow_timeout";
      type uint32;
      units "second";
      description "timeout in secs";
    }
  }

  grouping ACTION-PFC-INFO-ST {
    description "Pfc info bag";

    container buffer-size {
      description "buffer size";
      uses POLICY-PARAM-UINT32-ST;
    }

    container pause-threshold {
      description "pause threshold";
      uses POLICY-PARAM-UINT32-ST;
    }

    container resume-threshold {
      description "resume threshold";
      uses POLICY-PARAM-UINT32-ST;
    }
    leaf pfc-pause-set {
      xr:xr-xml-map "policymgr:pfc_pause_set";
      type uint32;
      description "pfc pause set";
    }
    leaf buffer-size-flag {
      xr:xr-xml-map "policymgr:buffer_size_flag";
      type uint32;
      description "buffer size flag";
    }
  }

  grouping ACTION-CAC-INFO-ST {
    description "CAC action info bag";

    container flow-rate {
      description "flow rate";
      uses POLICY-PARAM-UINT32-ST;
    }

    container rate {
      description "rate";
      uses POLICY-PARAM-UINT32-ST;
    }
    leaf cac-type {
      xr:xr-xml-map "policymgr:cac_type";
      type Cac-flow-actn;
      description "cac type";
    }
    leaf idle-timeout {
      xr:xr-xml-map "policymgr:idle_timeout";
      type uint16;
      description "idle timeout";
    }
  }

  grouping POLICY-MAP-HD-ST {
    description "POLICY MAP HD ST";

    container data-hd {
      description "data hd";
    }
    leaf hd {
      xr:xr-xml-map "policymgr:hd";
      type Policy-map-hd-inbag;
      description "hd";
    }
  }

  grouping POLICY-MAP-TYPE-N-NAME-ST {
    description "POLICY MAP TYPE N NAME ST";
    leaf name {
      xr:xr-xml-map "policymgr:name";
      type Policy-map-name;
      description "name";
    }
    leaf type {
      xr:xr-xml-map "policymgr:type";
      type Policy-map;
      description "type";
    }
  }

  grouping CHLD-POL-ENC-UN {
    description "Union of object name and app object ptr";

    container info {
      when "../enc = 'policy-obj-enc-name'" {
        description "../enc = 'POLICY_OBJ_ENC_NAME'";
      }
      description "info";
      uses POLICY-MAP-TYPE-N-NAME-ST;
    }

    container hd-info {
      when "../enc = 'policy-obj-enc-hdl'" {
        description "../enc = 'POLICY_OBJ_ENC_HDL'";
      }
      description "hd info";
      uses POLICY-MAP-HD-ST;
    }
    leaf enc {
      xr:xr-xml-map "policymgr:enc";
      type Policy-obj-enc;
      description "enc";
    }
  }

  grouping ACTION-SHAPE-INFO-ST {
    description "Shape info bag";

    container bw {
      description "bw";
      uses POLICY-PARAM-UINT32-ST;
    }

    container be {
      description "be";
      uses POLICY-PARAM-UINT32-ST;
    }
  }

  grouping POLICE-ACTION-UN {
    description "Police action bag";

    container mark {
      when "../type = 'police-action-mark'" {
        description "../type = 'POLICE_ACTION_MARK'";
      }
      description "mark";
      uses ACTION-MARK-INFO-ST;
    }
    leaf type {
      xr:xr-xml-map "policymgr:type";
      type Police-action;
      description "type";
    }
  }

  grouping POLICE-ACTION-ARRAY {
    description "POLICE ACTION ARRAY";

    list police-action-array {
      description "police action array";
      uses POLICE-ACTION-UN;
    }
  }

  grouping ACTION-POLICE-INFO-ST {
    description "Police action info bag";

    container rate {
      description "rate";
      uses POLICY-PARAM-UINT32-ST;
    }

    container burst {
      description "burst";
      uses POLICY-PARAM-UINT32-ST;
    }

    container peak-rate {
      description "peak rate";
      uses POLICY-PARAM-UINT32-ST;
    }

    container peak-burst {
      description "peak burst";
      uses POLICY-PARAM-UINT32-ST;
    }

    container cdvt {
      description "cdvt";
      uses POLICY-PARAM-UINT32-ST;
    }

    container conform-actns {
      description "conform actns";
      uses POLICE-ACTION-ARRAY;
    }

    container exceed-actns {
      description "exceed actns";
      uses POLICE-ACTION-ARRAY;
    }

    container violate-actns {
      description "violate actns";
      uses POLICE-ACTION-ARRAY;
    }

    container confclass-encode {
      description "confclass encode";
      uses POL-CLASS-ENC-UN;
    }

    container confclass-p {
      description "confclass p";
      uses CLASS-MAP-BG;
    }

    container excdclass-encode {
      description "excdclass encode";
      uses POL-CLASS-ENC-UN;
    }

    container excdclass-p {
      description "excdclass p";
      uses CLASS-MAP-BG;
    }
    leaf flags {
      xr:xr-xml-map "policymgr:flags";
      type uint32;
      description "flags";
    }
    leaf police-flags {
      xr:xr-xml-map "policymgr:police_flags";
      type uint32;
      description "police flags";
    }
    leaf sbuck-name {
      xr:xr-xml-map "policymgr:sbuck_name";
      type Shared-bucket-name;
      description "sbuck name";
    }
    leaf sbuck-type {
      xr:xr-xml-map "policymgr:sbuck_type";
      type Shared-bucket;
      description "sbuck type";
    }
  }

  grouping ACTION-SERVICE-FUNCTION-PATH-ST {
    description "service function path";
    leaf path-id {
      xr:xr-xml-map "policymgr:path_id";
      type uint32;
      description "service path id";
    }
    leaf service-index {
      xr:xr-xml-map "policymgr:service_index";
      type uint8;
      description "service path index";
    }
    leaf meta-name {
      xr:xr-xml-map "policymgr:meta_name";
      type string;
      description "metadata name";
    }
    leaf vs-index {
      xr:xr-xml-map "policymgr:vs_index";
      type uint32;
      description "vservice index";
    }
  }

  grouping ACTION-OUTPUT-INTERFACE-INFO-ST {
    description "output_interface action";
    leaf out-ifname {
      xr:xr-xml-map "policymgr:out_ifname";
      type string;
      description "output interface name";
    }
  }

  grouping ACTION-REDIRECT-INFO-ST {
    description "redirect action";
    leaf value {
      xr:xr-xml-map "policymgr:value";
      type uint32;
      description "value";
    }
    leaf type {
      xr:xr-xml-map "policymgr:type";
      type Redirect;
      description "type";
    }
  }

  grouping ACTION-SFRAG-INFO-ST {
    description "service fragment action";
    leaf name {
      xr:xr-xml-map "policymgr:name";
      type string;
      description "Service Fragment Name";
    }
  }

  grouping ACTION-COPY-INFO-ST {
    description "copy action";
    leaf num-byte {
      xr:xr-xml-map "policymgr:num_byte";
      type uint32;
      units "byte";
      description "number of bytes";
    }
    leaf sn-type {
      xr:xr-xml-map "policymgr:sn_type";
      type Dpss-snid;
      description "service node ID type";
    }
    leaf sn-index {
      xr:xr-xml-map "policymgr:sn_index";
      type uint32;
      description "service node index";
    }
    leaf sn-name {
      xr:xr-xml-map "policymgr:sn_name";
      type string;
      description "service node url";
    }
    leaf app-id {
      xr:xr-xml-map "policymgr:app_id";
      type uint32;
      description "application ID";
    }
    leaf local-id {
      xr:xr-xml-map "policymgr:local_id";
      type uint32;
      description "local ID";
    }
    leaf vsnode-type {
      xr:xr-xml-map "policymgr:vsnode_type";
      type Vsvc-service;
      description "vservice node type";
    }
  }

  grouping ACTION-PUNT-INFO-ST {
    description "punt action";
    leaf sn-type {
      xr:xr-xml-map "policymgr:sn_type";
      type Dpss-snid;
      description "service node ID type";
    }
    leaf sn-index {
      xr:xr-xml-map "policymgr:sn_index";
      type uint32;
      description "service node index";
    }
    leaf sn-name {
      xr:xr-xml-map "policymgr:sn_name";
      type string;
      description "service node name";
    }
    leaf app-id {
      xr:xr-xml-map "policymgr:app_id";
      type uint32;
      description "application ID";
    }
    leaf local-id {
      xr:xr-xml-map "policymgr:local_id";
      type uint32;
      description "local ID";
    }
    leaf vsnode-type {
      xr:xr-xml-map "policymgr:vsnode_type";
      type Vsvc-service;
      description "vservice node type";
    }
  }

  grouping ACTION-HTTPR-INFO-ST {
    description "httpr action";
    leaf redirect-url {
      xr:xr-xml-map "policymgr:redirect_url";
      type string;
      description "redirect url";
    }
  }

  grouping ACTION-AFMON-REACT-ST {
    description "AFMon React Configuration";
    leaf oper-id {
      xr:xr-xml-map "policymgr:oper_id";
      type uint32;
      description "React Operation ID";
    }
    leaf description {
      xr:xr-xml-map "policymgr:description";
      type String1;
      description "Describing the oper";
    }
    leaf trig-num-intvls {
      xr:xr-xml-map "policymgr:trig_num_intvls";
      type uint32;
      description "Averaged over N intvls";
    }
    leaf clone-ifh {
      xr:xr-xml-map "policymgr:clone_ifh";
      type uint32;
      description "Clone interface handle";
    }
    leaf notif-actns {
      xr:xr-xml-map "policymgr:notif_actns";
      type uint8;
      description "Bitmap of actions on alert";
    }
    leaf criterion {
      xr:xr-xml-map "policymgr:criterion";
      type uint8;
      description "React Criterion";
    }
    leaf trig-type {
      xr:xr-xml-map "policymgr:trig_type";
      type uint8;
      description "Immediate or averaged thresh trigger";
    }
    leaf trig-relop {
      xr:xr-xml-map "policymgr:trig_relop";
      type uint8;
      description "Trigger LT|LE|GT|GE|Range";
    }
    leaf trig-level-1 {
      xr:xr-xml-map "policymgr:trig_level_1";
      type String1;
      description "Trigger threshold 1/lower";
    }
    leaf trig-level-2 {
      xr:xr-xml-map "policymgr:trig_level_2";
      type String1;
      description "Trigger upper threshold for range";
    }
    leaf alm-grp-thresh {
      xr:xr-xml-map "policymgr:alm_grp_thresh";
      type uint16;
      units "percentage";
      description "Num/percent in grp";
    }
    leaf alm-type {
      xr:xr-xml-map "policymgr:alm_type";
      type uint8;
      description "Discrete | grouped alarm";
    }
    leaf alm-severity {
      xr:xr-xml-map "policymgr:alm_severity";
      type uint8;
      description "Major|Minor|... alarm";
    }
  }

  grouping ACTION-AFMON-REACT-INFO {
    description "ACTION AFMON REACT INFO";

    list action-afmon-react-info {
      description "action afmon react info";
      uses ACTION-AFMON-REACT-ST;
    }
  }

  grouping ACTION-AUTHORIZE-ID-ST {
    description "authorize identifiers";
    leaf id {
      xr:xr-xml-map "policymgr:id";
      type uint8;
      description "id";
    }
    leaf aaa-list-name {
      xr:xr-xml-map "policymgr:aaa_list_name";
      type string;
      description "aaa list name";
    }
    leaf format-name {
      xr:xr-xml-map "policymgr:format_name";
      type string;
      description "format name";
    }
    leaf password {
      xr:xr-xml-map "policymgr:password";
      type string;
      description "password";
    }
  }

  grouping ACTION-ACCOUNTING-EVENT-ST {
    description "ACTION ACCOUNTING EVENT ST";
    leaf action {
      xr:xr-xml-map "policymgr:action";
      type Acct;
      description "action";
    }
    leaf aaa-list-name {
      xr:xr-xml-map "policymgr:aaa_list_name";
      type string;
      description "aaa list name";
    }
  }

  grouping ACTION-QLIMIT-INFO-ST {
    description "Queue Limit structure";

    container qlim {
      description "qlim";
      uses POLICY-PARAM-UINT32-ST;
    }

    container atmclp-qlim {
      description "atmclp qlim";
      uses POLICY-PARAM-UINT32-ST;
    }

    container match-values {
      description "match values";
      uses UINT8-RNG-ARRAY;
    }
    leaf type {
      xr:xr-xml-map "policymgr:type";
      type Qlimit;
      description "type";
    }
    leaf qlimit-flags {
      xr:xr-xml-map "policymgr:qlimit_flags";
      type uint32;
      description "qlimit flags";
    }
  }

  grouping ACTION-QLIMIT-INFO-ARRAY {
    description "ACTION QLIMIT INFO ARRAY";

    list action-qlimit-info-array {
      description "action qlimit info array";
      uses ACTION-QLIMIT-INFO-ST;
    }
  }

  grouping ACTION-TEMPLATE-ST {
    description "ACTION TEMPLATE ST";
    leaf template-name {
      xr:xr-xml-map "policymgr:template_name";
      type string;
      description "template name";
    }
    leaf aaa-list-name {
      xr:xr-xml-map "policymgr:aaa_list_name";
      type string;
      description "aaa list name";
    }
    leaf flags {
      xr:xr-xml-map "policymgr:flags";
      type uint32;
      description "flags";
    }
  }

  grouping ACTION-PROXY-AAA-ST {
    description "ACTION PROXY AAA ST";
    leaf aaa-list-name {
      xr:xr-xml-map "policymgr:aaa_list_name";
      type string;
      description "aaa list name";
    }
  }

  grouping ACTION-TIMEOUT-IDLE-ST {
    description "ACTION TIMEOUT IDLE ST";
    leaf secs {
      xr:xr-xml-map "policymgr:secs";
      type uint32;
      description "secs";
    }
  }

  grouping ACTION-PREPAID-CFG-ST {
    description "ACTION PREPAID CFG ST";
    leaf prepaid-config-profile-name {
      xr:xr-xml-map "policymgr:prepaid_config_profile_name";
      type string;
      description "prepaid config profile name";
    }
  }

  grouping ACTION-QUERY-ANCP-SESSION-ST {
    description "ACTION QUERY ANCP SESSION ST";
    leaf enable {
      xr:xr-xml-map "policymgr:enable";
      type uint8;
      description "enable";
    }
  }

  grouping ACTION-ACCT-AAA-LIST-ST {
    description "ACTION ACCT AAA LIST ST";
    leaf aaa-list-name {
      xr:xr-xml-map "policymgr:aaa_list_name";
      type string;
      description "aaa list name";
    }
    leaf secs {
      xr:xr-xml-map "policymgr:secs";
      type uint32;
      description "secs";
    }
  }

  grouping ACTION-STOP-TIMER-ST {
    description "ACTION STOP TIMER ST";
    leaf timer-name {
      xr:xr-xml-map "policymgr:timer_name";
      type string;
      description "timer name";
    }
  }

  grouping ACTION-SET-TIMER-ST {
    description "ACTION SET TIMER ST";
    leaf timer-name {
      xr:xr-xml-map "policymgr:timer_name";
      type string;
      description "timer name";
    }
    leaf duration {
      xr:xr-xml-map "policymgr:duration";
      type uint32;
      description "duration";
    }
    leaf absolute-time {
      xr:xr-xml-map "policymgr:absolute_time";
      type string;
      description "absolute time";
    }
  }

  grouping ACTION-DECODE-IDENTIFIER-ST {
    description "ACTION DECODE IDENTIFIER ST";
    leaf id {
      xr:xr-xml-map "policymgr:id";
      type Decode-identifier;
      description "id";
    }
    leaf format-name {
      xr:xr-xml-map "policymgr:format_name";
      type string;
      description "format name";
    }
  }

  grouping ACTION-COLLECT-ID-ST {
    description "Collect identifiers";
    leaf id {
      xr:xr-xml-map "policymgr:id";
      type Identifier;
      description "id";
    }
    leaf aaa-list-name {
      xr:xr-xml-map "policymgr:aaa_list_name";
      type string;
      description "aaa list name";
    }
  }

  grouping ACTION-AUTHEN-AAA-ST {
    description "Authenticate AAA list info";
    leaf aaa-list-name {
      xr:xr-xml-map "policymgr:aaa_list_name";
      type string;
      description "aaa list name";
    }
    leaf authen-password {
      xr:xr-xml-map "policymgr:authen_password";
      type string;
      description "authen password";
    }
  }

  grouping ACTION-MINBW-INFO-ST {
    description "Min BW action";

    container bw {
      description "bw";
      uses POLICY-PARAM-UINT32-ST;
    }
  }

  grouping ACTION-BWREM-INFO-ST {
    description "BW remaining action";

    container bwrem {
      description "bwrem";
      uses POLICY-PARAM-UINT32-ST;
    }
  }

  grouping ACTION-PRIO-INFO-ST {
    description "Priority action";
    leaf prio-lvl {
      xr:xr-xml-map "policymgr:prio_lvl";
      type uint32;
      description "prio lvl";
    }
  }

  grouping ACTION-ENCAP-INFO-ST {
    description "Encapsulation sequence action";
    leaf seq {
      xr:xr-xml-map "policymgr:seq";
      type uint8;
      description "seq";
    }
  }

  grouping ACTION-WRED-INFO-ST {
    description "WRED parameters info structure";

    container match-ranges {
      description "match ranges";
      uses UINT8-RNG-ARRAY;
    }

    container min-threshold {
      description "min threshold";
      uses POLICY-PARAM-UINT32-ST;
    }

    container max-threshold {
      description "max threshold";
      uses POLICY-PARAM-UINT32-ST;
    }
    leaf type {
      xr:xr-xml-map "policymgr:type";
      type Wred;
      description "cos/prec/dscp/ based WRED";
    }
    leaf wred-flags {
      xr:xr-xml-map "policymgr:wred_flags";
      type uint32;
      description "wred flags";
    }
    leaf probability {
      xr:xr-xml-map "policymgr:probability";
      type uint32;
      description "probability";
    }
  }

  grouping ACTION-WRED-INFO {
    description "ACTION WRED INFO";

    list action-wred-info {
      description "action wred info";
      uses ACTION-WRED-INFO-ST;
    }
  }

  grouping ACTION-MARK2-INFO-ST {
    description "Mark action";
    leaf value {
      xr:xr-xml-map "policymgr:value";
      type uint32;
      description "value";
    }
    leaf value-overflow {
      xr:xr-xml-map "policymgr:value_overflow";
      type uint16;
      description "value overflow";
    }
    leaf type {
      xr:xr-xml-map "policymgr:type";
      type Mark1;
      description "type";
    }
    leaf mark-flags {
      xr:xr-xml-map "policymgr:mark_flags";
      type uint8;
      description "mark flags";
    }
  }

  grouping ACTION-MARK2-INFO {
    description "ACTION MARK2 INFO";

    list action-mark2-info {
      description "action mark2 info";
      uses ACTION-MARK2-INFO-ST;
    }
  }

  grouping ACTION-MARK-INFO-ST {
    description "Mark action";
    leaf type {
      xr:xr-xml-map "policymgr:type";
      type Mark;
      description "type";
    }
    leaf mark-flags {
      xr:xr-xml-map "policymgr:mark_flags";
      type uint32;
      description "mark flags";
    }
    leaf value {
      xr:xr-xml-map "policymgr:value";
      type uint16;
      description "value";
    }
  }

  grouping ACTION-MARK-INFO {
    description "ACTION MARK INFO";

    list action-mark-info {
      description "action mark info";
      uses ACTION-MARK-INFO-ST;
    }
  }

  grouping POLICY-ACTION-DATAP-UN {
    description "Pointers to the action data of different type";

    container mark {
      when "../type = 'policy-action-mark'" {
        description "../type = 'POLICY_ACTION_MARK'";
      }
      description "mark";
      uses ACTION-MARK-INFO;
    }

    container mark2 {
      when "../type = 'policy-action-mark2'" {
        description "../type = 'POLICY_ACTION_MARK2'";
      }
      description "mark2";
      uses ACTION-MARK2-INFO;
    }

    container wred {
      when "../type = 'policy-action-wred'" {
        description "../type = 'POLICY_ACTION_WRED'";
      }
      description "wred";
      uses ACTION-WRED-INFO;
    }

    container encap {
      when "../type = 'policy-action-encap-seq'" {
        description "../type = 'POLICY_ACTION_ENCAP_SEQ'";
      }
      description "encap";
      uses ACTION-ENCAP-INFO-ST;
    }

    container prio {
      when "../type = 'policy-action-priority'" {
        description "../type = 'POLICY_ACTION_PRIORITY'";
      }
      description "prio";
      uses ACTION-PRIO-INFO-ST;
    }

    container bwrem {
      when "../type = 'policy-action-bw-remaining'" {
        description "../type = 'POLICY_ACTION_BW_REMAINING'";
      }
      description "bwrem";
      uses ACTION-BWREM-INFO-ST;
    }

    container min-bw {
      when "../type = 'policy-action-min-bw'" {
        description "../type = 'POLICY_ACTION_MIN_BW'";
      }
      description "min bw";
      uses ACTION-MINBW-INFO-ST;
    }

    container authen-aaa {
      when "../type = 'policy-action-authenticate-aaa'" {
        description "../type = 'POLICY_ACTION_AUTHENTICATE_AAA'";
      }
      description "authen aaa";
      uses ACTION-AUTHEN-AAA-ST;
    }

    container collect-id {
      when "../type = 'policy-action-collect-id'" {
        description "../type = 'POLICY_ACTION_COLLECT_ID'";
      }
      description "collect id";
      uses ACTION-COLLECT-ID-ST;
    }

    container decode-id {
      when "../type = 'policy-action-decode-identifier'" {
        description "../type = 'POLICY_ACTION_DECODE_IDENTIFIER'";
      }
      description "decode id";
      uses ACTION-DECODE-IDENTIFIER-ST;
    }

    container set-timer {
      when "../type = 'policy-action-set-timer'" {
        description "../type = 'POLICY_ACTION_SET_TIMER'";
      }
      description "set timer";
      uses ACTION-SET-TIMER-ST;
    }

    container stop-timer {
      when "../type = 'policy-action-stop-timer'" {
        description "../type = 'POLICY_ACTION_STOP_TIMER'";
      }
      description "stop timer";
      uses ACTION-STOP-TIMER-ST;
    }

    container acct-aaa-list {
      when "../type = 'policy-action-accounting-aaa-list'" {
        description "../type = 'POLICY_ACTION_ACCOUNTING_AAA_LIST'";
      }
      description "acct aaa list";
      uses ACTION-ACCT-AAA-LIST-ST;
    }

    container query-ancp {
      when "../type = 'policy-action-query-ancp'" {
        description "../type = 'POLICY_ACTION_QUERY_ANCP'";
      }
      description "query ancp";
      uses ACTION-QUERY-ANCP-SESSION-ST;
    }

    container prepaid-cfg {
      when "../type = 'policy-action-prepaid-config'" {
        description "../type = 'POLICY_ACTION_PREPAID_CONFIG'";
      }
      description "prepaid cfg";
      uses ACTION-PREPAID-CFG-ST;
    }

    container timeout-idle {
      when "../type = 'policy-action-timeout-idle'" {
        description "../type = 'POLICY_ACTION_TIMEOUT_IDLE'";
      }
      description "timeout idle";
      uses ACTION-TIMEOUT-IDLE-ST;
    }

    container proxy-aaa {
      when "../type = 'policy-action-proxy-aaa'" {
        description "../type = 'POLICY_ACTION_PROXY_AAA'";
      }
      description "proxy aaa";
      uses ACTION-PROXY-AAA-ST;
    }

    container act-template {
      when "../type = 'policy-action-template-activate'" {
        description "../type = 'POLICY_ACTION_TEMPLATE_ACTIVATE'";
      }
      description "act template";
      uses ACTION-TEMPLATE-ST;
    }

    container deact-template {
      when "../type = 'policy-action-template-deactivate'" {
        description "../type = 'POLICY_ACTION_TEMPLATE_DEACTIVATE'";
      }
      description "deact template";
      uses ACTION-TEMPLATE-ST;
    }

    container qlimit {
      when "../type = 'policy-action-q-limit'" {
        description "../type = 'POLICY_ACTION_Q_LIMIT'";
      }
      description "qlimit";
      uses ACTION-QLIMIT-INFO-ARRAY;
    }

    container accounting-event-aaa {
      when "../type = 'policy-action-accounting-event-aaa-list'" {
        description
          "../type =
          'POLICY_ACTION_ACCOUNTING_EVENT_AAA_LIST'";
      }
      description "accounting event aaa";
      uses ACTION-ACCOUNTING-EVENT-ST;
    }

    container authorize-id {
      when "../type = 'policy-action-authorize-id'" {
        description "../type = 'POLICY_ACTION_AUTHORIZE_ID'";
      }
      description "authorize id";
      uses ACTION-AUTHORIZE-ID-ST;
    }

    container afm-react {
      when "../type = 'policy-action-afmon-react'" {
        description "../type = 'POLICY_ACTION_AFMON_REACT'";
      }
      description "afm react";
      uses ACTION-AFMON-REACT-INFO;
    }

    container httpr {
      when "../type = 'policy-action-httpr'" {
        description "../type = 'POLICY_ACTION_HTTPR'";
      }
      description "httpr";
      uses ACTION-HTTPR-INFO-ST;
    }

    container punt {
      when "../type = 'policy-action-punt'" {
        description "../type = 'POLICY_ACTION_PUNT'";
      }
      description "punt";
      uses ACTION-PUNT-INFO-ST;
    }

    container copy {
      when "../type = 'policy-action-copy'" {
        description "../type = 'POLICY_ACTION_COPY'";
      }
      description "copy";
      uses ACTION-COPY-INFO-ST;
    }

    container sfrag {
      when "../type = 'policy-action-sfrag'" {
        description "../type = 'POLICY_ACTION_SFRAG'";
      }
      description "sfrag";
      uses ACTION-SFRAG-INFO-ST;
    }

    container redirect {
      when "../type = 'policy-action-redirect'" {
        description "../type = 'POLICY_ACTION_REDIRECT'";
      }
      description "redirect";
      uses ACTION-REDIRECT-INFO-ST;
    }

    container out-intf {
      when "../type = 'policy-action-output-interface'" {
        description "../type = 'POLICY_ACTION_OUTPUT_INTERFACE'";
      }
      description "out intf";
      uses ACTION-OUTPUT-INTERFACE-INFO-ST;
    }

    container serv-func {
      when "../type = 'policy-action-service-function-path'" {
        description
          "../type = 'POLICY_ACTION_SERVICE_FUNCTION_PATH'";
      }
      description "serv func";
      uses ACTION-SERVICE-FUNCTION-PATH-ST;
    }

    container police {
      when "../type = 'policy-action-police'" {
        description "../type = 'POLICY_ACTION_POLICE'";
      }
      description "police";
      uses ACTION-POLICE-INFO-ST;
    }

    container shape {
      when "../type = 'policy-action-shape'" {
        description "../type = 'POLICY_ACTION_SHAPE'";
      }
      description "shape";
      uses ACTION-SHAPE-INFO-ST;
    }

    container child-policy {
      when "../type = 'policy-action-serv-pol'" {
        description "../type = 'POLICY_ACTION_SERV_POL'";
      }
      description "child policy";
      uses CHLD-POL-ENC-UN;
    }

    container cac {
      when "../type = 'policy-action-cac'" {
        description "../type = 'POLICY_ACTION_CAC'";
      }
      description "cac";
      uses ACTION-CAC-INFO-ST;
    }

    container pfc {
      when "../type = 'policy-action-pfc'" {
        description "../type = 'POLICY_ACTION_PFC'";
      }
      description "pfc";
      uses ACTION-PFC-INFO-ST;
    }

    container flow-parm {
      when "../type = 'policy-action-afmon-flow-parm'" {
        description "../type = 'POLICY_ACTION_AFMON_FLOW_PARM'";
      }
      description "flow parm";
      uses ACTION-AFMON-FLOW-PARM-INFO-ST;
    }

    container ipcbr {
      when "../type = 'policy-action-afmon-ipcbr-metric'" {
        description "../type = 'POLICY_ACTION_AFMON_IPCBR_METRIC'";
      }
      description "ipcbr";
      uses ACTION-AFMON-IPCBR-INFO-ST;
    }

    container rtp {
      when "../type = 'policy-action-afmon-rtp-metric'" {
        description "../type = 'POLICY_ACTION_AFMON_RTP_METRIC'";
      }
      description "rtp";
      uses ACTION-AFMON-RTP-INFO-ST;
    }

    container rtp-mmr {
      when "../type = 'policy-action-afmon-rtp-mmr-metric'" {
        description
          "../type = 'POLICY_ACTION_AFMON_RTP_MMR_METRIC'";
      }
      description "rtp mmr";
      uses ACTION-AFMON-RTP-INFO-ST;
    }

    container rtp-j2k {
      when "../type = 'policy-action-afmon-rtp-j2k-metric'" {
        description
          "../type = 'POLICY_ACTION_AFMON_RTP_J2K_METRIC'";
      }
      description "rtp j2k";
      uses ACTION-AFMON-RTP-INFO-ST;
    }

    container rtp-voice {
      when "../type = 'policy-action-afmon-rtp-voice-metric'" {
        description
          "../type =
          'POLICY_ACTION_AFMON_RTP_VOICE_METRIC'";
      }
      description "rtp voice";
      uses ACTION-AFMON-RTP-INFO-ST;
    }

    container mdi {
      when "../type = 'policy-action-afmon-mdi-metric'" {
        description "../type = 'POLICY_ACTION_AFMON_MDI_METRIC'";
      }
      description "mdi";
      uses ACTION-AFMON-MDI-INFO-ST;
    }

    container mdi-rtp {
      when "../type = 'policy-action-afmon-mdi-rtp-metric'" {
        description
          "../type = 'POLICY_ACTION_AFMON_MDI_RTP_METRIC'";
      }
      description "mdi rtp";
      uses ACTION-AFMON-MDI-INFO-ST;
    }

    container fmm {
      when "../type = 'policy-action-afmon-fmm'" {
        description "../type = 'POLICY_ACTION_AFMON_FMM'";
      }
      description "fmm";
      uses ACTION-AFMON-FMM-INFO-ST;
    }

    container pbf {
      when "../type = 'policy-action-pbr-next-hop'" {
        description "../type = 'POLICY_ACTION_PBR_NEXTHOP'";
      }
      description "pbf";
      uses ACTION-PBF-INFO-ARRAY;
    }

    container ipv4-nh {
      when "../type = 'policy-action-ipv4-nh'" {
        description "../type = 'POLICY_ACTION_IPV4_NH'";
      }
      description "ipv4 nh";
      uses ACTION-IPV4-NH-INFO-ARRAY;
    }

    container ipv6-nh {
      when "../type = 'policy-action-ipv6-nh'" {
        description "../type = 'POLICY_ACTION_IPV6_NH'";
      }
      description "ipv6 nh";
      uses ACTION-IPV6-NH-INFO-ARRAY;
    }
    leaf type {
      xr:xr-xml-map "policymgr:type";
      type Policy-action;
      description "type";
    }
    leaf data-p {
      xr:xr-xml-map "policymgr:data_p";
      when "../type != 'policy-action-mark' and ../type !="+
        " 'policy-action-mark2' and ../type !="+
        " 'policy-action-wred' and ../type !="+
        " 'policy-action-encap-seq' and ../type !="+
        " 'policy-action-priority' and ../type !="+
        " 'policy-action-bw-remaining' and ../type !="+
        " 'policy-action-min-bw' and ../type !="+
        " 'policy-action-authenticate-aaa' and ../type !="+
        " 'policy-action-collect-id' and ../type !="+
        " 'policy-action-decode-identifier' and ../type !="+
        " 'policy-action-set-timer' and ../type !="+
        " 'policy-action-stop-timer' and ../type !="+
        " 'policy-action-accounting-aaa-list' and ../type !="+
        " 'policy-action-query-ancp' and ../type !="+
        " 'policy-action-prepaid-config' and ../type !="+
        " 'policy-action-timeout-idle' and ../type !="+
        " 'policy-action-proxy-aaa' and ../type !="+
        " 'policy-action-template-activate' and ../type !="+
        " 'policy-action-template-deactivate' and ../type !="+
        " 'policy-action-q-limit' and ../type !="+
        " 'policy-action-accounting-event-aaa-list' and ../type !="+
        " 'policy-action-authorize-id' and ../type !="+
        " 'policy-action-afmon-react' and ../type !="+
        " 'policy-action-httpr' and ../type !="+
        " 'policy-action-punt' and ../type != 'policy-action-copy'"+
        " and ../type != 'policy-action-sfrag' and ../type !="+
        " 'policy-action-redirect' and ../type !="+
        " 'policy-action-output-interface' and ../type !="+
        " 'policy-action-service-function-path' and ../type !="+
        " 'policy-action-police' and ../type !="+
        " 'policy-action-shape' and ../type !="+
        " 'policy-action-serv-pol' and ../type !="+
        " 'policy-action-cac' and ../type != 'policy-action-pfc'"+
        " and ../type != 'policy-action-afmon-flow-parm' and"+
        " ../type != 'policy-action-afmon-ipcbr-metric' and"+
        " ../type != 'policy-action-afmon-rtp-metric' and ../type"+
        " != 'policy-action-afmon-rtp-mmr-metric' and ../type !="+
        " 'policy-action-afmon-rtp-j2k-metric' and ../type !="+
        " 'policy-action-afmon-rtp-voice-metric' and ../type !="+
        " 'policy-action-afmon-mdi-metric' and ../type !="+
        " 'policy-action-afmon-mdi-rtp-metric' and ../type !="+
        " 'policy-action-afmon-fmm' and ../type !="+
        " 'policy-action-pbr-next-hop' and ../type !="+
        " 'policy-action-ipv4-nh' and ../type !="+
        " 'policy-action-ipv6-nh'" {
          description
            "../type != 'POLICY_ACTION_MARK' and ../type !=
            'POLICY_ACTION_MARK2' and ../type !=
            'POLICY_ACTION_WRED' and ../type !=
            'POLICY_ACTION_ENCAP_SEQ' and ../type !=
            'POLICY_ACTION_PRIORITY' and ../type !=
            'POLICY_ACTION_BW_REMAINING' and ../type !=
            'POLICY_ACTION_MIN_BW' and ../type !=
            'POLICY_ACTION_AUTHENTICATE_AAA' and ../type 
            != 'POLICY_ACTION_COLLECT_ID' and ../type !=
            'POLICY_ACTION_DECODE_IDENTIFIER' and ../type 
            != 'POLICY_ACTION_SET_TIMER' and ../type !=
            'POLICY_ACTION_STOP_TIMER' and ../type !=
            'POLICY_ACTION_ACCOUNTING_AAA_LIST' and .
            ./type != 'POLICY_ACTION_QUERY_ANCP' and .
            ./type != 'POLICY_ACTION_PREPAID_CONFIG' and .
            ./type != 'POLICY_ACTION_TIMEOUT_IDLE' and .
            ./type != 'POLICY_ACTION_PROXY_AAA' and .
            ./type != 'POLICY_ACTION_TEMPLATE_ACTIVATE'
            and ../type !=
            'POLICY_ACTION_TEMPLATE_DEACTIVATE' and .
            ./type != 'POLICY_ACTION_Q_LIMIT' and ../type 
            != 'POLICY_ACTION_ACCOUNTING_EVENT_AAA_LIST'
            and ../type != 'POLICY_ACTION_AUTHORIZE_ID'
            and ../type != 'POLICY_ACTION_AFMON_REACT' and
            ../type != 'POLICY_ACTION_HTTPR' and ../type 
            != 'POLICY_ACTION_PUNT' and ../type !=
            'POLICY_ACTION_COPY' and ../type !=
            'POLICY_ACTION_SFRAG' and ../type !=
            'POLICY_ACTION_REDIRECT' and ../type !=
            'POLICY_ACTION_OUTPUT_INTERFACE' and ../type 
            != 'POLICY_ACTION_SERVICE_FUNCTION_PATH' and .
            ./type != 'POLICY_ACTION_POLICE' and ../type 
            != 'POLICY_ACTION_SHAPE' and ../type !=
            'POLICY_ACTION_SERV_POL' and ../type !=
            'POLICY_ACTION_CAC' and ../type !=
            'POLICY_ACTION_PFC' and ../type !=
            'POLICY_ACTION_AFMON_FLOW_PARM' and ../type !=
            'POLICY_ACTION_AFMON_IPCBR_METRIC' and ../type
            != 'POLICY_ACTION_AFMON_RTP_METRIC' and .
            ./type != 'POLICY_ACTION_AFMON_RTP_MMR_METRIC'
            and ../type !=
            'POLICY_ACTION_AFMON_RTP_J2K_METRIC' and .
            ./type !=
            'POLICY_ACTION_AFMON_RTP_VOICE_METRIC' and .
            ./type != 'POLICY_ACTION_AFMON_MDI_METRIC' and
            ../type !=
            'POLICY_ACTION_AFMON_MDI_RTP_METRIC' and .
            ./type != 'POLICY_ACTION_AFMON_FMM' and .
            ./type != 'POLICY_ACTION_PBR_NEXTHOP' and .
            ./type != 'POLICY_ACTION_IPV4_NH' and ../type 
            != 'POLICY_ACTION_IPV6_NH'";
      }
      type uint32;
      description "data p";
    }
  }

  grouping POLICY-ACTION-INFO-ST {
    description "Per class action structure";

    list policy-action-info-st {
      description "policy action info st";

      container actp {
        description "actp";
        uses POLICY-ACTION-DATAP-UN;
      }
      leaf seq {
        type uint16;
        description "seq";
      }
      leaf flags {
        type uint16;
        description "flags";
      }
    }
  }

  grouping CLASS-MAP-BG {
    description "Class-map bag";

    list class-map-bg {
      description "class map bg";

      container match-infop {
        description "Pointer to the first Match info";
        uses CLASS-MATCH-INFO-ST;
      }
      leaf magic {
        type uint32;
        description "Magic number on top of class-map bag";
      }
      leaf name {
        type Class-map-name;
        description "Name of the class-map";
      }
      leaf type {
        type Class-map;
        description "Class-Map Type QoS/PBR/Netflow/...";
      }
      leaf mode {
        type Class-map-mode;
        description "Class-Map Mode Match any/Match all";
      }
      leaf flags {
        type uint32;
        description "Class-Map Internal";
      }
      leaf match-count {
        type uint32;
        description "Number of Match infos";
      }
      leaf chk-sum {
        type Policy-chk-sum;
        description "MD5 checksum of the encoded class-map bag";
      }
      leaf description {
        type String1;
        description "description";
      }
    }
  }

  grouping FLOW-KEY-ARRAY {
    description "FLOW KEY ARRAY";
    leaf keys {
      xr:xr-xml-map "policymgr:keys";
      type yang:hex-string;
      description "keys";
    }
    leaf num {
      xr:xr-xml-map "policymgr:num";
      type uint8;
      description "num";
    }
  }

  grouping FLOW-KEY-ST {
    description "FLOW KEY ST";

    container flow-keys {
      description "flow keys";
      uses FLOW-KEY-ARRAY;
    }
    leaf max-count {
      xr:xr-xml-map "policymgr:max_count";
      type uint16;
      description "Maximum count of flows";
    }
    leaf idle-timeout {
      xr:xr-xml-map "policymgr:idle_timeout";
      type uint16;
      units "second";
      description "Idle timeout of flows (in seconds)";
    }
  }

  grouping UINT64-ARRAY {
    description "UINT64 ARRAY";
    leaf-list uint64_array {
      xr:xr-xml-map "policymgr:uint64_array";
      type uint64;
      description "uint64 array";
    }
  }

  grouping MAC-ADDR-ARRAY {
    description "MAC ADDR ARRAY";

    list mac-addr-array {
      description "mac addr array";
      uses MAC-ADDR-ST;
    }
  }

  grouping MATCH-IPV6-ST {
    description "MATCH IPV6 ST";
    leaf prefix {
      xr:xr-xml-map "policymgr:prefix";
      type inet:ipv6-address;
      description "IPV6 prefix";
    }
    leaf mask {
      xr:xr-xml-map "policymgr:mask";
      type uint32;
      description "IPV6 mask";
    }
  }

  grouping IPV6-ADDR-ARRAY {
    description "IPV6 ADDR ARRAY";

    list ipv6-addr-array {
      description "ipv6 addr array";
      uses MATCH-IPV6-ST;
    }
  }

  grouping MATCH-IPV4-ST {
    description "Source Address IPv4";
    leaf prefix {
      xr:xr-xml-map "policymgr:prefix";
      type inet:ipv4-address;
      description "prefix";
    }
    leaf mask {
      xr:xr-xml-map "policymgr:mask";
      type inet:ipv4-address;
      description "mask";
    }
  }

  grouping IPV4-ADDR-ARRAY {
    description "IPV4 ADDR ARRAY";

    list ipv4-addr-array {
      description "ipv4 addr array";
      uses MATCH-IPV4-ST;
    }
  }

  grouping MATCH-NAS-PORT-ST {
    description "NAS Port";
    leaf sub-id {
      xr:xr-xml-map "policymgr:sub_id";
      type Match-nas-port-sub-id;
      description "sub id";
    }
    leaf operator {
      xr:xr-xml-map "policymgr:operator";
      type Match-logical-operator;
      description "operator";
    }
    leaf value {
      xr:xr-xml-map "policymgr:value";
      type uint32;
      description "value";
    }
  }

  grouping NAS-PORT-ARRAY {
    description "NAS PORT ARRAY";

    list nas-port-array {
      description "nas port array";
      uses MATCH-NAS-PORT-ST;
    }
  }

  grouping MATCH-DOMAIN-ST {
    description "Domain Format";
    leaf domain-name {
      xr:xr-xml-map "policymgr:domain_name";
      type String1;
      description "domain name";
    }
    leaf format-name {
      xr:xr-xml-map "policymgr:format_name";
      type String1;
      description "format name";
    }
  }

  grouping DOMAIN-ARRAY {
    description "DOMAIN ARRAY";

    list domain-array {
      description "domain array";
      uses MATCH-DOMAIN-ST;
    }
  }

  grouping MAC-ADDR-ST {
    description "MAC ADDR ST";
    leaf-list mac-addr {
      xr:xr-xml-map "policymgr:mac_addr";
      type uint16;
      max-elements "3";
      description "MAC address";
    }
    leaf-list mask {
      xr:xr-xml-map "policymgr:mask";
      type uint16;
      max-elements "3";
      description "MAC mask";
    }
  }

  grouping VLAN-ID-ST {
    description "VLAN ID ST";
    leaf min {
      xr:xr-xml-map "policymgr:min";
      type uint16;
      description "Lower limit of the range";
    }
    leaf max {
      xr:xr-xml-map "policymgr:max";
      type uint16;
      description "Upper limit of the range";
    }
    leaf mask {
      xr:xr-xml-map "policymgr:mask";
      type uint16;
      description "VLAN mask";
    }
  }

  grouping VLAN-ID-ARRAY {
    description "VLAN ID ARRAY";

    list vlan-id-array {
      description "vlan id array";
      uses VLAN-ID-ST;
    }
  }

  grouping DEI-BIT-ST {
    description "DEI BIT ST";
    leaf bit-value {
      xr:xr-xml-map "policymgr:bit_value";
      type uint32;
      description "Value of the DEI bit";
    }
  }

  grouping UINT32-RNG-ST {
    description "UINT32 RNG ST";
    leaf min {
      xr:xr-xml-map "policymgr:min";
      type uint32;
      description "Lower limit of the range";
    }
    leaf max {
      xr:xr-xml-map "policymgr:max";
      type uint32;
      description "Upper limit of the range";
    }
  }

  grouping UINT32-RNG-ARRAY {
    description "UINT32 RNG ARRAY";

    list uint32_rng_array {
      description "uint32 rng array";
      uses UINT32-RNG-ST;
    }
  }

  grouping STRING-ARRAY {
    description "STRING ARRAY";
    leaf-list string-array {
      xr:xr-xml-map "policymgr:string_array";
      type String1;
      description "string array";
    }
  }

  grouping TCP-FLAG-ST {
    description "TCP FLAG ST";
    leaf value {
      xr:xr-xml-map "policymgr:value";
      type uint16;
      description "Value of TCP flag";
    }
    leaf match-any {
      xr:xr-xml-map "policymgr:match_any";
      type boolean;
      description "Match any TCP flag bit";
    }
  }

  grouping PROTO-ICMP-ST {
    description "PROTO ICMP ST";
    leaf type {
      xr:xr-xml-map "policymgr:type";
      type uint8;
      description "Protocol type";
    }
    leaf code {
      xr:xr-xml-map "policymgr:code";
      type uint8;
      description "Protocol code";
    }
  }

  grouping UINT16-RNG-ST {
    description "UINT16 RNG ST";
    leaf min {
      xr:xr-xml-map "policymgr:min";
      type uint16;
      description "Lower limit of the range";
    }
    leaf max {
      xr:xr-xml-map "policymgr:max";
      type uint16;
      description "Upper limit of the range";
    }
  }

  grouping UINT16-RNG-ARRAY {
    description "UINT16 RNG ARRAY";

    list uint16_rng_array {
      description "uint16 rng array";
      uses UINT16-RNG-ST;
    }
  }

  grouping UINT8-ARRAY {
    description "UINT8 ARRAY";
    leaf-list uint8_array {
      xr:xr-xml-map "policymgr:uint8_array";
      type uint8;
      description "uint8 array";
    }
  }

  grouping UINT8-RNG-ST {
    description "UINT8 RNG ST";
    leaf min {
      xr:xr-xml-map "policymgr:min";
      type uint8;
      description "Lower limit of the range";
    }
    leaf max {
      xr:xr-xml-map "policymgr:max";
      type uint8;
      description "Upper limit of the range";
    }
  }

  grouping UINT8-RNG-ARRAY {
    description "UINT8 RNG ARRAY";

    list uint8_rng_array {
      description "uint8 rng array";
      uses UINT8-RNG-ST;
    }
  }

  grouping CLASS-MATCH-DATA-UN {
    description "Union of pointers to the supported match criteria";

    container ipv4-dscp {
      when "../type = 'match-type-ipv4-dscp'" {
        description "../type = 'MATCH_TYPE_IPV4_DSCP'";
      }
      description "IPv4 DSCP";
      uses UINT8-RNG-ARRAY;
    }

    container ipv6-dscp {
      when "../type = 'match-type-ipv6-dscp'" {
        description "../type = 'MATCH_TYPE_IPV6_DSCP'";
      }
      description "IPv6 DSCP";
      uses UINT8-RNG-ARRAY;
    }

    container dscp {
      when "../type = 'match-type-dscp'" {
        description "../type = 'MATCH_TYPE_DSCP'";
      }
      description "Match DSCP range array";
      uses UINT8-RNG-ARRAY;
    }

    container ipv4-prec {
      when "../type = 'match-type-ipv4-prec'" {
        description "../type = 'MATCH_TYPE_IPV4_PREC'";
      }
      description "IPv4 Precedence";
      uses UINT8-ARRAY;
    }

    container ipv6-prec {
      when "../type = 'match-type-ipv6-prec'" {
        description "../type = 'MATCH_TYPE_IPV6_PREC'";
      }
      description "IPv6 Precedence";
      uses UINT8-ARRAY;
    }

    container prec {
      when "../type = 'match-type-prec'" {
        description "../type = 'MATCH_TYPE_PREC'";
      }
      description "Match Precedence array";
      uses UINT8-ARRAY;
    }

    container discard-class {
      when "../type = 'match-type-disc-cls'" {
        description "../type = 'MATCH_TYPE_DISC_CLS'";
      }
      description "Match Discard Class array";
      uses UINT8-ARRAY;
    }

    container qos-group {
      when "../type = 'match-type-qos-grp'" {
        description "../type = 'MATCH_TYPE_QOS_GRP'";
      }
      description "Match QoS group array";
      uses UINT16-RNG-ARRAY;
    }

    container traffic-class {
      when "../type = 'match-type-traffic-class'" {
        description "../type = 'MATCH_TYPE_TRAFFIC_CLASS'";
      }
      description "Match Traffic class array";
      uses UINT8-RNG-ARRAY;
    }

    container proto {
      when "../type = 'match-type-proto'" {
        description "../type = 'MATCH_TYPE_PROTO'";
      }
      description "Match Protocol array";
      uses UINT16-RNG-ARRAY;
    }

    container icmp-v4 {
      when "../type = 'match-type-proto-icmpv4'" {
        description "../type = 'MATCH_TYPE_PROTO_ICMPV4'";
      }
      description "Match ICMPV4 Protocol";
      uses PROTO-ICMP-ST;
    }

    container icmp-v6 {
      when "../type = 'match-type-proto-icmpv6'" {
        description "../type = 'MATCH_TYPE_PROTO_ICMPV6'";
      }
      description "Match ICMPV6 Protocol array";
      uses PROTO-ICMP-ST;
    }

    container ipv4-packet-len {
      when "../type = 'match-type-ipv4-packet-length'" {
        description "../type = 'MATCH_TYPE_IPV4_PACKET_LENGTH'";
      }
      description "IPv4 packet length array";
      uses UINT16-RNG-ARRAY;
    }

    container ipv6-packet-len {
      when "../type = 'match-type-ipv6-packet-length'" {
        description "../type = 'MATCH_TYPE_IPV6_PACKET_LENGTH'";
      }
      description "IPv6 packet length array";
      uses UINT16-RNG-ARRAY;
    }

    container packet-len {
      when "../type = 'match-type-packet-length'" {
        description "../type = 'MATCH_TYPE_PACKET_LENGTH'";
      }
      description "Match packet length array";
      uses UINT16-RNG-ARRAY;
    }

    container flow-tag {
      when "../type = 'match-type-flow-tag'" {
        description "../type = 'MATCH_TYPE_FLOW_TAG'";
      }
      description "Match flow-tag array";
      uses UINT8-RNG-ARRAY;
    }

    container tcp-flag {
      when "../type = 'match-type-tcp-flag'" {
        description "../type = 'MATCH_TYPE_TCP_FLAG'";
      }
      description "Match tcp flag value";
      uses TCP-FLAG-ST;
    }

    container icmpv4-type {
      when "../type = 'match-type-icmpv4-type'" {
        description "../type = 'MATCH_TYPE_ICMPV4_TYPE'";
      }
      description "Match ipv4 icmp type";
      uses UINT8-RNG-ARRAY;
    }

    container icmpv4-code {
      when "../type = 'match-type-icmpv4-code'" {
        description "../type = 'MATCH_TYPE_ICMPV4_CODE'";
      }
      description "Match ipv4 icmp code";
      uses UINT8-RNG-ARRAY;
    }

    container icmpv6-type {
      when "../type = 'match-type-icmpv6-type'" {
        description "../type = 'MATCH_TYPE_ICMPV6_TYPE'";
      }
      description "Match ipv6 icmp type";
      uses UINT8-RNG-ARRAY;
    }

    container icmpv6-code {
      when "../type = 'match-type-icmpv6-code'" {
        description "../type = 'MATCH_TYPE_ICMPV6_CODE'";
      }
      description "Match ipv6 icmp code";
      uses UINT8-RNG-ARRAY;
    }

    container mpls-exp {
      when "../type = 'match-type-mpls-exp-top'" {
        description "../type = 'MATCH_TYPE_MPLS_EXP_TOP'";
      }
      description "Match MPLS experimental topmost array";
      uses UINT8-ARRAY;
    }

    container mpls-exp-imp {
      when "../type = 'match-type-mpls-exp-imp'" {
        description "../type = 'MATCH_TYPE_MPLS_EXP_IMP'";
      }
      description "Match MPLS experimental imposition array";
      uses UINT8-ARRAY;
    }

    container mpls-disp-ipv4-acl {
      when "../type = 'match-type-mpls-disp-ipv4-acl'" {
        description "../type = 'MATCH_TYPE_MPLS_DISP_IPV4_ACL'";
      }
      description "MPLS Disposition IPv4 Access-list";
      uses STRING-ARRAY;
    }

    container mpls-disp-ipv6-acl {
      when "../type = 'match-type-mpls-disp-ipv6-acl'" {
        description "../type = 'MATCH_TYPE_MPLS_DISP_IPV6_ACL'";
      }
      description "MPLS Disposition IPv6 Access-list";
      uses STRING-ARRAY;
    }

    container mpls-top-label {
      when "../type = 'match-type-mpls-topmost-label'" {
        description "../type = 'MATCH_TYPE_MPLS_TOPMOST_LABEL'";
      }
      description "MPLS Topmost LABEL";
      uses UINT32-RNG-ARRAY;
    }

    container cos {
      when "../type = 'match-type-cos'" {
        description "../type = 'MATCH_TYPE_COS'";
      }
      description "Match CoS array";
      uses UINT8-ARRAY;
    }

    container cos-inr {
      when "../type = 'match-type-cos-inner'" {
        description "../type = 'MATCH_TYPE_COS_INNER'";
      }
      description "Match inner header CoS";
      uses UINT8-ARRAY;
    }

    container dei {
      when "../type = 'match-type-dei'" {
        description "../type = 'MATCH_TYPE_DEI'";
      }
      description "Match DEI Bit";
      uses DEI-BIT-ST;
    }

    container dei-inr {
      when "../type = 'match-type-dei-inner'" {
        description "../type = 'MATCH_TYPE_DEI_INNER'";
      }
      description "Match inner DEI Bit";
      uses DEI-BIT-ST;
    }

    container vlan {
      when "../type = 'match-type-vlan'" {
        description "../type = 'MATCH_TYPE_VLAN'";
      }
      description "Match VLAN array";
      uses VLAN-ID-ARRAY;
    }

    container vlan-inr {
      when "../type = 'match-type-vlan-inner'" {
        description "../type = 'MATCH_TYPE_VLAN_INNER'";
      }
      description "Match inner header VLAN range array";
      uses UINT16-RNG-ARRAY;
    }

    container fr-dlci {
      when "../type = 'match-type-fr-dlci'" {
        description "../type = 'MATCH_TYPE_FR_DLCI'";
      }
      description "Match FR DLCI range array";
      uses UINT16-RNG-ARRAY;
    }

    container src-mac {
      when "../type = 'match-type-src-mac'" {
        description "../type = 'MATCH_TYPE_SRC_MAC'";
      }
      description "Match Source MAC address";
      uses MAC-ADDR-ST;
    }

    container dst-mac {
      when "../type = 'match-type-dst-mac'" {
        description "../type = 'MATCH_TYPE_DST_MAC'";
      }
      description "Match Destination MAC address";
      uses MAC-ADDR-ST;
    }

    container atm-clp {
      when "../type = 'match-type-atm-clp'" {
        description "../type = 'MATCH_TYPE_ATM_CLP'";
      }
      description "Match ATM CLP level";
      uses UINT8-ARRAY;
    }

    container fr-de {
      when "../type = 'match-type-fr-de'" {
        description "../type = 'MATCH_TYPE_FR_DE'";
      }
      description "Match FR DE value";
      uses UINT8-ARRAY;
    }

    container ipv4-acl {
      when "../type = 'match-type-ipv4-acl'" {
        description "../type = 'MATCH_TYPE_IPV4_ACL'";
      }
      description "IPv4 Access-list";
      uses STRING-ARRAY;
    }

    container ipv6-acl {
      when "../type = 'match-type-ipv6-acl'" {
        description "../type = 'MATCH_TYPE_IPV6_ACL'";
      }
      description "IPv6 Access-list";
      uses STRING-ARRAY;
    }

    container ether-service-acl {
      when "../type = 'match-type-ethernet-service-s-acl'" {
        description "../type = 'MATCH_TYPE_ETHERNET_SERVICES_ACL'";
      }
      description "Ethernet-Services Access-list";
      uses STRING-ARRAY;
    }

    container avail-id {
      when "../type = 'match-type-avail-id'" {
        description "../type = 'MATCH_TYPE_AVAIL_ID'";
      }
      description "Available Identifiers";
      uses UINT8-ARRAY;
    }

    container media-type {
      when "../type = 'match-type-media'" {
        description "../type = 'MATCH_TYPE_MEDIA'";
      }
      description "Media Type";
      uses UINT8-ARRAY;
    }

    container subs-protocol {
      when "../type = 'match-type-subs-protocol'" {
        description "../type = 'MATCH_TYPE_SUBS_PROTOCOL'";
      }
      description "Protocol";
      uses UINT8-ARRAY;
    }

    container dnis {
      when "../type = 'match-type-dnis'" {
        description "../type = 'MATCH_TYPE_DNIS'";
      }
      description "DNIS";
      uses STRING-ARRAY;
    }

    container dnis-regex {
      when "../type = 'match-type-dnis-regexp'" {
        description "../type = 'MATCH_TYPE_DNIS_REGEXP'";
      }
      description "DNIS Regular Expression";
      uses STRING-ARRAY;
    }

    container domain {
      when "../type = 'match-type-domain'" {
        description "../type = 'MATCH_TYPE_DOMAIN'";
      }
      description "Domain Name";
      uses DOMAIN-ARRAY;
    }

    container domain-regex {
      when "../type = 'match-type-domain-regexp'" {
        description "../type = 'MATCH_TYPE_DOMAIN_REGEXP'";
      }
      description "Domain Regular Expression";
      uses DOMAIN-ARRAY;
    }

    container nas-port {
      when "../type = 'match-type-nas-port'" {
        description "../type = 'MATCH_TYPE_NAS_PORT'";
      }
      description "NAS Port";
      uses NAS-PORT-ARRAY;
    }

    container service-name {
      when "../type = 'match-type-service-name'" {
        description "../type = 'MATCH_TYPE_SERVICE_NAME'";
      }
      description "Service Name";
      uses STRING-ARRAY;
    }

    container service-name-regex {
      when "../type = 'match-type-service-name-regexp'" {
        description "../type = 'MATCH_TYPE_SERVICE_NAME_REGEXP'";
      }
      description "Service Name Regular Exp";
      uses STRING-ARRAY;
    }

    container src-addr-ipv4 {
      when "../type = 'match-type-src-addr-ipv4'" {
        description "../type = 'MATCH_TYPE_SRC_ADDR_IPV4'";
      }
      description "Source Address IPV4";
      uses IPV4-ADDR-ARRAY;
    }

    container dst-addr-ipv4 {
      when "../type = 'match-type-dst-addr-ipv4'" {
        description "../type = 'MATCH_TYPE_DST_ADDR_IPV4'";
      }
      description "Destination Address IPV4";
      uses IPV4-ADDR-ARRAY;
    }

    container src-addr-ipv6 {
      when "../type = 'match-type-src-addr-ipv6'" {
        description "../type = 'MATCH_TYPE_SRC_ADDR_IPV6'";
      }
      description "Source Address IPV6";
      uses IPV6-ADDR-ARRAY;
    }

    container dst-addr-ipv6 {
      when "../type = 'match-type-dst-addr-ipv6'" {
        description "../type = 'MATCH_TYPE_DST_ADDR_IPV6'";
      }
      description "Destination Address IPV6";
      uses IPV6-ADDR-ARRAY;
    }

    container src-addr-mac {
      when "../type = 'match-type-src-addr-mac'" {
        description "../type = 'MATCH_TYPE_SRC_ADDR_MAC'";
      }
      description "Source Address MAC";
      uses MAC-ADDR-ARRAY;
    }

    container timer {
      when "../type = 'match-type-timer'" {
        description "../type = 'MATCH_TYPE_TIMER'";
      }
      description "Timer";
      uses STRING-ARRAY;
    }

    container timer-regexp {
      when "../type = 'match-type-timer-regexp'" {
        description "../type = 'MATCH_TYPE_TIMER_REGEXP'";
      }
      description "Timer Regular Expression";
      uses STRING-ARRAY;
    }

    container tunnel-name {
      when "../type = 'match-type-tunnel-name'" {
        description "../type = 'MATCH_TYPE_TUNNEL_NAME'";
      }
      description "Tunnel Name";
      uses STRING-ARRAY;
    }

    container tunnel-name-regex {
      when "../type = 'match-type-tunnel-name-regexp'" {
        description "../type = 'MATCH_TYPE_TUNNEL_NAME_REGEXP'";
      }
      description "Tunnel Name Regular Expression";
      uses STRING-ARRAY;
    }

    container user-name {
      when "../type = 'match-type-user-name'" {
        description "../type = 'MATCH_TYPE_USERNAME'";
      }
      description "User Name";
      uses STRING-ARRAY;
    }

    container user-name-regex {
      when "../type = 'match-type-user-name-regexp'" {
        description "../type = 'MATCH_TYPE_USERNAME_REGEXP'";
      }
      description "User Name Regular Expression";
      uses STRING-ARRAY;
    }

    container auth-username {
      when "../type = 'match-type-auth-user-name'" {
        description "../type = 'MATCH_TYPE_AUTH_USERNAME'";
      }
      description "Authenticated User Name";
      uses STRING-ARRAY;
    }

    container auth-username-regex {
      when "../type = 'match-type-auth-user-name-regexp'" {
        description "../type = 'MATCH_TYPE_AUTH_USERNAME_REGEXP'";
      }
      description "Authenticated User Name RegEx";
      uses STRING-ARRAY;
    }

    container unauth-username {
      when "../type = 'match-type-unauth-user-name'" {
        description "../type = 'MATCH_TYPE_UNAUTH_USERNAME'";
      }
      description "Unauthenticated User Name";
      uses STRING-ARRAY;
    }

    container unauth-username-regex {
      when "../type = 'match-type-unauth-user-name-regexp'" {
        description "../type = 'MATCH_TYPE_UNAUTH_USERNAME_REGEXP'";
      }
      description "Unauthenticated User Name RegEx";
      uses STRING-ARRAY;
    }

    container auth-domain {
      when "../type = 'match-type-auth-domain'" {
        description "../type = 'MATCH_TYPE_AUTH_DOMAIN'";
      }
      description "Authenticated domain name";
      uses STRING-ARRAY;
    }

    container auth-domain-regex {
      when "../type = 'match-type-auth-domain-regexp'" {
        description "../type = 'MATCH_TYPE_AUTH_DOMAIN_REGEXP'";
      }
      description "Authenticated Domain Name RegEx";
      uses STRING-ARRAY;
    }

    container unauth-domain {
      when "../type = 'match-type-unauth-domain'" {
        description "../type = 'MATCH_TYPE_UNAUTH_DOMAIN'";
      }
      description "Unauthenticated Domain Name";
      uses STRING-ARRAY;
    }

    container unauth-domain-regex {
      when "../type = 'match-type-unauth-domain-regexp'" {
        description "../type = 'MATCH_TYPE_UNAUTH_DOMAIN_REGEXP'";
      }
      description "Unauthenticated Domain Name RegEx";
      uses STRING-ARRAY;
    }

    container vendor-id {
      when "../type = 'match-type-vendor-id'" {
        description "../type = 'MATCH_TYPE_VENDOR_ID'";
      }
      description "Vendor ID";
      uses STRING-ARRAY;
    }

    container vendor-id-regex {
      when "../type = 'match-type-vendor-id-regexp'" {
        description "../type = 'MATCH_TYPE_VENDOR_ID_REGEXP'";
      }
      description "Vendor ID RegEx";
      uses STRING-ARRAY;
    }

    container access-interface {
      when "../type = 'match-type-access-interface'" {
        description "../type = 'MATCH_TYPE_ACCESS_INTERFACE'";
      }
      description "Access interface";
      uses STRING-ARRAY;
    }

    container input-interface {
      when "../type = 'match-type-input-interface'" {
        description "../type = 'MATCH_TYPE_INPUT_INTERFACE'";
      }
      description "Input interface";
      uses STRING-ARRAY;
    }

    container input-intfhdl {
      when "../type = 'match-type-input-interface-hdl'" {
        description "../type = 'MATCH_TYPE_INPUT_INTERFACE_HDL'";
      }
      description "Input interface handle";
      uses UINT64-ARRAY;
    }

    container ethertype {
      when "../type = 'match-type-ether-type'" {
        description "../type = 'MATCH_TYPE_ETHERTYPE'";
      }
      description "Ethernet type";
      uses UINT16-RNG-ARRAY;
    }

    container flow-key-data {
      when "../type = 'match-type-flow-key'" {
        description "../type = 'MATCH_TYPE_FLOW_KEY'";
      }
      description "Flow key structure";
      uses FLOW-KEY-ST;
    }

    container dhcp-client-id {
      when "../type = 'match-type-dhcp-client-id'" {
        description "../type = 'MATCH_TYPE_DHCP_CLIENT_ID'";
      }
      description "Dhcp Client ID";
      uses STRING-ARRAY;
    }

    container dhcp-client-id-regex {
      when "../type = 'match-type-dhcp-client-id-regexp'" {
        description "../type = 'MATCH_TYPE_DHCP_CLIENT_ID_REGEXP'";
      }
      description "Dhcp Client ID RegEx";
      uses STRING-ARRAY;
    }

    container circuit-id {
      when "../type = 'match-type-circuit-id'" {
        description "../type = 'MATCH_TYPE_CIRCUIT_ID'";
      }
      description "Circuit ID";
      uses STRING-ARRAY;
    }

    container circuit-id-regex {
      when "../type = 'match-type-circuit-id-regexp'" {
        description "../type = 'MATCH_TYPE_CIRCUIT_ID_REGEXP'";
      }
      description "Circuit ID RegEx";
      uses STRING-ARRAY;
    }

    container remote-id {
      when "../type = 'match-type-remote-id'" {
        description "../type = 'MATCH_TYPE_REMOTE_ID'";
      }
      description "Remote ID";
      uses STRING-ARRAY;
    }

    container remote-id-regex {
      when "../type = 'match-type-remote-id-regexp'" {
        description "../type = 'MATCH_TYPE_REMOTE_ID_REGEXP'";
      }
      description "Remote ID RegEx";
      uses STRING-ARRAY;
    }

    container src-port {
      when "../type = 'match-type-src-port'" {
        description "../type = 'MATCH_TYPE_SRC_PORT'";
      }
      description "Source port";
      uses UINT16-RNG-ARRAY;
    }

    container dst-port {
      when "../type = 'match-type-dst-port'" {
        description "../type = 'MATCH_TYPE_DST_PORT'";
      }
      description "Destination port";
      uses UINT16-RNG-ARRAY;
    }
    leaf type {
      xr:xr-xml-map "policymgr:type";
      type Match;
      description "type";
    }
    leaf mpls-top-eos {
      xr:xr-xml-map "policymgr:mpls_top_eos";
      when "../type = 'match-type-mpls-topmost-eos'" {
        description "../type = 'MATCH_TYPE_MPLS_TOPMOST_EOS'";
      }
      type uint8;
      description "MPLS Topmost EOS";
    }
    leaf fragment-type {
      xr:xr-xml-map "policymgr:fragment_type";
      when "../type = 'match-type-fragment-type'" {
        description "../type = 'MATCH_TYPE_FRAGMENT_TYPE'";
      }
      type uint8;
      description "Fragment type";
    }
    leaf authen-status {
      xr:xr-xml-map "policymgr:authen_status";
      when "../type = 'match-type-authen-status'" {
        description "../type = 'MATCH_TYPE_AUTHEN_STATUS'";
      }
      type Match-authen-status;
      description "Authentication Status";
    }
    leaf mlp-negotiated {
      xr:xr-xml-map "policymgr:mlp_negotiated";
      when "../type = 'match-type-mlp-negotiated'" {
        description "../type = 'MATCH_TYPE_MLP_NEGOTIATED'";
      }
      type Match-mlp-negotiated;
      description "MLP Negotiated";
    }
  }

  grouping CLASS-MATCH-INFO-ST {
    description "Class-map match info";

    list class-match-info-st {
      description "class match info st";

      container match-data {
        description "Match criteria";
        uses CLASS-MATCH-DATA-UN;
      }
      leaf flags {
        type uint32;
        description "Flags";
      }
    }
  }

  grouping INLINE-CLASS-MAP-BG {
    description "Inline Class-map bag";

    container match-infop {
      description "Pointer to the first Match info";
      uses CLASS-MATCH-INFO-ST;
    }
    leaf mode {
      xr:xr-xml-map "policymgr:mode";
      type Class-map-mode;
      description "Inline Class-Map Mode Match any/all";
    }
    leaf flags {
      xr:xr-xml-map "policymgr:flags";
      type uint32;
      description "Inline Class-Map flags";
    }
    leaf match-count {
      xr:xr-xml-map "policymgr:match_count";
      type uint32;
      description "Number of Match infos";
    }
  }

  grouping POL-CLASS-ENC-UN {
    description "Union of object name and app object ptr";

    container inline-cmap {
      when "../enc = 'policy-obj-enc-in-line'" {
        description "../enc = 'POLICY_OBJ_ENC_INLINE'";
      }
      description "inline cmap";
      uses INLINE-CLASS-MAP-BG;
    }
    leaf enc {
      xr:xr-xml-map "policymgr:enc";
      type Policy-obj-enc;
      description "enc";
    }
    leaf class-name {
      xr:xr-xml-map "policymgr:class_name";
      when "../enc = 'policy-obj-enc-name'" {
        description "../enc = 'POLICY_OBJ_ENC_NAME'";
      }
      type Class-map-name;
      description "class name";
    }
    leaf hd {
      xr:xr-xml-map "policymgr:hd";
      when "../enc = 'policy-obj-enc-hdl'" {
        description "../enc = 'POLICY_OBJ_ENC_HDL'";
      }
      type Class-map-hd-inbag;
      description "hd";
    }
    leaf idx {
      xr:xr-xml-map "policymgr:idx";
      when "../enc = 'policy-obj-enc-var-idx'" {
        description "../enc = 'POLICY_OBJ_ENC_VAR_IDX'";
      }
      type uint8;
      description "idx";
    }
  }

  grouping POLICY-CLASS-INFO-BG {
    description "Class per policy info";

    list policy-class-info-bg {
      description "policy class info bg";

      container cl-encode {
        description "cl encode";
        uses POL-CLASS-ENC-UN;
      }

      container clmp-p {
        description "clmp p";
        uses CLASS-MAP-BG;
      }

      container act-infop {
        description "act infop";
        uses POLICY-ACTION-INFO-ST;
      }
      leaf policy-class-hd {
        type uint32;
        description "policy class hd";
      }
      leaf seq {
        type uint32;
        description "seq";
      }
      leaf flags {
        type uint32;
        description "flags";
      }
      leaf ctype {
        type Class-map;
        description "ctype";
      }
      leaf num-actions {
        type uint16;
        description "num actions";
      }
      leaf version {
        type uint8;
        description "version";
      }
      leaf exe-strat {
        type Pclass-exec-strat;
        description "exe strat";
      }
    }
  }

  grouping POLICY-EVENT-INFO-BG {
    description "Event info bag";

    list policy-event-info-bg {
      description "policy event info bg";

      container class-infop {
        description "class infop";
        uses POLICY-CLASS-INFO-BG;
      }
      leaf event-type {
        type Pevent;
        description "event type";
      }
      leaf cond-eval {
        type Pevent-cond-eval;
        description "cond eval";
      }
      leaf avl-tree {
        type Pclass-data-avl-inbag;
        description "avl tree";
      }
      leaf flags {
        type uint32;
        description "flags";
      }
    }
  }

  grouping PLMGR-VAR-VAL-UN {
    description
      "Union of default values corrosponding to variable
      type";
    leaf type {
      xr:xr-xml-map "policymgr:type";
      type Plmgr-var;
      description "type";
    }
    leaf class-name {
      xr:xr-xml-map "policymgr:class_name";
      when "../type = 'plmgr-var-type-class-name'" {
        description "../type = 'PLMGR_VAR_TYPE_CLASS_NAME'";
      }
      type Var-cmap-name;
      description "class name";
    }
    leaf uint8_val {
      xr:xr-xml-map "policymgr:uint8_val";
      when "../type = 'plmgr-var-type-uint8'" {
        description "../type = 'PLMGR_VAR_TYPE_UINT8'";
      }
      type uint8;
      description "uint8 val";
    }
    leaf uint16_val {
      xr:xr-xml-map "policymgr:uint16_val";
      when "../type = 'plmgr-var-type-uint16'" {
        description "../type = 'PLMGR_VAR_TYPE_UINT16'";
      }
      type uint16;
      description "uint16 val";
    }
    leaf uint32_val {
      xr:xr-xml-map "policymgr:uint32_val";
      when "../type = 'plmgr-var-type-uint32'" {
        description "../type = 'PLMGR_VAR_TYPE_UINT32'";
      }
      type uint32;
      description "uint32 val";
    }
    leaf param-uint32-val {
      xr:xr-xml-map "policymgr:param_uint32_val";
      when "../type = 'plmgr-var-type-param-uint32'" {
        description "../type = 'PLMGR_VAR_TYPE_PARAM_UINT32'";
      }
      type uint32;
      description "param uint32 val";
    }
    leaf dscp-val {
      xr:xr-xml-map "policymgr:dscp_val";
      when "../type = 'plmgr-var-type-dscp'" {
        description "../type = 'PLMGR_VAR_TYPE_DSCP'";
      }
      type uint8;
      description "dscp val";
    }
    leaf prec-val {
      xr:xr-xml-map "policymgr:prec_val";
      when "../type = 'plmgr-var-type-prec'" {
        description "../type = 'PLMGR_VAR_TYPE_PREC'";
      }
      type uint8;
      description "prec val";
    }
  }

  grouping PMAP-VAR-INFO-ST {
    description "PMAP VAR INFO ST";

    container val {
      description "val";
      uses PLMGR-VAR-VAL-UN;
    }
    leaf name {
      xr:xr-xml-map "policymgr:name";
      type string {
        length "0..32";
      }
      description "name";
    }
    leaf id {
      xr:xr-xml-map "policymgr:id";
      type uint32;
      description "id";
    }
  }

  grouping PMAP-VAR-LIST-ST {
    description "PMAP VAR LIST ST";
    leaf-list offset {
      xr:xr-xml-map "policymgr:offset";
      type uint8;
      description "offset";
    }

    list pmap-var-list-arr {
      description "pmap var list arr";
      uses PMAP-VAR-INFO-ST;
    }
  }

  grouping POLICY-MAP-BG {
    description "Policy-map Bag";

    list policy-map-bg {
      description "policy map bg";

      container pmap-var-list {
        description "pmap var list";
        uses PMAP-VAR-LIST-ST;
      }

      container event-infop {
        description "event infop";
        uses POLICY-EVENT-INFO-BG;
      }
      leaf name {
        type Policy-map-name;
        description "name";
      }
      leaf type {
        type Policy-map;
        description "type";
      }
      leaf magic {
        type uint32;
        description "magic";
      }
      leaf flags {
        type uint32;
        description "flags";
      }
      leaf num-classes {
        type uint32;
        description "num classes";
      }
      leaf max-hierarchy {
        type uint16;
        description "max hierarchy";
      }
      leaf class-dflt-hrchy-depth {
        type uint16;
        description "class dflt hrchy depth";
      }
      leaf num-policy-class-info {
        type uint32;
        description "num policy class info";
      }
      leaf table-id {
        type uint32;
        description "table id";
      }
      leaf handle {
        type uint32;
        description "handle";
      }
      leaf chk-sum {
        type Policy-chk-sum;
        description "MD5 checksum of the encoded class-map bag";
      }
      leaf rateless-chk-sum {
        type Policy-chk-sum;
        description "rateless chk sum";
      }
      leaf description {
        type String1;
        description "description";
      }
      leaf pclass-diff {
        type Pclass-diff-inbag;
        description "pclass diff";
      }
    }
  }

  grouping POLICY-MAP-APPLIED-SHOW-BG {
    description "Policy-map applied show bag";
    leaf parent-pmap-name {
      xr:xr-xml-map "policymgr:parent_pmap_name";
      type Policy-map-name;
      description "parent pmap name";
    }
    leaf pmap-type {
      xr:xr-xml-map "policymgr:pmap_type";
      type Policy-map;
      description "pmap type";
    }

    list pmaps {
      description "pmaps";
      uses POLICY-MAP-BG;
    }

    list pmap-var {
      description "pmap var";
      uses PLMGR-APPLIED-VARLIST-BG;
    }
  }
}
