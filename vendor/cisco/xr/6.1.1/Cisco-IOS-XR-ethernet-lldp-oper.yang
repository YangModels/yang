module Cisco-IOS-XR-ethernet-lldp-oper {

  /*** NAMESPACE / PREFIX DEFINITION ***/

  namespace "http://cisco.com/ns"+
    "/yang/Cisco-IOS-XR-ethernet-lldp-oper";


  prefix "ethernet-lldp-oper";

  /*** LINKAGE (IMPORTS / INCLUDES) ***/

  import Cisco-IOS-XR-types { prefix "xr"; }

  include Cisco-IOS-XR-ethernet-lldp-oper-sub2 {
    revision-date 2015-11-09;
  }

  include Cisco-IOS-XR-ethernet-lldp-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ethernet-lldp package operational data.

     This module contains definitions
     for the following management objects:
       lldp: Link Layer Discovery Protocol operational data

     Copyright (c) 2013-2016 by Cisco Systems, Inc.
     All rights reserved.";

  revision "2015-11-09" {
    description
      "IOS XR 6.0 revision.";
  }


  container lldp {
    xr:xr-xml-map "lldp_oper:LLDP";
    config false;
    description "Link Layer Discovery Protocol operational data";

    container global-lldp {
      xr:xr-xml-map "lldp_oper:GlobalLLDP";
      description "Global LLDP data";

      container lldp-info {
        xr:xr-xml-map "lldp_oper:LLDPInfo";
        description "The LLDP Global Information of this box";
        uses LLDP-MGR-GLOBAL-INFO;
      }
    }

    container nodes {
      xr:xr-xml-map "lldp_oper:NodeTable";
      description "Per node LLDP operational data";

      list node {
        xr:xr-xml-map "lldp_oper:Node";
        key "node-name";
        description
          "The LLDP operational data for a particular node";

        container neighbors {
          xr:xr-xml-map "lldp_oper:Neighbors";
          description "The LLDP neighbor tables on this node";

          container devices {
            xr:xr-xml-map "lldp_oper:DeviceTable";
            description
              "The detailed LLDP neighbor table on this
              device";

            list device {
              xr:xr-xml-map "lldp_oper:Device";
              description
                "Detailed information about a LLDP neighbor
                entry";
              leaf device-id {
                xr:xr-xml-map "lldp_oper:DeviceID";
                type string;
                description "The neighboring device identifier";
              }
              leaf interface-name {
                xr:xr-xml-map "lldp_oper:InterfaceName";
                type xr:Interface-name;
                description "The interface name";
              }
              uses LLDP-NEIGHBOR;
            }
          }

          container details {
            xr:xr-xml-map "lldp_oper:DetailTable";
            description "The detailed LLDP neighbor table";

            list detail {
              xr:xr-xml-map "lldp_oper:Detail";
              description
                "Detailed information about a LLDP neighbor
                entry";
              leaf interface-name {
                xr:xr-xml-map "lldp_oper:InterfaceName";
                type xr:Interface-name;
                description "The interface name";
              }
              leaf device-id {
                xr:xr-xml-map "lldp_oper:DeviceID";
                type string;
                description "The neighboring device identifier";
              }
              uses LLDP-NEIGHBOR;
            }
          }

          container summaries {
            xr:xr-xml-map "lldp_oper:SummaryTable";
            description "The LLDP neighbor summary table";

            list summary {
              xr:xr-xml-map "lldp_oper:Summary";
              description
                "Brief information about a LLDP neighbor
                entry";
              leaf interface-name {
                xr:xr-xml-map "lldp_oper:InterfaceName";
                type xr:Interface-name;
                description "The interface name";
              }
              leaf device-id {
                xr:xr-xml-map "lldp_oper:DeviceID";
                type string;
                description "The neighboring device identifier";
              }
              uses LLDP-NEIGHBOR;
            }
          }
        }

        container interfaces {
          xr:xr-xml-map "lldp_oper:InterfaceTable";
          description
            "The table of interfaces on which LLDP is
            running on this node";

          list interface {
            xr:xr-xml-map "lldp_oper:Interface";
            key "interface-name";
            description
              "Operational data for an interface on which
              LLDP is running";
            leaf interface-name {
              xr:xr-xml-map "lldp_oper:InterfaceName";
              type xr:Interface-name;
              description "The interface name";
            }
            uses LLDP-INTERFACE;
          }
        }

        container statistics {
          xr:xr-xml-map "lldp_oper:Statistics";
          description "The LLDP traffic statistics for this node";
          uses LLDP-STATS;
        }
        leaf node-name {
          xr:xr-xml-map "lldp_oper:NodeName";
          type xr:Node-id;
          description "The identifier for the node";
        }
      }
    }
  }
}
