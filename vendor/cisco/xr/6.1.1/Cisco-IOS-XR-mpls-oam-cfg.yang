module Cisco-IOS-XR-mpls-oam-cfg {

  /*** NAMESPACE / PREFIX DEFINITION ***/

  namespace "http://cisco.com/ns/yang/Cisco-IOS-XR-mpls-oam-cfg";


  prefix "mpls-oam-cfg";

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR mpls-oam package configuration.

     This module contains definitions
     for the following management objects:
       mpls-oam: MPLS LSP verification configuration

     Copyright (c) 2013-2016 by Cisco Systems, Inc.
     All rights reserved.";

  revision "2015-11-09" {
    description
      "IOS XR 6.0 revision.";
  }


  container mpls-oam {
    xr:xr-xml-map "mpls_oam_cfg:MPLS_OAM";
    description "MPLS LSP verification configuration";

    container reply-mode {
      xr:xr-xml-map "mpls_oam_cfg:ReplyMode";
      description "Echo request reply mode attributes";

      container control-channel {
        xr:xr-xml-map "mpls_oam_cfg:ControlChannel";
        description "Configure control channel reply mode";
        leaf allow-reverse-lsp {
          xr:xr-xml-map "mpls_oam_cfg:AllowReverseLSP";
          xr:xr-cli-map "oam echo reply-mode control-channel allow-"+
            "reverse-lsp ";
          type empty;
          description "Use Reverse LSP as the control channel";
        }
      }
    }
    leaf enable-oam {
      xr:xr-xml-map "mpls_oam_cfg:EnableOAM";
      type empty;
      description
        "Enable/Disable MPLS OAM globally.Without
        creating this object the MPLS OAM feature will
        not be enabled. Deleting this object will stop
        the MPLS OAM feature.";
    }
    leaf disable-vendor-extension {
      xr:xr-xml-map "mpls_oam_cfg:DisableVendorExtension";
      xr:xr-cli-map "oam echo disable-vendor-extension ";
      type empty;
      description "Disable vendor extension";
    }
  }
}
