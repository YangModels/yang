submodule Cisco-IOS-XR-snmp-agent-oper-sub4 {

  belongs-to Cisco-IOS-XR-snmp-agent-oper {
    prefix Cisco-IOS-XR-snmp-agent-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR snmp-agent package operational data.

     Copyright (c) 2013-2016 by Cisco Systems, Inc.
     All rights reserved.";

  revision "2016-06-01" {
    description
      "IOS XR 6.0.1 revision.";
  }

  revision "2015-01-07" {
    description
      "IOS XR 5.3.1 revision.";
  }


  grouping SNMP-USM-USER-ENTRY {
    description "SNMP usmUserTable Information";
    leaf usm-user-storage-type {
      xr:xr-xml-map "snmpv3mib:USMUserStorageType";
      type uint32;
      description "Storage type";
    }
    leaf usm-user-status {
      xr:xr-xml-map "snmpv3mib:USMUserStatus";
      type uint32;
      description "Status of this user";
    }
  }

  grouping SNMP-VACM-ACCESS-ENTRY {
    description "SNMP vacmAccessTable Information";
    leaf vacm-access-read-view-name {
      xr:xr-xml-map "snmpv3mib:VACMAccessReadViewName";
      type string;
      description "Read view name";
    }
    leaf vacm-access-write-view-name {
      xr:xr-xml-map "snmpv3mib:VACMAccessWriteViewName";
      type string;
      description "Write view name";
    }
    leaf vacm-access-notify-view-name {
      xr:xr-xml-map "snmpv3mib:VACMAccessNotifyViewName";
      type string;
      description "Notify view name";
    }
    leaf vacm-access-status {
      xr:xr-xml-map "snmpv3mib:VACMAccessStatus";
      type uint32;
      description "Status of this view configuration";
    }
  }

  grouping SNMP-SNMP-VIEW-XML-ENTRY {
    description "SNMP SNMPViewXmlTable Information";
    leaf snmp-view-family-type {
      xr:xr-xml-map "snmpv3mib:SNMPViewFamilyType";
      type string;
      description "Include or exclude";
    }
    leaf snmp-view-family-storage-type {
      xr:xr-xml-map "snmpv3mib:SNMPViewFamilyStorageType";
      type string;
      description "Storage type";
    }
    leaf snmp-view-family-status {
      xr:xr-xml-map "snmpv3mib:SNMPViewFamilyStatus";
      type string;
      description "Status of this entry";
    }
  }

  grouping SNMP-SNMP-HOST-XML {
    description "SNMP host xml information";
    leaf snmp-target-address-t-host {
      xr:xr-xml-map "snmpv3mib:SNMPTargetAddressTHost";
      type string;
      description "Transport type of address";
    }
    leaf snmp-target-address-port {
      xr:xr-xml-map "snmpv3mib:SNMPTargetAddressPort";
      type string;
      description "Target UDP port";
    }
    leaf snmp-target-addresstype {
      xr:xr-xml-map "snmpv3mib:SNMPTargetAddresstype";
      type string;
      description "Target host type (Inform or Trap)";
    }
    leaf snmp-target-params-security-model {
      xr:xr-xml-map "snmpv3mib:SNMPTargetParamsSecurityModel";
      type string;
      description "Security model";
    }
    leaf snmp-target-params-security-name {
      xr:xr-xml-map "snmpv3mib:SNMPTargetParamsSecurityName";
      type string;
      description "Security name";
    }
    leaf snmp-target-params-security-level {
      xr:xr-xml-map "snmpv3mib:SNMPTargetParamsSecurityLevel";
      type string;
      description "Security level";
    }
  }
}
