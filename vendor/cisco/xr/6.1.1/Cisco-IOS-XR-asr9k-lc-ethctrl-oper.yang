module Cisco-IOS-XR-asr9k-lc-ethctrl-oper {

  /*** NAMESPACE / PREFIX DEFINITION ***/

  namespace "http://cisco.com/ns/yang"+
    "/Cisco-IOS-XR-asr9k-lc-ethctrl-oper";


  prefix "asr9k-lc-ethctrl-oper";

  /*** LINKAGE (IMPORTS / INCLUDES) ***/

  import Cisco-IOS-XR-types { prefix "xr"; }

  include Cisco-IOS-XR-asr9k-lc-ethctrl-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR asr9k-lc-ethctrl package operational data.

     This module contains definitions
     for the following management objects:
       mlan: Management LAN Operational data space

     Copyright (c) 2013-2016 by Cisco Systems, Inc.
     All rights reserved.";

  revision "2015-11-09" {
    description
      "IOS XR 6.0 revision.";
  }


  container mlan {
    xr:xr-xml-map "mlan_oper:Mlan";
    config false;
    description "Management LAN Operational data space";

    container nodes {
      xr:xr-xml-map "mlan_oper:NodeTable";
      description "Table of nodes";

      list node {
        xr:xr-xml-map "mlan_oper:Node";
        key "node";
        description "Number";

        container port-status-numbers {
          xr:xr-xml-map "mlan_oper:PortStatusTable";
          description "Table of port status";

          list port-status-number {
            xr:xr-xml-map "mlan_oper:PortStatusNumber";
            key "number";
            description "Number";

            container port-status {
              xr:xr-xml-map "mlan_oper:PortStatus";
              description "mlan port status info";
              uses MLAN-PORT-STATUS;
            }
            leaf number {
              xr:xr-xml-map "mlan_oper:Number";
              type int32;
              description "port number";
            }
          }
        }

        container switch-status-table {
          xr:xr-xml-map "mlan_oper:SwitchStatusTable";
          description "Table of switch status";

          container switch-status {
            xr:xr-xml-map "mlan_oper:SwitchStatus";
            description "mlan switch status info";
            uses MLAN-SWITCH-STATUS-DATA;
          }
        }

        container port-counters-numbers {
          xr:xr-xml-map "mlan_oper:PortCountersTable";
          description "Table of port counters";

          list port-counters-number {
            xr:xr-xml-map "mlan_oper:PortCountersNumber";
            key "number";
            description "Number";

            container port-counters {
              xr:xr-xml-map "mlan_oper:PortCounters";
              description "mlan port counters info";
              uses MLAN-PORT-COUNTERS;
            }
            leaf number {
              xr:xr-xml-map "mlan_oper:Number";
              type int32;
              description "port number";
            }
          }
        }

        container atu-entry-numbers {
          xr:xr-xml-map "mlan_oper:SwitchATUTable";
          description "Table of switch ATU";

          list atu-entry-number {
            xr:xr-xml-map "mlan_oper:AtuEntryNumbers";
            key "entry";
            description "Entry number";

            container switch-counters {
              xr:xr-xml-map "mlan_oper:SwitchCounters";
              description "mlan switch counters info";
              uses MLAN-SWITCH-ATU-DATA;
            }
            leaf entry {
              xr:xr-xml-map "mlan_oper:entry";
              type int32;
              description "entry number";
            }
          }
        }
        leaf node {
          xr:xr-xml-map "mlan_oper:Node";
          type xr:Node-id;
          description "node number";
        }
      }
    }
  }
}
