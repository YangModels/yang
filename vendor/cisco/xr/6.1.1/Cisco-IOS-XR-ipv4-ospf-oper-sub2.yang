submodule Cisco-IOS-XR-ipv4-ospf-oper-sub2 {

  belongs-to Cisco-IOS-XR-ipv4-ospf-oper {
    prefix Cisco-IOS-XR-ipv4-ospf-oper;
  }

  /*** LINKAGE (IMPORTS / INCLUDES) ***/

  import ietf-inet-types { prefix "inet"; }

  import ietf-yang-types { prefix "yang"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR ipv4-ospf package operational data.

     Copyright (c) 2013-2016 by Cisco Systems, Inc.
     All rights reserved.";

  revision "2015-11-09" {
    description
      "IOS XR 6.0 revision.";
  }

  typedef Ospf-sh-opq-ri-pce-addr-types {
    type enumeration {
      enum mgmt-ospf-opq-pce-addr-type-invalid {
        value 0;
        description "Invalid PCE Address";
      }
      enum mgmt-ospf-opq-pce-addr-type-ipv4 {
        value 1;
        description "IPv4 PCE Address";
      }
      enum mgmt-ospf-opq-pce-addr-type-ipv6 {
        value 2;
        description "IPv6 PCE Address";
      }
    }
    description "OSPF PCE Address Type";
  }
  typedef Ospf-sh-opq-ri-tlv-types {
    type enumeration {
      enum mgmt-ospf-opq-ri-tlv-type-unknown {
        description "Unknown";
      }
      enum mgmt-ospf-opq-ri-tlv-type-rtrcap {
        description "Router Capabilities";
      }
      enum mgmt-ospf-opq-ri-tlv-type-pce-discovery {
        description "PCE Discovery";
      }
      enum mgmt-ospf-opq-ri-tlv-type-sr-algo {
        description "Segment Routing Algorithm";
      }
      enum mgmt-ospf-opq-ri-tlv-type-sr-range {
        description "Segment Routing SID Range";
      }
    }
    description "OSPF Router Information TLV types";
  }
  typedef Ospf-lsa-opq-ri-scope {
    type enumeration {
      enum mgmt-lsa-opq-ri-scope-link {
        value 9;
        description "Link-local Router Information LSA";
      }
      enum mgmt-lsa-opq-ri-scope-area {
        value 10;
        description "Area-scope Router Information LSA";
      }
      enum mgmt-lsa-opq-ri-scope-as {
        value 11;
        description "AS-scope Router Information LSA";
      }
    }
    description "OSPF Router Information LSA scope types";
  }
  typedef Ospf-gr-reason {
    type enumeration {
      enum mgmt-gr-reason-unknown {
        description "Unknown";
      }
      enum mgmt-gr-reason-sw-restart {
        description "Software restart";
      }
      enum mgmt-gr-reason-sw-upgrade {
        description "Software reload/upgrade";
      }
      enum mgmt-gr-reason-switchover {
        description "Switch to redundant control processor";
      }
    }
    description "Ospf gr reason";
  }
  typedef Stlv {
    type enumeration {
      enum mgmt-rrr-link-type {
        value 1;
        description "Link Type";
      }
      enum mgmt-rrr-link-id {
        value 2;
        description "Link ID";
      }
      enum mgmt-rrr-link-local-if-addr {
        value 3;
        description "Local interface IP address";
      }
      enum mgmt-rrr-link-remote-if-addr {
        value 4;
        description "Remote interface IP address";
      }
      enum mgmt-rrr-link-metric {
        value 5;
        description "Traffic Engineering metric";
      }
      enum mgmt-rrr-link-max-bw {
        value 6;
        description "Maximum Link Bandwidth";
      }
      enum mgmt-rrr-link-max-reservable-bw {
        value 7;
        description "Maximum Reservable bandwidth";
      }
      enum mgmt-rrr-link-unreserved-bw {
        value 8;
        description "Unreserved Bandwidth";
      }
      enum mgmt-rrr-link-re-source-class {
        value 9;
        description "Administrative group";
      }
      enum mgmt-rrr-link-in-out-if-id {
        value 11;
        description "Link Local/Remote Identifiers";
      }
      enum mgmt-rrr-link-if-switching-cap-desc {
        value 15;
        description "Interface Switching Capability Descriptor";
      }
      enum mgmt-ospf-rrr-link-srlg {
        value 16;
        description "Shared Risk Link Group";
      }
      enum mgmt-rrr-link-bw-constraints-sub {
        value 17;
        description "Bandwidth constraints";
      }
      enum mgmt-ospf-rrr-link-uni-delay {
        value 27;
        description "Unidirectional link delay";
      }
      enum mgmt-ospf-rrr-link-max-reservable-bw-sub {
        value 32768;
        description "Maximum reservable sub-pool bandwidth";
      }
      enum mgmt-ospf-rrr-link-unreserved-bw-sub {
        value 32769;
        description "Unreserved sub-pool bandwidth";
      }
      enum mgmt-rrr-link-igp-metric {
        value 32770;
        description "IGP Link Metric";
      }
      enum mgmt-ospf-rrr-link-ext-admin-sub {
        value 32771;
        description "Extended admin";
      }
    }
    description "OSPF Opaque-area Type 1 sub TLV types";
  }
  typedef Ex-metric {
    type enumeration {
      enum mgmt-ex-metric-type-none {
        value 0;
        description "No metric type";
      }
      enum mgmt-ex-metric-type-1 {
        value 1;
        description "Type 1 External";
      }
      enum mgmt-ex-metric-type-2 {
        value 2;
        description "Type 2 External";
      }
    }
    description "Ex metric";
  }
  typedef Ospf-link-types {
    type enumeration {
      enum mgmt-rtr-link {
        value 1;
        description "Link to a Router";
      }
      enum mgmt-trans-link {
        value 2;
        description "Link to a transit network";
      }
      enum mgmt-stub-net {
        value 3;
        description "Link to Stub network";
      }
      enum mgmt-vitural-link {
        value 4;
        description "Link to Virtual Link";
      }
    }
    description "Type of router LSA links";
  }
  typedef Ospf-internal-lsa-types {
    type enumeration {
      enum mgmt-rtr-type {
        value 1;
        description "Router LSA";
      }
      enum mgmt-ntwk-type {
        value 2;
        description "Network LSA";
      }
      enum mgmt-sum-type {
        value 3;
        description "Summary and ASBR summary LSA";
      }
      enum mgmt-ext-type {
        value 4;
        description "Type 5 and NSSA external LSA";
      }
      enum mgmt-opq-type {
        value 5;
        description "Generic AS/Area Opaque LSA";
      }
      enum mgmt-opq-link-type {
        value 6;
        description "Generic Link Opaque LSA";
      }
      enum mgmt-opq-rrr-type {
        value 7;
        description "Opaque Area type 1 LSA";
      }
      enum mgmt-opq-gr-type {
        value 8;
        description "Opaque link type 1 LSA";
      }
      enum mgmt-opq-ri-type {
        value 9;
        description "Opaque Router Information LSA";
      }
      enum mgmt-opq-epl-type {
        value 10;
        description "Opaque Area type 128";
      }
      enum mgmt-opq-ell-type {
        value 11;
        description "Opaque Area type 8";
      }
    }
    description "OSPF LSA format types";
  }
  typedef Timer {
    type enumeration {
      enum mgmt-db-stop {
        description "Timer stopped";
      }
      enum mgmt-db-refresh {
        description "Refresh";
      }
      enum mgmt-db-checksum {
        description "Checksum";
      }
      enum mgmt-db-max-age {
        description "Maxage";
      }
    }
    description
      "The LSA timer running can be refresh, checksum or
      maxage";
  }
  typedef Timer-table {
    type enumeration {
      enum mgmt-db-no-table {
        description "Not in time table";
      }
      enum mgmt-db-sec-table {
        description "In second table";
      }
      enum mgmt-db-buffer-table {
        description "In buffer table";
      }
      enum mgmt-db-min-table {
        description "In minute table";
      }
    }
    description
      "The throttled LSA can be in second, buffer or
      minute timer table";
  }
  typedef Ospf-srgb-status {
    type enumeration {
      enum not-allocated {
        value 0;
        description "Not allocated";
      }
      enum pending {
        value 1;
        description "Allocation pending";
      }
      enum allocated {
        value 2;
        description "Allocated";
      }
    }
    description "Ospf srgb status";
  }
  typedef Gs-state {
    type enumeration {
      enum mgmt-gs-init {
        description "Process in initialization ";
      }
      enum mgmt-gs-normal {
        description "Graceful Shutdown not running";
      }
      enum mgmt-gs-delay {
        description "Delaying  before Graceful Shutdown";
      }
      enum mgmt-gs-flush {
        description "Flushing self originated LSAs";
      }
      enum mgmt-gs-hello {
        description "Sending empty hellos";
      }
      enum mgmt-gs-quiet {
        description "Shutdown mode.";
      }
    }
    description "Gs state";
  }
  typedef Max-metric-unset-reason {
    type enumeration {
      enum mgmt-max-metric-unset-none {
        description "none";
      }
      enum mgmt-max-metric-unset-bgp {
        description "BGP converged";
      }
      enum mgmt-max-metric-unset-timer {
        description "timer expired";
      }
      enum mgmt-max-metric-unset-cfg {
        description "unconfigured";
      }
      enum mgmt-max-metric-unset-process-cleared {
        description "process cleared";
      }
      enum mgmt-max-metric-unset-over-write {
        description "set for other reason";
      }
    }
    description "Max metric unset reason";
  }
  typedef Ospf-max-metric-abr-off-reasons {
    type enumeration {
      enum ospf-max-metric-abr-off-reason-none {
        value 0;
        description "No reason";
      }
      enum ospf-max-metric-abr-off-reason-no-nbr {
        value 1;
        description "No neighbors seen yet";
      }
      enum ospf-max-metric-abr-off-reason-new-nbr {
        value 2;
        description "New neighbor seen recently";
      }
      enum ospf-max-metric-abr-off-reason-nbr-full {
        value 4;
        description "Adjacency FULL seen recently";
      }
      enum ospf-max-metric-abr-off-reason-flush-p-end {
        value 8;
        description "LSA flushes pending";
      }
    }
    description "Ospf max metric abr off reasons";
  }
  typedef Max-metric-set-reason {
    type enumeration {
      enum mgmt-max-metric-on-proc-migration {
        description "proc migration";
      }
      enum mgmt-max-metric-on-proc-restart {
        description "proc restart";
      }
      enum mgmt-max-metric-on-switchover {
        description "switch over";
      }
      enum mgmt-max-metric-on-startup {
        description "start up";
      }
      enum mgmt-max-metric-always {
        description "always";
      }
      enum mgmt-max-metric-reason-none {
        description "none";
      }
    }
    description "Max metric set reason";
  }
  typedef Ospf-br {
    type enumeration {
      enum mgmt-d-type-abr-asbr {
        description "Both Area Border Router and AS Border Router";
      }
      enum mgmt-d-type-asbr {
        description "AS Border Router";
      }
      enum mgmt-d-type-abr {
        description "Area Border Router";
      }
    }
    description "Ospf br";
  }
  typedef Ipfrr-tbrkr {
    type enumeration {
      enum downstream {
        value 0;
        description "Downsteram";
      }
      enum line-card-disjoint {
        value 1;
        description "LC Disjoint";
      }
      enum backup-metric {
        value 2;
        description "Backup metric";
      }
      enum node-protect {
        value 3;
        description "Node protection";
      }
      enum primary-path {
        value 4;
        description "Primary path";
      }
      enum secondary-path {
        value 5;
        description "Secondary path";
      }
      enum srlg-disjoint {
        value 6;
        description "SRLG disjoint";
      }
      enum tunnel {
        value 7;
        description "Tunnel";
      }
      enum post-convergence {
        value 8;
        description "Post Convergence";
      }
    }
    description "FRR Tiebreakers";
  }
  typedef Ipfrr {
    type enumeration {
      enum none {
        value 0;
        description "Disabled";
      }
      enum per-link {
        value 1;
        description "Per link";
      }
      enum per-prefix {
        value 2;
        description "Per prefix";
      }
    }
    description "FRR Types";
  }
  typedef Interface-state {
    type enumeration {
      enum mgmt-ifs-unknown {
        description "Interface state unknown";
      }
      enum mgmt-ifs-admin-down {
        description "Interface is administratively down";
      }
      enum mgmt-ifs-down {
        description "Interface is down";
      }
      enum mgmt-ifs-up {
        description "Interface is up";
      }
      enum mgmt-ifs-shutdown {
        description "Interface is administratively down";
      }
    }
    description "Interface state";
  }
  typedef Authentication {
    type enumeration {
      enum mgmt-ospf-auth-none {
        value 0;
        description "No Authentication";
      }
      enum mgmt-ospf-auth-ct {
        value 1;
        description "Clear Text";
      }
      enum mgmt-ospf-auth-md {
        value 2;
        description "MD5";
      }
      enum mgmt-ospf-auth-kc {
        value 3;
        description "Keychain";
      }
    }
    description "Authentication";
  }
  typedef Ospf-interface-state {
    type enumeration {
      enum mgmt-ospf-ifs-down {
        value 0;
        description "Down";
      }
      enum mgmt-ospf-ifs-loop-back {
        value 1;
        description "Loopback";
      }
      enum mgmt-ospf-ifs-waiting {
        value 2;
        description "Waiting";
      }
      enum mgmt-ospf-ifs-point-to-m-point {
        value 3;
        description "Point to multipoint";
      }
      enum mgmt-ospf-ifs-point-to-point {
        value 4;
        description "Point to point";
      }
      enum mgmt-ospf-ifs-dr {
        value 5;
        description "DesignatedRouter";
      }
      enum mgmt-ospf-ifs-backup {
        value 6;
        description "Backup Designated Router";
      }
      enum mgmt-ospf-ifs-other {
        value 7;
        description "Designated Router Other";
      }
    }
    description "Ospf interface state";
  }
  typedef String1 {
    type string;
    description "String1";
  }
  typedef Redist-protocol {
    type enumeration {
      enum mgmt-rib-protocol-all {
        description "Unknown";
      }
      enum mgmt-rib-protocol-connected {
        description "Connected";
      }
      enum mgmt-rib-protocol-local {
        description "Local";
      }
      enum mgmt-rib-protocol-static {
        description "Static";
      }
      enum mgmt-rib-protocol-bgp {
        description "BGP";
      }
      enum mgmt-rib-protocol-rip {
        description "RIP";
      }
      enum mgmt-rib-protocol-isis {
        description "ISIS";
      }
      enum mgmt-rib-protocol-ospf {
        description "OSPF";
      }
      enum mgmt-rib-protocol-eigrp {
        description "EIGRP";
      }
      enum mgmt-rib-protocol-dagr {
        description "DAGR";
      }
      enum mgmt-rib-protocol-subscriber {
        description "Subscriber";
      }
      enum mgmt-rib-protocol-application {
        description "Application";
      }
      enum mgmt-rib-protocol-mobile {
        description "Mobile";
      }
    }
    description "Redist protocol";
  }
  typedef Ospf-route {
    type enumeration {
      enum mgmt-r-type-none {
        value 0;
        description "No route type";
      }
      enum mgmt-r-type-other {
        value 1;
        description "Not set";
      }
      enum mgmt-r-type-intra {
        value 2;
        description "Intra-area route";
      }
      enum mgmt-r-type-inter {
        value 4;
        description "Inter-area route";
      }
      enum mgmt-r-type-extern1 {
        value 8;
        description "Type 1 External route";
      }
      enum mgmt-r-type-extern2 {
        value 16;
        description "Type 2 External route";
      }
      enum mgmt-r-type-isis-sum {
        value 32;
        description "IS-IS summary route";
      }
      enum mgmt-r-type-isis-l1 {
        value 64;
        description "IS-IS level 1 route";
      }
      enum mgmt-r-type-isis-l2 {
        value 128;
        description "IS-IS level 2 route";
      }
      enum mgmt-r-type-isis-l1-ia {
        value 256;
        description "IS-IS level 1 inter-area route";
      }
      enum mgmt-r-type-bgp-int {
        value 512;
        description "iBGP route";
      }
      enum mgmt-r-type-bgp-ext {
        value 1024;
        description "eBGP route";
      }
      enum mgmt-r-type-bgp-loc {
        value 2048;
        description "BGP local route";
      }
      enum mgmt-r-type-nssa1 {
        value 4096;
        description "Type 1 NSSA route";
      }
      enum mgmt-r-type-nssa2 {
        value 8192;
        description "Type 2 NSSA route";
      }
      enum mgmt-r-type-i-grp2-int {
        value 16384;
        description "EIGRP internal route";
      }
      enum mgmt-r-type-i-grp2-ext {
        value 32768;
        description "EIGRP external route";
      }
    }
    description "Ospf route";
  }
  typedef Nsf-rtr {
    type enumeration {
      enum mgmt-nsf-rtr-none {
        description "None";
      }
      enum mgmt-nsf-rtr-requester {
        description "Requester";
      }
      enum mgmt-nsf-rtr-receiver {
        description "Receiver";
      }
    }
    description "Nsf rtr";
  }
  typedef Interface {
    type enumeration {
      enum mgmt-if-broadcast {
        value 1;
        description "Broadcast";
      }
      enum mgmt-if-nonbroadcast {
        value 2;
        description "Non broadcast multi access";
      }
      enum mgmt-if-point-to-point {
        value 3;
        description "Point to Point";
      }
      enum mgmt-if-point-to-m-point {
        value 4;
        description "Point to multipoint";
      }
      enum mgmt-if-p2mp-non-bcast {
        value 5;
        description "Non broadcast point to multipoint";
      }
      enum mgmt-if-virtual-link {
        value 6;
        description "Virtual link";
      }
      enum mgmt-if-sham-link {
        value 7;
        description "Sham link";
      }
      enum mgmt-if-loop-back {
        value 8;
        description "Loopback";
      }
    }
    description "Interface";
  }
  typedef Dr-bdr-state {
    type enumeration {
      enum mgmt-dbdr-none {
        description "None";
      }
      enum mgmt-dbdr-dr {
        description "Designated Router";
      }
      enum mgmt-dbdr-bdr {
        description "Backup Designated Router";
      }
      enum mgmt-dbdr-dr-other {
        description "Designated Router Other";
      }
    }
    description "Dr bdr state";
  }
  typedef Neighbor-state {
    type enumeration {
      enum mgmt-nbr-down {
        value 0;
        description "Down";
      }
      enum mgmt-nbr-attempt {
        value 1;
        description "Attempt";
      }
      enum mgmt-nbr-init {
        value 2;
        description "Init";
      }
      enum mgmt-nbr-2way {
        value 3;
        description "2 Way";
      }
      enum mgmt-nbr-ex-start {
        value 4;
        description "Exstart";
      }
      enum mgmt-nbr-ex-change {
        value 5;
        description "Exchange";
      }
      enum mgmt-nbr-load-ing {
        value 6;
        description "Loading";
      }
      enum mgmt-nbr-full {
        value 7;
        description "Full";
      }
      enum mgmt-nbr-sc-virtual {
        value 8;
        description "SCvirtual";
      }
    }
    description "Neighbor state";
  }
  typedef Mpls-te-opt-tlv {
    type enumeration {
      enum mpls-te-opt-tlv-type-none {
        value 0;
        description "None";
      }
      enum mpls-te-opt-tlv-type-srlg {
        value 1;
        description "SRLGs";
      }
      enum mpls-te-opt-tlv-type-bc {
        value 2;
        description "Bandwidth Constraints";
      }
      enum mpls-te-opt-tlv-type-ixcd {
        value 3;
        description "Intarface Switching Capability Descriptor";
      }
      enum mpls-te-opt-tlv-type-uni-delay {
        value 4;
        description "Unidirectional Link Delay";
      }
    }
    description "Mpls te opt tlv";
  }
  typedef Igpte-lib-bw-model {
    type enumeration {
      enum rdm {
        value 0;
        description "Russian Dolls Model";
      }
      enum mam {
        value 1;
        description "Maximum Allocation Model";
      }
      enum not-set {
        value 2;
        description "No model set";
      }
    }
    description "Bandwidth model";
  }
  typedef Link-subnet {
    type enumeration {
      enum mgmt-igp-subnet-type-none {
        value 0;
        description "None";
      }
      enum mgmt-igp-subnet-type-p2p {
        value 1;
        description "Point to Point";
      }
      enum mgmt-igp-subnet-type-broadcast {
        value 2;
        description "Broadcast";
      }
      enum mgmt-igp-subnet-type-nbma {
        value 3;
        description "Non Broadcast Multi Access";
      }
      enum mgmt-igp-subnet-type-p2mp {
        value 4;
        description "Point to multipoint";
      }
      enum mgmt-igp-subnet-type-loop-back {
        value 5;
        description "Loopback";
      }
      enum mgmt-igp-subnet-type-max {
        value 6;
        description "Unsupported";
      }
    }
    description "Link subnet";
  }
  typedef Lsa {
    type enumeration {
      enum mgmt-lsa-type-rtr {
        value 1;
        description "Router LSA";
      }
      enum mgmt-lsa-type-net {
        value 2;
        description "Network LSA";
      }
      enum mgmt-lsa-type-sum-net {
        value 3;
        description "Summary LSA";
      }
      enum mgmt-lsa-type-sum-asb {
        value 4;
        description "Summary-ASBR LSA";
      }
      enum mgmt-lsa-type-ext {
        value 5;
        description "AS external LSA";
      }
      enum mgmt-lsa-type-mospf {
        value 6;
        description "MOSPF LSA";
      }
      enum mgmt-lsa-type-7-ase {
        value 7;
        description "Type-7 External LSA";
      }
      enum mgmt-lsa-type-8-ignore {
        value 8;
        description "Invalid type";
      }
      enum mgmt-lsa-type-opq-link {
        value 9;
        description "Opaque link LSA";
      }
      enum mgmt-lsa-type-opq-area {
        value 10;
        description "Opaque Area LSA";
      }
      enum mgmt-lsa-type-opq-as {
        value 11;
        description "Opaque AS LSA";
      }
    }
    description "Lsa";
  }

  grouping OSPF-SH-IPFRR-TOPO-ENTRY {
    description "OSPF_IPFRR Topology Entry";
    leaf node-id {
      xr:xr-xml-map "ospf_mgmt:NodeID";
      type inet:ipv4-address;
      description "IPFRR Topology Node ID";
    }
    leaf distance {
      xr:xr-xml-map "ospf_mgmt:Distance";
      type uint32;
      description "IPFRR Topology Distance";
    }
    leaf distance-reverse {
      xr:xr-xml-map "ospf_mgmt:DistanceReverse";
      type uint32;
      description "IPFRR Topology Reverse Distance";
    }
    leaf type4 {
      xr:xr-xml-map "ospf_mgmt:Type4";
      type boolean;
      description "IPFRR Topoogy Type-4 entry";
    }
    leaf revision {
      xr:xr-xml-map "ospf_mgmt:Revision";
      type uint32;
      description "IPFRR Topology Revision";
    }
    leaf neighbor-sourced {
      xr:xr-xml-map "ospf_mgmt:NeighborSourced";
      type boolean;
      description "IPFRR Topology Neighbor Sourced";
    }
    leaf dr {
      xr:xr-xml-map "ospf_mgmt:DR";
      type boolean;
      description "IPFRR Topology DR entry";
    }
    leaf poison {
      xr:xr-xml-map "ospf_mgmt:Poison";
      type boolean;
      description "IPFRR Topology rSPT poison";
    }
  }

  grouping OSPF-SH-IPFRR-TOPO {
    description "OSPF IPFRR Topology Information";
    leaf ipfrr-topo-area-id {
      xr:xr-xml-map "ospf_mgmt:IPFRRTopoAreaID";
      type string {
        length "0..16";
      }
      description
        "Area ID string in decimal or dotted decimal
        format";
    }
    leaf ipfrr-router-id {
      xr:xr-xml-map "ospf_mgmt:IPFRRRouterID";
      type inet:ipv4-address;
      description "OSPF Router ID";
    }
    leaf ipfrr-area-revision {
      xr:xr-xml-map "ospf_mgmt:IPFRRAreaRevision";
      type uint32;
      description "IPFRR Topology Revision";
    }

    list ipfrr-topo {
      description "IPFRR Topology entries";
      uses OSPF-SH-IPFRR-TOPO-ENTRY;
    }
  }

  grouping OSPF-SH-STATS-AGGT {
    description "OSPF SH STATS AGGT";
    leaf sa-num-nbrs {
      xr:xr-xml-map "ospf_mgmt:sa_num_nbrs";
      type uint32;
      description "sa num nbrs";
    }
    leaf sa-num-nbrs-up {
      xr:xr-xml-map "ospf_mgmt:sa_num_nbrs_up";
      type uint32;
      description "sa num nbrs up";
    }
    leaf sa-num-intf {
      xr:xr-xml-map "ospf_mgmt:sa_num_intf";
      type uint32;
      description "sa num intf";
    }
    leaf sa-num-intf-up {
      xr:xr-xml-map "ospf_mgmt:sa_num_intf_up";
      type uint32;
      description "sa num intf up";
    }
    leaf sa-num-vintf-up {
      xr:xr-xml-map "ospf_mgmt:sa_num_vintf_up";
      type uint32;
      description "sa num vintf up";
    }
    leaf sa-num-slintf-up {
      xr:xr-xml-map "ospf_mgmt:sa_num_slintf_up";
      type uint32;
      description "sa num slintf up";
    }
    leaf sa-num-areas {
      xr:xr-xml-map "ospf_mgmt:sa_num_areas";
      type uint32;
      description "sa num areas";
    }
    leaf sa-lsa-cnt-type-rtr {
      xr:xr-xml-map "ospf_mgmt:sa_lsa_cnt_type_rtr";
      type uint32;
      description "sa lsa cnt type rtr";
    }
    leaf sa-lsa-cnt-type-net {
      xr:xr-xml-map "ospf_mgmt:sa_lsa_cnt_type_net";
      type uint32;
      description "sa lsa cnt type net";
    }
    leaf sa-lsa-cnt-type-sum-net {
      xr:xr-xml-map "ospf_mgmt:sa_lsa_cnt_type_sum_net";
      type uint32;
      description "sa lsa cnt type sum net";
    }
    leaf sa-lsa-cnt-type-sum-asb {
      xr:xr-xml-map "ospf_mgmt:sa_lsa_cnt_type_sum_asb";
      type uint32;
      description "sa lsa cnt type sum asb";
    }
    leaf sa-lsa-cnt-type-ase {
      xr:xr-xml-map "ospf_mgmt:sa_lsa_cnt_type_ase";
      type uint32;
      description "sa lsa cnt type ase";
    }
    leaf sa-lsa-cnt-type-mospf {
      xr:xr-xml-map "ospf_mgmt:sa_lsa_cnt_type_mospf";
      type uint32;
      description "sa lsa cnt type mospf";
    }
    leaf sa-lsa-cnt-type-7ase {
      xr:xr-xml-map "ospf_mgmt:sa_lsa_cnt_type_7ase";
      type uint32;
      description "sa lsa cnt type 7ase";
    }
    leaf sa-lsa-cnt-type-8-ignore {
      xr:xr-xml-map "ospf_mgmt:sa_lsa_cnt_type_8_ignore";
      type uint32;
      description "sa lsa cnt type 8 ignore";
    }
    leaf sa-lsa-cnt-type-opq-link {
      xr:xr-xml-map "ospf_mgmt:sa_lsa_cnt_type_opq_link";
      type uint32;
      description "sa lsa cnt type opq link";
    }
    leaf sa-lsa-cnt-type-opq-area {
      xr:xr-xml-map "ospf_mgmt:sa_lsa_cnt_type_opq_area";
      type uint32;
      description "sa lsa cnt type opq area";
    }
    leaf sa-lsa-cnt-type-opq-as {
      xr:xr-xml-map "ospf_mgmt:sa_lsa_cnt_type_opq_as";
      type uint32;
      description "sa lsa cnt type opq as";
    }
  }

  grouping OSPF-SH-SUMMARY-ADDRESS {
    description "OSPF Summary Address";
    leaf summary-prefix {
      xr:xr-xml-map "ospf_mgmt:SummaryPrefix";
      type inet:ipv4-address;
      description "Summary prefix";
    }
    leaf summary-mask {
      xr:xr-xml-map "ospf_mgmt:SummaryMask";
      type inet:ipv4-address;
      description "Summary Netmask";
    }
    leaf summary-metric {
      xr:xr-xml-map "ospf_mgmt:SummaryMetric";
      type uint32;
      description "Cost of Summary";
    }
    leaf summary-metric-type {
      xr:xr-xml-map "ospf_mgmt:SummaryMetricType";
      type Ex-metric;
      description "Type of Metric";
    }
    leaf summary-tag {
      xr:xr-xml-map "ospf_mgmt:SummaryTag";
      type uint32;
      description "Tag associated with this summary prefix";
    }
  }

  grouping OSPF-SH-DB-AS-SUM {
    description "OSPF AS Scope LSA Database Summary counters";

    list as-lsa-counter {
      description "Summary counter for AS scope LSAs";
      uses OSPF-SH-DB-SUM-CNTR;
    }
  }

  grouping OSPF-SH-DB-SUM-CNTR {
    description "OSPF Summary counters for a type";
    leaf lsa-type {
      xr:xr-xml-map "ospf_mgmt:LSAType";
      type Lsa;
      description "Type of LSAs";
    }
    leaf lsa-count {
      xr:xr-xml-map "ospf_mgmt:LSACount";
      type int32;
      description "Number of LSAs of this type";
    }
    leaf lsa-delete-count {
      xr:xr-xml-map "ospf_mgmt:LSADeleteCount";
      type int32;
      description "Number of deleted LSAs of this type";
    }
    leaf lsa-maxage-count {
      xr:xr-xml-map "ospf_mgmt:LSAMaxageCount";
      type int32;
      description "Number of MaxAged LSAs of this type";
    }
    leaf lsa-self-count {
      xr:xr-xml-map "ospf_mgmt:LSASelfCount";
      type int32;
      description "Number of self-generated LSAs";
    }
  }

  grouping OSPF-SH-DB-AREA-SUM {
    description "OSPF Area Scope Database Summary counters";
    leaf dbase-sum-area-id-string {
      xr:xr-xml-map "ospf_mgmt:Dbase_Sum_AreaIDString";
      type string {
        length "0..16";
      }
      description "Area id";
    }

    list area-lsa-counter {
      description "Summary counters for Area scope LSAs";
      uses OSPF-SH-DB-SUM-CNTR;
    }
  }

  grouping OSPF-SH-DATABASE {
    description "OSPF Database Information";

    container lsa-header {
      description "LSA header information";
      uses OSPF-SH-DB-HEADER;
    }
    leaf external-tag {
      xr:xr-xml-map "ospf_mgmt:ExternalTag";
      type uint32;
      description "Route Tag";
    }
    leaf link-count {
      xr:xr-xml-map "ospf_mgmt:LinkCount";
      type uint16;
      description "Number of links";
    }
  }

  grouping OSPF-SH-LSA-OPQ-ELL {
    description
      "OSPF Opaque-area type 8 ExtendedLink LSA
      Information";

    list tlv {
      description "List of TLVs";
      uses OSPF-SH-OPQ-TLV;
    }
  }

  grouping OSPF-SH-LSA-OPQ-EPL {
    description
      "OSPF Opaque-area type 128 ExtendedPrefix LSA
      Information";

    list tlv {
      description "List of TLVs";
      uses OSPF-SH-OPQ-TLV;
    }
  }

  grouping OSPF-SH-SR-SID-STLV {
    description "OSPF PCE-Discovery PCE Scope SubTLV";
    leaf sr-sid-length {
      xr:xr-xml-map "ospf_mgmt:SrSIDLength";
      type uint16;
      description "Length of sub-TLV";
    }
    leaf sr-sid-value {
      xr:xr-xml-map "ospf_mgmt:SrSIDValue";
      type uint32;
      description "SID Value";
    }
  }

  grouping OSPF-SH-OPQ-RI-SR-RANGE-TLV {
    description "OSPF SR Range TLV";

    container sidtlv {
      description "SID sub-TLV";
      uses OSPF-SH-SR-SID-STLV;
    }
    leaf sr-range-length {
      xr:xr-xml-map "ospf_mgmt:SrRangeLength";
      type uint16;
      description "Length of TLV";
    }
    leaf sr-range-size {
      xr:xr-xml-map "ospf_mgmt:SrRangeSize";
      type uint32;
      description "SR Range Size";
    }
  }

  grouping OSPF-SH-OPQ-RI-SR-ALGO-TLV {
    description "OSPF SR Algorithm TLV";
    leaf sr-algo-length {
      xr:xr-xml-map "ospf_mgmt:SrAlgoLength";
      type uint16;
      description "Length of TLV";
    }
    leaf sr-algo-value {
      xr:xr-xml-map "ospf_mgmt:SrAlgoValue";
      type yang:hex-string;
      description "SR Algorithms";
    }
  }

  grouping OSPF-SH-OPQ-RI-PCED-SCOPE-STLV {
    description "OSPF PCE-Discovery PCE Scope SubTLV";
    leaf lbit {
      xr:xr-xml-map "ospf_mgmt:LBit";
      type boolean;
      description "L Bit";
    }
    leaf rbit {
      xr:xr-xml-map "ospf_mgmt:RBit";
      type boolean;
      description "R Bit";
    }
    leaf rd-bit {
      xr:xr-xml-map "ospf_mgmt:RdBit";
      type boolean;
      description "Rd Bit";
    }
    leaf sbit {
      xr:xr-xml-map "ospf_mgmt:SBit";
      type boolean;
      description "S Bit";
    }
    leaf sd-bit {
      xr:xr-xml-map "ospf_mgmt:SdBit";
      type boolean;
      description "Sd Bit";
    }
    leaf ybit {
      xr:xr-xml-map "ospf_mgmt:YBit";
      type boolean;
      description "Y Bit";
    }
    leaf pref-l {
      xr:xr-xml-map "ospf_mgmt:PrefL";
      type uint8;
      description "Pref L";
    }
    leaf pref-r {
      xr:xr-xml-map "ospf_mgmt:PrefR";
      type uint8;
      description "Pref R";
    }
    leaf pref-s {
      xr:xr-xml-map "ospf_mgmt:PrefS";
      type uint8;
      description "Pref S";
    }
    leaf pref-y {
      xr:xr-xml-map "ospf_mgmt:PrefY";
      type uint8;
      description "Pref Y";
    }
    leaf all-scope-info-bits {
      xr:xr-xml-map "ospf_mgmt:AllScopeInfoBits";
      type uint32;
      description "PCE Scope Information";
    }
  }

  grouping OSPF-SH-OPQ-RI-PCE-IPV6-ADDR-STLV {
    description "PCE IPv6 Address SubTLV";
    leaf pceipv6-addr {
      xr:xr-xml-map "ospf_mgmt:PCEIPv6Addr";
      type inet:ipv6-address;
      description "PCE IPv6 Address";
    }
  }

  grouping OSPF-SH-OPQ-RI-PCE-IPV4-ADDR-STLV {
    description "PCE IPv4 Address SubTLV";
    leaf pceipv4-addr {
      xr:xr-xml-map "ospf_mgmt:PCEIPv4Addr";
      type inet:ipv4-address;
      description "PCE IPv4 Address";
    }
  }

  grouping OSPF-SH-OPQ-RI-PCE-ADDR-STLVS-UNION {
    description "OSPF PCE Address SubTLVs";

    container pce-addr-unknown-tlv {
      when "../pce-addr-type ="+
        " 'mgmt-ospf-opq-pce-addr-type-invalid'" {
          description
            "../PCEAddrType =
            'MGMT_OSPF_OPQ_PCE_ADDR_TYPE_INVALID'";
      }
      description "Unknown PCE Addr TLV";
      uses OSPF-SH-OPQ-RI-UNKNOWN-TLV;
    }

    container ipv4pce-addr {
      when "../pce-addr-type = 'mgmt-ospf-opq-pce-addr-type-ipv4'" {
        description
          "../PCEAddrType =
          'MGMT_OSPF_OPQ_PCE_ADDR_TYPE_IPV4'";
      }
      description "IPv4 PCE Address";
      uses OSPF-SH-OPQ-RI-PCE-IPV4-ADDR-STLV;
    }

    container ipv6pce-addr {
      when "../pce-addr-type = 'mgmt-ospf-opq-pce-addr-type-ipv6'" {
        description
          "../PCEAddrType =
          'MGMT_OSPF_OPQ_PCE_ADDR_TYPE_IPV6'";
      }
      description "IPv6 PCE Address";
      uses OSPF-SH-OPQ-RI-PCE-IPV6-ADDR-STLV;
    }
    leaf pce-addr-type {
      xr:xr-xml-map "ospf_mgmt:PCEAddrType";
      type Ospf-sh-opq-ri-pce-addr-types;
      description "PCEAddrType";
    }
  }

  grouping OSPF-SH-OPQ-RI-PCED-TLV {
    description "OSPF PCE Discovery TLV";

    container pced-addr {
      description "PCE Address";
      uses OSPF-SH-OPQ-RI-PCE-ADDR-STLVS-UNION;
    }

    container pced-scope {
      description "PCE Scope Information";
      uses OSPF-SH-OPQ-RI-PCED-SCOPE-STLV;
    }
    leaf pcedtlv-length {
      xr:xr-xml-map "ospf_mgmt:PCEDTLVLength";
      type uint16;
      description "Length of TLV";
    }
  }

  grouping OSPF-SH-OPQ-RI-RTRCAP-TLV {
    description "OSPF Router Capabilities TLV";
    leaf rtr-cap-tlv-length {
      xr:xr-xml-map "ospf_mgmt:RtrCapTLVLength";
      type uint16;
      description "Length of TLV";
    }
    leaf rtr-cap-graceful-restart {
      xr:xr-xml-map "ospf_mgmt:RtrCapGracefulRestart";
      type boolean;
      description "Graceful Restart Capability";
    }
    leaf rtr-cap-graceful-restart-helper {
      xr:xr-xml-map "ospf_mgmt:RtrCapGracefulRestartHelper";
      type boolean;
      description "Graceful Restart Helper Capability";
    }
    leaf rtr-cap-stub-rtr {
      xr:xr-xml-map "ospf_mgmt:RtrCapStubRtr";
      type boolean;
      description "Stub Router capability";
    }
    leaf rtr-cap-area-te {
      xr:xr-xml-map "ospf_mgmt:RtrCapAreaTE";
      type boolean;
      description "Traffic Engineering capability of area";
    }
    leaf rtr-cap-p2plan {
      xr:xr-xml-map "ospf_mgmt:RtrCapP2PLAN";
      type boolean;
      description "P2P LAN Capability";
    }
    leaf rtr-cap-te-exp {
      xr:xr-xml-map "ospf_mgmt:RtrCapTEExp";
      type boolean;
      description "TE Experimental bit";
    }
    leaf rtr-cap-all-bits {
      xr:xr-xml-map "ospf_mgmt:RtrCapAllBits";
      type uint32;
      description "All capability bits";
    }
    leaf rtr-cap-additional-info {
      xr:xr-xml-map "ospf_mgmt:RtrCapAdditionalInfo";
      type yang:hex-string;
      description "Additional Information in TLV";
    }
  }

  grouping OSPF-SH-OPQ-RI-UNKNOWN-TLV {
    description "OSPF Opaque Router Information TLV";
    leaf ri-gen-tlv-type {
      xr:xr-xml-map "ospf_mgmt:RIGenTLVType";
      type uint16;
      description "Type of TLV";
    }
    leaf ri-gen-tlv-length {
      xr:xr-xml-map "ospf_mgmt:RIGenTLVLength";
      type uint16;
      description "Length of TLV";
    }
    leaf ri-genvalue {
      xr:xr-xml-map "ospf_mgmt:RIGenValue";
      type yang:hex-string;
      description "Data in TLV";
    }
  }

  grouping OSPF-SH-OPQ-RI-TLVS-UNION {
    description "OSPF Router Information TLVs";

    container unknown-tlv {
      when "../ritlv-internal-type ="+
        " 'mgmt-ospf-opq-ri-tlv-type-unknown'" {
          description
            "../RITLVInternalType =
            'MGMT_OSPF_OPQ_RI_TLV_TYPE_UNKNOWN'";
      }
      description "Unknown Rtr Info TLV";
      uses OSPF-SH-OPQ-RI-UNKNOWN-TLV;
    }

    container rtr-cap-tlv {
      when "../ritlv-internal-type ="+
        " 'mgmt-ospf-opq-ri-tlv-type-rtrcap'" {
          description
            "../RITLVInternalType =
            'MGMT_OSPF_OPQ_RI_TLV_TYPE_RTRCAP'";
      }
      description "Rtr Cap TLV";
      uses OSPF-SH-OPQ-RI-RTRCAP-TLV;
    }

    container pcedtlv {
      when "../ritlv-internal-type ="+
        " 'mgmt-ospf-opq-ri-tlv-type-pce-discovery'" {
          description
            "../RITLVInternalType =
            'MGMT_OSPF_OPQ_RI_TLV_TYPE_PCEDISCOVERY'";
      }
      description "PCE Discovery TLV";
      uses OSPF-SH-OPQ-RI-PCED-TLV;
    }

    container sr-algo-tlv {
      when "../ritlv-internal-type ="+
        " 'mgmt-ospf-opq-ri-tlv-type-sr-algo'" {
          description
            "../RITLVInternalType =
            'MGMT_OSPF_OPQ_RI_TLV_TYPE_SR_ALGO'";
      }
      description "SR Algorithm TLV";
      uses OSPF-SH-OPQ-RI-SR-ALGO-TLV;
    }

    container sr-range-tlv {
      when "../ritlv-internal-type ="+
        " 'mgmt-ospf-opq-ri-tlv-type-sr-range'" {
          description
            "../RITLVInternalType =
            'MGMT_OSPF_OPQ_RI_TLV_TYPE_SR_RANGE'";
      }
      description "SR Range TLV";
      uses OSPF-SH-OPQ-RI-SR-RANGE-TLV;
    }
    leaf ritlv-internal-type {
      xr:xr-xml-map "ospf_mgmt:RITLVInternalType";
      type Ospf-sh-opq-ri-tlv-types;
      description "RITLVInternalType";
    }
  }

  grouping OSPF-SH-LSA-OPQ-RI {
    description "OSPF Router Information LSA";
    leaf opaque-rilsa-scope {
      xr:xr-xml-map "ospf_mgmt:OpaqueRILSAScope";
      type Ospf-lsa-opq-ri-scope;
      description
        "Opaque LSA flooding scope, a.k.a., Opaque LSA
        Type";
    }
    leaf opaque-ri-interface-name {
      xr:xr-xml-map "ospf_mgmt:OpaqueRIInterfaceName";
      type xr:Interface-name;
      description
        "Interface on which this Link-Local Opaque link
        LSA is received";
    }

    list opaque-ritlv {
      description "Router Information TLV";
      uses OSPF-SH-OPQ-RI-TLVS-UNION;
    }
  }

  grouping OSPF-SH-LSA-OPQ-GRACE {
    description "OSPF Opaque-link type 3 grace LSA Information";
    leaf grace-period {
      xr:xr-xml-map "ospf_mgmt:GracePeriod";
      type uint32;
      description
        "The amount of time the router's neighbor should
        advertise it fully adjacent (s)";
    }
    leaf grace-reason {
      xr:xr-xml-map "ospf_mgmt:GraceReason";
      type Ospf-gr-reason;
      description "Reason for router restart";
    }
    leaf ip-address {
      xr:xr-xml-map "ospf_mgmt:IPAddress";
      type inet:ipv4-address;
      description
        "IP interface address on the subnet associated
        with the grace LSA";
    }
  }

  grouping OSPF-SH-OPQ-SUBTLV {
    description "OSPF Opaque LSA Sub-TLV Information";
    leaf sub-tlv-type {
      xr:xr-xml-map "ospf_mgmt:SubTLVType";
      type Stlv;
      description "Type of sub TLV";
    }
    leaf sub-tlv-length {
      xr:xr-xml-map "ospf_mgmt:SubTLVLength";
      type uint16;
      description "Length of sub TLV";
    }
    leaf sub-tlv-value {
      xr:xr-xml-map "ospf_mgmt:SubTLVValue";
      type yang:hex-string;
      description "Value of sub TLV";
    }
  }

  grouping OSPF-SH-OPQ-TLV {
    description "OSPF Opaque LSA TLV Information";
    leaf tlv-type {
      xr:xr-xml-map "ospf_mgmt:TLVType";
      type uint16;
      description "Type of top-level TLV";
    }
    leaf tlv-length {
      xr:xr-xml-map "ospf_mgmt:TLVLength";
      type uint16;
      description "Length of top-level TLV";
    }
    leaf mpls-router-id {
      xr:xr-xml-map "ospf_mgmt:MPLS_RouterID";
      type uint32;
      description "MPLS-TE Router ID";
    }
    leaf mpls-dste-link {
      xr:xr-xml-map "ospf_mgmt:MPLS_DSTE_Link";
      type boolean;
      description "MPLS DS-TE supported";
    }
    leaf tlv-data {
      xr:xr-xml-map "ospf_mgmt:TlvData";
      type yang:hex-string;
      description "TLV direct data";
    }

    list te-link-sub-tlv {
      description "List of Sub-TLVs";
      uses OSPF-SH-OPQ-SUBTLV;
    }
  }

  grouping OSPF-SH-LSA-OPQ-RRR {
    description "OSPF Opaque-area type 1 MPLS-TE LSA Information";

    list tlv {
      description "List of TLVs";
      uses OSPF-SH-OPQ-TLV;
    }
  }

  grouping OSPF-SH-LSA-OPQ-LINK {
    description "OSPF Opaque-link LSA Information";
    leaf opaque-interface-name {
      xr:xr-xml-map "ospf_mgmt:OpaqueInterfaceName";
      type xr:Interface-name;
      description
        "Interface on which the Opaque link LSA is
        received";
    }
  }

  grouping OSPF-SH-LSA-EX-TOS {
    description
      "OSPF External Type of service specific
      Information";
    leaf external-metric {
      xr:xr-xml-map "ospf_mgmt:ExternalMetric";
      type uint32;
      description "Cost of this route";
    }
    leaf external-metric-type {
      xr:xr-xml-map "ospf_mgmt:ExternalMetricType";
      type Ex-metric;
      description "External LSA metric type";
    }
    leaf external-tos {
      xr:xr-xml-map "ospf_mgmt:ExternalTOS";
      type uint32;
      description "Type of Service";
    }
    leaf forwarding-address {
      xr:xr-xml-map "ospf_mgmt:ForwardingAddress";
      type inet:ipv4-address;
      description "Forwarding Address";
    }
    leaf external-tag {
      xr:xr-xml-map "ospf_mgmt:ExternalTag";
      type uint32;
      description "Route Tag";
    }
  }

  grouping OSPF-SH-LSA-EXTERNAL {
    description "OSPF External LSA";
    leaf external-prefix-length {
      xr:xr-xml-map "ospf_mgmt:ExternalPrefixLength";
      type uint32;
      description "Prefix length";
    }
    leaf internal-external-lsa {
      xr:xr-xml-map "ospf_mgmt:InternalExternalLSA";
      type boolean;
      description "If true, internal max-metric LSA";
    }

    list external-tos-metric {
      description "Type of service information";
      uses OSPF-SH-LSA-EX-TOS;
    }
  }

  grouping OSPF-SH-LSA-SUMMARY {
    description "OSPF Summary LSA";
    leaf summary-prefix-length {
      xr:xr-xml-map "ospf_mgmt:SummaryPrefixLength";
      type uint32;
      description "Summary LSA prefix length";
    }
    leaf internal-sum-lsa {
      xr:xr-xml-map "ospf_mgmt:InternalSumLSA";
      type boolean;
      description "If true, internal max-metric LSA";
    }
    leaf-list summary-lsa-metric {
      xr:xr-xml-map "ospf_mgmt:SummaryLSAMetric";
      type uint32;
      description "Metric";
    }
  }

  grouping OSPF-SH-LSA-NETWORK {
    description "OSPF Network LSA";
    leaf network-prefix-length {
      xr:xr-xml-map "ospf_mgmt:NetworkPrefixLength";
      type uint32;
      description "Network prefix length";
    }
    leaf-list neighbor-router {
      xr:xr-xml-map "ospf_mgmt:NeighborRouterList";
      type inet:ipv4-address;
      description "Neighbor router list";
    }
  }

  grouping OSPF-SH-TOS-METRIC {
    description "OSPF Router LSA TOS Metric";
    leaf router-tos {
      xr:xr-xml-map "ospf_mgmt:RouterTOS";
      type uint16;
      description "Type of Service";
    }
    leaf tos-cost {
      xr:xr-xml-map "ospf_mgmt:TOSCost";
      type uint16;
      description "Type of service specific metric";
    }
  }

  grouping OSPF-SH-LINK {
    description "OSPF Router LSA Links";
    leaf link-id {
      xr:xr-xml-map "ospf_mgmt:LinkID";
      type inet:ipv4-address;
      description "Link ID";
    }
    leaf link-data {
      xr:xr-xml-map "ospf_mgmt:LinkData";
      type inet:ipv4-address;
      description "Link Data";
    }
    leaf link-type {
      xr:xr-xml-map "ospf_mgmt:LinkType";
      type Ospf-link-types;
      description "Type of link";
    }
    leaf link-metric {
      xr:xr-xml-map "ospf_mgmt:LinkMetric";
      type uint16;
      description "Cost for using this link";
    }

    list link-tos {
      description "List of type of service metrics";
      uses OSPF-SH-TOS-METRIC;
    }
  }

  grouping OSPF-SH-LSA-ROUTER {
    description "OSPF Router LSA";
    leaf router-asbr {
      xr:xr-xml-map "ospf_mgmt:RouterASBR";
      type boolean;
      description
        "If True, router is an Autonomous system Border
        Router";
    }
    leaf router-abr {
      xr:xr-xml-map "ospf_mgmt:RouterABR";
      type boolean;
      description "If True, router is an Area Border Router";
    }
    leaf internal-lsa {
      xr:xr-xml-map "ospf_mgmt:InternalLSA";
      type boolean;
      description "If true, internal LSA";
    }

    list link {
      description "List of links in this LSA";
      uses OSPF-SH-LINK;
    }

    list internal-link {
      description "List of links for internal LSA";
      uses OSPF-SH-LINK;
    }
  }

  grouping OSPF-LSA-INTERNAL-UNION {
    description "LSA internal information for an LSA";

    container router-lsa-type {
      when "../internal-lsa-type = 'mgmt-rtr-type'" {
        description "../InternalLSAType = 'MGMT_RTR_TYPE'";
      }
      description "Router LSA";
      uses OSPF-SH-LSA-ROUTER;
    }

    container network-lsa-type {
      when "../internal-lsa-type = 'mgmt-ntwk-type'" {
        description "../InternalLSAType = 'MGMT_NTWK_TYPE'";
      }
      description "Network LSA";
      uses OSPF-SH-LSA-NETWORK;
    }

    container summary-lsa-type {
      when "../internal-lsa-type = 'mgmt-sum-type'" {
        description "../InternalLSAType = 'MGMT_SUM_TYPE'";
      }
      description "Summary LSA";
      uses OSPF-SH-LSA-SUMMARY;
    }

    container external-lsa-type {
      when "../internal-lsa-type = 'mgmt-ext-type'" {
        description "../InternalLSAType = 'MGMT_EXT_TYPE'";
      }
      description "External LSA";
      uses OSPF-SH-LSA-EXTERNAL;
    }

    container opaque-link-lsa-type {
      when "../internal-lsa-type = 'mgmt-opq-link-type'" {
        description "../InternalLSAType = 'MGMT_OPQ_LINK_TYPE'";
      }
      description "Opaque-Link LSA";
      uses OSPF-SH-LSA-OPQ-LINK;
    }

    container opaque-mpls-te-lsa-type {
      when "../internal-lsa-type = 'mgmt-opq-rrr-type'" {
        description "../InternalLSAType = 'MGMT_OPQ_RRR_TYPE'";
      }
      description "Opaque-Area, opaque type 1 LSA";
      uses OSPF-SH-LSA-OPQ-RRR;
    }

    container opaque-grace-lsa {
      when "../internal-lsa-type = 'mgmt-opq-gr-type'" {
        description "../InternalLSAType = 'MGMT_OPQ_GR_TYPE'";
      }
      description "Opaque-link, opaque type 3 Grace LSA";
      uses OSPF-SH-LSA-OPQ-GRACE;
    }

    container opaque-router-info-lsa-type {
      when "../internal-lsa-type = 'mgmt-opq-ri-type'" {
        description "../InternalLSAType = 'MGMT_OPQ_RI_TYPE'";
      }
      description "Opaque Router Information LSA";
      uses OSPF-SH-LSA-OPQ-RI;
    }

    container opaque-ep-lsa-type {
      when "../internal-lsa-type = 'mgmt-opq-epl-type'" {
        description "../InternalLSAType = 'MGMT_OPQ_EPL_TYPE'";
      }
      description "Extende Prefix LSA type";
      uses OSPF-SH-LSA-OPQ-EPL;
    }

    container opaque-el-lsa-type {
      when "../internal-lsa-type = 'mgmt-opq-ell-type'" {
        description "../InternalLSAType = 'MGMT_OPQ_ELL_TYPE'";
      }
      description "Extended Link LSA type";
      uses OSPF-SH-LSA-OPQ-ELL;
    }
    leaf internal-lsa-type {
      xr:xr-xml-map "ospf_mgmt:InternalLSAType";
      type Ospf-internal-lsa-types;
      description "InternalLSAType";
    }
  }

  grouping OSPF-SH-DB-NOT-DELETE {
    description "Reason why LSA is not deleted";
    leaf free-time {
      xr:xr-xml-map "ospf_mgmt:FreeTime";
      type uint32;
      description
        "The amount of time since the last check was made
        to free this LSA (s)";
    }
    leaf no-delete {
      xr:xr-xml-map "ospf_mgmt:NoDelete";
      type boolean;
      description
        "If true, the reason not to delete this LSA is
        because delete flag not set on this LSA";
    }
    leaf neighbor-exchange {
      xr:xr-xml-map "ospf_mgmt:NeighborExchange";
      type boolean;
      description
        "If true, the reason  not to delete this LSA is
        because neighbor is in exchange state";
    }
    leaf routing-table {
      xr:xr-xml-map "ospf_mgmt:RoutingTable";
      type boolean;
      description
        "If true, the reason  not to delete this LSA is
        because it has a contributing entry in the
        routing table";
    }
    leaf acknowledgement {
      xr:xr-xml-map "ospf_mgmt:Acknowledgement";
      type boolean;
      description
        "If true, the reason not to delete this LSA is
        because it's Acknowledgement list is not empty";
    }
    leaf maximum-age {
      xr:xr-xml-map "ospf_mgmt:MaximumAge";
      type boolean;
      description
        "If true, the reason not to delete this LSA is
        because it is in Maxage Queue";
    }
    leaf partial-spf {
      xr:xr-xml-map "ospf_mgmt:PartialSPF";
      type boolean;
      description
        "If true, the reason not to delete this LSA is
        because it is in partial SPF queue";
    }
    leaf flood-pending {
      xr:xr-xml-map "ospf_mgmt:FloodPending";
      type boolean;
      description
        "If true, the reason not to delete this LSA is
        because waiting for flooding or retransmission";
    }
    leaf rate-limit {
      xr:xr-xml-map "ospf_mgmt:RateLimit";
      type boolean;
      description
        "If true, the reason not to delete this LSA is
        because waiting for next wait-interval to expire";
    }
    leaf nsr-ack-pending {
      xr:xr-xml-map "ospf_mgmt:NSRAckPending";
      type boolean;
      description
        "If true, the reason not to delete this LSA is
        because NSR ACK from standby is pending";
    }
    leaf sum-orig-pending {
      xr:xr-xml-map "ospf_mgmt:SumOrigPending";
      type boolean;
      description
        "If true, the reason not to delete this LSA is
        because it is pending summary LSA originating";
    }
    leaf nsr-flood-required {
      xr:xr-xml-map "ospf_mgmt:NSRFloodRequired";
      type boolean;
      description
        "If true, the reason not to delete this LSA is
        because it is pending flooding on switchover";
    }
  }

  grouping OSPF-SH-DB-THROTTLE-TIMER {
    description "OSPF LSA throttle timer table information";
    leaf timer-location {
      xr:xr-xml-map "ospf_mgmt:TimerLocation";
      type Timer-table;
      description "Timer table";
    }
    leaf timer-type {
      xr:xr-xml-map "ospf_mgmt:TimerType";
      type Timer;
      description "Timer type";
    }
    leaf second-table-index {
      xr:xr-xml-map "ospf_mgmt:SecondTableIndex";
      type uint8;
      description "Second table index";
    }
    leaf minute-table-index {
      xr:xr-xml-map "ospf_mgmt:MinuteTableIndex";
      type uint8;
      description "Minute table index";
    }
    leaf last-inst-second-table-index {
      xr:xr-xml-map "ospf_mgmt:LastInstSecondTableIndex";
      type uint8;
      description "Last Second table index processed";
    }
    leaf last-inst-minute-table-index {
      xr:xr-xml-map "ospf_mgmt:LastInstMinuteTableIndex";
      type uint8;
      description "Last Minute table index processed";
    }
  }

  grouping OSPF-SH-DB-DETAIL {
    description "OSPF Detailed LSA Database Information";

    container lsa-throttle-timer {
      description "LSA throttle timer table information";
      uses OSPF-SH-DB-THROTTLE-TIMER;
    }

    container lsa-last-updated-time {
      description "Time LSA was last updated";
      uses OSPF-SH-TIME;
    }

    container lsadb-base-time-stamp {
      description "Current time stamp";
      uses OSPF-SH-TIME;
    }

    container not-delete {
      description "Reason why LSA is not deleted";
      uses OSPF-SH-DB-NOT-DELETE;
    }
    leaf tos-capable {
      xr:xr-xml-map "ospf_mgmt:TOSCapable";
      type boolean;
      description
        "If true, type of service capable indicated by
        LSA's option field";
    }
    leaf nssa-translation {
      xr:xr-xml-map "ospf_mgmt:NSSATranslation";
      type boolean;
      description
        "If true,  capable of type 7 to 5 translation
        indicated by LSA's option field";
    }
    leaf demand-circuit {
      xr:xr-xml-map "ospf_mgmt:DemandCircuit";
      type boolean;
      description
        "If true, capable of demand circuit as indicated
        by LSA's option field";
    }
    leaf dn-bit {
      xr:xr-xml-map "ospf_mgmt:DNBit";
      type boolean;
      description
        "if true, DN bit set on the summary LSA indicated
        by LSA's option field";
    }
    leaf lsa-rate-limit-due-time {
      xr:xr-xml-map "ospf_mgmt:LSARateLimitDueTime";
      type uint32;
      description "Due time for rate-limit timer (ms)";
    }
    leaf lsadb-base-clock {
      xr:xr-xml-map "ospf_mgmt:LSADBBaseClock";
      type uint64;
      description "Clock stamp since boot";
    }
    leaf routing-bit {
      xr:xr-xml-map "ospf_mgmt:RoutingBit";
      type boolean;
      description "If true, Routing Bit set on the LSA";
    }
    leaf advertising-router-reachable {
      xr:xr-xml-map "ospf_mgmt:AdvertisingRouterReachable";
      type boolean;
      description "If true, Advertising Router is reachable";
    }
    leaf length {
      xr:xr-xml-map "ospf_mgmt:Length";
      type uint16;
      description "Length of the LSA";
    }
    leaf sum-origin {
      xr:xr-xml-map "ospf_mgmt:SumOrigin";
      type uint16;
      description "Summary Origin";
    }
    leaf ase-origin {
      xr:xr-xml-map "ospf_mgmt:AseOrigin";
      type uint16;
      description "External Origin";
    }
    leaf in-sync {
      xr:xr-xml-map "ospf_mgmt:InSync";
      type uint8;
      description "Not In Sync With Active";
    }
    leaf lsa-prefix-priority {
      xr:xr-xml-map "ospf_mgmt:LSAPrefixPriority";
      type uint8;
      description "Current LSA prefix priority";
    }
    leaf new-lsa-prefix-priority {
      xr:xr-xml-map "ospf_mgmt:NewLSAPrefixPriority";
      type uint8;
      description "New LSA prefix priority";
    }
    leaf lsa-flood-required-post-fail-over {
      xr:xr-xml-map "ospf_mgmt:LSAFloodRequiredPostFailOver";
      type boolean;
      description "LSA flood required after FO";
    }
  }

  grouping OSPF-SH-DB-HEADER {
    description "OSPF LSA Database Header";
    leaf ls-type {
      xr:xr-xml-map "ospf_mgmt:LSType";
      type Lsa;
      description "LSA type";
    }
    leaf lsid {
      xr:xr-xml-map "ospf_mgmt:LSID";
      type inet:ipv4-address;
      description "LS ID";
    }
    leaf advertising-router {
      xr:xr-xml-map "ospf_mgmt:AdvertisingRouter";
      type inet:ipv4-address;
      description "Router ID of Advertising Router";
    }
    leaf lsa-area-id {
      xr:xr-xml-map "ospf_mgmt:LSAAreaID";
      type string {
        length "0..16";
      }
      description "Area ID in decimal or dotted-decimal format";
    }
    leaf lsa-age {
      xr:xr-xml-map "ospf_mgmt:LSAAge";
      type uint16;
      description "LSA's Age (s)";
    }
    leaf dn-age-lsa {
      xr:xr-xml-map "ospf_mgmt:DNAgeLSA";
      type boolean;
      description "If true, Do Not Age this LSA";
    }
    leaf nsf {
      xr:xr-xml-map "ospf_mgmt:NSF";
      type boolean;
      description "If true,  LSA received from neighbor during NSF";
    }
    leaf sequence-number {
      xr:xr-xml-map "ospf_mgmt:SequenceNumber";
      type uint32;
      description "Current Sequence number";
    }
    leaf checksum {
      xr:xr-xml-map "ospf_mgmt:Checksum";
      type uint16;
      description "Checksum value";
    }
  }

  grouping OSPF-SH-DATABASE-DETAIL {
    description "OSPF Database Information";

    container lsa-header {
      description "Header information";
      uses OSPF-SH-DB-HEADER;
    }

    container lsa-detail-data {
      description "Detailed LSA Information";
      uses OSPF-SH-DB-DETAIL;
    }

    container lsa-internal-data {
      description "Information pertaining to a specific LSA type";
      uses OSPF-LSA-INTERNAL-UNION;
    }
  }

  grouping OSPF-SH-SLINK-NEIGHBOR {
    description "Sham Link Neighbor Information";

    container sham-link-retransmissoin {
      description "Neighbor retransmission info";
      uses OSPF-SH-NEIGHBOR-RETRANS;
    }
    leaf sham-link-suppress-hello {
      xr:xr-xml-map "ospf_mgmt:ShamLinkSuppressHello";
      type boolean;
      description "If true Hellos suppressed";
    }
    leaf sham-link-state {
      xr:xr-xml-map "ospf_mgmt:ShamLinkState";
      type Neighbor-state;
      description "Adjacency state";
    }
  }

  grouping OSPF-SH-SHAM-LINKS {
    description "OSPF Sham Link";

    container sham-link-neighbor {
      description "Neighbor information";
      uses OSPF-SH-SLINK-NEIGHBOR;
    }
    leaf sham-link-name-xr {
      xr:xr-xml-map "ospf_mgmt:sham-link-name-xr";
      type string;
      description "Sham link name";
    }
    leaf sham-link-neighbor-id {
      xr:xr-xml-map "ospf_mgmt:ShamLinkNeighborID";
      type inet:ipv4-address;
      description "Neighbor on other end of this sham link";
    }
    leaf sham-link-source-address {
      xr:xr-xml-map "ospf_mgmt:ShamLinkSourceAddress";
      type inet:ipv4-address;
      description "Sham-link source";
    }
    leaf sham-link-dest-address {
      xr:xr-xml-map "ospf_mgmt:ShamLinkDestAddress";
      type inet:ipv4-address;
      description "Sham-link dest";
    }
    leaf sham-link-state {
      xr:xr-xml-map "ospf_mgmt:ShamLinkState";
      type Ospf-interface-state;
      description "OSPF interface state for the sham link";
    }
    leaf sham-link-demand-circuit {
      xr:xr-xml-map "ospf_mgmt:ShamLinkDemandCircuit";
      type boolean;
      description "If true, the link runs as demand circuit";
    }
    leaf sham-link-dc-bitless-lsa {
      xr:xr-xml-map "ospf_mgmt:ShamLinkDCBitlessLSA";
      type uint32;
      description "Number of LSA's with demand circuit bit not set";
    }
    leaf sham-link-ifindex {
      xr:xr-xml-map "ospf_mgmt:ShamLinkIfindex";
      type uint32;
      description "Sham-link ifindex";
    }
    leaf sham-link-area {
      xr:xr-xml-map "ospf_mgmt:ShamLinkArea";
      type string;
      description "Area id";
    }
    leaf sham-link-cost {
      xr:xr-xml-map "ospf_mgmt:ShamLinkCost";
      type uint16;
      description "Cost of the sham link";
    }
    leaf sham-link-transmission-delay {
      xr:xr-xml-map "ospf_mgmt:ShamLinkTransmissionDelay";
      type uint16;
      units "second";
      description "Transmission delay in seconds";
    }
    leaf sham-link-hello-interval {
      xr:xr-xml-map "ospf_mgmt:ShamLinkHelloInterval";
      type uint32;
      description "Hello interval (s)";
    }
    leaf sham-link-hello-interval-ms {
      xr:xr-xml-map "ospf_mgmt:ShamLinkHelloIntervalMs";
      type uint32;
      description "Hello interval (ms)";
    }
    leaf sham-link-dead-interval {
      xr:xr-xml-map "ospf_mgmt:ShamLinkDeadInterval";
      type uint32;
      description "Dead interval (s)";
    }
    leaf sham-link-wait-interval {
      xr:xr-xml-map "ospf_mgmt:ShamLinkWaitInterval";
      type uint32;
      description "Wait interval (s)";
    }
    leaf sham-link-retransmission-interval {
      xr:xr-xml-map "ospf_mgmt:ShamLinkRetransmissionInterval";
      type uint32;
      description "Retransmission interval (s)";
    }
    leaf sham-link-next-hello {
      xr:xr-xml-map "ospf_mgmt:ShamLinkNextHello";
      type uint32;
      description "Time until next hello (s)";
    }
    leaf sham-link-next-hello-ms {
      xr:xr-xml-map "ospf_mgmt:ShamLinkNextHelloMs";
      type uint32;
      description "Time until next hello (ms)";
    }
    leaf sham-link-passive {
      xr:xr-xml-map "ospf_mgmt:ShamLinkPassive";
      type boolean;
      description "If true, interface is passive";
    }
    leaf sham-link-authentication-type {
      xr:xr-xml-map "ospf_mgmt:ShamLinkAuthenticationType";
      type Authentication;
      description "Authentication type";
    }
    leaf sham-link-youngest-md-key {
      xr:xr-xml-map "ospf_mgmt:ShamLinkYoungestMDKey";
      type boolean;
      description "If true, MD key configured";
    }
    leaf sham-link-youngest-md-key-id {
      xr:xr-xml-map "ospf_mgmt:ShamLinkYoungestMDKeyID";
      type uint16;
      description "Youngest MD key ID";
    }
    leaf sham-link-old-md-key-count {
      xr:xr-xml-map "ospf_mgmt:ShamLinkOldMDKeyCount";
      type uint32;
      description
        "Number of neighbors still using the old key
        (rollover in progress)";
    }
    leaf sham-link-keychain-id {
      xr:xr-xml-map "ospf_mgmt:ShamLinkKeychainID";
      type uint64;
      description "Sham Link Keychain ID";
    }
    leaf sham-link-nsf-enabled {
      xr:xr-xml-map "ospf_mgmt:ShamLinkNSFEnabled";
      type boolean;
      description "If true, NSF enabled";
    }
    leaf sham-link-nsf {
      xr:xr-xml-map "ospf_mgmt:ShamLinkNSF";
      type boolean;
      description
        "If true, NSF restart in progress on the sham
        link";
    }
    leaf sham-link-last-nsf {
      xr:xr-xml-map "ospf_mgmt:ShamLinkLastNSF";
      type uint32;
      units "second";
      description "Time in seconds since last NSF";
    }
    leaf-list sham-link-md-key {
      xr:xr-xml-map "ospf_mgmt:ShamLinkMDKeyList";
      type uint16;
      description "List of old MD keys (if any)";
    }
  }

  grouping OSPF-SH-DOMAIN-ID-ENTRY {
    description "OSPF Domain ID";
    leaf domain-id-type {
      xr:xr-xml-map "ospf_mgmt:DomainIDType";
      type uint16;
      description "Domain ID Type";
    }
    leaf domain-id-value {
      xr:xr-xml-map "ospf_mgmt:DomainIDValue";
      type yang:hex-string;
      description "Domain ID value";
    }
  }

  grouping OSPF-SH-DOMAIN-ID {
    description "OSPF Domain ID entries";

    container primary-domain-id {
      description "Primary Domain ID";
      uses OSPF-SH-DOMAIN-ID-ENTRY;
    }

    list secondary-domain-id {
      description "List of secondary domain IDs";
      uses OSPF-SH-DOMAIN-ID-ENTRY;
    }
  }

  grouping OSPF-SH-MAX-METRIC {
    description "OSPF Max-metric Information";

    container maximum-metric-time-unset {
      description "Time max-metric condition was cleared";
      uses OSPF-SH-TIME;
    }
    leaf max-metric-reason {
      xr:xr-xml-map "ospf_mgmt:MaxMetricReason";
      type uint8;
      description "Max-metric reason";
    }
    leaf max-metric-enabled {
      xr:xr-xml-map "ospf_mgmt:MaxMetricEnabled";
      type boolean;
      description "Max-metric enabled";
    }
    leaf unset-maximum-metric {
      xr:xr-xml-map "ospf_mgmt:UnsetMaximumMetric";
      type boolean;
      description
        "If true, BGP is up, no maximum metric Router LSA";
    }
    leaf saved-unset-maximum-metric {
      xr:xr-xml-map "ospf_mgmt:SavedUnsetMaximumMetric";
      type boolean;
      description "Saved UnsetMaximumMetric";
    }
    leaf maximum-metric-start-time {
      xr:xr-xml-map "ospf_mgmt:MaximumMetricStartTime";
      type uint32;
      description
        "Time remaining until we will start using normal
        metrics (s)";
    }
    leaf saved-startup-time {
      xr:xr-xml-map "ospf_mgmt:SavedStartupTime";
      type uint32;
      description "Hold time configured (s)";
    }
    leaf maximum-metric-include-stubs {
      xr:xr-xml-map "ospf_mgmt:MaximumMetricIncludeStubs";
      type boolean;
      description "If true, set max-metric in stub links";
    }
    leaf maximum-metric-summary-lsa {
      xr:xr-xml-map "ospf_mgmt:MaximumMetricSummaryLSA";
      type boolean;
      description "If true, advertise max-metric in summary-LSAs";
    }
    leaf maximum-metric-summary-lsa-metric {
      xr:xr-xml-map "ospf_mgmt:MaximumMetricSummaryLSAMetric";
      type uint32;
      description "Max-metric value to advertise in summary-LSAs";
    }
    leaf maximum-metric-external-lsa {
      xr:xr-xml-map "ospf_mgmt:MaximumMetricExternalLSA";
      type boolean;
      description "If true, advertise max-metric in external-LSAs";
    }
    leaf maximum-metric-external-lsa-metric {
      xr:xr-xml-map "ospf_mgmt:MaximumMetricExternalLSAMetric";
      type uint32;
      description "Max-metric value to advertise in external-LSAs";
    }
    leaf maximum-metric-originated-for {
      xr:xr-xml-map "ospf_mgmt:MaximumMetricOriginatedFor";
      type uint32;
      description "Time max-metric was used for";
    }
    leaf maximum-metric-unset-reason {
      xr:xr-xml-map "ospf_mgmt:MaximumMetricUnsetReason";
      type Max-metric-unset-reason;
      description "Max-metric unset reason";
    }
  }

  grouping OSPF-SH-SUMMARY {
    description "OSPF Summary";

    container domain-id {
      description "Domain ID information";
      uses OSPF-SH-DOMAIN-ID;
    }
    leaf role-standby {
      xr:xr-xml-map "ospf_mgmt:RoleStandby";
      type boolean;
      description "If true, Role is Standby, Active otherwise";
    }
    leaf role {
      xr:xr-xml-map "ospf_mgmt:Role";
      type uint32;
      description "Role, V1/V2 Active/Standby";
    }
    leaf nsr-enabled {
      xr:xr-xml-map "ospf_mgmt:NSREnabled";
      type boolean;
      description "If true, NSR is enabled";
    }
    leaf nsr-switchover-on-restart {
      xr:xr-xml-map "ospf_mgmt:NSRSwitchoverOnRestart";
      type boolean;
      description
        "Trigger RP Switchover on detectable process
        restart";
    }
    leaf igp-intact-on {
      xr:xr-xml-map "ospf_mgmt:IGPIntactOn";
      type boolean;
      description "If true, running in IGP-Intact mode";
    }
    leaf router-id {
      xr:xr-xml-map "ospf_mgmt:RouterID";
      type inet:ipv4-address;
      description "Router ID";
    }
    leaf tos-options {
      xr:xr-xml-map "ospf_mgmt:TOSOptions";
      type uint8;
      description "Type of Service supported";
    }
    leaf opaque-capable {
      xr:xr-xml-map "ospf_mgmt:OpaqueCapable";
      type boolean;
      description "Opaque LSA capable";
    }
    leaf area-border-router {
      xr:xr-xml-map "ospf_mgmt:AreaBorderRouter";
      type boolean;
      description "If true, is an Area Border Router";
    }
    leaf as-border-router {
      xr:xr-xml-map "ospf_mgmt:ASBorderRouter";
      type boolean;
      description "If true, is an AS Border Router";
    }
    leaf vrf-lite-enabled {
      xr:xr-xml-map "ospf_mgmt:VRFLiteEnabled";
      type boolean;
      description "If true, vrf lite is enabled";
    }
    leaf maximum-metric-start {
      xr:xr-xml-map "ospf_mgmt:MaximumMetricStart";
      type boolean;
      description
        "If true, originate Router LSA with maximum
        metric";
    }
    leaf maximum-metric-start-timer {
      xr:xr-xml-map "ospf_mgmt:MaximumMetricStartTimer";
      type uint32;
      description "Time remaining for hold down timer (s)";
    }
    leaf maximum-metric-set-reason {
      xr:xr-xml-map "ospf_mgmt:MaximumMetricSetReason";
      type Max-metric-set-reason;
      description "Max-metric set reason";
    }
    leaf maximum-metric-abr-off-mode {
      xr:xr-xml-map "ospf_mgmt:MaximumMetricABROffMode";
      type boolean;
      description "If true, ABR duties temporarily disabled";
    }
    leaf maximum-metric-abr-off-reasons {
      xr:xr-xml-map "ospf_mgmt:MaximumMetricABROffReasons";
      type Ospf-max-metric-abr-off-reasons;
      description
        "Reasons for ABR duties being temporarily
        disabled";
    }
    leaf maximum-metric-abr-off-buffer-time {
      xr:xr-xml-map "ospf_mgmt:MaximumMetricABROffBufferTime";
      type uint32;
      units "second";
      description
        "Buffer time in seconds since last neighbor
        activity, to remain in max-metric ABR off state";
    }
    leaf spf-start-time {
      xr:xr-xml-map "ospf_mgmt:SPFStartTime";
      type uint16;
      description
        "Scheduling delay for SPF (ms) This is valid if
        configured below 64k Deprecated by
        SPFStartTimeU32]";
    }
    leaf spf-hold-time {
      xr:xr-xml-map "ospf_mgmt:SPFHoldTime";
      type uint16;
      description
        "Minimum delay time between SPF runs (ms) This is
        valid if configured below 64k Deprecated by
        SPFHoldTimeU32]";
    }
    leaf spf-maximum-time {
      xr:xr-xml-map "ospf_mgmt:SPFMaximumTime";
      type uint16;
      description
        "Maximum delay time between SPF runs (ms) This is
        valid if configured below 64k Deprecated by
        SPFMaximumTimeU32]";
    }
    leaf spf-start-time-u32 {
      xr:xr-xml-map "ospf_mgmt:SPFStartTimeU32";
      type uint32;
      description "Scheduling delay for SPF (ms)";
    }
    leaf spf-hold-time-u32 {
      xr:xr-xml-map "ospf_mgmt:SPFHoldTimeU32";
      type uint32;
      description "Minimum delay time between SPF runs (ms)";
    }
    leaf spf-maximum-time-u32 {
      xr:xr-xml-map "ospf_mgmt:SPFMaximumTimeU32";
      type uint32;
      description "Maximum delay time between SPF runs (ms)";
    }
    leaf spf-prefix-priority {
      xr:xr-xml-map "ospf_mgmt:SPFPrefixPriority";
      type boolean;
      description "If true, prefix-priority policy is configured";
    }
    leaf spf-prefix-priority-route-policy {
      xr:xr-xml-map "ospf_mgmt:SPFPrefixPriorityRoutePolicy";
      type string;
      description "SPF Prefix-priority route policy";
    }
    leaf lsa-start-time {
      xr:xr-xml-map "ospf_mgmt:LSAStartTime";
      type int32;
      description "Inital LSA throttle delay (ms)";
    }
    leaf lsa-hold-time {
      xr:xr-xml-map "ospf_mgmt:LSAHoldTime";
      type uint32;
      description "Second delay before generating next LSA (ms)";
    }
    leaf lsa-maximum-time {
      xr:xr-xml-map "ospf_mgmt:LSAMaximumTime";
      type uint32;
      description "Maximum delay before generating an LSA (ms)";
    }
    leaf minimum-lsa-interval {
      xr:xr-xml-map "ospf_mgmt:MinimumLSAInterval";
      type uint16;
      description
        "Minimum time between LSA regeneration (ms) Rel 4
        .0.1, deprecated by MinimumLSAIntervalU32]";
    }
    leaf minimum-lsa-interval-u32 {
      xr:xr-xml-map "ospf_mgmt:MinimumLSAIntervalU32";
      type uint32;
      description "Minimum time between LSA regeneration (ms)";
    }
    leaf lsa-refresh-interval {
      xr:xr-xml-map "ospf_mgmt:LSARefreshInterval";
      type uint32;
      description "LSA refresh interval (sec)";
    }
    leaf minimum-lsa-arrival-interval {
      xr:xr-xml-map "ospf_mgmt:MinimumLSAArrivalInterval";
      type uint16;
      description
        "Minimum time between accepting LSAs (ms) Rel 4.0
        .1, deprecated by MinimumLSAArrivalIntervalU32]";
    }
    leaf minimum-lsa-arrival-interval-u32 {
      xr:xr-xml-map "ospf_mgmt:MinimumLSAArrivalIntervalU32";
      type uint32;
      description "Minimum time between accepting LSAs (ms)";
    }
    leaf if-flood-pacing-interval {
      xr:xr-xml-map "ospf_mgmt:IfFloodPacingInterval";
      type uint16;
      description "Flood pacing timer (ms)";
    }
    leaf if-retrans-pacing-interval {
      xr:xr-xml-map "ospf_mgmt:IfRetransPacingInterval";
      type uint16;
      description "Retransmission pacing timer (ms)";
    }
    leaf adj-stag-init-num-nbr {
      xr:xr-xml-map "ospf_mgmt:AdjStagInitNumNbr";
      type uint16;
      description "Num of nbrs brought up initially per area";
    }
    leaf adj-stag-max-num-nbr {
      xr:xr-xml-map "ospf_mgmt:AdjStagMaxNumNbr";
      type uint16;
      description
        "Max num of nbrs brought up simultaneously per
        OSPF instance";
    }
    leaf adj-stagger-enabled {
      xr:xr-xml-map "ospf_mgmt:AdjStaggerEnabled";
      type boolean;
      description
        "If true, OSPF Adjacency Staggering is configured";
    }
    leaf adj-stag-num-nbr-forming {
      xr:xr-xml-map "ospf_mgmt:AdjStagNumNbrForming";
      type uint16;
      description "Num of nbrs currently forming for OSPF instance";
    }
    leaf number-nbrs-full {
      xr:xr-xml-map "ospf_mgmt:NumberNbrsFull";
      type uint16;
      description "Num of full nbrs";
    }
    leaf as-lsa-count {
      xr:xr-xml-map "ospf_mgmt:AS_LSACount";
      type uint32;
      description "Number of AS scope LSAs";
    }
    leaf as-lsa-checksum {
      xr:xr-xml-map "ospf_mgmt:AS_LSAChecksum";
      type uint32;
      description "Sum of AS scope LSA checksum";
    }
    leaf opaque-lsa-count {
      xr:xr-xml-map "ospf_mgmt:OpaqueLSACount";
      type uint32;
      description "Number of Opaque LSAs";
    }
    leaf opaque-lsa-checksum {
      xr:xr-xml-map "ospf_mgmt:OpaqueLSAChecksum";
      type uint32;
      description "Sum of opaque LSA checksum";
    }
    leaf as-dc-bitless-lsa-count {
      xr:xr-xml-map "ospf_mgmt:AS_DCBitlessLSACount";
      type uint32;
      description
        "Number of External and AS Opaque LSAs with
        demand circut bit not set";
    }
    leaf as-dna-lsa-count {
      xr:xr-xml-map "ospf_mgmt:AS_DNA_LSACount";
      type uint32;
      description
        "Number of External and AS Opaque LSAs with
        DoNotAge set ";
    }
    leaf area-count {
      xr:xr-xml-map "ospf_mgmt:AreaCount";
      type uint16;
      description "Number of areas";
    }
    leaf normal-area-count {
      xr:xr-xml-map "ospf_mgmt:NormalAreaCount";
      type uint16;
      description "Number of normal Areas";
    }
    leaf stub-area-count {
      xr:xr-xml-map "ospf_mgmt:StubAreaCount";
      type uint16;
      description "Number of Stub and Total Stub Areas";
    }
    leaf nssa-area-count {
      xr:xr-xml-map "ospf_mgmt:NSSAAreaCount";
      type uint16;
      description "Number of NSSA Areas";
    }
    leaf maximum-interfaces {
      xr:xr-xml-map "ospf_mgmt:MaximumInterfaces";
      type uint32;
      description "Maximum number of interfaces";
    }
    leaf as-lsa-flood-list-length {
      xr:xr-xml-map "ospf_mgmt:AS_LSAFloodListLength";
      type uint32;
      description "Length of AS LSAs flood list";
    }
    leaf nsf-enabled {
      xr:xr-xml-map "ospf_mgmt:NSFEnabled";
      type boolean;
      description "If true, NSF enabled";
    }
    leaf last-nsf-time {
      xr:xr-xml-map "ospf_mgmt:LastNSFTime";
      type uint32;
      description " Length of time since the last NSF (s)";
    }
    leaf nsf-time {
      xr:xr-xml-map "ospf_mgmt:NSFTime";
      type uint32;
      description "Total time to complete NSF (s)";
    }
    leaf redistribution-limit {
      xr:xr-xml-map "ospf_mgmt:RedistributionLimit";
      type uint32;
      description "The number of redistributed prefixes allowed";
    }
    leaf redistribution-threshold {
      xr:xr-xml-map "ospf_mgmt:RedistributionThreshold";
      type uint32;
      description
        "When the number of redistributed prefixes
        reaches this threshold, a warning message is
        issued";
    }
    leaf redistribution-limit-warn {
      xr:xr-xml-map "ospf_mgmt:RedistributionLimitWarn";
      type boolean;
      description
        "If true, only a syslog message is printed when
        redistribution prefix limit is reached";
    }
    leaf graceful-shutdown-retention-time {
      xr:xr-xml-map "ospf_mgmt:GracefulShutdownRetentionTime";
      type uint32;
      description
        "Amount of time routes are retained after
        graceful shutdown (s)";
    }
    leaf graceful-shutdown-state {
      xr:xr-xml-map "ospf_mgmt:GracefulShutdownState";
      type Gs-state;
      description "State of graceful shutdown";
    }
    leaf table-prefix-limit-reached {
      xr:xr-xml-map "ospf_mgmt:TablePrefixLimitReached";
      type boolean;
      description
        "If true, prefix limit for table has been 
        reached";
    }
    leaf non-self-lsa-count {
      xr:xr-xml-map "ospf_mgmt:NonSelfLSACount";
      type uint32;
      description "Non self-generated LSA count";
    }
    leaf max-lsa-enabled {
      xr:xr-xml-map "ospf_mgmt:MaxLSAEnabled";
      type boolean;
      description "If true, max-lsa protection enabled";
    }
    leaf max-lsa-limit {
      xr:xr-xml-map "ospf_mgmt:MaxLSALimit";
      type uint32;
      description
        "Maximum allowed number of non self-generated
        LSAs";
    }
    leaf max-lsa-treshold {
      xr:xr-xml-map "ospf_mgmt:MaxLSATreshold";
      type uint32;
      description "max-lsa protection warning threshold";
    }
    leaf max-lsa-warning-only {
      xr:xr-xml-map "ospf_mgmt:MaxLSAWarningOnly";
      type boolean;
      description "Warning only when max-lsa reached";
    }
    leaf max-lsa-ignore-time {
      xr:xr-xml-map "ospf_mgmt:MaxLSAIgnoreTime";
      type uint32;
      description "Time ignoring new LSAs after max-lsa reached";
    }
    leaf max-lsa-reset-time {
      xr:xr-xml-map "ospf_mgmt:MaxLSAResetTime";
      type uint32;
      description
        "Time after which LSA protection counter is reset";
    }
    leaf max-lsa-ignore-limit {
      xr:xr-xml-map "ospf_mgmt:MaxLSAIgnoreLimit";
      type uint32;
      description "Max allowed number of entering ignore state";
    }
    leaf max-lsa-ignore-count {
      xr:xr-xml-map "ospf_mgmt:MaxLSAIgnoreCount";
      type uint32;
      description "How many times ignore state has been entered";
    }
    leaf max-lsa-ignore-timer {
      xr:xr-xml-map "ospf_mgmt:MaxLSAIgnoreTimer";
      type uint32;
      description "Remaining time when ignore timer is running";
    }
    leaf max-lsa-reset-timer {
      xr:xr-xml-map "ospf_mgmt:MaxLSAResetTimer";
      type uint32;
      description "Remaining time when reset timer is running";
    }
    leaf context-name {
      xr:xr-xml-map "ospf_mgmt:ContextName";
      type string {
        length "0..32";
      }
      description "Context name";
    }
    leaf snmp-trap-enabled {
      xr:xr-xml-map "ospf_mgmt:SNMPTrapEnabled";
      type boolean;
      description "If true, snmp trap is enabled";
    }
    leaf ucmp {
      xr:xr-xml-map "ospf_mgmt:UCMP";
      type boolean;
      description "If true, UCMP is enabled";
    }
    leaf ucmp-prefix-list {
      xr:xr-xml-map "ospf_mgmt:UCMP_PrefixList";
      type string;
      description "UCMP Prefix-list";
    }
    leaf ucmp-variance {
      xr:xr-xml-map "ospf_mgmt:UCMP_Variance";
      type int32;
      description "UCMP Variance";
    }
    leaf ucmp-delay {
      xr:xr-xml-map "ospf_mgmt:UCMP_Delay";
      type uint32;
      description
        "Delay between end of SPF and start of UCMP
        calculation (ms)";
    }
    leaf lsd-connected {
      xr:xr-xml-map "ospf_mgmt:LSDConnected";
      type boolean;
      description "True if connected to LSD";
    }
    leaf lsd-registered {
      xr:xr-xml-map "ospf_mgmt:LSDRegistered";
      type boolean;
      description "True if registered with LSD";
    }
    leaf lsd-bound {
      xr:xr-xml-map "ospf_mgmt:LSDBound";
      type boolean;
      description "True if bound to LSD";
    }
    leaf lsd-connection-revision {
      xr:xr-xml-map "ospf_mgmt:LSDConnectionRevision";
      type uint32;
      description "LSD Connection Revision";
    }
    leaf srgb-configured {
      xr:xr-xml-map "ospf_mgmt:SRGBConfigured";
      type boolean;
      description "True if Segment Routing Global Block configured";
    }
    leaf srgb-start {
      xr:xr-xml-map "ospf_mgmt:SRGBStart";
      type uint32;
      description "Segment Routing Global Block start label value";
    }
    leaf srgb-end {
      xr:xr-xml-map "ospf_mgmt:SRGBEnd";
      type uint32;
      description "Segment Routing Global Block end label value";
    }
    leaf srgb-status {
      xr:xr-xml-map "ospf_mgmt:SRGBStatus";
      type Ospf-srgb-status;
      description "Segment Routing Global Block allocation status";
    }
    leaf sr-strict-spf-cap {
      xr:xr-xml-map "ospf_mgmt:SRStrictSPFCap";
      type boolean;
      description "True if Segment Routing Strict-SPF capable";
    }

    list maximum-metric {
      description "Max-metric list";
      uses OSPF-SH-MAX-METRIC;
    }

    list redistribution {
      description "Redistribution list";
      uses OSPF-SH-REDIST;
    }
  }

  grouping OSPF-SH-AREA-RANGE {
    description "OSPF Area Range Information";
    leaf range-prefix {
      xr:xr-xml-map "ospf_mgmt:RangePrefix";
      type inet:ipv4-address;
      description "IP prefix for summarization";
    }
    leaf range-mask {
      xr:xr-xml-map "ospf_mgmt:RangeMask";
      type inet:ipv4-address;
      description "Network mask";
    }
    leaf cost {
      xr:xr-xml-map "ospf_mgmt:Cost";
      type uint32;
      description "Cost";
    }
    leaf advertise-flag {
      xr:xr-xml-map "ospf_mgmt:AdvertiseFlag";
      type boolean;
      description
        "Whether to advertise Summary LSAs for this range";
    }
  }

  grouping OSPF-SH-AREA {
    description "OSPF Area Summary Information";
    leaf area-id-string {
      xr:xr-xml-map "ospf_mgmt:AreaIDString";
      type string {
        length "0..16";
      }
      description "Area ID string";
    }
    leaf backbone-area-active {
      xr:xr-xml-map "ospf_mgmt:BackboneAreaActive";
      type boolean;
      description "If true, Backbone area is active";
    }
    leaf area-interface-count {
      xr:xr-xml-map "ospf_mgmt:AreaInterfaceCount";
      type uint16;
      description "Number of interfaces in the area";
    }
    leaf area-stub {
      xr:xr-xml-map "ospf_mgmt:AreaStub";
      type boolean;
      description "If true, stub area";
    }
    leaf area-total-stub {
      xr:xr-xml-map "ospf_mgmt:AreaTotalStub";
      type boolean;
      description "If true, totally stubby area";
    }
    leaf stub-default-cost {
      xr:xr-xml-map "ospf_mgmt:StubDefaultCost";
      type uint16;
      description "Default cost for Stub or NSSA area";
    }
    leaf area-nssa {
      xr:xr-xml-map "ospf_mgmt:AreaNSSA";
      type boolean;
      description "If true, area is a NSSA";
    }
    leaf nssa-no-redistribution {
      xr:xr-xml-map "ospf_mgmt:NSSANoRedistribution";
      type boolean;
      description "If true, No redistribution into this NSSA area";
    }
    leaf nssa-translate {
      xr:xr-xml-map "ospf_mgmt:NSSATranslate";
      type boolean;
      description "If true, perform 7/5 translation";
    }
    leaf nssa-default {
      xr:xr-xml-map "ospf_mgmt:NSSADefault";
      type boolean;
      description "If true, generate NSSA default route";
    }
    leaf te-enabled {
      xr:xr-xml-map "ospf_mgmt:TEEnabled";
      type boolean;
      description "If true, MPLS-TE enabled";
    }
    leaf te-topology-version {
      xr:xr-xml-map "ospf_mgmt:TETopologyVersion";
      type uint32;
      description "TE area topology version number";
    }
    leaf external-out {
      xr:xr-xml-map "ospf_mgmt:ExternalOut";
      type boolean;
      description
        "If true, advertise intra-area prefixes as
        external";
    }
    leaf summary-in {
      xr:xr-xml-map "ospf_mgmt:SummaryIn";
      type boolean;
      description
        "If true, advertise redistributedprefixes as
        summary";
    }
    leaf segment-routing {
      xr:xr-xml-map "ospf_mgmt:SegmentRouting";
      type uint32;
      description "If true, Segment Routing enabled";
    }
    leaf sr-strict-spf-cap {
      xr:xr-xml-map "ospf_mgmt:SRStrictSPFCap";
      type boolean;
      description
        "If true, All routers in Area are SR Strict-SPF
        Capable";
    }
    leaf sr-strict-spfsids-available {
      xr:xr-xml-map "ospf_mgmt:SRStrictSPFSIDsAvailable";
      type boolean;
      description
        "If true, All routers in Area have SR Strict-SPF
        SIDs";
    }
    leaf authentication-type {
      xr:xr-xml-map "ospf_mgmt:AuthenticationType";
      type Authentication;
      description "Authentication type";
    }
    leaf spf-count {
      xr:xr-xml-map "ospf_mgmt:SPFCount";
      type uint32;
      description "Number of SPF calculations run";
    }
    leaf area-policy-in {
      xr:xr-xml-map "ospf_mgmt:AreaPolicyIn";
      type boolean;
      description "If true, inbound policy is configured";
    }
    leaf area-policy-in-name {
      xr:xr-xml-map "ospf_mgmt:AreaPolicyInName";
      type string;
      description "Inbound summary lsa filtering policy";
    }
    leaf area-policy-out {
      xr:xr-xml-map "ospf_mgmt:AreaPolicyOut";
      type boolean;
      description "If true, outbound policy is configured";
    }
    leaf area-policy-out-name {
      xr:xr-xml-map "ospf_mgmt:AreaPolicyOutName";
      type string;
      description "Outbound summary lsa filtering policy";
    }
    leaf area-lsa-count {
      xr:xr-xml-map "ospf_mgmt:AreaLSACount";
      type uint32;
      description "Number of LSAs in the Area";
    }
    leaf area-lsa-checksum {
      xr:xr-xml-map "ospf_mgmt:AreaLSAChecksum";
      type uint32;
      description "Sum of all area LSAs checksum";
    }
    leaf area-opaque-lsa-count {
      xr:xr-xml-map "ospf_mgmt:AreaOpaqueLSACount";
      type uint32;
      description "Number of Opaque LSAs in the Area";
    }
    leaf area-opaque-lsa-checksum {
      xr:xr-xml-map "ospf_mgmt:AreaOpaqueLSAChecksum";
      type uint32;
      description "Sum of opaque LSA checksums";
    }
    leaf area-dc-bitless-lsa-count {
      xr:xr-xml-map "ospf_mgmt:AreaDCBitlessLSACount";
      type uint32;
      description "Number of LSA with demand circuit bit not set";
    }
    leaf indication-lsa-count {
      xr:xr-xml-map "ospf_mgmt:IndicationLSACount";
      type uint32;
      description "Number of indication LSAs";
    }
    leaf dna-lsa-count {
      xr:xr-xml-map "ospf_mgmt:DNA_LSACount";
      type uint32;
      description "Number of DoNotAge LSAs";
    }
    leaf flood-list-length {
      xr:xr-xml-map "ospf_mgmt:FloodListLength";
      type uint32;
      description "Number of LSAs which need to be flooded";
    }
    leaf area-lfa-interface-count {
      xr:xr-xml-map "ospf_mgmt:AreaLFAInterfaceCount";
      type uint32;
      description "Number of LFA enabled interfaces";
    }
    leaf area-per-prefix-lfa-interface-count {
      xr:xr-xml-map "ospf_mgmt:AreaPerPrefixLFAInterfaceCount";
      type uint32;
      description "Number of Per Prefix LFA enabled interfaces";
    }
    leaf area-lfa-revision {
      xr:xr-xml-map "ospf_mgmt:AreaLFARevision";
      type uint32;
      description "Area LFA revision";
    }
    leaf area-adj-stag-num-nbr-forming {
      xr:xr-xml-map "ospf_mgmt:AreaAdjStagNumNbrForming";
      type uint16;
      description "Num of nbrs currently forming";
    }
    leaf area-num-nbr-full {
      xr:xr-xml-map "ospf_mgmt:AreaNumNbrFull";
      type uint16;
      description "Num of full nbrs in area";
    }

    list area-range {
      description "List of ranges to summarize";
      uses OSPF-SH-AREA-RANGE;
    }
  }

  grouping OSPF-SH-REDIST {
    description "OSPF Redistribution Information";

    container redistribution-protocol {
      description "Protocol Information";
      uses OSPF-SH-REDIST-PROTO;
    }
    leaf metric-flag {
      xr:xr-xml-map "ospf_mgmt:MetricFlag";
      type boolean;
      description "If true, Metric configured";
    }
    leaf metric {
      xr:xr-xml-map "ospf_mgmt:Metric";
      type uint32;
      description "Route metric";
    }
    leaf classless {
      xr:xr-xml-map "ospf_mgmt:Classless";
      type boolean;
      description "Whether to use CIDR";
    }
    leaf nssa-only {
      xr:xr-xml-map "ospf_mgmt:NSSAOnly";
      type boolean;
      description "To NSSA areas only";
    }
  }

  grouping OSPF-SH-PROTOCOL {
    description "OSPF Protocol Information";
    leaf protocol-router-id {
      xr:xr-xml-map "ospf_mgmt:ProtocolRouterID";
      type inet:ipv4-address;
      description "Router ID";
    }
    leaf protocol-distance {
      xr:xr-xml-map "ospf_mgmt:ProtocolDistance";
      type uint32;
      description "Administrative distance";
    }
    leaf administrative-distance-inter-area {
      xr:xr-xml-map "ospf_mgmt:AdministrativeDistanceInterArea";
      type uint32;
      description "Administrative Distance for Inter Area routes";
    }
    leaf administrative-distance-external {
      xr:xr-xml-map "ospf_mgmt:AdministrativeDistanceExternal";
      type uint32;
      description "Administrative Distance for External routes";
    }
    leaf protocol-nsf {
      xr:xr-xml-map "ospf_mgmt:ProtocolNSF";
      type boolean;
      description "True if NSF enabled";
    }
    leaf dist-list-in {
      xr:xr-xml-map "ospf_mgmt:DistListIn";
      type string;
      description "Distribute List In";
    }
  }

  grouping OSPF-SH-PROTO-INTF {
    description "OSPF Protocol Interface Information";
    leaf protocol-interface-name {
      xr:xr-xml-map "ospf_mgmt:ProtocolInterfaceName";
      type xr:Interface-name;
      description "Interface";
    }
    leaf protocol-authentication-type {
      xr:xr-xml-map "ospf_mgmt:ProtocolAuthenticationType";
      type Authentication;
      description "Authentication type";
    }
    leaf protocol-interface-dist-list-in {
      xr:xr-xml-map "ospf_mgmt:ProtocolInterfaceDistListIn";
      type string;
      description "Distribute List In";
    }
  }

  grouping OSPF-SH-PROTO-AREA {
    description "OSPF Protocol Area Information";
    leaf protcol-area {
      xr:xr-xml-map "ospf_mgmt:ProtcolArea";
      type string {
        length "0..16";
      }
      description
        "Area ID string in decimal and dotted-decimal
        format";
    }
    leaf protocol-mpls {
      xr:xr-xml-map "ospf_mgmt:ProtocolMPLS";
      type boolean;
      description "MPLS-TE enabled";
    }
    leaf protocol-area-dist-list-in {
      xr:xr-xml-map "ospf_mgmt:ProtocolAreaDistListIn";
      type string;
      description "Distribute List In";
    }

    list protocol-interface {
      description "Interface list";
      uses OSPF-SH-PROTO-INTF;
    }
  }

  grouping OSPF-SH-BR-PATH {
    description "OSPF Border Router Path";
    leaf border-router-route-type {
      xr:xr-xml-map "ospf_mgmt:BorderRouterRouteType";
      type Ospf-route;
      description "Route type";
    }
    leaf border-router-route-metric {
      xr:xr-xml-map "ospf_mgmt:BorderRouterRouteMetric";
      type uint32;
      description "Metric";
    }
    leaf border-router-next-hop {
      xr:xr-xml-map "ospf_mgmt:BorderRouterNextHop";
      type inet:ipv4-address;
      description "Next hop address";
    }
    leaf border-router-next-hop-interface-name {
      xr:xr-xml-map "ospf_mgmt:BorderRouterNextHopInterfaceName";
      type xr:Interface-name;
      description "Next hop Interface";
    }
    leaf border-router-type {
      xr:xr-xml-map "ospf_mgmt:BorderRouterType";
      type Ospf-br;
      description "Border router type";
    }
    leaf border-router-area-id {
      xr:xr-xml-map "ospf_mgmt:BorderRouterAreaID";
      type string {
        length "0..16";
      }
      description "Area string in decimal or dotted-decimal format";
    }
    leaf spf-version {
      xr:xr-xml-map "ospf_mgmt:SPFVersion";
      type uint64;
      description "SPF run instance count";
    }
  }

  grouping OSPF-SH-BORDER-ROUTER {
    description "OSPF Border Router";
    leaf border-router-id-xr {
      xr:xr-xml-map "ospf_mgmt:border-router-id-xr";
      type inet:ipv4-address;
      description "Router ID of Border Router";
    }

    list border-router-path {
      description "List of Border Router paths";
      uses OSPF-SH-BR-PATH;
    }
  }

  grouping OSPF-SH-IPFRR-TB {
    description "OSPF IPFRR Tiebreakers";
    leaf tiebreaker-type {
      xr:xr-xml-map "ospf_mgmt:TiebreakerType";
      type Ipfrr-tbrkr;
      description "Tiebreaker Type";
    }
    leaf tiebreaker-index {
      xr:xr-xml-map "ospf_mgmt:TiebreakerIndex";
      type uint32;
      description "Tiebreaker Index";
    }
  }

  grouping OSPF-SH-INTERFACE-UP {
    description "OSPF Interface Up-only Information";
    leaf wait-time {
      xr:xr-xml-map "ospf_mgmt:WaitTime";
      type uint32;
      description "Wait time for DR/BDR selection (s)";
    }
    leaf interface-area-flood-index {
      xr:xr-xml-map "ospf_mgmt:InterfaceAreaFloodIndex";
      type uint32;
      description "Area scope LSAs flood index";
    }
    leaf interface-as-flood-index {
      xr:xr-xml-map "ospf_mgmt:InterfaceASFloodIndex";
      type uint32;
      description "AS scope LSAs flood index";
    }
    leaf interface-flood-length {
      xr:xr-xml-map "ospf_mgmt:InterfaceFloodLength";
      type uint32;
      description "Flood queue length";
    }
    leaf interface-area-next-flood {
      xr:xr-xml-map "ospf_mgmt:InterfaceAreaNextFlood";
      type uint32;
      description "Next LSA to flood (Area scope)";
    }
    leaf interface-area-next-flood-index {
      xr:xr-xml-map "ospf_mgmt:InterfaceAreaNextFloodIndex";
      type uint32;
      description "Index of next LSA to flood (Area scope)";
    }
    leaf interface-as-next-flood {
      xr:xr-xml-map "ospf_mgmt:InterfaceASNextFlood";
      type uint32;
      description "Next LSA to flood (AS scope)";
    }
    leaf interface-as-next-flood-index {
      xr:xr-xml-map "ospf_mgmt:InterfaceASNextFloodIndex";
      type uint32;
      description "Index of next LSA to flood (AS scope)";
    }
    leaf flood-scan-length {
      xr:xr-xml-map "ospf_mgmt:FloodScanLength";
      type uint32;
      description "Last flood scan length";
    }
    leaf maximum-flood-length {
      xr:xr-xml-map "ospf_mgmt:MaximumFloodLength";
      type uint32;
      description "Maximum flood length";
    }
    leaf last-flood-time {
      xr:xr-xml-map "ospf_mgmt:LastFloodTime";
      type uint32;
      description "Last flood scan time (ms)";
    }
    leaf maximum-flood-time {
      xr:xr-xml-map "ospf_mgmt:MaximumFloodTime";
      type uint32;
      description "Maximum flood time (ms)";
    }
    leaf interface-flood-pacing-timer {
      xr:xr-xml-map "ospf_mgmt:InterfaceFloodPacingTimer";
      type uint32;
      description "Time until next flood pacing timer (ms)";
    }
    leaf interface-neighbor-count {
      xr:xr-xml-map "ospf_mgmt:InterfaceNeighborCount";
      type uint16;
      description "Total number of Neighbors";
    }
    leaf suppress-hello-count {
      xr:xr-xml-map "ospf_mgmt:SuppressHelloCount";
      type uint16;
      description
        "Number of neighbors for which hellos are
        suppressed";
    }
    leaf interface-authentication-type {
      xr:xr-xml-map "ospf_mgmt:InterfaceAuthenticationType";
      type Authentication;
      description "Authentication type";
    }
    leaf youngest-md-key {
      xr:xr-xml-map "ospf_mgmt:YoungestMDKey";
      type boolean;
      description "If true, MD key is configured";
    }
    leaf old-md5-key-neighbor-count {
      xr:xr-xml-map "ospf_mgmt:OldMD5KeyNeighborCount";
      type uint32;
      description
        "Number of neighbors using the old key (if
        rollover in progress)";
    }
    leaf youngest-md-key-id {
      xr:xr-xml-map "ospf_mgmt:YoungestMDKeyID";
      type uint16;
      description "Youngest MD key ID";
    }
    leaf keychain-id {
      xr:xr-xml-map "ospf_mgmt:KeychainID";
      type uint64;
      description "Keychain ID";
    }
    leaf-list md-keys {
      xr:xr-xml-map "ospf_mgmt:MDKeysList";
      type uint16;
      description "List of old MD keys";
    }
  }

  grouping OSPF-SH-INTERFACE-BFD {
    description "Interface BFD information";
    leaf bfd-intf-enable-mode {
      xr:xr-xml-map "ospf_mgmt:BFDIntfEnableMode";
      type uint32;
      description "BFD enable mode - Default/Strict";
    }
    leaf interval {
      xr:xr-xml-map "ospf_mgmt:Interval";
      type uint32;
      description "BFD interval (ms)";
    }
    leaf detection-multiplier {
      xr:xr-xml-map "ospf_mgmt:DetectionMultiplier";
      type uint32;
      description "BFD detection multiplier";
    }
  }

  grouping OSPF-SH-INTERFACE-NBR {
    description "OSPF Interface Neighbor Information";
    leaf interface-neighbor-id {
      xr:xr-xml-map "ospf_mgmt:InterfaceNeighborID";
      type inet:ipv4-address;
      description "Neighbor Router ID";
    }
    leaf interface-neighbor-cost {
      xr:xr-xml-map "ospf_mgmt:InterfaceNeighborCost";
      type uint32;
      description "Cost of link to neighbor";
    }
    leaf neighbor-dr {
      xr:xr-xml-map "ospf_mgmt:NeighborDR";
      type boolean;
      description "If true, Designated router";
    }
    leaf neighbor-bdr {
      xr:xr-xml-map "ospf_mgmt:NeighborBDR";
      type boolean;
      description "If true, Backup designated router";
    }
    leaf suppress-hello {
      xr:xr-xml-map "ospf_mgmt:SuppressHello";
      type boolean;
      description "If true, hellos suppressed";
    }
  }

  grouping OSPF-SH-INTERFACE {
    description "OSPF Interface Information";

    container interface-bfd-information {
      description "BFD information";
      uses OSPF-SH-INTERFACE-BFD;
    }

    container active-interface {
      description "Active interface details";
      uses OSPF-SH-INTERFACE-UP;
    }
    leaf interface-name-xr {
      xr:xr-xml-map "ospf_mgmt:interface-name-xr";
      type xr:Interface-name;
      description "Interface";
    }
    leaf interface-state {
      xr:xr-xml-map "ospf_mgmt:InterfaceState";
      type Interface-state;
      description "Interface state";
    }
    leaf interface-line-state {
      xr:xr-xml-map "ospf_mgmt:InterfaceLineState";
      type boolean;
      description "If true, line protocol is up";
    }
    leaf interface-address {
      xr:xr-xml-map "ospf_mgmt:InterfaceAddress";
      type inet:ipv4-address;
      description "Interface IP Address";
    }
    leaf interface-mask {
      xr:xr-xml-map "ospf_mgmt:InterfaceMask";
      type uint32;
      description "Interface IP Mask";
    }
    leaf interface-area {
      xr:xr-xml-map "ospf_mgmt:InterfaceArea";
      type string {
        length "0..16";
      }
      description
        "Area ID string in decimal or dotted-decimal
        format";
    }
    leaf interface-sid {
      xr:xr-xml-map "ospf_mgmt:InterfaceSid";
      type uint32;
      description "Interface SID";
    }
    leaf interface-sid-php-off {
      xr:xr-xml-map "ospf_mgmt:InterfaceSidPhpOff";
      type boolean;
      description "SID PHP Off";
    }
    leaf interface-sid-n-flag-clear {
      xr:xr-xml-map "ospf_mgmt:InterfaceSidNFlagClear";
      type boolean;
      description "SID N-Flag Clear";
    }
    leaf interface-strict-spf-sid {
      xr:xr-xml-map "ospf_mgmt:InterfaceStrictSPFSid";
      type uint32;
      description "Interface Strict-SPF SID";
    }
    leaf interface-strict-spf-sid-php-off {
      xr:xr-xml-map "ospf_mgmt:InterfaceStrictSPFSidPhpOff";
      type boolean;
      description "Strict-SPF SID PHP Off";
    }
    leaf interface-strict-spf-sid-n-flag-clear {
      xr:xr-xml-map "ospf_mgmt:InterfaceStrictSPFSidNFlagClear";
      type boolean;
      description "Strict-SPF SID N-Flag Clear";
    }
    leaf interface-router-id {
      xr:xr-xml-map "ospf_mgmt:InterfaceRouterID";
      type inet:ipv4-address;
      description "Interface Router ID";
    }
    leaf network-type {
      xr:xr-xml-map "ospf_mgmt:NetworkType";
      type Interface;
      description "Network type";
    }
    leaf ip-mtu {
      xr:xr-xml-map "ospf_mgmt:IpMtu";
      type uint16;
      description "IP MTU";
    }
    leaf maximum-packet-size {
      xr:xr-xml-map "ospf_mgmt:MaximumPacketSize";
      type uint16;
      description "Maximum Packet Size";
    }
    leaf interface-tunnel-flags {
      xr:xr-xml-map "ospf_mgmt:InterfaceTunnelFlags";
      type uint32;
      description "Interface tunnel flags";
    }
    leaf interface-link-cost {
      xr:xr-xml-map "ospf_mgmt:InterfaceLinkCost";
      type uint16;
      description "Interface link cost";
    }
    leaf interface-bandwidth {
      xr:xr-xml-map "ospf_mgmt:InterfaceBandwidth";
      type uint32;
      description "Interface bandwidth";
    }
    leaf cfg-cost-fallback {
      xr:xr-xml-map "ospf_mgmt:CfgCostFallback";
      type boolean;
      description "If true, cost fallback is configured";
    }
    leaf interface-cost-fallback {
      xr:xr-xml-map "ospf_mgmt:InterfaceCostFallback";
      type uint16;
      description "Interface fallback cost";
    }
    leaf cost-fallback-active {
      xr:xr-xml-map "ospf_mgmt:CostFallbackActive";
      type boolean;
      description "If true, cost fallback is active";
    }
    leaf configured-ldp-sync {
      xr:xr-xml-map "ospf_mgmt:ConfiguredLdpSync";
      type boolean;
      description "If true, configured as LDP sync";
    }
    leaf configured-ldp-sync-igp-shortcuts {
      xr:xr-xml-map "ospf_mgmt:ConfiguredLdpSyncIgpShortcuts";
      type boolean;
      description "If true, sync igp shortcuts";
    }
    leaf interface-ldp-sync {
      xr:xr-xml-map "ospf_mgmt:InterfaceLdpSync";
      type boolean;
      description "If true, interface LDP sync is achieved";
    }
    leaf configured-demand-circuit {
      xr:xr-xml-map "ospf_mgmt:ConfiguredDemandCircuit";
      type boolean;
      description "If true, configured as demand circuit";
    }
    leaf interface-demand-circuit {
      xr:xr-xml-map "ospf_mgmt:InterfaceDemandCircuit";
      type boolean;
      description "If true, interface running as demand circuit";
    }
    leaf interface-dc-bitless-lsa-count {
      xr:xr-xml-map "ospf_mgmt:InterfaceDCBitlessLSACount";
      type uint32;
      description
        "Number of LSAs with demand circuit bit not set
        for the area in which the interface is running";
    }
    leaf transmission-delay {
      xr:xr-xml-map "ospf_mgmt:TransmissionDelay";
      type uint16;
      description "Interface Transmission delay";
    }
    leaf ospf-interface-state {
      xr:xr-xml-map "ospf_mgmt:OSPFInterfaceState";
      type Ospf-interface-state;
      description "Interface OSPF state";
    }
    leaf interface-priority {
      xr:xr-xml-map "ospf_mgmt:InterfacePriority";
      type uint8;
      description "Interface priority";
    }
    leaf designated-router {
      xr:xr-xml-map "ospf_mgmt:DesignatedRouter";
      type boolean;
      description "If true, designated router";
    }
    leaf designated-router-id {
      xr:xr-xml-map "ospf_mgmt:DesignatedRouterID";
      type inet:ipv4-address;
      description "Designated router ID";
    }
    leaf designated-router-address {
      xr:xr-xml-map "ospf_mgmt:DesignatedRouterAddress";
      type inet:ipv4-address;
      description "Designated router interface address";
    }
    leaf backup-designated-router {
      xr:xr-xml-map "ospf_mgmt:BackupDesignatedRouter";
      type boolean;
      description "If true, backup designated router";
    }
    leaf backup-designated-router-id {
      xr:xr-xml-map "ospf_mgmt:BackupDesignatedRouterID";
      type inet:ipv4-address;
      description "Backup designated router ID";
    }
    leaf backup-designated-router-address {
      xr:xr-xml-map "ospf_mgmt:BackupDesignatedRouterAddress";
      type inet:ipv4-address;
      description "Backup designated router interface address";
    }
    leaf network-lsa-flush-timer {
      xr:xr-xml-map "ospf_mgmt:NetworkLSAFlushTimer";
      type uint32;
      units "second";
      description
        "The amount of time in seconds before flush timer
        for old network LSA expires";
    }
    leaf interface-lsa-filter {
      xr:xr-xml-map "ospf_mgmt:InterfaceLSAFilter";
      type boolean;
      description "Filter is configured for out going LSAs";
    }
    leaf hello-interval {
      xr:xr-xml-map "ospf_mgmt:HelloInterval";
      type uint32;
      description "Configured hello interval (s)";
    }
    leaf hello-interval-ms {
      xr:xr-xml-map "ospf_mgmt:HelloIntervalMs";
      type uint32;
      description "Configured hello interval (ms)";
    }
    leaf dead-interval {
      xr:xr-xml-map "ospf_mgmt:DeadInterval";
      type uint32;
      description "Configured dead interval (s)";
    }
    leaf wait-interval {
      xr:xr-xml-map "ospf_mgmt:WaitInterval";
      type uint32;
      description "Configured wait interval (s)";
    }
    leaf interface-retransmission-interrval {
      xr:xr-xml-map "ospf_mgmt:InterfaceRetransmissionInterrval";
      type uint32;
      description "Configured retransmit interval (s)";
    }
    leaf interface-nsf-enabled {
      xr:xr-xml-map "ospf_mgmt:InterfaceNSFEnabled";
      type boolean;
      description "If true, NSF is enabled";
    }
    leaf interface-nsf {
      xr:xr-xml-map "ospf_mgmt:InterfaceNSF";
      type boolean;
      description
        "If true, NSF restart in progress on this
        interface";
    }
    leaf interface-last-nsf {
      xr:xr-xml-map "ospf_mgmt:InterfaceLastNSF";
      type uint32;
      description "Time since last NSF restart (s)";
    }
    leaf passive-interface {
      xr:xr-xml-map "ospf_mgmt:PassiveInterface";
      type boolean;
      description "If true, passive interface";
    }
    leaf next-hello-time {
      xr:xr-xml-map "ospf_mgmt:NextHelloTime";
      type uint32;
      description "Time until next Hello (s)";
    }
    leaf next-hello-time-ms {
      xr:xr-xml-map "ospf_mgmt:NextHelloTimeMs";
      type uint32;
      description "Time until next Hello (ms)";
    }
    leaf ttl-security-enabled {
      xr:xr-xml-map "ospf_mgmt:TTLSecurityEnabled";
      type boolean;
      description "TTL security enabled on the interface";
    }
    leaf ttl-security-hop-count {
      xr:xr-xml-map "ospf_mgmt:TTLSecurityHopCount";
      type uint32;
      description "TTL security hop counts";
    }
    leaf interfaceis-madj {
      xr:xr-xml-map "ospf_mgmt:InterfaceisMadj";
      type boolean;
      description "If true, interface is multi-area";
    }
    leaf interface-madj-count {
      xr:xr-xml-map "ospf_mgmt:InterfaceMadjCount";
      type uint16;
      description "Total number of multi-area";
    }
    leaf prefix-suppress-primary-addresses {
      xr:xr-xml-map "ospf_mgmt:PrefixSuppressPrimaryAddresses";
      type boolean;
      description "Prefix Suppression for primary addresses";
    }
    leaf prefix-suppress-secondary-addresses {
      xr:xr-xml-map "ospf_mgmt:PrefixSuppressSecondaryAddresses";
      type boolean;
      description "Prefix Suppression for secondary addresses";
    }
    leaf is-loopback-stub-network {
      xr:xr-xml-map "ospf_mgmt:IsLoopbackStubNetwork";
      type boolean;
      description
        "If true, loopback interface is advertised as a
        stub network";
    }
    leaf interface-ack-list-count {
      xr:xr-xml-map "ospf_mgmt:InterfaceAckListCount";
      type uint32;
      description "Ack List Count";
    }
    leaf interface-ack-list-high-watermark {
      xr:xr-xml-map "ospf_mgmt:InterfaceAckListHighWatermark";
      type uint32;
      description "Ack List High Watermark";
    }
    leaf registered-for-link-down-fast-detection {
      xr:xr-xml-map "ospf_mgmt:RegisteredForLinkDownFastDetection";
      type boolean;
      description "Registered for Link Down Fast Detection";
    }
    leaf fast-detect-hold-down-time {
      xr:xr-xml-map "ospf_mgmt:FastDetectHoldDownTime";
      type uint32;
      description "Hold-down time in ms for fast-detect event";
    }
    leaf interface-fast-detect-hold-down {
      xr:xr-xml-map "ospf_mgmt:InterfaceFastDetectHoldDown";
      type boolean;
      description
        "Link in hold-down state due to fast detect event";
    }
    leaf fast-detect-hold-down-time-remaining {
      xr:xr-xml-map "ospf_mgmt:FastDetectHoldDownTimeRemaining";
      type uint32;
      description "Remaining hold down time in ms";
    }
    leaf fast-reroute-type {
      xr:xr-xml-map "ospf_mgmt:FastRerouteType";
      type Ipfrr;
      description "IP Fast Reroute Type";
    }
    leaf fast-reroute-topology-independent-lfa {
      xr:xr-xml-map "ospf_mgmt:FastRerouteTopologyIndependentLFA";
      type boolean;
      description "Topology Independent LFA";
    }
    leaf-list srlg {
      xr:xr-xml-map "ospf_mgmt:SRLG";
      type uint32;
      description "SRLG Values";
    }

    list interface-neighbor {
      description "Information for neighbors on the interface";
      uses OSPF-SH-INTERFACE-NBR;
    }

    list interface-madj {
      description "Information for multi-area on the interface";
      uses OSPF-SH-INTERFACE-MADJ;
    }

    list ipfrr-tiebreakers {
      description "IPFRR-Tiebreakers list";
      uses OSPF-SH-IPFRR-TB;
    }
  }

  grouping OSPF-SH-VLINK-NEIGHBOR {
    description "Virtual Link Neighbor Information";

    container virtual-link-retransmissoin {
      description "Neighbor retransmission info";
      uses OSPF-SH-NEIGHBOR-RETRANS;
    }
    leaf virtual-link-suppress-hello {
      xr:xr-xml-map "ospf_mgmt:VirtualLinkSuppressHello";
      type boolean;
      description "If true Hellos suppressed";
    }
    leaf virtual-link-state {
      xr:xr-xml-map "ospf_mgmt:VirtualLinkState";
      type Neighbor-state;
      description "Adjacency state";
    }
  }

  grouping OSPF-SH-VIRTUAL-LINKS {
    description "OSPF Virtual Link";

    container virtual-link-neighbor {
      description "Neighbor information";
      uses OSPF-SH-VLINK-NEIGHBOR;
    }
    leaf virtual-link-name-xr {
      xr:xr-xml-map "ospf_mgmt:virtual-link-name-xr";
      type string;
      description "Virtual link name";
    }
    leaf virtual-link-neighbor-id {
      xr:xr-xml-map "ospf_mgmt:VirtualLinkNeighborID";
      type inet:ipv4-address;
      description "Neighbor on other end of this virtual link";
    }
    leaf virtual-link-state {
      xr:xr-xml-map "ospf_mgmt:VirtualLinkState";
      type Ospf-interface-state;
      description "OSPF interface state for the virtual link";
    }
    leaf virtual-link-demand-circuit {
      xr:xr-xml-map "ospf_mgmt:VirtualLinkDemandCircuit";
      type boolean;
      description "If true, the link runs as demand circuit";
    }
    leaf virtual-link-dc-bitless-lsa {
      xr:xr-xml-map "ospf_mgmt:VirtualLinkDCBitlessLSA";
      type uint32;
      description "Number of LSA's with demand circuit bit not set";
    }
    leaf transit-area {
      xr:xr-xml-map "ospf_mgmt:TransitArea";
      type string;
      description "Transit area id";
    }
    leaf virtual-link-interface-name {
      xr:xr-xml-map "ospf_mgmt:VirtualLinkInterfaceName";
      type xr:Interface-name;
      description "Interface on which this virtual link is formed";
    }
    leaf virtual-link-cost {
      xr:xr-xml-map "ospf_mgmt:VirtualLinkCost";
      type uint16;
      description "Cost of the virtual link";
    }
    leaf virual-link-transmission-delay {
      xr:xr-xml-map "ospf_mgmt:VirualLinkTransmissionDelay";
      type uint16;
      units "second";
      description "Transmission delay in seconds";
    }
    leaf virtual-link-hello-interval {
      xr:xr-xml-map "ospf_mgmt:VirtualLinkHelloInterval";
      type uint32;
      description "Hello interval (s)";
    }
    leaf virtual-link-hello-interval-ms {
      xr:xr-xml-map "ospf_mgmt:VirtualLinkHelloIntervalMs";
      type uint32;
      description "Hello interval (ms)";
    }
    leaf virtual-link-dead-interval {
      xr:xr-xml-map "ospf_mgmt:VirtualLinkDeadInterval";
      type uint32;
      description "Dead interval (s)";
    }
    leaf virtual-link-wait-interval {
      xr:xr-xml-map "ospf_mgmt:VirtualLinkWaitInterval";
      type uint32;
      description "Wait interval (s)";
    }
    leaf virtaul-link-retransmission-interval {
      xr:xr-xml-map "ospf_mgmt:VirtaulLinkRetransmissionInterval";
      type uint32;
      description "Retransmission interval (s)";
    }
    leaf virtual-link-next-hello {
      xr:xr-xml-map "ospf_mgmt:VirtualLinkNextHello";
      type uint32;
      description "Time until next hello (s)";
    }
    leaf virtual-link-next-hello-ms {
      xr:xr-xml-map "ospf_mgmt:VirtualLinkNextHelloMs";
      type uint32;
      description "Time until next hello (ms)";
    }
    leaf virtual-link-passive {
      xr:xr-xml-map "ospf_mgmt:VirtualLinkPassive";
      type boolean;
      description "If true, interface is passive";
    }
    leaf virtual-link-authentication-type {
      xr:xr-xml-map "ospf_mgmt:VirtualLinkAuthenticationType";
      type Authentication;
      description "Authentication type";
    }
    leaf virtual-link-youngest-md-key {
      xr:xr-xml-map "ospf_mgmt:VirtualLinkYoungestMDKey";
      type boolean;
      description "If true, MD key configured";
    }
    leaf virtual-link-youngest-md-key-id {
      xr:xr-xml-map "ospf_mgmt:VirtualLinkYoungestMDKeyID";
      type uint16;
      description "Youngest MD key ID";
    }
    leaf virtual-link-old-md-key-count {
      xr:xr-xml-map "ospf_mgmt:VirtualLinkOldMDKeyCount";
      type uint32;
      description
        "Number of neighbors still using the old key
        (rollover in progress)";
    }
    leaf virtual-link-keychain-id {
      xr:xr-xml-map "ospf_mgmt:VirtualLinkKeychainID";
      type uint64;
      description "Virtual Link Keychain ID";
    }
    leaf virtual-link-nsf-enabled {
      xr:xr-xml-map "ospf_mgmt:VirtualLinkNSFEnabled";
      type boolean;
      description "If true, NSF enabled";
    }
    leaf virtual-link-nsf {
      xr:xr-xml-map "ospf_mgmt:VirtualLinkNSF";
      type boolean;
      description
        "If true, NSF restart in progress on the virtual
        link";
    }
    leaf virtual-link-last-nsf {
      xr:xr-xml-map "ospf_mgmt:VirtualLinkLastNSF";
      type uint32;
      units "second";
      description "Time in seconds since last NSF";
    }
    leaf-list virtual-link-md-key {
      xr:xr-xml-map "ospf_mgmt:VirtualLinkMDKeyList";
      type uint16;
      description "List of old MD keys (if any)";
    }
  }

  grouping OSPF-SH-INTERFACE-MADJ {
    description "OSPF Interface Multi-Area Information";
    leaf interface-area {
      xr:xr-xml-map "ospf_mgmt:InterfaceArea";
      type string {
        length "0..16";
      }
      description
        "Area ID string in decimal or dotted-decimal
        format";
    }
    leaf madj-area-id {
      xr:xr-xml-map "ospf_mgmt:MadjAreaID";
      type uint32;
      description "Area ID";
    }
    leaf interface-neighbor-count {
      xr:xr-xml-map "ospf_mgmt:InterfaceNeighborCount";
      type uint16;
      description "Number of Neighbors";
    }
    leaf interface-adj-neighbor-count {
      xr:xr-xml-map "ospf_mgmt:InterfaceAdjNeighborCount";
      type uint16;
      description "Total number of Adjacent Neighbors";
    }
    leaf interface-link-cost {
      xr:xr-xml-map "ospf_mgmt:InterfaceLinkCost";
      type uint16;
      description "Interface link cost";
    }
    leaf ospf-interface-state {
      xr:xr-xml-map "ospf_mgmt:OSPFInterfaceState";
      type Ospf-interface-state;
      description "Interface OSPF state";
    }
  }

  grouping OSPF-SH-IF-BRIEF {
    description "OSPF Interface Brief Information";
    leaf interface-name-xr {
      xr:xr-xml-map "ospf_mgmt:interface-name-xr";
      type xr:Interface-name;
      description "Interface name";
    }
    leaf interface-area {
      xr:xr-xml-map "ospf_mgmt:InterfaceArea";
      type string {
        length "0..16";
      }
      description
        "Area ID string in decimal or dotted-decimal
        format";
    }
    leaf interface-address {
      xr:xr-xml-map "ospf_mgmt:InterfaceAddress";
      type inet:ipv4-address;
      description "Interface IP Address";
    }
    leaf interface-mask {
      xr:xr-xml-map "ospf_mgmt:InterfaceMask";
      type uint32;
      description "Interface IP Mask";
    }
    leaf interface-link-cost {
      xr:xr-xml-map "ospf_mgmt:InterfaceLinkCost";
      type uint16;
      description "Interface link cost";
    }
    leaf ospf-interface-state {
      xr:xr-xml-map "ospf_mgmt:OSPFInterfaceState";
      type Ospf-interface-state;
      description "Interface OSPF state";
    }
    leaf interface-fast-detect-hold-down {
      xr:xr-xml-map "ospf_mgmt:InterfaceFastDetectHoldDown";
      type boolean;
      description "Interface in fast detect hold down state";
    }
    leaf interface-neighbor-count {
      xr:xr-xml-map "ospf_mgmt:InterfaceNeighborCount";
      type uint16;
      description "Total number of Neighbors";
    }
    leaf interface-adj-neighbor-count {
      xr:xr-xml-map "ospf_mgmt:InterfaceAdjNeighborCount";
      type uint16;
      description "Total number of Adjacent Neighbors";
    }
    leaf interfaceis-madj {
      xr:xr-xml-map "ospf_mgmt:InterfaceisMadj";
      type boolean;
      description "If true, interface is multi-area";
    }
    leaf interface-madj-count {
      xr:xr-xml-map "ospf_mgmt:InterfaceMadjCount";
      type uint16;
      description "Total number of multi-area";
    }

    list interface-madj {
      description "Information for multi-area on the interface";
      uses OSPF-SH-INTERFACE-MADJ;
    }
  }

  grouping OSPF-SH-ROUTE-EXTENDED-COMM {
    description
      "OSPF External Route Extended Community
      Information";
    leaf extended-community-domain-id-value {
      xr:xr-xml-map "ospf_mgmt:ExtendedCommunityDomainIDValue";
      type yang:hex-string;
      description "Domain ID value";
    }
    leaf extended-communityl-domain-id-type {
      xr:xr-xml-map "ospf_mgmt:ExtendedCommunitylDomainIDType";
      type uint16;
      description "Domain ID type";
    }
    leaf extended-community-area-id {
      xr:xr-xml-map "ospf_mgmt:ExtendedCommunityAreaID";
      type uint32;
      description "Area id";
    }
    leaf extended-community-router-id {
      xr:xr-xml-map "ospf_mgmt:ExtendedCommunityRouterID";
      type inet:ipv4-address;
      description "Router id";
    }
    leaf extended-community-route-type {
      xr:xr-xml-map "ospf_mgmt:ExtendedCommunityRouteType";
      type uint8;
      description "Route type";
    }
    leaf extended-community-options {
      xr:xr-xml-map "ospf_mgmt:ExtendedCommunityOptions";
      type uint8;
      description "Route Options";
    }
  }

  grouping OSPF-SH-REDIST-PROTO {
    description "Redistributed protocol instance";
    leaf protocol-type {
      xr:xr-xml-map "ospf_mgmt:ProtocolType";
      type Redist-protocol;
      description "ProtocolType";
    }
    leaf isis-instance-id {
      xr:xr-xml-map "ospf_mgmt:ISISInstanceID";
      when "../protocol-type = 'mgmt-rib-protocol-isis'" {
        description "../ProtocolType = 'MGMT_RIB_PROTOCOL_ISIS'";
      }
      type String1;
      description "ISIS instance identifier";
    }
    leaf ospf-process-id {
      xr:xr-xml-map "ospf_mgmt:OSPFProcessID";
      when "../protocol-type = 'mgmt-rib-protocol-ospf'" {
        description "../ProtocolType = 'MGMT_RIB_PROTOCOL_OSPF'";
      }
      type String1;
      description "OSPF process identifier";
    }
    leaf bgp-as-number {
      xr:xr-xml-map "ospf_mgmt:BGP_ASNumber";
      when "../protocol-type = 'mgmt-rib-protocol-bgp'" {
        description "../ProtocolType = 'MGMT_RIB_PROTOCOL_BGP'";
      }
      type String1;
      description "BGP Autonomous System Number";
    }
    leaf eigrp-as-number {
      xr:xr-xml-map "ospf_mgmt:EIGRP_ASNumber";
      when "../protocol-type = 'mgmt-rib-protocol-eigrp'" {
        description "../ProtocolType = 'MGMT_RIB_PROTOCOL_EIGRP'";
      }
      type String1;
      description "Autonomous System Number";
    }
    leaf connected-instance {
      xr:xr-xml-map "ospf_mgmt:ConnectedInstance";
      when "../protocol-type = 'mgmt-rib-protocol-connected'" {
        description
          "../ProtocolType = 'MGMT_RIB_PROTOCOL_CONNECTED'";
      }
      type String1;
      description "Connected instance name";
    }
  }

  grouping OSPF-SH-ROUTE-EXT {
    description "OSPF External Route Information";

    container route-information {
      description "Route information";
      uses OSPF-SH-TOPOLOGY;
    }

    container protocol-name {
      description
        "Name of protocol from which the external route
        was redistributed";
      uses OSPF-SH-REDIST-PROTO;
    }

    container route-extended-community {
      description "Extended communities in the route";
      uses OSPF-SH-ROUTE-EXTENDED-COMM;
    }
  }

  grouping OSPF-SH-ROUTE-SUMM-COMMON {
    description "OSPF Route Summary Common Information";
    leaf external-type1s {
      xr:xr-xml-map "ospf_mgmt:ExternalType1s";
      type uint32;
      description "External type 1 count";
    }
    leaf external-type2s {
      xr:xr-xml-map "ospf_mgmt:ExternalType2s";
      type uint32;
      description "External type 2 count";
    }
    leaf external-nssa-type1s {
      xr:xr-xml-map "ospf_mgmt:ExternalNSSAType1s";
      type uint32;
      description "External NSSA type 1 count";
    }
    leaf external-nssa-type2s {
      xr:xr-xml-map "ospf_mgmt:ExternalNSSAType2s";
      type uint32;
      description "External NSSA type 2 count";
    }
    leaf inter-areas {
      xr:xr-xml-map "ospf_mgmt:InterAreas";
      type uint32;
      description "Inter-area count";
    }
    leaf intra-areas {
      xr:xr-xml-map "ospf_mgmt:IntraAreas";
      type uint32;
      description "Intra-area count";
    }
    leaf total {
      xr:xr-xml-map "ospf_mgmt:Total";
      type uint32;
      description "Total count";
    }
  }

  grouping OSPF-SH-ROUTE-SUMMARY {
    description "OSPF Route Summary Information";

    container failure-time {
      description "Last time failed";
      uses OSPF-SH-TIME;
    }

    container common {
      description "OSPF route summary Information";
      uses OSPF-SH-ROUTE-SUMM-COMMON;
    }
    leaf failures {
      xr:xr-xml-map "ospf_mgmt:Failures";
      type uint32;
      description "RIB failure count";
    }
    leaf failure-address {
      xr:xr-xml-map "ospf_mgmt:FailureAddress";
      type inet:ipv4-address;
      description "Last failed address";
    }
  }

  grouping OSPF-SH-TOP-PATH {
    description "OSPF Route Path Information";
    leaf route-interface-name {
      xr:xr-xml-map "ospf_mgmt:RouteInterfaceName";
      type xr:Interface-name;
      description "Next hop Interface";
    }
    leaf route-next-hop-address {
      xr:xr-xml-map "ospf_mgmt:RouteNextHopAddress";
      type inet:ipv4-address;
      description "Nexthop IP address";
    }
    leaf route-source {
      xr:xr-xml-map "ospf_mgmt:RouteSource";
      type inet:ipv4-address;
      description "IP address of source of route";
    }
    leaf route-lsaid {
      xr:xr-xml-map "ospf_mgmt:RouteLSAID";
      type inet:ipv4-address;
      description "LSA ID, see RFC2328";
    }
    leaf route-path-is-mcast-intact {
      xr:xr-xml-map "ospf_mgmt:RoutePathIsMcastIntact";
      type boolean;
      description "Multicast-intact path";
    }
    leaf route-path-is-ucmp-path {
      xr:xr-xml-map "ospf_mgmt:RoutePathIsUCMPPath";
      type boolean;
      description "UCMP path";
    }
    leaf route-metric {
      xr:xr-xml-map "ospf_mgmt:RouteMetric";
      type uint32;
      description "Metric";
    }
    leaf lsa-type {
      xr:xr-xml-map "ospf_mgmt:LSAType";
      type uint8;
      description "LSA type, see RFC2328 etc.";
    }
    leaf area-id {
      xr:xr-xml-map "ospf_mgmt:AreaID";
      type uint32;
      description "Area ID";
    }
    leaf area-format {
      xr:xr-xml-map "ospf_mgmt:AreaFormat";
      type boolean;
      description "Area format IP or uint32";
    }
  }

  grouping OSPF-SH-TOPOLOGY {
    description "OSPF Route Information";

    container route-info {
      description "Route information";
      uses OSPF-SH-TOP-COMMON;
    }
    leaf route-prefix {
      xr:xr-xml-map "ospf_mgmt:RoutePrefix";
      type inet:ipv4-address;
      description "Prefix";
    }
    leaf route-prefix-length {
      xr:xr-xml-map "ospf_mgmt:RoutePrefixLength";
      type uint32;
      description "Prefix length";
    }
    leaf route-metric {
      xr:xr-xml-map "ospf_mgmt:RouteMetric";
      type uint32;
      description "Metric";
    }
    leaf route-type {
      xr:xr-xml-map "ospf_mgmt:RouteType";
      type Ospf-route;
      description "Route type";
    }
    leaf route-connected {
      xr:xr-xml-map "ospf_mgmt:RouteConnected";
      type boolean;
      description "If true, connected route";
    }

    list route-path {
      description "List of paths to this route";
      uses OSPF-SH-TOP-PATH;
    }
  }

  grouping OSPF-SH-REP-EL {
    description "OSPF Repair Element";
    leaf repair-element-id {
      xr:xr-xml-map "ospf_mgmt:RepairElementID";
      type inet:ipv4-address;
      description "Repair Element ID";
    }
    leaf repair-label {
      xr:xr-xml-map "ospf_mgmt:RepairLabel";
      type uint32;
      description "Repair Label";
    }
    leaf repair-element-type {
      xr:xr-xml-map "ospf_mgmt:Repair_element_type";
      type uint32;
      description "Repair Element Type";
    }
  }

  grouping OSPF-SH-BACKUP-PATH {
    description "OSPF Route Backup Path Information";
    leaf backup-route-interface-name {
      xr:xr-xml-map "ospf_mgmt:BackupRouteInterfaceName";
      type xr:Interface-name;
      description "Next hop Interface";
    }
    leaf backup-route-next-hop-address {
      xr:xr-xml-map "ospf_mgmt:BackupRouteNextHopAddress";
      type inet:ipv4-address;
      description "Nexthop IP address";
    }
    leaf backup-route-source {
      xr:xr-xml-map "ospf_mgmt:BackupRouteSource";
      type inet:ipv4-address;
      description "IP address of source of route";
    }
    leaf backup-metric {
      xr:xr-xml-map "ospf_mgmt:BackupMetric";
      type uint32;
      description "Metric";
    }
    leaf primary-path {
      xr:xr-xml-map "ospf_mgmt:PrimaryPath";
      type boolean;
      description "Primary Path";
    }
    leaf line-card-disjoint {
      xr:xr-xml-map "ospf_mgmt:LineCardDisjoint";
      type boolean;
      description "Line Card Disjoint";
    }
    leaf downstream {
      xr:xr-xml-map "ospf_mgmt:Downstream";
      type boolean;
      description "Downstream";
    }
    leaf node-protect {
      xr:xr-xml-map "ospf_mgmt:NodeProtect";
      type boolean;
      description "Node Protect";
    }
    leaf srlg-disjoint {
      xr:xr-xml-map "ospf_mgmt:SRLGDisjoint";
      type boolean;
      description "SRLG Disjoint";
    }
    leaf backup-remote-lfa {
      xr:xr-xml-map "ospf_mgmt:BackupRemoteLFA";
      type inet:ipv4-address;
      description "IP address of remote LFA";
    }
    leaf backup-repair-list-sizei {
      xr:xr-xml-map "ospf_mgmt:BackupRepairListSizei";
      type uint32;
      description "Repair List Size";
    }
    leaf backup-tunnel-interface-name {
      xr:xr-xml-map "ospf_mgmt:BackupTunnelInterfaceName";
      type xr:Interface-name;
      description "Backup Tunnel Interface";
    }

    list backup-repair {
      max-elements "10";
      description "BAckup Repair List";
      uses OSPF-SH-REP-EL;
    }
  }

  grouping OSPF-SH-TOP-PATH-BACKUP {
    description "OSPF Route Path Wit Backup Path Information";

    container route-backup-path {
      description "Backup Path Info";
      uses OSPF-SH-BACKUP-PATH;
    }
    leaf route-interface-name {
      xr:xr-xml-map "ospf_mgmt:RouteInterfaceName";
      type xr:Interface-name;
      description "Next hop Interface";
    }
    leaf route-next-hop-address {
      xr:xr-xml-map "ospf_mgmt:RouteNextHopAddress";
      type inet:ipv4-address;
      description "Nexthop IP address";
    }
    leaf route-source {
      xr:xr-xml-map "ospf_mgmt:RouteSource";
      type inet:ipv4-address;
      description "IP address of source of route";
    }
    leaf route-lsaid {
      xr:xr-xml-map "ospf_mgmt:RouteLSAID";
      type inet:ipv4-address;
      description "LSA ID, see RFC2328";
    }
    leaf route-path-is-mcast-intact {
      xr:xr-xml-map "ospf_mgmt:RoutePathIsMcastIntact";
      type boolean;
      description "Multicast-intact path";
    }
    leaf route-path-is-ucmp-path {
      xr:xr-xml-map "ospf_mgmt:RoutePathIsUCMPPath";
      type boolean;
      description "UCMP path";
    }
    leaf route-metric {
      xr:xr-xml-map "ospf_mgmt:RouteMetric";
      type uint32;
      description "Metric";
    }
    leaf route-path-id {
      xr:xr-xml-map "ospf_mgmt:RoutePathID";
      type uint16;
      description "Path ID of path";
    }
    leaf lsa-type {
      xr:xr-xml-map "ospf_mgmt:LSAType";
      type uint8;
      description "LSA type, see RFC2328 etc.";
    }
  }

  grouping OSPF-SH-TIME {
    description "OSPF SH TIME";
    leaf second {
      xr:xr-xml-map "ospf_mgmt:Second";
      type uint32;
      description "Second";
    }
    leaf nanosecond {
      xr:xr-xml-map "ospf_mgmt:Nanosecond";
      type uint32;
      description "Nanosecond";
    }
  }

  grouping OSPF-SH-TOP-COMMON {
    description "OSPF Common Route Information";

    container route-update-time {
      description "Last time updated";
      uses OSPF-SH-TIME;
    }

    container route-fail-time {
      description "Last time update failed";
      uses OSPF-SH-TIME;
    }
    leaf route-area-id {
      xr:xr-xml-map "ospf_mgmt:RouteAreaID";
      type uint32;
      description "Area ID";
    }
    leaf route-te-metric {
      xr:xr-xml-map "ospf_mgmt:RouteTEMetric";
      type uint32;
      description "TE metric";
    }
    leaf route-rib-version {
      xr:xr-xml-map "ospf_mgmt:RouteRIBVersion";
      type uint32;
      description "RIB version";
    }
    leaf route-spf-version {
      xr:xr-xml-map "ospf_mgmt:RouteSPFVersion";
      type uint64;
      description "SPF version";
    }
    leaf route-forward-distance {
      xr:xr-xml-map "ospf_mgmt:RouteForwardDistance";
      type uint32;
      description "Forward distance";
    }
    leaf route-source {
      xr:xr-xml-map "ospf_mgmt:RouteSource";
      type uint16;
      description "Protocol source";
    }
    leaf route-spf-priority {
      xr:xr-xml-map "ospf_mgmt:RouteSPFPriority";
      type uint8;
      description "SPF priority";
    }
    leaf route-auto-excluded {
      xr:xr-xml-map "ospf_mgmt:RouteAutoExcluded";
      type boolean;
      description "If true, exclude from TE paths";
    }
    leaf route-srte-prefix-registered {
      xr:xr-xml-map "ospf_mgmt:RouteSRTEPrefixRegistered";
      type boolean;
      description "If true, SRTE registered prefix route";
    }
    leaf route-srte-nbr-registered {
      xr:xr-xml-map "ospf_mgmt:RouteSRTENbrRegistered";
      type uint16;
      description "SRTE registered neigbhor count on route";
    }
  }

  grouping OSPF-SH-TOPOLOGY-BACKUP {
    description "OSPF Route Information With Backup Path";

    container route-info {
      description "Route information";
      uses OSPF-SH-TOP-COMMON;
    }
    leaf route-prefix {
      xr:xr-xml-map "ospf_mgmt:RoutePrefix";
      type inet:ipv4-address;
      description "Prefix";
    }
    leaf route-prefix-length {
      xr:xr-xml-map "ospf_mgmt:RoutePrefixLength";
      type uint32;
      description "Prefix length";
    }
    leaf route-metric {
      xr:xr-xml-map "ospf_mgmt:RouteMetric";
      type uint32;
      description "Metric";
    }
    leaf route-type {
      xr:xr-xml-map "ospf_mgmt:RouteType";
      type Ospf-route;
      description "Route type";
    }
    leaf route-connected {
      xr:xr-xml-map "ospf_mgmt:RouteConnected";
      type boolean;
      description "If true, connected route";
    }

    list route-path {
      description "List of paths to this route";
      uses OSPF-SH-TOP-PATH-BACKUP;
    }
  }

  grouping OSPF-SH-NEIGHBOR-RETRANS {
    description "OSPF Neighbor Retransmission Information";
    leaf dbd-retransmission-count {
      xr:xr-xml-map "ospf_mgmt:DBDRetransmissionCount";
      type uint32;
      description
        "Number of DBD retransmissions during last
        exchange";
    }
    leaf dbd-retransmission-total-count {
      xr:xr-xml-map "ospf_mgmt:DBDRetransmissionTotalCount";
      type uint32;
      description
        "Total number of DBD retransmissions for this
        neighbor";
    }
    leaf area-flooding-index {
      xr:xr-xml-map "ospf_mgmt:AreaFloodingIndex";
      type uint32;
      description "Area scope LSA's flood index";
    }
    leaf as-flood-index {
      xr:xr-xml-map "ospf_mgmt:ASFloodIndex";
      type uint32;
      description "AS scope LSA's flood index";
    }
    leaf neighbor-retransmission-count {
      xr:xr-xml-map "ospf_mgmt:NeighborRetransmissionCount";
      type uint32;
      description "Retransmission queue length";
    }
    leaf number-of-retransmissions {
      xr:xr-xml-map "ospf_mgmt:NumberOfRetransmissions";
      type uint32;
      description "Number of retransmissions for this neighbor";
    }
    leaf area-first-flood-information {
      xr:xr-xml-map "ospf_mgmt:AreaFirstFloodInformation";
      type uint32;
      description "First flood item for area scope LSAs";
    }
    leaf area-first-flood-information-index {
      xr:xr-xml-map "ospf_mgmt:AreaFirstFloodInformationIndex";
      type uint32;
      description
        "Index of the first flood item for area scope
        LSAs";
    }
    leaf as-first-flood-information {
      xr:xr-xml-map "ospf_mgmt:ASFirstFloodInformation";
      type uint32;
      description "First flood item for AS scope LSAs";
    }
    leaf as-first-flood-information-index {
      xr:xr-xml-map "ospf_mgmt:ASFirstFloodInformationIndex";
      type uint32;
      description "Index for first flood item for AS scope LSAs";
    }
    leaf area-next-flood-information {
      xr:xr-xml-map "ospf_mgmt:AreaNextFloodInformation";
      type uint32;
      description "Next flood item for area scope LSAs";
    }
    leaf area-next-flood-information-index {
      xr:xr-xml-map "ospf_mgmt:AreaNextFloodInformationIndex";
      type uint32;
      description "Index of next flood item for Area scope LSAs";
    }
    leaf as-next-flood-information {
      xr:xr-xml-map "ospf_mgmt:ASNextFloodInformation";
      type uint32;
      description "Next flood item for AS scope LSAs";
    }
    leaf as-next-flood-information-index {
      xr:xr-xml-map "ospf_mgmt:ASNextFloodInformationIndex";
      type uint32;
      description "Index of next flood item for AS scope LSAs";
    }
    leaf last-retransmission-length {
      xr:xr-xml-map "ospf_mgmt:LastRetransmissionLength";
      type uint32;
      description "Number of LSAs sent in last retransmission";
    }
    leaf maximum-retransmission-length {
      xr:xr-xml-map "ospf_mgmt:MaximumRetransmissionLength";
      type uint32;
      description "Maximum number of LSAs sent in a retransmission";
    }
    leaf last-retransmission-time {
      xr:xr-xml-map "ospf_mgmt:LastRetransmissionTime";
      type uint32;
      description "Last retransmission scan time (ms)";
    }
    leaf maximum-retransmission-time {
      xr:xr-xml-map "ospf_mgmt:MaximumRetransmissionTime";
      type uint32;
      description "Maximum retransmission scan time (ms)";
    }
    leaf lsa-retransmission-timer {
      xr:xr-xml-map "ospf_mgmt:LSARetransmissionTimer";
      type uint32;
      description "Time until next LSA retransmission (ms)";
    }
  }

  grouping OSPF-SH-NEIGHBOR-DETAIL {
    description "OSPF Neighbor Detailed Information";

    container neighbor-summary {
      description "Neighbor summary information";
      uses OSPF-SH-NEIGHBOR;
    }

    container neighbor-bfd-information {
      description "Neighbor BFD information";
      uses OSPF-SH-NEIGHBOR-BFD;
    }

    container neighbor-retransmission-information {
      description "Retransmission information with this neighbor";
      uses OSPF-SH-NEIGHBOR-RETRANS;
    }
    leaf neighbor-area-id {
      xr:xr-xml-map "ospf_mgmt:NeighborAreaID";
      type string {
        length "0..16";
      }
      description
        "Area ID string in decimal or dotted-decimal
        format";
    }
    leaf state-change-count {
      xr:xr-xml-map "ospf_mgmt:StateChangeCount";
      type uint16;
      description "Number of state changes";
    }
    leaf neighbor-cost {
      xr:xr-xml-map "ospf_mgmt:NeighborCost";
      type uint16;
      description "Cost of path to this neighbor";
    }
    leaf neighbor-filter {
      xr:xr-xml-map "ospf_mgmt:NeighborFilter";
      type boolean;
      description "If true, filter outgoing LSAs";
    }
    leaf neighbor-designated-router-address {
      xr:xr-xml-map "ospf_mgmt:NeighborDesignatedRouterAddress";
      type inet:ipv4-address;
      description "Address of designated router";
    }
    leaf neighbor-backup-designated-router-address {
      xr:xr-xml-map "ospf_mgmt:NeighborBackupDesignatedRouterAddres"+
        "s";
      type inet:ipv4-address;
      description "Address of backup designated router";
    }
    leaf interface-type {
      xr:xr-xml-map "ospf_mgmt:InterfaceType";
      type Interface;
      description "Interface type";
    }
    leaf poll-interval {
      xr:xr-xml-map "ospf_mgmt:PollInterval";
      type uint32;
      description "Poll interval (s)";
    }
    leaf next-poll-interval {
      xr:xr-xml-map "ospf_mgmt:NextPollInterval";
      type uint32;
      units "second";
      description
        "For NBMA networks, amount of time remaining in
        seconds before the next poll interval expires
        and Hello is sent (s)";
    }
    leaf neighbor-option {
      xr:xr-xml-map "ospf_mgmt:NeighborOption";
      type uint8;
      description
        " This is bitmaks of neighbor's option field
        received";
    }
    leaf pending-events {
      xr:xr-xml-map "ospf_mgmt:PendingEvents";
      type uint16;
      description "Number of pending events";
    }
    leaf neighbor-lls-option {
      xr:xr-xml-map "ospf_mgmt:NeighborLLSOption";
      type uint16;
      description
        "This is a bitmask of Link Local signalling
        options received from the neighbor";
    }
    leaf oob-resynchronization {
      xr:xr-xml-map "ospf_mgmt:OOBResynchronization";
      type boolean;
      description "Out-Of-Bound resynchronization in progress";
    }
    leaf nsf-router-state {
      xr:xr-xml-map "ospf_mgmt:NSFRouterState";
      type Nsf-rtr;
      description
        "For cisco NSF, the router is either Requester or
        Receiver";
    }
    leaf last-oob-time {
      xr:xr-xml-map "ospf_mgmt:LastOOBTime";
      type uint32;
      units "second";
      description
        "The amount of time in seconds since last time
        Out-Of-Band resynchronization was done with this
        neighbor";
    }
    leaf lfa-interface {
      xr:xr-xml-map "ospf_mgmt:LFAInterface";
      type xr:Interface-name;
      description "LFA Interface";
    }
    leaf lfa-next-hop {
      xr:xr-xml-map "ospf_mgmt:LFANextHop";
      type inet:ipv4-address;
      description "LFA Next Hop";
    }
    leaf lfa-neighbor-id {
      xr:xr-xml-map "ospf_mgmt:LFANeighborID";
      type inet:ipv4-address;
      description "LFA Neighbor ID";
    }
    leaf lfa-neighbor-revision {
      xr:xr-xml-map "ospf_mgmt:LFANeighborRevision";
      type uint32;
      description "LFA Neighbor Revision";
    }
    leaf neighbor-ack-list-count {
      xr:xr-xml-map "ospf_mgmt:NeighborAckListCount";
      type uint32;
      description "Ack List Count";
    }
    leaf neighbor-ack-list-high-watermark {
      xr:xr-xml-map "ospf_mgmt:NeighborAckListHighWatermark";
      type uint32;
      description "Ack List High Watermark";
    }
    leaf adjacency-sid-label {
      xr:xr-xml-map "ospf_mgmt:AdjacencySIDLabel";
      type uint32;
      description "SR Adjacency SID Label";
    }
    leaf adjacency-sid-protected {
      xr:xr-xml-map "ospf_mgmt:AdjacencySIDProtected";
      type boolean;
      description "SR Adjacency SID Protected";
    }
    leaf adjacency-sid-unprotected-label {
      xr:xr-xml-map "ospf_mgmt:AdjacencySIDUnprotectedLabel";
      type uint32;
      description "SR Adjacency SID Unprotected Label";
    }
  }

  grouping OSPF-SH-RETRANS-LIST {
    description "OSPF Retransmission List";
    leaf retransmission-neighbor-id {
      xr:xr-xml-map "ospf_mgmt:RetransmissionNeighborID";
      type inet:ipv4-address;
      description "Neighbor ID";
    }
    leaf retransmission-neighbor-ip-address {
      xr:xr-xml-map "ospf_mgmt:RetransmissionNeighborIPAddress";
      type inet:ipv4-address;
      description "Neighbor IP Address";
    }
    leaf retransmission-interface-name {
      xr:xr-xml-map "ospf_mgmt:RetransmissionInterfaceName";
      type xr:Interface-name;
      description "Retransmission list interface";
    }
    leaf retransmission-timer {
      xr:xr-xml-map "ospf_mgmt:RetransmissionTimer";
      type uint32;
      description
        "Amount of time remaining on retransmission timer
        (ms)";
    }
    leaf retransmission-count {
      xr:xr-xml-map "ospf_mgmt:RetransmissionCount";
      type uint32;
      description "Retransmission queue length";
    }

    list retransmission-area-db {
      description "List of Area scope entries";
      uses OSPF-SH-LSA-SUM;
    }

    list retransmission-asdb {
      description "List of AS Scope entries";
      uses OSPF-SH-LSA-SUM;
    }
  }

  grouping OSPF-SH-REQUEST-LIST {
    description "OSPF Request List Information";
    leaf request-neighbor-id {
      xr:xr-xml-map "ospf_mgmt:RequestNeighborID";
      type inet:ipv4-address;
      description "Neighbor ID";
    }
    leaf request-neighbor-address {
      xr:xr-xml-map "ospf_mgmt:RequestNeighborAddress";
      type inet:ipv4-address;
      description "Neighbor IP address";
    }
    leaf request-interface-name {
      xr:xr-xml-map "ospf_mgmt:RequestInterfaceName";
      type xr:Interface-name;
      description "Request list interface";
    }

    list request {
      description "List of request list entries";
      uses OSPF-SH-LSA-SUM;
    }
  }

  grouping OSPF-SH-NEIGHBOR-BFD {
    description "OSPF Neighbor BFD information";
    leaf bfd-intf-enable-mode {
      xr:xr-xml-map "ospf_mgmt:BFDIntfEnableMode";
      type uint32;
      description "BFD enable mode - Default/Strict";
    }
    leaf bfd-status-flag {
      xr:xr-xml-map "ospf_mgmt:BFDStatusFlag";
      type uint8;
      description "Status of the BFD Session";
    }
  }

  grouping OSPF-SH-NEIGHBOR {
    description "OSPF Neighbor Summary Information";

    container neighbor-bfd-information {
      description "Neighbor BFD information";
      uses OSPF-SH-NEIGHBOR-BFD;
    }
    leaf neighbor-id {
      xr:xr-xml-map "ospf_mgmt:NeighborID";
      type inet:ipv4-address;
      description "Neighbor ID";
    }
    leaf neighbor-address-xr {
      xr:xr-xml-map "ospf_mgmt:neighbor-address-xr";
      type inet:ipv4-address;
      description "Neighbor IP Address";
    }
    leaf neighbor-interface-name {
      xr:xr-xml-map "ospf_mgmt:NeighborInterfaceName";
      type xr:Interface-name;
      description "Interface via which the neighbor is seen";
    }
    leaf neighbor-dr-priority {
      xr:xr-xml-map "ospf_mgmt:NeighborDRPriority";
      type uint8;
      description "Neighbor's DR priority";
    }
    leaf neighbor-state {
      xr:xr-xml-map "ospf_mgmt:NeighborState";
      type Neighbor-state;
      description "Neighbor's state";
    }
    leaf dr-bdr-state {
      xr:xr-xml-map "ospf_mgmt:DR_BDRState";
      type Dr-bdr-state;
      description "Designated Router state";
    }
    leaf neighbor-dead-timer {
      xr:xr-xml-map "ospf_mgmt:NeighborDeadTimer";
      type uint32;
      description "Time until neighbor's dead timer expires (s)";
    }
    leaf neighbor-up-time {
      xr:xr-xml-map "ospf_mgmt:NeighborUpTime";
      type uint32;
      description "Amount of time since the adjacency is up (s)";
    }
    leaf neighbor-madj-interface {
      xr:xr-xml-map "ospf_mgmt:NeighborMadjInterface";
      type boolean;
      description "Interface is MADJ";
    }
  }

  grouping OSPF-SH-MPLS-FRAGMENT {
    description "OSPF MPLS-TE Fragment Information";
    leaf fragment-instance {
      xr:xr-xml-map "ospf_mgmt:FragmentInstance";
      type uint32;
      description "Fragment instance";
    }
    leaf fragment-id {
      xr:xr-xml-map "ospf_mgmt:FragmentID";
      type uint32;
      description "Fragment ID";
    }
    leaf dste-model-id {
      xr:xr-xml-map "ospf_mgmt:DSTEModelID";
      type uint8;
      description "DS-TE Allocation Model ID";
    }
    leaf same-fragment-count {
      xr:xr-xml-map "ospf_mgmt:SameFragmentCount";
      type uint8;
      description
        "Number of fragment links which haven't changed
        since the last update";
    }

    list mpls-te-link {
      description "List of fragment links";
      uses OSPF-SH-MPLS-LINK;
    }
  }

  grouping OSPF-SH-MPLS-EAG {
    description "EXTENDED administrative group TLVs";
    leaf extended-admin-size {
      xr:xr-xml-map "ospf_mgmt:ExtendedAdminSize";
      type uint32;
      description "Size of the extended admin group";
    }
    leaf-list ext-admin-data {
      xr:xr-xml-map "ospf_mgmt:ExtAdminData";
      type uint32;
      description "Value of Extended Admin Group";
    }
  }

  grouping MPLS-TEL-OPT-UNID-VAL {
    description "MPLS TE Link Optional TLV IXCD Data";
    leaf uni-dir-delay {
      xr:xr-xml-map "ospf_mgmt:UniDirDelay";
      type uint32;
      description "Uni Dir Delay";
    }
  }

  grouping BW-FLEX-SUBTLV-VALUE {
    description "Value of Flex Sub TLV";

    container flex-sub-tlv-value-common {
      description "Flex Sub TLV Value";
      uses BW-SUB-TLV-VALUE-COMMON;
    }
    leaf-list unres-lspbw {
      xr:xr-xml-map "ospf_mgmt:UnresLSPBW";
      type uint64;
      max-elements "8";
      description "Array of Unres LSP BW";
    }
    leaf-list max-lspbw {
      xr:xr-xml-map "ospf_mgmt:MaxLSPBW";
      type uint64;
      max-elements "8";
      description "Max LSP BW Array";
    }
  }

  grouping BW-SUB-TLV-VALUE-COMMON {
    description "Common values in both Fixed and Flex Sub TLV";
    leaf signal-type {
      xr:xr-xml-map "ospf_mgmt:SignalType";
      type uint8;
      description "Signal Type";
    }
    leaf num-stages {
      xr:xr-xml-map "ospf_mgmt:NumStages";
      type uint8;
      description "Number of stages";
    }
    leaf tbit {
      xr:xr-xml-map "ospf_mgmt:TBit";
      type uint8;
      description "T Bit";
    }
    leaf sbit {
      xr:xr-xml-map "ospf_mgmt:SBit";
      type uint8;
      description "S Bit";
    }
    leaf tsg {
      xr:xr-xml-map "ospf_mgmt:TSG";
      type uint8;
      description "TSG";
    }
    leaf res {
      xr:xr-xml-map "ospf_mgmt:Res";
      type uint8;
      description "Res";
    }
    leaf priority-bit0 {
      xr:xr-xml-map "ospf_mgmt:PriorityBit0";
      type uint8;
      description "Priority 0";
    }
    leaf priority-bit1 {
      xr:xr-xml-map "ospf_mgmt:PriorityBit1";
      type uint8;
      description "Priority 1";
    }
    leaf priority-bit2 {
      xr:xr-xml-map "ospf_mgmt:PriorityBit2";
      type uint8;
      description "Priority 2";
    }
    leaf priority-bit3 {
      xr:xr-xml-map "ospf_mgmt:PriorityBit3";
      type uint8;
      description "Priority 3";
    }
    leaf priority-bit4 {
      xr:xr-xml-map "ospf_mgmt:PriorityBit4";
      type uint8;
      description "Priority 4";
    }
    leaf priority-bit5 {
      xr:xr-xml-map "ospf_mgmt:PriorityBit5";
      type uint8;
      description "Priority 5";
    }
    leaf priority-bit6 {
      xr:xr-xml-map "ospf_mgmt:PriorityBit6";
      type uint8;
      description "Priority 6";
    }
    leaf priority-bit7 {
      xr:xr-xml-map "ospf_mgmt:PriorityBit7";
      type uint8;
      description "Priority 7";
    }
    leaf stage {
      xr:xr-xml-map "ospf_mgmt:Stage";
      type yang:hex-string;
      description "Array of Stages";
    }
  }

  grouping BW-FIXED-SUBTLV-VALUE {
    description "Value of Fixed Sub TLV";

    container fixed-sub-tlv-value {
      description "Value of Fixed Sub TLV";
      uses BW-SUB-TLV-VALUE-COMMON;
    }
    leaf-list unres-oduj-prio {
      xr:xr-xml-map "ospf_mgmt:UnresOdujPrio";
      type uint32;
      max-elements "8";
      description "Array of Unres Oduj Prio";
    }
  }

  grouping IXCD-BW-SUB-TLV-VALUE-UNION {
    description "Sub Tlv values for IXCD Bandwidth";

    container fixed-bw-sub-tlv-value {
      when "../ixcdbw-sub-tlv-type = '1'" {
        description "../IXCDBWSubTLVType = '1'";
      }
      description "Value of Fixed Sub TLV";
      uses BW-FIXED-SUBTLV-VALUE;
    }

    container flex-bw-sub-tlv-value {
      when "../ixcdbw-sub-tlv-type = '2'" {
        description "../IXCDBWSubTLVType = '2'";
      }
      description "Value of Flex Sub TLV";
      uses BW-FLEX-SUBTLV-VALUE;
    }
    leaf ixcdbw-sub-tlv-type {
      xr:xr-xml-map "ospf_mgmt:IXCDBWSubTLVType";
      type uint16;
      description "IXCDBWSubTLVType";
    }
  }

  grouping IXCD-BW-SUB-TLV {
    description "IXCD BW sub tlv";

    container bw-sub-tlv-value {
      description "Value of BW Sub TLV";
      uses IXCD-BW-SUB-TLV-VALUE-UNION;
    }
    leaf bw-sub-tlv-type {
      xr:xr-xml-map "ospf_mgmt:BWSubTLVType";
      type uint16;
      description "Type of Sub TLV";
    }
    leaf bw-sub-tlv-length {
      xr:xr-xml-map "ospf_mgmt:BWSubTLVLength";
      type uint16;
      description "Length of BW Sub TLV";
    }
  }

  grouping IXCD-BW-SUB-TLV-ARR {
    description "Array of BW Sub TLVs";

    list arr-bw-sub-tlv {
      description "Array of sub tlvs";
      uses IXCD-BW-SUB-TLV;
    }
  }

  grouping IXCD-LE-PSC-INFO {
    description "IXCD LE PSC information";
    leaf min-lsp-bandwidth {
      xr:xr-xml-map "ospf_mgmt:MinLSPBandwidth";
      type uint64;
      description "Min LSP bandwidth";
    }
    leaf psc-interface-mtu {
      xr:xr-xml-map "ospf_mgmt:PSCInterfaceMTU";
      type uint16;
      description " Interface MTU";
    }
  }

  grouping IXCD-TLV-SWITCHINGCAP-VALUE-UNION {
    description "Switching Cap values";

    container ixcdpsc-info {
      when "../switching-cap-type = 'rrr-proto-l-switch-cap-psc4'" {
        description
          "../SwitchingCapType =
          'RRR_PROTO_LSWITCH_CAP_PSC4'";
      }
      description "IXCD PSC information";
      uses IXCD-LE-PSC-INFO;
    }

    container ixcdbw-sub-tlv {
      when "../switching-cap-type ="+
        " 'rrr-proto-l-switch-cap-otn-tdm'" {
          description
            "../SwitchingCapType =
            'RRR_PROTO_LSWITCH_CAP_OTN_TDM'";
      }
      description "Sub TLVs";
      uses IXCD-BW-SUB-TLV-ARR;
    }
    leaf switching-cap-type {
      xr:xr-xml-map "ospf_mgmt:SwitchingCapType";
      type uint8;
      description "SwitchingCapType";
    }
  }

  grouping MPLS-TEL-OPT-IXCD-VAL {
    description "MPLS TE Link Optional TLV IXCD Data";

    container ixcd-switching-cap-type {
      description "Switching Cap type";
      uses IXCD-TLV-SWITCHINGCAP-VALUE-UNION;
    }
    leaf switching-cap {
      xr:xr-xml-map "ospf_mgmt:SwitchingCap";
      type uint8;
      description "SCap";
    }
    leaf rile-len-code {
      xr:xr-xml-map "ospf_mgmt:RileLenCode";
      type uint8;
      description "Rile LenCode";
    }
    leaf fixed-scsi-count {
      xr:xr-xml-map "ospf_mgmt:FixedSCSICount";
      type uint32;
      description "Fixed SCSI count";
    }
    leaf flex-scsi-count {
      xr:xr-xml-map "ospf_mgmt:FlexSCSICount";
      type uint32;
      description "Flexible SCSI count";
    }
    leaf-list max-lspbw {
      xr:xr-xml-map "ospf_mgmt:MaxLSPBW";
      type int64;
      max-elements "8";
      description "Max LSP bandwidth array";
    }
  }

  grouping MPLS-TEL-OPT-SRLG-VAL {
    description "MPLS TE Link Optional TLV SRLG Data";
    leaf srlg-len {
      xr:xr-xml-map "ospf_mgmt:SRLGLen";
      type uint32;
      description "Length of SRLG TLV";
    }
    leaf num-srl-gs {
      xr:xr-xml-map "ospf_mgmt:NumSRLGs";
      type uint32;
      description "Number of SRLG TLVs";
    }
    leaf-list mplste-link-srlg-data {
      xr:xr-xml-map "ospf_mgmt:MPLSTELinkSRLGData";
      type uint32;
      description "Value of SRLG TLV";
    }
  }

  grouping MPLS-TEL-OPT-BC-VAL {
    description "MPLS TE Link Optional TLV BC Data";
    leaf model-id {
      xr:xr-xml-map "ospf_mgmt:ModelID";
      type uint8;
      description "Allocation Model ID";
    }
    leaf num-b-cs {
      xr:xr-xml-map "ospf_mgmt:NumBCs";
      type uint32;
      description "Number of BC TLVs";
    }
    leaf-list mplste-link-bc-bandwidth {
      xr:xr-xml-map "ospf_mgmt:MPLSTELinkBCBandwidth";
      type uint64;
      description "Value of BC TLV";
    }
  }

  grouping MPLSTEL-TLV-VALUE-UNION {
    description "Value of TLVs";

    container bctlv-value {
      when "../opaque-tlv-type = 'mpls-te-opt-tlv-type-bc'" {
        description "../OpaqueTLVType = 'MPLS_TE_OPT_TLV_TYPE_BC'";
      }
      description "Value of Bandwidth Constraints TLV";
      uses MPLS-TEL-OPT-BC-VAL;
    }

    container srlgtlv-value {
      when "../opaque-tlv-type = 'mpls-te-opt-tlv-type-srlg'" {
        description
          "../OpaqueTLVType = 'MPLS_TE_OPT_TLV_TYPE_SRLG'";
      }
      description "Value of SRLG TLV";
      uses MPLS-TEL-OPT-SRLG-VAL;
    }

    container ixcdtlv-value {
      when "../opaque-tlv-type = 'mpls-te-opt-tlv-type-ixcd'" {
        description
          "../OpaqueTLVType = 'MPLS_TE_OPT_TLV_TYPE_IXCD'";
      }
      description "Value of IXCD TLV";
      uses MPLS-TEL-OPT-IXCD-VAL;
    }

    container unidtlv-value {
      when "../opaque-tlv-type = 'mpls-te-opt-tlv-type-uni-delay'" {
        description
          "../OpaqueTLVType =
          'MPLS_TE_OPT_TLV_TYPE_UNI_DELAY'";
      }
      description "Value of Uni Delay TLV";
      uses MPLS-TEL-OPT-UNID-VAL;
    }
    leaf opaque-tlv-type {
      xr:xr-xml-map "ospf_mgmt:OpaqueTLVType";
      type Mpls-te-opt-tlv;
      description "OpaqueTLVType";
    }
  }

  grouping OSPF-SH-MPLS-TEL-OPT-TLV {
    description "MPLS TE Link Optional TLVs";
    leaf mplste-link-opt-tlv-type {
      xr:xr-xml-map "ospf_mgmt:MPLSTELinkOptTLVType";
      type Mpls-te-opt-tlv;
      description "Type of Opt TLV";
    }
    leaf mplste-link-opt-tlv-len {
      xr:xr-xml-map "ospf_mgmt:MPLSTELinkOptTLVLen";
      type uint16;
      description "Length of Opt TLV";
    }

    list mplste-link-opt-tlv-value {
      description "Value of Opt TLV";
      uses MPLSTEL-TLV-VALUE-UNION;
    }
  }

  grouping OSPF-SH-MPLS-IXCD-CAP {
    description "Link switching capability";
    leaf link-switching-capability {
      xr:xr-xml-map "ospf_mgmt:LinkSwitchingCapability";
      type uint8;
      description "Link Switching Capability";
    }
    leaf link-encoding {
      xr:xr-xml-map "ospf_mgmt:LinkEncoding";
      type uint8;
      description "Link Encoding";
    }
    leaf minimum-lsp-bw {
      xr:xr-xml-map "ospf_mgmt:MinimumLSP_BW";
      type uint64;
      units "byte/s";
      description "Minimum LSP bandwidth (bytes/s)";
    }
    leaf link-mtu {
      xr:xr-xml-map "ospf_mgmt:LinkMTU";
      type uint16;
      units "byte";
      description "Link MTU size (bytes)";
    }
    leaf-list maximum-lsp-bw-per-priority {
      xr:xr-xml-map "ospf_mgmt:MaximumLSP_BWPerPriority";
      type uint64;
      units "byte/s";
      max-elements "8";
      description
        "Maximum LSP bandwidth for each priority
        (bytes/s)";
    }
  }

  grouping OSPF-SH-MPLS-LINK-PROTOPRIO {
    description "Link protocol and priority capability";
    leaf link-protocol-capability {
      xr:xr-xml-map "ospf_mgmt:LinkProtocolCapability";
      type uint8;
      description "Link protocol capability";
    }
    leaf link-protocol-priority {
      xr:xr-xml-map "ospf_mgmt:LinkProtocolPriority";
      type uint8;
      description "Link protocol priority";
    }
  }

  grouping OSPF-SH-MPLS-BW {
    description "Available bandwidth for each priority level";
    leaf-list bw-per-priority {
      xr:xr-xml-map "ospf_mgmt:BWPerPriority";
      type uint64;
      units "byte/s";
      max-elements "8";
      description
        "Unreserved bandwidth for each priority (bytes/s)";
    }
  }

  grouping OSPF-SH-MPLS-LINK {
    description "OSPF MPLS-TE link Information";

    container global-unreserve-bw-per-priority {
      description
        "Global pool unreserved bandwidth for each
        priority (bytes/s)";
      uses OSPF-SH-MPLS-BW;
    }

    container sub-pool-unreserve-bw-per-priority {
      description
        "Sub pool unreserved bandwidth for each priority
        (bytes/s)";
      uses OSPF-SH-MPLS-BW;
    }

    container link-protocol-priority-capability {
      description "Link protocol and protocol priority capability";
      uses OSPF-SH-MPLS-LINK-PROTOPRIO;
    }

    container link-sw-capability {
      description "Link switching capability";
      uses OSPF-SH-MPLS-IXCD-CAP;
    }

    container extended-admin-group-list {
      description "Extended Admin Group";
      uses OSPF-SH-MPLS-EAG;
    }
    leaf new-link {
      xr:xr-xml-map "ospf_mgmt:NewLink";
      type boolean;
      description "If true, Link is new";
    }
    leaf fragment-id {
      xr:xr-xml-map "ospf_mgmt:FragmentID";
      type uint32;
      description "Fragment ID for this link";
    }
    leaf mpls-link-instance {
      xr:xr-xml-map "ospf_mgmt:MPLSLinkInstance";
      type uint32;
      description "Link instance";
    }
    leaf mpls-link-type {
      xr:xr-xml-map "ospf_mgmt:MPLSLinkType";
      type Link-subnet;
      description "Type of link";
    }
    leaf neighbor-system-id {
      xr:xr-xml-map "ospf_mgmt:NeighborSystemID";
      type inet:ipv4-address;
      description "Neighbor system ID";
    }
    leaf link-address {
      xr:xr-xml-map "ospf_mgmt:LinkAddress";
      type inet:ipv4-address;
      description "The local interface address";
    }
    leaf neighbor-ip-address {
      xr:xr-xml-map "ospf_mgmt:NeighborIPAddress";
      type inet:ipv4-address;
      description "Neighbor IP address.";
    }
    leaf igp-metric {
      xr:xr-xml-map "ospf_mgmt:IGPMetric";
      type uint32;
      description "Link IGP metric";
    }
    leaf te-metric {
      xr:xr-xml-map "ospf_mgmt:TEMetric";
      type uint32;
      description "Link TE metric";
    }
    leaf maximum-link-bw {
      xr:xr-xml-map "ospf_mgmt:MaximumLinkBW";
      type uint32;
      units "byte/s";
      description "Maximum link bandwidth (bytes/s)";
    }
    leaf maximum-link-reservable-bw {
      xr:xr-xml-map "ospf_mgmt:MaximumLinkReservableBW";
      type uint32;
      units "byte/s";
      description
        "Maximum link global pool reservable bandwidth
        (bytes/s)";
    }
    leaf maximum-link-sub-reservable-bw {
      xr:xr-xml-map "ospf_mgmt:MaximumLinkSubReservableBW";
      type uint32;
      units "byte/s";
      description
        "Maximum link subpool reservable bandwidth
        (bytes/s)";
    }
    leaf priority-count {
      xr:xr-xml-map "ospf_mgmt:PriorityCount";
      type int32;
      description "Number of priorities.";
    }
    leaf affinity {
      xr:xr-xml-map "ospf_mgmt:Affinity";
      type uint32;
      description "Affinity";
    }
    leaf output-interface-id {
      xr:xr-xml-map "ospf_mgmt:OutputInterfaceID";
      type uint32;
      description "Output interface ID";
    }
    leaf input-interface-id {
      xr:xr-xml-map "ospf_mgmt:InputInterfaceID";
      type uint32;
      description "Input interface ID";
    }
    leaf dste-in-use {
      xr:xr-xml-map "ospf_mgmt:DSTEInUse";
      type boolean;
      description "A DS-TE Allocation Model in use";
    }
    leaf dste-allocation-model-id {
      xr:xr-xml-map "ospf_mgmt:DSTEAllocationModelID";
      type Igpte-lib-bw-model;
      description "DS-TE Allocation Model ID";
    }
    leaf number-of-optional-tl-vs {
      xr:xr-xml-map "ospf_mgmt:NumberOfOptionalTLVs";
      type uint8;
      description "Number of Optional TLVs";
    }

    list mplste-link-opt-tlv {
      description "List of Optional TLVs";
      uses OSPF-SH-MPLS-TEL-OPT-TLV;
    }
  }

  grouping OSPF-SH-MPLS {
    description "OSPF MPLS-TE Information";
    leaf mpls-te-router-id {
      xr:xr-xml-map "ospf_mgmt:MPLS_TERouterID";
      type inet:ipv4-address;
      description "OSPF MPLS-TE router ID";
    }
    leaf mpls-te-enabled {
      xr:xr-xml-map "ospf_mgmt:MPLS_TEEnabled";
      type boolean;
      description "If true, MPLS-TE enabled in area";
    }
    leaf mpls-te-initialized {
      xr:xr-xml-map "ospf_mgmt:MPLS_TEInitialized";
      type boolean;
      description "If true, MPLS-TE initialized in the area";
    }
    leaf mpls-te-area-id {
      xr:xr-xml-map "ospf_mgmt:MPLS_TEAreaID";
      type string {
        length "0..16";
      }
      description
        "Area ID string in decimal or dotted decimal
        format";
    }
    leaf mpls-te-area-instance {
      xr:xr-xml-map "ospf_mgmt:MPLS_TEAreaInstance";
      type uint32;
      description "Area information instance";
    }
    leaf mpls-te-router-address {
      xr:xr-xml-map "ospf_mgmt:MPLS_TERouterAddress";
      type inet:ipv4-address;
      description "MPLS-TE router address";
    }
    leaf mpls-te-next-fragment-id {
      xr:xr-xml-map "ospf_mgmt:MPLS_TENextFragmentID";
      type uint32;
      description "Next MPLS-TE fragment ID";
    }
    leaf spacious-fragment {
      xr:xr-xml-map "ospf_mgmt:SpaciousFragment";
      type boolean;
      description "If true, fragment has space for next link";
    }

    list mpls-te-link {
      description "MPLS-TE links in the area";
      uses OSPF-SH-MPLS-LINK;
    }

    list mpls-te-fragment {
      description "MPLS TE fragments in the area";
      uses OSPF-SH-MPLS-FRAGMENT;
    }
  }

  grouping OSPF-SH-LSA-SUM {
    description "LSA Summary Entry";
    leaf header-lsa-type {
      xr:xr-xml-map "ospf_mgmt:HeaderLSAType";
      type Lsa;
      description "LSA Type";
    }
    leaf header-lsa-age {
      xr:xr-xml-map "ospf_mgmt:HeaderLSAAge";
      type uint16;
      description "Age of the LSA (s)";
    }
    leaf header-ls-id {
      xr:xr-xml-map "ospf_mgmt:HeaderLS_ID";
      type inet:ipv4-address;
      description "LSA ID";
    }
    leaf header-advertising-router {
      xr:xr-xml-map "ospf_mgmt:HeaderAdvertisingRouter";
      type inet:ipv4-address;
      description "Router ID of the Advertising Router";
    }
    leaf header-sequence-number {
      xr:xr-xml-map "ospf_mgmt:HeaderSequenceNumber";
      type uint32;
      description "Current LSA sequence number";
    }
    leaf header-lsa-checksum {
      xr:xr-xml-map "ospf_mgmt:HeaderLSAChecksum";
      type uint16;
      description "Checksum of the LSA";
    }
  }

  grouping OSPF-SH-FLOOD-LIST {
    description "OSPF Flood List";
    leaf flood-interface-name {
      xr:xr-xml-map "ospf_mgmt:FloodInterfaceName";
      type xr:Interface-name;
      description "Interface name";
    }
    leaf flood-pacing-timer {
      xr:xr-xml-map "ospf_mgmt:FloodPacingTimer";
      type uint32;
      description "Time until next LS update due (ms)";
    }
    leaf flood-lsa-count {
      xr:xr-xml-map "ospf_mgmt:FloodLSACount";
      type uint32;
      description "Number of LSAs currently being flooded";
    }

    list area-flood {
      description "Area scope floodlist";
      uses OSPF-SH-LSA-SUM;
    }

    list as-flood {
      description "AS scope floodlist";
      uses OSPF-SH-LSA-SUM;
    }
  }
}
