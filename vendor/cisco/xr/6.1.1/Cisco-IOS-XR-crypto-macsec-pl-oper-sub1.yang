submodule Cisco-IOS-XR-crypto-macsec-pl-oper-sub1 {

  belongs-to Cisco-IOS-XR-crypto-macsec-pl-oper {
    prefix Cisco-IOS-XR-crypto-macsec-pl-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR crypto-macsec-pl package operational data.

     Copyright (c) 2013-2016 by Cisco Systems, Inc.
     All rights reserved.";

  revision "2015-11-09" {
    description
      "IOS XR 6.0 revision.";
  }


  grouping PL-MSFPGA-FLOW-INFO {
    description "Flow Information";
    leaf flow-id {
      xr:xr-xml-map "platform_macsec_ea_show:flow_id";
      type uint8;
      description "Flow Index";
    }
    leaf valid {
      xr:xr-xml-map "platform_macsec_ea_show:valid";
      type boolean;
      description "Flow Validity";
    }
    leaf is-egress {
      xr:xr-xml-map "platform_macsec_ea_show:is_egress";
      type boolean;
      description "rx_tx direction";
    }
    leaf in-use {
      xr:xr-xml-map "platform_macsec_ea_show:in_use";
      type boolean;
      description "In Use";
    }
    leaf action {
      xr:xr-xml-map "platform_macsec_ea_show:action";
      type uint8;
      description "Action";
    }
    leaf smac-inuse {
      xr:xr-xml-map "platform_macsec_ea_show:smac_inuse";
      type boolean;
      description "If MAC SA in Use";
    }
    leaf dmac-inuse {
      xr:xr-xml-map "platform_macsec_ea_show:dmac_inuse";
      type boolean;
      description "If MAC DA in Use";
    }
    leaf ethertype {
      xr:xr-xml-map "platform_macsec_ea_show:ethertype";
      type uint16;
      description "Ether Type";
    }
    leaf outer-vlan {
      xr:xr-xml-map "platform_macsec_ea_show:outer_vlan";
      type uint16;
      description "Outer VLAN ID";
    }
    leaf outer-vlan-up {
      xr:xr-xml-map "platform_macsec_ea_show:outer_vlan_up";
      type uint8;
      description "Outer Vlan UserPri";
    }
    leaf outer-vlan-tpid {
      xr:xr-xml-map "platform_macsec_ea_show:outer_vlan_tpid";
      type uint16;
      description "Outer Vlan TPID";
    }
    leaf inner-vlan {
      xr:xr-xml-map "platform_macsec_ea_show:inner_vlan";
      type uint16;
      description "Inner VLAN ID";
    }
    leaf inner-vlan-up {
      xr:xr-xml-map "platform_macsec_ea_show:inner_vlan_up";
      type uint8;
      description "Inner Vlan UserPri";
    }
    leaf inner-vlan-tpid {
      xr:xr-xml-map "platform_macsec_ea_show:inner_vlan_tpid";
      type uint16;
      description "Inner Vlan TPID";
    }
    leaf source-port {
      xr:xr-xml-map "platform_macsec_ea_show:source_port";
      type uint32;
      description "Source Port";
    }
    leaf source-port-chk {
      xr:xr-xml-map "platform_macsec_ea_show:source_port_chk_en";
      type boolean;
      description "Source Port ChkEn";
    }
    leaf sci-inuse {
      xr:xr-xml-map "platform_macsec_ea_show:sci_inuse";
      type boolean;
      description "If SCI in use";
    }
    leaf sci {
      xr:xr-xml-map "platform_macsec_ea_show:sci";
      type uint64;
      description "SCI";
    }
    leaf match-pri {
      xr:xr-xml-map "platform_macsec_ea_show:match_pri";
      type uint8;
      description "Match Priority";
    }
    leaf is-ctrl-pkt {
      xr:xr-xml-map "platform_macsec_ea_show:is_ctrl_pkt";
      type boolean;
      description "Is Control Pkt";
    }
    leaf ctrl-check {
      xr:xr-xml-map "platform_macsec_ea_show:ctrl_check_en";
      type boolean;
      description "Ctrl Pkt ChkEn";
    }
    leaf match-untagged {
      xr:xr-xml-map "platform_macsec_ea_show:match_untagged";
      type boolean;
      description "MatchUntagged";
    }
    leaf match-tagged {
      xr:xr-xml-map "platform_macsec_ea_show:match_tagged";
      type boolean;
      description "MatchTagged";
    }
    leaf match-bad-tag {
      xr:xr-xml-map "platform_macsec_ea_show:match_bad_tag";
      type boolean;
      description "Match Bad Tag";
    }
    leaf match-kay-tag {
      xr:xr-xml-map "platform_macsec_ea_show:match_kay_tag";
      type boolean;
      description "MatchKaYTag";
    }
    leaf tci-v {
      xr:xr-xml-map "platform_macsec_ea_show:tci_v";
      type uint8;
      description "TCI V";
    }
    leaf tci-e-xr {
      xr:xr-xml-map "platform_macsec_ea_show:tci_es";
      type uint8;
      description "TCI ES";
    }
    leaf tci-sc {
      xr:xr-xml-map "platform_macsec_ea_show:tci_sc";
      type uint8;
      description "TCI SC";
    }
    leaf tci-scb {
      xr:xr-xml-map "platform_macsec_ea_show:tci_scb";
      type uint8;
      description "TCI SCB";
    }
    leaf tci {
      xr:xr-xml-map "platform_macsec_ea_show:tci_e";
      type uint8;
      description "TCI E";
    }
    leaf tci-c {
      xr:xr-xml-map "platform_macsec_ea_show:tci_c";
      type uint8;
      description "TCI C";
    }
    leaf tci-an {
      xr:xr-xml-map "platform_macsec_ea_show:tci_an";
      type uint8;
      description "TCI AN";
    }
    leaf tci-an-chk {
      xr:xr-xml-map "platform_macsec_ea_show:tci_an_chk_en";
      type boolean;
      description "TciAnChkEn";
    }
    leaf tci-chk {
      xr:xr-xml-map "platform_macsec_ea_show:tci_chk_en";
      type boolean;
      description "TciChkEn";
    }
    leaf sai {
      xr:xr-xml-map "platform_macsec_ea_show:sai";
      type uint32;
      description "SAI";
    }
    leaf-list macsa {
      xr:xr-xml-map "platform_macsec_ea_show:MACSA";
      type uint8;
      description "MAC SA";
    }
    leaf-list macda {
      xr:xr-xml-map "platform_macsec_ea_show:MACDA";
      type uint8;
      description "MAC DA";
    }
  }

  grouping PL-MSFPGA-FLOW {
    description "Flow Details";

    container tx-flow {
      description "Tx Flow Details";
      uses PL-MSFPGA-FLOW-INFO;
    }

    container rx-flow {
      description "Rx Flow Details";
      uses PL-MSFPGA-FLOW-INFO;
    }
  }

  grouping PL-MACSEC-FLOW {
    description "MACSec HW Flow Details";

    container msfpga-flow {
      description "MSFPGA Flow Information";
      uses PL-MSFPGA-FLOW;
    }
    leaf hw-type {
      xr:xr-xml-map "platform_macsec_ea_show:hw_type";
      type uint8;
      description "Hardware Type";
    }
  }

  grouping PL-MSFPGA-SA-INFO {
    description "SA specific information";
    leaf sa-id {
      xr:xr-xml-map "platform_macsec_ea_show:sa_id";
      type uint8;
      description "SA Index";
    }
    leaf valid {
      xr:xr-xml-map "platform_macsec_ea_show:valid";
      type boolean;
      description "SA Validity";
    }
    leaf is-egress {
      xr:xr-xml-map "platform_macsec_ea_show:is_egress";
      type boolean;
      description "rx_tx direction";
    }
    leaf crypto-algo {
      xr:xr-xml-map "platform_macsec_ea_show:crypto_algo";
      type uint8;
      description "Crypto Algorithm";
    }
    leaf key-len {
      xr:xr-xml-map "platform_macsec_ea_show:key_len";
      type uint8;
      description "Key Length";
    }
    leaf an {
      xr:xr-xml-map "platform_macsec_ea_show:an";
      type uint8;
      description "Association Number";
    }
    leaf xpn {
      xr:xr-xml-map "platform_macsec_ea_show:xpn_en";
      type uint8;
      description "XPN EN";
    }
    leaf sci {
      xr:xr-xml-map "platform_macsec_ea_show:sci";
      type uint64;
      description "SCI";
    }
    leaf in-use {
      xr:xr-xml-map "platform_macsec_ea_show:in_use";
      type boolean;
      description "In Use";
    }
    leaf next-pn {
      xr:xr-xml-map "platform_macsec_ea_show:next_pn";
      type uint64;
      description "Next Packet Number";
    }
    leaf c-offset {
      xr:xr-xml-map "platform_macsec_ea_show:c_offset";
      type uint8;
      description "Conf offset";
    }
    leaf action {
      xr:xr-xml-map "platform_macsec_ea_show:action";
      type uint8;
      description "Action";
    }
    leaf q-bit {
      xr:xr-xml-map "platform_macsec_ea_show:q_bit";
      type boolean;
      description "Q bit";
    }
    leaf qq-bit {
      xr:xr-xml-map "platform_macsec_ea_show:qq_bit";
      type boolean;
      description "QQ bit";
    }
  }

  grouping PL-MSFPGA-SA {
    description "SA details";

    container tx-sa {
      description "Tx SA Details";
      uses PL-MSFPGA-SA-INFO;
    }

    container rx-sa {
      description "Rx SA Details";
      uses PL-MSFPGA-SA-INFO;
    }
  }

  grouping PL-MACSEC-SA {
    description "MACSec HW SA Details";

    container msfpga-sa {
      description "MSFPGA SA Information";
      uses PL-MSFPGA-SA;
    }
    leaf hw-type {
      xr:xr-xml-map "platform_macsec_ea_show:hw_type";
      type uint8;
      description "Hardware Type";
    }
  }

  grouping PL-MSFPGA-RX-INTERFACE-MACSEC-STATS {
    description "Per Interface Macsec Ingress Stats";
    leaf in-pkt-untagged {
      xr:xr-xml-map "platform_macsec_ea_show:in_pkt_untagged";
      type uint64;
      description "Rx Pkts Untagged";
    }
    leaf in-pkt-notag {
      xr:xr-xml-map "platform_macsec_ea_show:in_pkt_notag";
      type uint64;
      description "Rx Pkts Notag";
    }
    leaf in-pkt-bad-tag {
      xr:xr-xml-map "platform_macsec_ea_show:in_pkt_bad_tag";
      type uint64;
      description "Rx Pkts Bad tag";
    }
    leaf in-pkt-no-sci {
      xr:xr-xml-map "platform_macsec_ea_show:in_pkt_no_sci";
      type uint64;
      description "Rx Pkts No Sci";
    }
    leaf in-pkt-unknown-sci {
      xr:xr-xml-map "platform_macsec_ea_show:in_pkt_unknown_sci";
      type uint64;
      description "Rx Pkts Unknown Sci";
    }
    leaf in-pkt-tagged {
      xr:xr-xml-map "platform_macsec_ea_show:in_pkt_tagged";
      type uint64;
      description "Rx Pkts Tagged";
    }
    leaf in-pkt-overrun {
      xr:xr-xml-map "platform_macsec_ea_show:in_pkt_overrun";
      type uint64;
      description "Rx Pkts Over Run";
    }
    leaf in-pkt-uncontrolled {
      xr:xr-xml-map "platform_macsec_ea_show:in_pkt_uncontrolled";
      type uint64;
      description "Rx Pkts Uncontrolled";
    }
  }

  grouping PL-MSFPGA-TX-INTERFACE-MACSEC-STATS {
    description "Per Interface Macsec Egress Stats";
    leaf out-pkt-uncontrolled {
      xr:xr-xml-map "platform_macsec_ea_show:out_pkt_uncontrolled";
      type uint64;
      description "Tx Pkts Uncontrolled";
    }
    leaf out-pkt-untagged {
      xr:xr-xml-map "platform_macsec_ea_show:out_pkt_untagged";
      type uint64;
      description "Tx Pkts Untagged";
    }
    leaf out-pkt-too-long {
      xr:xr-xml-map "platform_macsec_ea_show:out_pkt_too_long";
      type uint64;
      description "Tx Pkts Too Long";
    }
  }

  grouping PL-MSFPGA-RX-SA-STATS {
    description "Per SA Ingress Stats";
    leaf in-pkts-unused-sa {
      xr:xr-xml-map "platform_macsec_ea_show:in_pkts_unused_sa";
      type uint64;
      description "Rx Pkts Unused SA";
    }
    leaf in-pkts-not-using-sa {
      xr:xr-xml-map "platform_macsec_ea_show:in_pkts_not_using_sa";
      type uint64;
      description "Rx Pkts Not Using SA";
    }
    leaf in-pkts-not-valid {
      xr:xr-xml-map "platform_macsec_ea_show:in_pkts_not_valid";
      type uint64;
      description "Rx Pkts Not Valid";
    }
    leaf in-pkts-invalid {
      xr:xr-xml-map "platform_macsec_ea_show:in_pkts_invalid";
      type uint64;
      description "Rx Pkts Invalid";
    }
    leaf in-pkts-ok {
      xr:xr-xml-map "platform_macsec_ea_show:in_pkts_ok";
      type uint64;
      description "Rx Pkts OK";
    }
    leaf in-pkts-delayed {
      xr:xr-xml-map "platform_macsec_ea_show:in_pkts_delayed";
      type uint64;
      description "Rx Pkts Delayed";
    }
    leaf in-pkts-late {
      xr:xr-xml-map "platform_macsec_ea_show:in_pkts_late";
      type uint64;
      description "Rx Pkts Late";
    }
    leaf in-pkts-unchecked {
      xr:xr-xml-map "platform_macsec_ea_show:in_pkts_unchecked";
      type uint64;
      description "Rx Pkts Unchecked";
    }
    leaf in-octets-validated {
      xr:xr-xml-map "platform_macsec_ea_show:in_octets_validated";
      type uint64;
      description "Rx Octets Validated";
    }
    leaf in-octets-decrypted {
      xr:xr-xml-map "platform_macsec_ea_show:in_octets_decrypted";
      type uint64;
      description "Rx Octets Decrypted";
    }
  }

  grouping PL-MSFPGA-TX-SA-STATS {
    description "Per SA Egress Stats";
    leaf out-pkts-protected {
      xr:xr-xml-map "platform_macsec_ea_show:out_pkts_protected";
      type uint64;
      description "Tx Pkts Protected";
    }
    leaf out-pkts-encrypted {
      xr:xr-xml-map "platform_macsec_ea_show:out_pkts_encrypted";
      type uint64;
      description "Tx Pkts Encrypted";
    }
    leaf out-octets-protected {
      xr:xr-xml-map "platform_macsec_ea_show:out_octets_protected";
      type uint64;
      description "Tx Octets Protected";
    }
    leaf out-octets-encrypted {
      xr:xr-xml-map "platform_macsec_ea_show:out_octets_encrypted";
      type uint64;
      description "Tx Octets Encrypted";
    }
  }

  grouping PL-MSFPGA-STATS {
    description "Stats Details";

    container tx-sa-stats {
      description "Tx SA Stats";
      uses PL-MSFPGA-TX-SA-STATS;
    }

    container rx-sa-stats {
      description "Rx SA Stats";
      uses PL-MSFPGA-RX-SA-STATS;
    }

    container tx-interface-macsec-stats {
      description "Tx interface Macsec Stats";
      uses PL-MSFPGA-TX-INTERFACE-MACSEC-STATS;
    }

    container rx-interface-macsec-stats {
      description "Rx interface Macsec Stats";
      uses PL-MSFPGA-RX-INTERFACE-MACSEC-STATS;
    }
  }

  grouping PL-MACSEC-STATS {
    description "Per SA Stats Counters";

    container msfpga-stats {
      description "MSFPGA Stats";
      uses PL-MSFPGA-STATS;
    }
    leaf hw-type {
      xr:xr-xml-map "platform_macsec_ea_show:hw_type";
      type uint8;
      description "Hardware Type";
    }
  }
}
