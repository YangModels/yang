module Cisco-IOS-XR-asr9k-prm-cfg {

  /*** NAMESPACE / PREFIX DEFINITION ***/

  namespace "http://cisco.com/ns/yang/Cisco-IOS-XR-asr9k-prm-cfg";


  prefix "asr9k-prm-cfg";

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR asr9k-prm package configuration.

     This module contains definitions
     for the following management objects:
       hardware-module-qos-mode: QoS mode in hardware module port(s)
       hardware-module-tcp-mss-adjust: hardware module tcp mss adjust
       hardware-module-load-balance: hardware module load balance
       hardware-module-tcam: hardware module tcam
       hardware-module-efd: hardware module efd

     Copyright (c) 2013-2016 by Cisco Systems, Inc.
     All rights reserved.";

  revision "2015-11-09" {
    description
      "IOS XR 6.0 revision.";
  }

  typedef Asr9k-efd-operation {
    type enumeration {
      enum less-than {
        value 2;
        description "Less than";
      }
      enum greater-than-or-equal {
        value 3;
        description "Greater than or equal";
      }
    }
    description "Asr9k efd operation";
  }
  typedef Asr9k-efd-mode {
    type enumeration {
      enum only-outer-encap {
        value 0;
        description "Only check outer encap";
      }
      enum include-inner-encap {
        value 1;
        description "Check outer and inner encap";
      }
    }
    description "Asr9k efd mode";
  }
  typedef Prm-tcam-profile {
    type enumeration {
      enum profile0 {
        value 0;
        description "Profile 0";
      }
      enum profile1 {
        value 1;
        description "Profile 1";
      }
      enum profile2 {
        value 2;
        description "Profile 2";
      }
    }
    description "Prm tcam profile";
  }

  container hardware-module-qos-mode {
    xr:xr-xml-map "prm_qosmode_cfg:HardwareModuleQoSMode";
    description "QoS mode in hardware module port(s)";

    container nodes {
      xr:xr-xml-map "prm_qosmode_cfg:NodeTable";
      description "QoS applicable nodes";

      list node {
        xr:xr-xml-map "prm_qosmode_cfg:Node";
        key "node-name";
        description "A node";
        leaf child-shaping-disable {
          xr:xr-xml-map "prm_qosmode_cfg:ChildShapingDisable";
          xr:xr-cli-map "location <location> qos-mode qos-child-sha"+
            "ping-disabled ";
          type empty;
          description "Disable child level/flat policy shaping";
        }
        leaf lowburst-enable {
          xr:xr-xml-map "prm_qosmode_cfg:LowburstEnable";
          xr:xr-cli-map "location <location> qos-mode lowburst-enab"+
            "led ";
          type empty;
          description "Enable low burst mode for TM entity";
        }
        leaf node-name {
          xr:xr-xml-map "prm_qosmode_cfg:NodeName";
          type xr:Node-id;
          description "Node ID";
        }
      }
    }
  }

  container hardware-module-tcp-mss-adjust {
    xr:xr-xml-map "prm_tcp_mss_adj_cfg:HardwareModuleTCP_MSSAdjust";
    description "hardware module tcp mss adjust";

    container nodes {
      xr:xr-xml-map "prm_tcp_mss_adj_cfg:NodeTable";
      description "TCP MSS Adjust applicable nodes";

      list node {
        xr:xr-xml-map "prm_tcp_mss_adj_cfg:Node";
        key "node-name";
        description "A node";

        container nps {
          xr:xr-xml-map "prm_tcp_mss_adj_cfg:NPTable";
          description "TCP MSS Adjust NPs";

          list np {
            xr:xr-xml-map "prm_tcp_mss_adj_cfg:NP";
            key "np-id";
            description "NP number";
            leaf adjust-value {
              xr:xr-xml-map "prm_tcp_mss_adj_cfg:AdjustValue";
              xr:xr-cli-map "location <location> tcp-mss-adjust np "+
                "<number> value <number> ";
              type uint32 {
                range "1280..1535";
              }
              units "byte";
              description "TCP MSS Adjust value";
            }
            leaf np-id {
              xr:xr-xml-map "prm_tcp_mss_adj_cfg:NP_ID";
              type uint32 {
                range "0..7";
              }
              description "Number between 0-7";
            }
          }
        }
        leaf node-name {
          xr:xr-xml-map "prm_tcp_mss_adj_cfg:NodeName";
          type xr:Node-id;
          description "Node ID";
        }
      }
    }
  }

  container hardware-module-load-balance {
    xr:xr-xml-map "prm_bundle_lb_cfg:HardwareModuleLoadBalance";
    description "hardware module load balance";

    container bundle {
      xr:xr-xml-map "prm_bundle_lb_cfg:Bundle";
      description "Bundle load balance options";

      container l2-service {
        xr:xr-xml-map "prm_bundle_lb_cfg:L2Service";
        description "Load balance for L2 services";
        leaf l3-parameters {
          xr:xr-xml-map "prm_bundle_lb_cfg:L3Parameters";
          type empty;
          description
            "Load balance L2 services over bundle with L3
            parameters";
        }
      }
    }
  }

  container hardware-module-tcam {
    xr:xr-xml-map "prm_tcam_cfg:HardwareModuleTCAM";
    description "hardware module tcam";

    container nodes {
      xr:xr-xml-map "prm_tcam_cfg:NodeTable";
      description "TCAM applicable nodes";

      list node {
        xr:xr-xml-map "prm_tcam_cfg:Node";
        key "node-name";
        description "A TCAM applicable node";
        leaf profile {
          xr:xr-xml-map "prm_tcam_cfg:Profile";
          xr:xr-cli-map "<location> ";
          type Prm-tcam-profile;
          default "profile0";
          description "A TCAM partition profile";
        }
        leaf node-name {
          xr:xr-xml-map "prm_tcam_cfg:NodeName";
          type xr:Node-id;
          description "Node ID";
        }
      }
    }
    leaf global-profile {
      xr:xr-xml-map "prm_tcam_cfg:GlobalProfile";
      xr:xr-cli-map "all ";
      type Prm-tcam-profile;
      default "profile0";
      description
        "Global TCAM partition profile for all TCAM
        applicable nodes";
    }
  }

  container hardware-module-efd {
    xr:xr-xml-map "prm_efd_cfg:HardwareModuleEFD";
    description "hardware module efd";

    container nodes {
      xr:xr-xml-map "prm_efd_cfg:NodeTable";
      description "EFD applicable nodes";

      list node {
        xr:xr-xml-map "prm_efd_cfg:Node";
        key "node-name";
        description "A node";

        container ip-precedence {
          xr:xr-xml-map "prm_efd_cfg:IPPrecedence";
          presence "Indicates a ip-precedence node is configured.";
          description "EFD IP parameters";
          leaf precedence {
            xr:xr-xml-map "prm_efd_cfg:Precedence";
            type uint32 {
              range "0..7";
            }
            mandatory true;
            description "IP TOS precedence threshold";
          }
          leaf operation {
            xr:xr-xml-map "prm_efd_cfg:Operation";
            type Asr9k-efd-operation;
            default "greater-than-or-equal";
            description "IP operation";
          }
        }

        container vlan-cos {
          xr:xr-xml-map "prm_efd_cfg:VLAN_COS";
          presence "Indicates a vlan-cos node is configured.";
          description "EFD VLAN parameters";
          leaf cos {
            xr:xr-xml-map "prm_efd_cfg:COS";
            type uint32 {
              range "0..7";
            }
            mandatory true;
            description "VLAN COS threshold";
          }
          leaf operation {
            xr:xr-xml-map "prm_efd_cfg:Operation";
            type Asr9k-efd-operation;
            default "greater-than-or-equal";
            description "VLAN operation";
          }
        }

        container mpls-exp {
          xr:xr-xml-map "prm_efd_cfg:MPLS_EXP";
          presence "Indicates a mpls-exp node is configured.";
          description "EFD MPLS parameters";
          leaf exp {
            xr:xr-xml-map "prm_efd_cfg:EXP";
            type uint32 {
              range "0..7";
            }
            mandatory true;
            description "MPLS EXP threshold";
          }
          leaf operation {
            xr:xr-xml-map "prm_efd_cfg:Operation";
            type Asr9k-efd-operation;
            default "greater-than-or-equal";
            description "MPLS operation";
          }
        }
        leaf enable {
          xr:xr-xml-map "prm_efd_cfg:Enable";
          type empty;
          description "Enable EFD for this node";
        }
        leaf mode {
          xr:xr-xml-map "prm_efd_cfg:Mode";
          xr:xr-cli-map "location <location> early-fast-discard (mo"+
            "de <enum>)|(location <location> early-fast-discard (vl"+
            "an-cos <number> [vlan-op <enum>])|(ip-prec <number> [i"+
            "p-op <enum>])|(mpls-exp <number> [mpls-op <enum>])) ";
          type Asr9k-efd-mode;
          description "EFD mode parameter.";
        }
        leaf node-name {
          xr:xr-xml-map "prm_efd_cfg:NodeName";
          type xr:Node-id;
          description "Node Name";
        }
      }
    }
  }
}
