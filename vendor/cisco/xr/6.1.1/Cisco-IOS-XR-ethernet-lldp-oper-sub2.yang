submodule Cisco-IOS-XR-ethernet-lldp-oper-sub2 {

  belongs-to Cisco-IOS-XR-ethernet-lldp-oper {
    prefix Cisco-IOS-XR-ethernet-lldp-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR ethernet-lldp package operational data.

     Copyright (c) 2013-2016 by Cisco Systems, Inc.
     All rights reserved.";

  revision "2015-11-09" {
    description
      "IOS XR 6.0 revision.";
  }


  grouping LLDP-MGR-GLOBAL-INFO {
    description "LLDP global info";
    leaf timer {
      xr:xr-xml-map "lldp_mgr:Timer";
      type uint32;
      description
        "Rate at which LLDP packets                      
        are sent (in sec)";
    }
    leaf hold-time {
      xr:xr-xml-map "lldp_mgr:HoldTime";
      type uint32;
      description
        "Length  of time  (in sec)                       
        that receiver must keep this                    
        packet";
    }
    leaf re-init {
      xr:xr-xml-map "lldp_mgr:ReInit";
      type uint32;
      description
        "Delay (in sec) for LLDP                         
        initialization on any                           
        interface";
    }
  }
}
