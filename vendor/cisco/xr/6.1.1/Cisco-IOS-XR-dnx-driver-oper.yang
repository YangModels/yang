module Cisco-IOS-XR-dnx-driver-oper {

  /*** NAMESPACE / PREFIX DEFINITION ***/

  namespace "http://cisco.com/ns/yang/Cisco-IOS-XR-dnx-driver-oper";


  prefix "dnx-driver-oper";

  /*** LINKAGE (IMPORTS / INCLUDES) ***/

  import Cisco-IOS-XR-types { prefix "xr"; }

  include Cisco-IOS-XR-dnx-driver-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR dnx-driver package operational data.

     This module contains definitions
     for the following management objects:
       fia: FIA driver operational data

     Copyright (c) 2013-2016 by Cisco Systems, Inc.
     All rights reserved.";

  revision "2015-11-09" {
    description
      "IOS XR 6.0 revision.";
  }

  typedef Link-option-string {
    type string {
      pattern "(flap)|(topo)";
    }
    description
      "flap:Display link flap info, topo:Display link
      topo info";
  }
  typedef Fia-max-asic-instances {
    type uint32 {
      range "0..255";
    }
    description "Fia max asic instances";
  }
  typedef Link-info-max-number {
    type uint32 {
      range "0..35";
    }
    description "Link info max number";
  }
  typedef Diag-shell-unit-number {
    type uint32 {
      range "0..63";
    }
    description "Diag shell unit number";
  }

  container fia {
    xr:xr-xml-map "fia_oper:FIA";
    config false;
    description "FIA driver operational data";

    container nodes {
      xr:xr-xml-map "fia_oper:NodeTable";
      description "FIA driver operational data for available nodes";

      list node {
        xr:xr-xml-map "fia_oper:Node";
        key "node-name";
        description "FIA operational data for a particular node";

        container rx-link-information {
          xr:xr-xml-map "fia_oper:RXLinkInformation";
          description "FIA link rx information";

          container link-options {
            xr:xr-xml-map "fia_oper:LinkOptionTable";
            description "Option table for link rx information";

            list link-option {
              xr:xr-xml-map "fia_oper:LinkOption";
              key "option";
              description "Option : topo , flag , stats";

              container rx-asic-instances {
                xr:xr-xml-map "fia_oper:RXInstanceTable";
                description "Instance table for rx information";

                list rx-asic-instance {
                  xr:xr-xml-map "fia_oper:RXAsicInstance";
                  key "instance";
                  description
                    "Instance number for rx link information";

                  container rx-links {
                    xr:xr-xml-map "fia_oper:RXLinkTable";
                    description
                      "Link table class for rx information";

                    list rx-link {
                      xr:xr-xml-map "fia_oper:RXLinks";
                      description
                        "Link number for rx link information";
                      leaf start-number {
                        xr:xr-xml-map "fia_oper:StartNumber";
                        type Link-info-max-number;
                        description "Start number";
                      }
                      leaf end-number {
                        xr:xr-xml-map "fia_oper:EndNumber";
                        type Link-info-max-number;
                        description "End number";
                      }
                      leaf status-option {
                        xr:xr-xml-map "fia_oper:StatusOption";
                        type xr:Cisco-ios-xr-string;
                        description "RX link status option";
                      }

                      list rx-link {
                        xr:xr-xml-map "fia_oper:RXLink";
                        key "link";
                        description "Single link information";
                        leaf link {
                          xr:xr-xml-map "fia_oper:Link";
                          type int32;
                          description "Single link";
                        }
                        uses FIA-EDM-RXLINK;
                      }
                    }
                  }
                  leaf instance {
                    xr:xr-xml-map "fia_oper:Instance";
                    type Fia-max-asic-instances;
                    description "Receive instance";
                  }
                }
              }
              leaf option {
                xr:xr-xml-map "fia_oper:Option";
                type Link-option-string;
                description "Link option";
              }
            }
          }
        }

        container driver-information {
          xr:xr-xml-map "fia_oper:DriverInformation";
          description "FIA driver information";
          uses FIA-EDM-DRIVER-INFO;
        }

        container clear-statistics {
          xr:xr-xml-map "fia_oper:ClearStatistics";
          description "Clear statistics information";

          container asic-instances {
            xr:xr-xml-map "fia_oper:InstanceTable";
            description
              "Instance table for clear statistics
              information";

            list asic-instance {
              xr:xr-xml-map "fia_oper:AsicInstance";
              key "asic-instance";
              description "Asic instance to be cleared";
              leaf asic-instance {
                xr:xr-xml-map "fia_oper:AsicInstance";
                type Fia-max-asic-instances;
                description "Asic instance";
              }
              leaf instance {
                xr:xr-xml-map "fia_oper:Instance";
                type int32;
                mandatory true;
                description "Clear value";
              }
            }
          }
        }

        container tx-link-information {
          xr:xr-xml-map "fia_oper:TXLinkInformation";
          description "FIA link TX information";

          container tx-status-option-table {
            xr:xr-xml-map "fia_oper:TXStatusOptionTable";
            description "Link table for tx information";

            container tx-status-option {
              xr:xr-xml-map "fia_oper:TXStatusOption";
              description "Option: data, ctrl, all- for now none";

              container tx-asic-instances {
                xr:xr-xml-map "fia_oper:TXInstanceTable";
                description "Instance table for tx information";

                list tx-asic-instance {
                  xr:xr-xml-map "fia_oper:TXAsicInstance";
                  key "instance";
                  description
                    "Instance number for tx link information";

                  container tx-links {
                    xr:xr-xml-map "fia_oper:TXLinkTable";
                    description "Link table for tx information";

                    list tx-link {
                      xr:xr-xml-map "fia_oper:TXLinks";
                      description
                        "Link number for tx link information";
                      leaf start-number {
                        xr:xr-xml-map "fia_oper:StartNumber";
                        type Link-info-max-number;
                        description "Start number";
                      }
                      leaf end-number {
                        xr:xr-xml-map "fia_oper:EndNumber";
                        type Link-info-max-number;
                        description "End number";
                      }

                      list tx-link {
                        xr:xr-xml-map "fia_oper:TXLink";
                        key "link";
                        description "Single link information";
                        leaf link {
                          xr:xr-xml-map "fia_oper:Link";
                          type int32;
                          description "Single Link";
                        }
                        uses FIA-EDM-TXLINK;
                      }
                    }
                  }
                  leaf instance {
                    xr:xr-xml-map "fia_oper:Instance";
                    type Fia-max-asic-instances;
                    description "Transmit instance";
                  }
                }
              }
            }
          }
        }

        container register-dump {
          xr:xr-xml-map "fia_oper:RegisterDump";
          description "FIA register dump information";

          container register-dump-units {
            xr:xr-xml-map "fia_oper:RegisterUnitTable";
            description "Unit table for register dump";

            list register-dump-unit {
              xr:xr-xml-map "fia_oper:RegisterDumpUnit";
              key "unit";
              description "Unit number for register dump";
              leaf unit {
                xr:xr-xml-map "fia_oper:Unit";
                type int32;
                description "Unit number";
              }
              uses FIA-EDM-REG-INFO;
            }
          }
        }

        container diag-shell {
          xr:xr-xml-map "fia_oper:DiagShell";
          description "FIA diag shell information";

          container diag-shell-units {
            xr:xr-xml-map "fia_oper:DiagUnitTable";
            description "Unit table for diag shell";

            list diag-shell-unit {
              xr:xr-xml-map "fia_oper:DiagShellUnit";
              key "unit";
              description "Unit number for diag shell statistics";

              container commands {
                xr:xr-xml-map "fia_oper:CommandTable";
                description "Command table for diag shell";

                list command {
                  xr:xr-xml-map "fia_oper:Command";
                  key "cmd";
                  description "Command for diag shell statistics";
                  leaf cmd {
                    xr:xr-xml-map "fia_oper:Cmd";
                    type string;
                    description "Shell command";
                  }

                  list output {
                    xr:xr-xml-map "fia_oper:Output";
                    key "output";
                    description "Added to support datalist";
                    leaf output {
                      xr:xr-xml-map "fia_oper:Output";
                      type xr:Cisco-ios-xr-string;
                      description "First line";
                    }
                    uses FIA-EDM-DIAG-SHELL-OUTPUT;
                  }
                }
              }
              leaf unit {
                xr:xr-xml-map "fia_oper:Unit";
                type Diag-shell-unit-number;
                description "Unit number";
              }
            }
          }
        }

        container oir-history {
          xr:xr-xml-map "fia_oper:OIRHistory";
          description "FIA operational data of oir history";

          container flags {
            xr:xr-xml-map "fia_oper:FlagTable";
            description "Flag table for history";

            list flag {
              xr:xr-xml-map "fia_oper:Flag";
              key "flag";
              description "Flag value for physical location";

              container slots {
                xr:xr-xml-map "fia_oper:SlotTable";
                description "Slot table for history";

                list slot {
                  xr:xr-xml-map "fia_oper:Slot";
                  key "slot";
                  description "Slot number for getting history";
                  leaf slot {
                    xr:xr-xml-map "fia_oper:Slot";
                    type int32;
                    description "Slot number";
                  }
                  uses FIA-EDM-DRIVER-INFO;
                }
              }
              leaf flag {
                xr:xr-xml-map "fia_oper:Flag";
                type int32;
                description "Flag value";
              }
            }
          }
        }

        container asic-statistics {
          xr:xr-xml-map "fia_oper:AsicStatistics";
          description "FIA asic statistics information";

          container statistics-asic-instances {
            xr:xr-xml-map "fia_oper:StatisticsInstanceTable";
            description "Instance table for statistics";

            list statistics-asic-instance {
              xr:xr-xml-map "fia_oper:StatisticsAsicInstance";
              key "instance";
              description "Asic instance for statistics";

              container pbc-statistics {
                xr:xr-xml-map "fia_oper:PBCStatistics";
                description "Packet Byte Counter for a Asic";

                container pbc-stats {
                  xr:xr-xml-map "fia_oper:PBCStats";
                  description "PBC stats bag";
                  uses FIA-EDM-STATS-INFO;
                }
              }

              container fmac-statistics {
                xr:xr-xml-map "fia_oper:FMACStatistics";
                description "Statistics of FMAC";

                container fmac-links {
                  xr:xr-xml-map "fia_oper:FMACLinkTable";
                  description "Link table for statistics";

                  list fmac-link {
                    xr:xr-xml-map "fia_oper:FMACLink";
                    key "link";
                    description "Link number for statistics";
                    leaf link {
                      xr:xr-xml-map "fia_oper:Link";
                      type int32;
                      description "Link number";
                    }

                    list fmac-asic {
                      xr:xr-xml-map "fia_oper:FMACAsic";
                      key "asic";
                      description "Single aisc information";
                      leaf asic {
                        xr:xr-xml-map "fia_oper:Asic";
                        type int32;
                        description "Single asic";
                      }
                      uses FIA-EDM-STATS-ASIC-FMAC-INFO;
                    }
                  }
                }
              }
              leaf instance {
                xr:xr-xml-map "fia_oper:Instance";
                type Fia-max-asic-instances;
                description "Asic instance";
              }
            }
          }
        }
        leaf node-name {
          xr:xr-xml-map "fia_oper:NodeName";
          type xr:Node-id;
          description "Node ID";
        }
      }
    }
  }
}
