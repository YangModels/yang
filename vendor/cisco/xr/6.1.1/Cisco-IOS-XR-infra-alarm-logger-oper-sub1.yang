submodule Cisco-IOS-XR-infra-alarm-logger-oper-sub1 {

  belongs-to Cisco-IOS-XR-infra-alarm-logger-oper {
    prefix Cisco-IOS-XR-infra-alarm-logger-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR infra-alarm-logger package operational data.

     Copyright (c) 2013-2016 by Cisco Systems, Inc.
     All rights reserved.";

  revision "2015-01-07" {
    description
      "IOS XR 5.3.1 revision.";
  }

  typedef Al-alarm-bistate {
    type enumeration {
      enum not-available {
        value 0;
        description "not available";
      }
      enum active {
        value 1;
        description "active";
      }
      enum clear {
        value 2;
        description "clear";
      }
    }
    description "Al alarm bistate";
  }
  typedef Al-alarm-severity {
    type enumeration {
      enum unknown {
        value -1;
        description "unknown";
      }
      enum emergency {
        value 0;
        description "emergency";
      }
      enum alert {
        value 1;
        description "alert";
      }
      enum critical {
        value 2;
        description "critical";
      }
      enum error {
        value 3;
        description "error";
      }
      enum warning {
        value 4;
        description "warning";
      }
      enum notice {
        value 5;
        description "notice";
      }
      enum informational {
        value 6;
        description "informational";
      }
      enum debugging {
        value 7;
        description "debugging";
      }
    }
    description "Al alarm severity";
  }

  grouping AL-ALDEMS-ALARM-BAG {
    description "Alarm-Logger alarm";
    leaf source-id {
      xr:xr-xml-map "infra_alarm_logger:SourceID";
      type string;
      description
        "Source Identifier(Location).Indicates the node
        in which the alarm was generated";
    }
    leaf timestamp {
      xr:xr-xml-map "infra_alarm_logger:Timestamp";
      type uint64;
      units "millisecond";
      description
        "Time when the alarm was generated. It is
        expressed in number of milliseconds since 00:00
        :00 UTC, January 1, 1970";
    }
    leaf category {
      xr:xr-xml-map "infra_alarm_logger:Category";
      type string;
      description "Category of the alarm";
    }
    leaf group {
      xr:xr-xml-map "infra_alarm_logger:Group";
      type string;
      description
        "Group of messages to which this alarm belongs to";
    }
    leaf code {
      xr:xr-xml-map "infra_alarm_logger:Code";
      type string;
      description
        "Alarm code which further qualifies the alarm
        within a message group";
    }
    leaf severity {
      xr:xr-xml-map "infra_alarm_logger:Severity";
      type Al-alarm-severity;
      description "Severity of the alarm";
    }
    leaf state {
      xr:xr-xml-map "infra_alarm_logger:State";
      type Al-alarm-bistate;
      description "State of the alarm (bistate alarms only)";
    }
    leaf correlation-id {
      xr:xr-xml-map "infra_alarm_logger:CorrelationID";
      type uint32;
      description "Correlation Identifier";
    }
    leaf is-admin {
      xr:xr-xml-map "infra_alarm_logger:IsAdmin";
      type boolean;
      description "Indicates the event id admin-level";
    }
    leaf additional-text {
      xr:xr-xml-map "infra_alarm_logger:AdditionalText";
      type string;
      description "Full text of the Alarm";
    }
  }

  grouping AL-LOGGING-INFO-BAG {
    description "Logging information";
    leaf log-buffer-size {
      xr:xr-xml-map "infra_alarm_logger:LogBufferSize";
      type uint32;
      units "byte";
      description "Current Logging Buffer Size (Bytes)";
    }
    leaf max-log-buffer-size {
      xr:xr-xml-map "infra_alarm_logger:MaxLogBufferSize";
      type uint32;
      units "byte";
      description "Maximum Logging Buffer Size (Bytes) ";
    }
    leaf record-count {
      xr:xr-xml-map "infra_alarm_logger:RecordCount";
      type uint32;
      description "Number of Records in the Buffer";
    }
    leaf capacity-threshold {
      xr:xr-xml-map "infra_alarm_logger:CapacityThreshold";
      type uint32;
      units "percentage";
      description
        "Percentage of the buffer utilization which, when
        exceeded, triggers the  generation of a
        notification for the clients of the XML agent";
    }
    leaf severity-filter {
      xr:xr-xml-map "infra_alarm_logger:SeverityFilter";
      type Al-alarm-severity;
      description "Severity Filter";
    }
  }
}
