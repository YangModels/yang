submodule Cisco-IOS-XR-snmp-agent-oper-sub3 {

  belongs-to Cisco-IOS-XR-snmp-agent-oper {
    prefix Cisco-IOS-XR-snmp-agent-oper;
  }

  /*** LINKAGE (IMPORTS / INCLUDES) ***/

  import ietf-yang-types { prefix "yang"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR snmp-agent package operational data.

     Copyright (c) 2013-2016 by Cisco Systems, Inc.
     All rights reserved.";

  revision "2016-06-01" {
    description
      "IOS XR 6.0.1 revision.";
  }

  revision "2015-01-07" {
    description
      "IOS XR 5.3.1 revision.";
  }

  typedef Dup-req-drop-status {
    type enumeration {
      enum disabled {
        description "Disabled";
      }
      enum enabled {
        description "Enabled";
      }
    }
    description "Dup req drop status";
  }

  grouping SNMP-TRAPQUE {
    description "SNMP Trap  queue statistics";
    leaf trap-min {
      xr:xr-xml-map "snmp:trap_min";
      type uint32;
      description "trap min";
    }
    leaf trap-avg {
      xr:xr-xml-map "snmp:trap_avg";
      type uint32;
      description "trap avg";
    }
    leaf trap-max {
      xr:xr-xml-map "snmp:trap_max";
      type uint32;
      description "trap max";
    }
    leaf trap-q {
      xr:xr-xml-map "snmp:trapQ";
      type yang:hex-string;
      description "trapQ";
    }
  }

  grouping SNMP-SYSOBJID {
    description "SNMP sysObjID";
    leaf sys-obj-id {
      xr:xr-xml-map "snmp:SysObjID";
      type string;
      description "sysObjID  1.3.6.1.2.1.1.2";
    }
  }

  grouping SNMP-SYSDESCR {
    description "SNMP sysDescr";
    leaf sys-descr {
      xr:xr-xml-map "snmp:SysDescr";
      type string;
      description "sysDescr  1.3.6.1.2.1.1.1";
    }
  }

  grouping SNMP-PDU-DROP-STATS {
    description "SNMP Agent Req PDU Drop Stats";
    leaf nms-address {
      xr:xr-xml-map "snmp:NMSAddress";
      type string;
      description "NMS address of server";
    }
    leaf incoming-q-count {
      xr:xr-xml-map "snmp:IncomingQCount";
      type uint32;
      description "Drop Count at Incoming Q";
    }
    leaf threshold-incoming-q-count {
      xr:xr-xml-map "snmp:ThresholdIncomingQCount";
      type uint32;
      description "Drop Count at Incoming Q after threshold limit";
    }
    leaf encode-count {
      xr:xr-xml-map "snmp:EncodeCount";
      type uint32;
      description "Drop Count with Encode errors";
    }
    leaf duplicate-count {
      xr:xr-xml-map "snmp:DuplicateCount";
      type uint32;
      description "Duplicate request drop count";
    }
    leaf stack-count {
      xr:xr-xml-map "snmp:StackCount";
      type uint32;
      description "Drop Count at snmp Stack";
    }
    leaf aipc-count {
      xr:xr-xml-map "snmp:AIPCCount";
      type uint32;
      description "drop count with AIPC Buffer Full";
    }
    leaf overload-count {
      xr:xr-xml-map "snmp:OverloadCount";
      type uint32;
      description "Drop Count with overload notification";
    }
    leaf timeout-count {
      xr:xr-xml-map "snmp:TimeoutCount";
      type uint32;
      description "Drop count with timeout";
    }
    leaf internal-count {
      xr:xr-xml-map "snmp:InternalCount";
      type uint32;
      description " drop with Internal Errors";
    }
  }

  grouping SNMP-PDU-STATS {
    description "SNMP PDU STATS";
    leaf nms {
      xr:xr-xml-map "snmp:NMS";
      type string;
      description " NMS address Rx PDU";
    }
    leaf request-id {
      xr:xr-xml-map "snmp:RequestID";
      type uint32;
      description " SNMP request id per PDU";
    }
    leaf port-xr {
      xr:xr-xml-map "snmp:port-xr";
      type uint16;
      description "NMS port number";
    }
    leaf pdu-type {
      xr:xr-xml-map "snmp:PDUType";
      type uint16;
      description " PDU type";
    }
    leaf error-status {
      xr:xr-xml-map "snmp:ErrorStatus";
      type uint16;
      description "Is reques dropped due to error";
    }
    leaf serial-num {
      xr:xr-xml-map "snmp:SerialNum";
      type uint32;
      description "Serial number per PDU processing";
    }
    leaf input-q {
      xr:xr-xml-map "snmp:InputQ";
      type string;
      description "Request inserted into input queue";
    }
    leaf output-q {
      xr:xr-xml-map "snmp:OutputQ";
      type uint32;
      description "De-queue the request from the input queue";
    }
    leaf pending-q {
      xr:xr-xml-map "snmp:PendingQ";
      type uint32;
      description "Enqueue the request into pending queue";
    }
    leaf response-out {
      xr:xr-xml-map "snmp:ResponseOut";
      type uint32;
      description "Response sent";
    }
  }

  grouping SNMP-MIB-INFO {
    description "SNMP MIB Information";
    leaf mib-name {
      xr:xr-xml-map "snmp:MIBName";
      type string;
      description "Name of the MIB module";
    }
    leaf dll-name {
      xr:xr-xml-map "snmp:DLLName";
      type string;
      description
        "MIB DLL filename, non-DLL MIBs will have no
        value";
    }
    leaf mib-config-filename {
      xr:xr-xml-map "snmp:MIBConfigFilename";
      type string;
      description
        "MIB config filename, non-DLL MIBs will have no
        value";
    }
    leaf is-mib-loaded {
      xr:xr-xml-map "snmp:IsMIBLoaded";
      type boolean;
      description
        "TRUE if MIB DLL is currently loaded, will always
        be TRUE for non-DLL MIBs";
    }
    leaf dll-capabilities {
      xr:xr-xml-map "snmp:DLLCapabilities";
      type uint32;
      description "DLL capabilities";
    }
    leaf trap-strings {
      xr:xr-xml-map "snmp:TrapStrings";
      type string;
      description "List of trapstring configured";
    }
    leaf timeout {
      xr:xr-xml-map "snmp:Timeout";
      type boolean;
      description "TRUE is mib is in phase 1 timeout";
    }
    leaf load-time {
      xr:xr-xml-map "snmp:LoadTime";
      type uint32;
      description "Load time";
    }
  }

  grouping SNMP-TRAPS-COUNT {
    description "SNMP TRAPS COUNT";
    leaf trap-oid-count {
      xr:xr-xml-map "snmp:TrapOIDCount";
      type uint32;
      description "Total number of OID's sent";
    }
    leaf trap-oid-xr {
      xr:xr-xml-map "snmp:trap-oid-xr";
      type string;
      description "TRAP OID";
    }
  }

  grouping SNMP-CTX-MAPPING-ENTRY-XML {
    description "SNMP context mapping entry xml";
    leaf context {
      xr:xr-xml-map "snmp:Context";
      type string;
      description "Context name";
    }
    leaf feature-name {
      xr:xr-xml-map "snmp:FeatureName";
      type string;
      description "Feature name";
    }
    leaf instance {
      xr:xr-xml-map "snmp:Instance";
      type string;
      description "Instance name";
    }
    leaf topology {
      xr:xr-xml-map "snmp:Topology";
      type string;
      description "Topology name";
    }
    leaf feature {
      xr:xr-xml-map "snmp:Feature";
      type string;
      description "Feature";
    }
  }

  grouping SNMP-CTX-MAPPING-XML {
    description "SNMP context mapping";

    list contex-mapping {
      description "Context Mapping";
      uses SNMP-CTX-MAPPING-ENTRY-XML;
    }
  }

  grouping SNMP-INQ-DETAIL {
    description "SNMP Address Information";
    leaf address-of-queue {
      xr:xr-xml-map "snmp:AddressOfQueue";
      type string;
      description "Address of NMS Q";
    }
    leaf request-count {
      xr:xr-xml-map "snmp:RequestCount";
      type uint32;
      description "Request Count of Each Queue.";
    }
    leaf processed-request-count {
      xr:xr-xml-map "snmp:ProcessedRequestCount";
      type uint32;
      description "Processed request Count.";
    }
    leaf last-access-time {
      xr:xr-xml-map "snmp:LastAccessTime";
      type string;
      description "Last Access time of Each Queue.";
    }
    leaf priority {
      xr:xr-xml-map "snmp:Priority";
      type uint8;
      description "Priority of Each Queue.";
    }
  }

  grouping SNMP-INCOMING-Q-STATS-ENTRY {
    description "SNMP IncomingQ Stats Entry";
    leaf queue-count {
      xr:xr-xml-map "snmp:QueueCount";
      type uint32;
      description "Number of NMS Queues Exist.";
    }

    list inq-entry {
      max-elements "16";
      description "Each Entry Details.";
      uses SNMP-INQ-DETAIL;
    }
  }

  grouping SNMP-STATS {
    description "SNMP statistics";
    leaf packets-received {
      xr:xr-xml-map "snmp:PacketsReceived";
      type uint32;
      description "snmpInPkts";
    }
    leaf bad-versions-received {
      xr:xr-xml-map "snmp:BadVersionsReceived";
      type uint32;
      description "snmpInBadVersions";
    }
    leaf bad-community-names-received {
      xr:xr-xml-map "snmp:BadCommunityNamesReceived";
      type uint32;
      description "snmpInBadCommunityNames";
    }
    leaf bad-community-uses-received {
      xr:xr-xml-map "snmp:BadCommunityUsesReceived";
      type uint32;
      description "snmpInBadCommunityUses";
    }
    leaf asn-parse-errors-received {
      xr:xr-xml-map "snmp:ASNParseErrorsReceived";
      type uint32;
      description "snmpInASNParseErrs";
    }
    leaf silent-drop-count {
      xr:xr-xml-map "snmp:SilentDropCount";
      type uint32;
      description "snmpSilentDrops";
    }
    leaf proxy-drop-count {
      xr:xr-xml-map "snmp:ProxyDropCount";
      type uint32;
      description "snmpProxyDrops";
    }
    leaf too-big-packet-received {
      xr:xr-xml-map "snmp:TooBigPacketReceived";
      type uint32;
      description "snmpInTooBigs";
    }
    leaf max-packet-size {
      xr:xr-xml-map "snmp:MaxPacketSize";
      type uint32;
      description "snmp maximum packet size";
    }
    leaf no-such-names-received {
      xr:xr-xml-map "snmp:NoSuchNamesReceived";
      type uint32;
      description "snmpInNoSuchNames";
    }
    leaf bad-values-received {
      xr:xr-xml-map "snmp:BadValuesReceived";
      type uint32;
      description "snmpInBadValues";
    }
    leaf read-only-received {
      xr:xr-xml-map "snmp:ReadOnlyReceived";
      type uint32;
      description "snmpInReadOnlys";
    }
    leaf total-general-errors {
      xr:xr-xml-map "snmp:TotalGeneralErrors";
      type uint32;
      description "snmpInGenErrs";
    }
    leaf total-requested-variables {
      xr:xr-xml-map "snmp:TotalRequestedVariables";
      type uint32;
      description "snmpInTotalReqVars";
    }
    leaf total-set-variables-received {
      xr:xr-xml-map "snmp:TotalSetVariablesReceived";
      type uint32;
      description "snmpInTotalSetVars";
    }
    leaf get-requests-received {
      xr:xr-xml-map "snmp:GetRequestsReceived";
      type uint32;
      description "snmpInGetRequests";
    }
    leaf get-next-requests-received {
      xr:xr-xml-map "snmp:GetNextRequestsReceived";
      type uint32;
      description "snmpInGetNexts";
    }
    leaf set-requests-received {
      xr:xr-xml-map "snmp:SetRequestsReceived";
      type uint32;
      description "snmpInSetRequests";
    }
    leaf get-responses-received {
      xr:xr-xml-map "snmp:GetResponsesReceived";
      type uint32;
      description "snmpInGetResponses";
    }
    leaf traps-received {
      xr:xr-xml-map "snmp:TrapsReceived";
      type uint32;
      description "snmpInTraps";
    }
    leaf total-packets-sent {
      xr:xr-xml-map "snmp:TotalPacketsSent";
      type uint32;
      description "snmpOutPkts";
    }
    leaf too-big-packets-sent {
      xr:xr-xml-map "snmp:TooBigPacketsSent";
      type uint32;
      description "snmpOutTooBigs";
    }
    leaf no-such-names-sent {
      xr:xr-xml-map "snmp:NoSuchNamesSent";
      type uint32;
      description "snmpOutNoSuchNames";
    }
    leaf bad-values-sent {
      xr:xr-xml-map "snmp:BadValuesSent";
      type uint32;
      description "snmpOutBadValues";
    }
    leaf general-errors-sent {
      xr:xr-xml-map "snmp:GeneralErrorsSent";
      type uint32;
      description "snmpOutGenErrs";
    }
    leaf get-requests-sent {
      xr:xr-xml-map "snmp:GetRequestsSent";
      type uint32;
      description "snmpOutGetRequests";
    }
    leaf get-next-request-sent {
      xr:xr-xml-map "snmp:GetNextRequestSent";
      type uint32;
      description "snmpOutGetNexts";
    }
    leaf set-requests-sent {
      xr:xr-xml-map "snmp:SetRequestsSent";
      type uint32;
      description "snmpOutSetRequests";
    }
    leaf get-responses-sent {
      xr:xr-xml-map "snmp:GetResponsesSent";
      type uint32;
      description "snmpOutGetResponses";
    }
    leaf traps-sent {
      xr:xr-xml-map "snmp:TrapsSent";
      type uint32;
      description "snmpOutTraps";
    }
  }

  grouping SNMP-TRAP-OID-INFO {
    description "SNMP TRAP OID INFO";
    leaf trap-oid {
      xr:xr-xml-map "snmp:TrapOID";
      type string;
      description "TRAP OID";
    }
    leaf count {
      xr:xr-xml-map "snmp:Count";
      type uint32;
      description "Number of traps sent";
    }
    leaf drop-count {
      xr:xr-xml-map "snmp:DropCount";
      type uint32;
      description "Number of Traps Dropped";
    }
    leaf retry-count {
      xr:xr-xml-map "snmp:RetryCount";
      type uint32;
      description "Num of times retry";
    }
    leaf lastsent-time {
      xr:xr-xml-map "snmp:LastsentTime";
      type string;
      description "Timestamp of latest successfully sent";
    }
    leaf lasrdrop-time {
      xr:xr-xml-map "snmp:LasrdropTime";
      type string;
      description "Timestamp of latest droped";
    }
  }

  grouping SNMP-TRAPS-INFO {
    description "SNMP TRAPS INFO";
    leaf host {
      xr:xr-xml-map "snmp:HOST";
      type string;
      description "NMS/Host address";
    }
    leaf port-xr {
      xr:xr-xml-map "snmp:port-xr";
      type uint16;
      description "udp port number";
    }
    leaf trap-oid-count {
      xr:xr-xml-map "snmp:TrapOIDCount";
      type uint32;
      description "Total number of OID's sent";
    }

    list trap-oi-dinfo {
      description "Per trap OID statistics";
      uses SNMP-TRAP-OID-INFO;
    }
  }

  grouping SNMP-BULKSTATS-B {
    description "SNMP Bulkstats transfer Information";
    leaf transfer-name-xr {
      xr:xr-xml-map "snmp:transfer-name-xr";
      type string;
      description "Name of the bulkstats transfer session";
    }
    leaf url-primary {
      xr:xr-xml-map "snmp:URLPrimary";
      type string;
      description "Bulkstats transfer primary URL";
    }
    leaf url-secondary {
      xr:xr-xml-map "snmp:URLSecondary";
      type string;
      description "Bulkstats transfer secondary URL";
    }
    leaf retained-file {
      xr:xr-xml-map "snmp:RetainedFile";
      type string;
      description "Bulkstats transfer retained file name";
    }
    leaf time-left {
      xr:xr-xml-map "snmp:TimeLeft";
      type uint32;
      units "second";
      description "Bulkstats transfer retry time left in seconds";
    }
    leaf retry-left {
      xr:xr-xml-map "snmp:RetryLeft";
      type uint32;
      description "Bulkstats transfer retry attempt left";
    }
  }

  grouping SNMP-STATISTICS {
    description "SNMP Statistics extension";
    leaf duplicate-request-status {
      xr:xr-xml-map "snmp:DuplicateRequestStatus";
      type Dup-req-drop-status;
      description "Duplicate requests drop feature status.";
    }
    leaf last-status-change-time {
      xr:xr-xml-map "snmp:LastStatusChangeTime";
      type string;
      description
        "Duplicate request drop feature last enable
        disable time (Day Mon Date HH:MM:SS)";
    }
    leaf duplicate-drop-configured-timeout {
      xr:xr-xml-map "snmp:DuplicateDropConfiguredTimeout";
      type uint32;
      description "Configured Duplicate Drop feature Timeout.";
    }
    leaf duplicate-dropped-requests {
      xr:xr-xml-map "snmp:DuplicateDroppedRequests";
      type uint32;
      description "Number of duplicate SNMP requests are dropped.";
    }
    leaf retry-processed-requests {
      xr:xr-xml-map "snmp:RetryProcessedRequests";
      type uint32;
      description "Number of Retry SNMP requests are Processed.";
    }
    leaf first-enable-time {
      xr:xr-xml-map "snmp:FirstEnableTime";
      type string;
      description
        "Duplicate request drop feature first  enable
        time (Day Mon Date HH:MM:SS)";
    }
    leaf latest-duplicate-dropped-requests {
      xr:xr-xml-map "snmp:LatestDuplicateDroppedRequests";
      type uint32;
      description
        "Number of duplicate SNMP requests dropped, from
        the last enable time.";
    }
    leaf latest-retry-processed-requests {
      xr:xr-xml-map "snmp:LatestRetryProcessedRequests";
      type uint32;
      description
        "Number of retry SNMP requests processed, from
        the last enable time.";
    }
    leaf duplicate-request-latest-enable-time {
      xr:xr-xml-map "snmp:DuplicateRequestLatestEnableTime";
      type string;
      description
        "Duplicate request drop feature last enable
        time(Day Mon Date HH:MM:SS)";
    }
    leaf duplicate-drop-enable-count {
      xr:xr-xml-map "snmp:DuplicateDropEnableCount";
      type uint32;
      description
        " Number of times duplicate request drop feature
        is enabled.";
    }
    leaf duplicate-drop-disable-count {
      xr:xr-xml-map "snmp:DuplicateDropDisableCount";
      type uint32;
      description
        " Number of times duplicate request drop feature
        is disabled.";
    }
  }

  grouping SNMP-Q-STATS-B {
    description "SNMP incomming/processing queue statistics";
    leaf total-count {
      xr:xr-xml-map "snmp:TotalCount";
      type uint32;
      description
        "Total request count for each managment station
        or client";
    }
    leaf agent-request-count {
      xr:xr-xml-map "snmp:AgentRequestCount";
      type uint32;
      description
        "Processing agent request count for each client
        for particluar managment station";
    }
    leaf interface-request-count {
      xr:xr-xml-map "snmp:InterfaceRequestCount";
      type uint32;
      description
        "Processing interfce request count for each
        client for particluar managment station";
    }
    leaf entity-request-count {
      xr:xr-xml-map "snmp:EntityRequestCount";
      type uint32;
      description
        "Processing entity request count for each client
        for particluar managment station";
    }
    leaf route-request-count {
      xr:xr-xml-map "snmp:RouteRequestCount";
      type uint32;
      description
        "Processing route request count for each client
        for particluar Managment station";
    }
    leaf infra-request-count {
      xr:xr-xml-map "snmp:InfraRequestCount";
      type uint32;
      description
        "Processing infra request count for each client
        for particluar Managment station";
    }
  }

  grouping SNMP-SYSNAME {
    description "SNMP sysName";
    leaf system-name {
      xr:xr-xml-map "snmp:SystemName";
      type string;
      description "sysName  1.3.6.1.2.1.1.5";
    }
  }

  grouping SNMP-RXQUE {
    description "SNMP Incoming queue statistics";
    leaf qlen {
      xr:xr-xml-map "snmp:qlen";
      type uint32;
      description "qlen";
    }
    leaf in-min {
      xr:xr-xml-map "snmp:in_min";
      type uint32;
      description "in min";
    }
    leaf in-avg {
      xr:xr-xml-map "snmp:in_avg";
      type uint32;
      description "in avg";
    }
    leaf in-max {
      xr:xr-xml-map "snmp:in_max";
      type uint32;
      description "in max";
    }
    leaf pend-min {
      xr:xr-xml-map "snmp:pend_min";
      type uint32;
      description "pend min";
    }
    leaf pend-avg {
      xr:xr-xml-map "snmp:pend_avg";
      type uint32;
      description "pend avg";
    }
    leaf pend-max {
      xr:xr-xml-map "snmp:pend_max";
      type uint32;
      description "pend max";
    }
    leaf incoming-q {
      xr:xr-xml-map "snmp:incomingQ";
      type yang:hex-string;
      description "incomingQ";
    }
    leaf pending-q {
      xr:xr-xml-map "snmp:pendingQ";
      type yang:hex-string;
      description "pendingQ";
    }
  }

  grouping SNMP-ENGINEID {
    description "SNMPv3 engineID Information";
    leaf engine-id {
      xr:xr-xml-map "snmp:EngineID";
      type string;
      description "SNMPv3 engineID";
    }
  }

  grouping SNMP-REQ-NMS-SUM {
    description "SNMP Agent Req NMS Summary ";
    leaf nms-address {
      xr:xr-xml-map "snmp:NMSAddress";
      type string;
      description "NMS address of server";
    }
    leaf get-request-count {
      xr:xr-xml-map "snmp:GetRequestCount";
      type uint32;
      description "Get Request Count";
    }
    leaf getnext-request-count {
      xr:xr-xml-map "snmp:GetnextRequestCount";
      type uint32;
      description "Getnext Request Count";
    }
    leaf getbulk-request-count {
      xr:xr-xml-map "snmp:GetbulkRequestCount";
      type uint32;
      description "Getbulk Request Count";
    }
    leaf set-request-count {
      xr:xr-xml-map "snmp:SetRequestCount";
      type uint32;
      description "Set Request Count";
    }
    leaf test-request-count {
      xr:xr-xml-map "snmp:TestRequestCount";
      type uint32;
      description "Test Request Count";
    }
  }

  grouping SNMP-SYSUPTIME {
    description "SNMP sysUpTime in centi seconds";
    leaf system-up-time {
      xr:xr-xml-map "snmp:SystemUpTime";
      type uint32;
      description "sysUpTime  1.3.6.1.2.1.1.3";
    }
  }
}
