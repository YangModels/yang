module Cisco-IOS-XR-infra-correlator-cfg {

  /*** NAMESPACE / PREFIX DEFINITION ***/

  namespace "http://cisco.com/ns/yang"+
    "/Cisco-IOS-XR-infra-correlator-cfg";


  prefix "infra-correlator-cfg";

  /*** LINKAGE (IMPORTS / INCLUDES) ***/

  import Cisco-IOS-XR-types { prefix "xr"; }

  import Cisco-IOS-XR-infra-syslog-cfg { prefix "a1"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR infra-correlator package configuration.

     This YANG module augments the
       Cisco-IOS-XR-infra-syslog-cfg
     module with configuration data.

     Copyright (c) 2013-2016 by Cisco Systems, Inc.
     All rights reserved.";

  revision "2015-11-09" {
    description
      "IOS XR 6.0 revision.";
  }


  grouping CONTEXT-CORRELATION {
    description "Common node of non-stateful, stateful";
    leaf context-correlation {
      xr:xr-xml-map "infra_correlator_cfg:ContextCorrelation";
      type empty;
      description "Enable correlation on alarm context";
    }
  }

  grouping NON-ROOT-CAUSE-TABLE {
    description "Common node of non-stateful, stateful";

    container non-root-causes {
      xr:xr-xml-map "infra_correlator_cfg:NonRootCauseTable";
      description "Table of configured non-rootcause";

      list non-root-cause {
        xr:xr-xml-map "infra_correlator_cfg:NonRootCause";
        key "category group message-code";
        description "A non-rootcause";
        leaf category {
          xr:xr-xml-map "infra_correlator_cfg:Category";
          type string;
          description "Correlated message category";
        }
        leaf group {
          xr:xr-xml-map "infra_correlator_cfg:Group";
          type string;
          description "Correlated message group";
        }
        leaf message-code {
          xr:xr-xml-map "infra_correlator_cfg:MessageCode";
          type string;
          description "Correlated message code";
        }
      }
    }
  }

  grouping TIMEOUT-ROOT-CAUSE {
    description "Common node of non-stateful, stateful";
    leaf timeout-root-cause {
      xr:xr-xml-map "infra_correlator_cfg:TimeoutRootcause";
      type uint32 {
        range "1..7200000";
      }
      units "millisecond";
      description
        "Rootcause Timeout (time to wait for rootcause)
        in milliseconds";
    }
  }

  grouping APPLIED-TO {
    description "Common node of rule, rule-set";

    container applied-to {
      xr:xr-xml-map "infra_correlator_cfg:AppliedTo";
      description "Applied to the Rule or Ruleset";

      container contexts {
        xr:xr-xml-map "infra_correlator_cfg:ContextTable";
        description "Table of configured contexts to apply";

        list context {
          xr:xr-xml-map "infra_correlator_cfg:Context";
          key "context";
          description "A context";
          leaf context {
            xr:xr-xml-map "infra_correlator_cfg:Context";
            type string {
              length "0..32";
            }
            description "Context";
          }
        }
      }

      container locations {
        xr:xr-xml-map "infra_correlator_cfg:LocationTable";
        description "Table of configured locations to apply";

        list location {
          xr:xr-xml-map "infra_correlator_cfg:Location";
          key "location";
          description "A location";
          leaf location {
            xr:xr-xml-map "infra_correlator_cfg:Location";
            type xr:Node-id;
            description "Location";
          }
        }
      }
      leaf all {
        xr:xr-xml-map "infra_correlator_cfg:All";
        type empty;
        description "Apply to all of the router";
      }
    }
  }

  grouping TIMEOUT {
    description "Common node of non-stateful, stateful";
    leaf timeout {
      xr:xr-xml-map "infra_correlator_cfg:Timeout";
      type uint32 {
        range "1..7200000";
      }
      units "millisecond";
      description
        "Timeout (time to wait for active correlation) in
        milliseconds";
    }
  }

  grouping ROOT-CAUSE {
    description "Common node of non-stateful, stateful";

    container root-cause {
      xr:xr-xml-map "infra_correlator_cfg:RootCause";
      description "The root cause";
      leaf category {
        xr:xr-xml-map "infra_correlator_cfg:Category";
        type string;
        description "Root message category";
      }
      leaf group {
        xr:xr-xml-map "infra_correlator_cfg:Group";
        type string;
        description "Root message group";
      }
      leaf message-code {
        xr:xr-xml-map "infra_correlator_cfg:MessageCode";
        type string;
        description "Root message code";
      }
    }
  }

  augment "/a1:syslog" {

    container correlator {
      xr:xr-xml-map "infra_correlator_cfg:Correlator";
      description "Configure properties of the event correlator";

      container rules {
        xr:xr-xml-map "infra_correlator_cfg:RuleTable";
        description "Table of configured rules";

        list rule {
          xr:xr-xml-map "infra_correlator_cfg:Rule";
          key "name";
          description "Rule name";

          container definition {
            xr:xr-xml-map "infra_correlator_cfg:Definition";
            description "Configure a specified correlation rule";
            leaf timeout {
              xr:xr-xml-map "infra_correlator_cfg:Timeout";
              type uint32 {
                range "1..7200000";
              }
              description
                "Timeout (time the rule is to be active) in
                milliseconds";
            }
            leaf category-name-entry1 {
              xr:xr-xml-map "infra_correlator_cfg:CategoryNameEntry"+
                "1";
              type string;
              description "Root message category name";
            }
            leaf group-name-entry1 {
              xr:xr-xml-map "infra_correlator_cfg:GroupNameEntry1";
              type string;
              description "Root message group name";
            }
            leaf message-code-entry1 {
              xr:xr-xml-map "infra_correlator_cfg:MessageCodeEntry1";
              type string;
              description "Root message code";
            }
            leaf category-name-entry2 {
              xr:xr-xml-map "infra_correlator_cfg:CategoryNameEntry"+
                "2";
              type string;
              description "Correlated message category name";
            }
            leaf group-name-entry2 {
              xr:xr-xml-map "infra_correlator_cfg:GroupNameEntry2";
              type string;
              description "Correlated message group name";
            }
            leaf message-code-entry2 {
              xr:xr-xml-map "infra_correlator_cfg:MessageCodeEntry2";
              type string;
              description "Correlated message code";
            }
            leaf category-name-entry3 {
              xr:xr-xml-map "infra_correlator_cfg:CategoryNameEntry"+
                "3";
              type string;
              description "Correlated message category name";
            }
            leaf group-name-entry3 {
              xr:xr-xml-map "infra_correlator_cfg:GroupNameEntry3";
              type string;
              description "Correlated message group name";
            }
            leaf message-code-entry3 {
              xr:xr-xml-map "infra_correlator_cfg:MessageCodeEntry3";
              type string;
              description "Correlated message code";
            }
            leaf category-name-entry4 {
              xr:xr-xml-map "infra_correlator_cfg:CategoryNameEntry"+
                "4";
              type string;
              description "Correlated message category name";
            }
            leaf group-name-entry4 {
              xr:xr-xml-map "infra_correlator_cfg:GroupNameEntry4";
              type string;
              description "Correlated message group name";
            }
            leaf message-code-entry4 {
              xr:xr-xml-map "infra_correlator_cfg:MessageCodeEntry4";
              type string;
              description "Correlated message code";
            }
            leaf category-name-entry5 {
              xr:xr-xml-map "infra_correlator_cfg:CategoryNameEntry"+
                "5";
              type string;
              description "Correlated message category name";
            }
            leaf group-name-entry5 {
              xr:xr-xml-map "infra_correlator_cfg:GroupNameEntry5";
              type string;
              description "Correlated message group name";
            }
            leaf message-code-entry5 {
              xr:xr-xml-map "infra_correlator_cfg:MessageCodeEntry5";
              type string;
              description "Correlated message code";
            }
            leaf category-name-entry6 {
              xr:xr-xml-map "infra_correlator_cfg:CategoryNameEntry"+
                "6";
              type string;
              description "Correlated message category name";
            }
            leaf group-name-entry6 {
              xr:xr-xml-map "infra_correlator_cfg:GroupNameEntry6";
              type string;
              description "Correlated message group name";
            }
            leaf message-code-entry6 {
              xr:xr-xml-map "infra_correlator_cfg:MessageCodeEntry6";
              type string;
              description "Correlated message code";
            }
            leaf category-name-entry7 {
              xr:xr-xml-map "infra_correlator_cfg:CategoryNameEntry"+
                "7";
              type string;
              description "Correlated message category name";
            }
            leaf group-name-entry7 {
              xr:xr-xml-map "infra_correlator_cfg:GroupNameEntry7";
              type string;
              description "Correlated message group name";
            }
            leaf message-code-entry7 {
              xr:xr-xml-map "infra_correlator_cfg:MessageCodeEntry7";
              type string;
              description "Correlated message code";
            }
            leaf category-name-entry8 {
              xr:xr-xml-map "infra_correlator_cfg:CategoryNameEntry"+
                "8";
              type string;
              description "Correlated message category name";
            }
            leaf group-name-entry8 {
              xr:xr-xml-map "infra_correlator_cfg:GroupNameEntry8";
              type string;
              description "Correlated message group name";
            }
            leaf message-code-entry8 {
              xr:xr-xml-map "infra_correlator_cfg:MessageCodeEntry8";
              type string;
              description "Correlated message code";
            }
            leaf category-name-entry9 {
              xr:xr-xml-map "infra_correlator_cfg:CategoryNameEntry"+
                "9";
              type string;
              description "Correlated message category name";
            }
            leaf group-name-entry9 {
              xr:xr-xml-map "infra_correlator_cfg:GroupNameEntry9";
              type string;
              description "Correlated message group name";
            }
            leaf message-code-entry9 {
              xr:xr-xml-map "infra_correlator_cfg:MessageCodeEntry9";
              type string;
              description "Correlated message code";
            }
            leaf category-name-entry10 {
              xr:xr-xml-map "infra_correlator_cfg:CategoryNameEntry"+
                "10";
              type string;
              description "Correlated message category name";
            }
            leaf group-name-entry10 {
              xr:xr-xml-map "infra_correlator_cfg:GroupNameEntry10";
              type string;
              description "Correlated message group name";
            }
            leaf message-code-entry10 {
              xr:xr-xml-map "infra_correlator_cfg:MessageCodeEntry1"+
                "0";
              type string;
              description "Correlated message code";
            }
          }

          container non-stateful {
            xr:xr-xml-map "infra_correlator_cfg:NonStateful";
            description "The Non-Stateful Rule Type";
            uses CONTEXT-CORRELATION;
            uses TIMEOUT-ROOT-CAUSE;
            uses NON-ROOT-CAUSE-TABLE;
            uses ROOT-CAUSE;
            uses TIMEOUT;
          }

          container stateful {
            xr:xr-xml-map "infra_correlator_cfg:Stateful";
            description "The Stateful Rule Type";
            leaf reparent {
              xr:xr-xml-map "infra_correlator_cfg:Reparent";
              type empty;
              description
                "Enable reparent of alarm on rootcause alarm
                clear";
            }
            leaf reissue {
              xr:xr-xml-map "infra_correlator_cfg:Reissue";
              type empty;
              description
                "Enable reissue of non-bistate alarms on
                rootcause alarm clear";
            }
            uses CONTEXT-CORRELATION;
            uses TIMEOUT-ROOT-CAUSE;
            uses NON-ROOT-CAUSE-TABLE;
            uses ROOT-CAUSE;
            uses TIMEOUT;
          }

          container apply-to {
            xr:xr-xml-map "infra_correlator_cfg:ApplyTo";
            description "Apply the Rules";

            container contexts {
              xr:xr-xml-map "infra_correlator_cfg:ContextList";
              description
                "Apply rule to a specified list of contexts,
                e.g. interfaces";
              leaf-list context {
                xr:xr-xml-map "infra_correlator_cfg:ContextList";
                type string;
                max-elements "32";
                description "One or more context names";
              }
            }

            container locations {
              xr:xr-xml-map "infra_correlator_cfg:LocationList";
              description
                "Apply rule to a specified list of Locations";
              leaf-list location {
                xr:xr-xml-map "infra_correlator_cfg:LocationList";
                type xr:Node-id;
                max-elements "32";
                description "One or more Locations";
              }
            }
            leaf all-of-router {
              xr:xr-xml-map "infra_correlator_cfg:AllOfRouter";
              type empty;
              description "Apply the rule to all of the router";
            }
          }
          leaf name {
            xr:xr-xml-map "infra_correlator_cfg:Name";
            type string {
              length "0..32";
            }
            description "Rule name";
          }
          uses APPLIED-TO;
        }
      }

      container rule-sets {
        xr:xr-xml-map "infra_correlator_cfg:RulesetTable";
        description "Table of configured rulesets";

        list rule-set {
          xr:xr-xml-map "infra_correlator_cfg:Ruleset";
          key "name";
          description "Ruleset name";

          container rulenames {
            xr:xr-xml-map "infra_correlator_cfg:RulenameTable";
            description "Table of configured rulenames";

            list rulename {
              xr:xr-xml-map "infra_correlator_cfg:Rulename";
              key "rulename";
              description "A rulename";
              leaf rulename {
                xr:xr-xml-map "infra_correlator_cfg:Rulename";
                type string {
                  length "0..32";
                }
                description "Rule name";
              }
            }
          }
          leaf name {
            xr:xr-xml-map "infra_correlator_cfg:Name";
            type string {
              length "0..32";
            }
            description "Ruleset name";
          }
          uses APPLIED-TO;
        }
      }
      leaf buffer-size {
        xr:xr-xml-map "infra_correlator_cfg:BufferSize";
        type uint32 {
          range "1024..52428800";
        }
        description "Configure size of the correlator buffer";
      }
    }
    description
      "This augment extends the configuration data of
      'Cisco-IOS-XR-infra-syslog-cfg'";
  }

  augment "/a1:syslog" {

    container suppression {
      xr:xr-xml-map "infra_correlator_suppress_cfg:Suppression";
      description
        "Configure properties of the syslog/alarm
        suppression";

      container rules {
        xr:xr-xml-map "infra_correlator_suppress_cfg:RuleTable";
        description "Table of configured rules";

        list rule {
          xr:xr-xml-map "infra_correlator_suppress_cfg:Rule";
          key "name";
          description "Rule name";

          container applied-to {
            xr:xr-xml-map "infra_correlator_suppress_cfg:AppliedTo";
            description "Applied to the Rule";

            container sources {
              xr:xr-xml-map "infra_correlator_suppress_cfg:SourceTa"+
                "ble";
              description "Table of configured sources to apply";

              list source {
                xr:xr-xml-map "infra_correlator_suppress_cfg:Source";
                key "source";
                description "An alarm source";
                leaf source {
                  xr:xr-xml-map "infra_correlator_suppress_cfg:Sour"+
                    "ce";
                  type xr:Node-id;
                  description "Source";
                }
              }
            }
            leaf all {
              xr:xr-xml-map "infra_correlator_suppress_cfg:All";
              type empty;
              description "Apply to all of the router";
            }
          }

          container alarm-causes {
            xr:xr-xml-map "infra_correlator_suppress_cfg:AlarmCause"+
              "Table";
            description "Causes of alarms to be suppressed";

            list alarm-cause {
              xr:xr-xml-map "infra_correlator_suppress_cfg:AlarmCau"+
                "se";
              key "category group code";
              description
                "Category, Group and Code of alarm/syslog to
                be suppressed";
              leaf category {
                xr:xr-xml-map "infra_correlator_suppress_cfg:Catego"+
                  "ry";
                type string {
                  length "0..32";
                }
                description "Category";
              }
              leaf group {
                xr:xr-xml-map "infra_correlator_suppress_cfg:Group";
                type string {
                  length "0..32";
                }
                description "Group";
              }
              leaf code {
                xr:xr-xml-map "infra_correlator_suppress_cfg:Code";
                type string {
                  length "0..32";
                }
                description "Code";
              }
            }
          }
          leaf all-alarms {
            xr:xr-xml-map "infra_correlator_suppress_cfg:AllAlarms";
            type empty;
            description "Suppress all alarms";
          }
          leaf name {
            xr:xr-xml-map "infra_correlator_suppress_cfg:Name";
            type string {
              length "0..32";
            }
            description "Rule name";
          }
        }
      }
    }
    description
      "This augment extends the configuration data of
      'Cisco-IOS-XR-infra-syslog-cfg'";
  }
}
