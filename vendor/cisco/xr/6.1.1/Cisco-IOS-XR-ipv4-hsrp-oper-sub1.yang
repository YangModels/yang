submodule Cisco-IOS-XR-ipv4-hsrp-oper-sub1 {

  belongs-to Cisco-IOS-XR-ipv4-hsrp-oper {
    prefix Cisco-IOS-XR-ipv4-hsrp-oper;
  }

  /*** LINKAGE (IMPORTS / INCLUDES) ***/

  import ietf-inet-types { prefix "inet"; }

  import ietf-yang-types { prefix "yang"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR ipv4-hsrp package operational data.

     Copyright (c) 2013-2016 by Cisco Systems, Inc.
     All rights reserved.";

  revision "2015-11-09" {
    description
      "IOS XR 6.0 revision.";
  }

  typedef Hsrp-vmac-state {
    type enumeration {
      enum stored {
        value 0;
        description "VMAC stored locally";
      }
      enum reserved {
        value 1;
        description "VMAC reserved in mac table";
      }
      enum active {
        value 2;
        description "VMAC active in mac table";
      }
      enum reserving {
        value 3;
        description "VMAC not yet reserved in mac table";
      }
    }
    description "Hsrp vmac state";
  }
  typedef Hsrp-state-change-reason {
    type enumeration {
      enum state-change-bfd-down {
        value 0;
        description "BFD session down";
      }
      enum state-change-vip-learnt {
        value 1;
        description "Virtual IP learnt";
      }
      enum state-change-interface-ip {
        value 2;
        description "Interface IP update";
      }
      enum state-change-delay-timer {
        value 3;
        description "Delay timer expired";
      }
      enum state-change-startup {
        value 4;
        description "Ready on startup";
      }
      enum state-change-shutdown {
        value 5;
        description "HSRP shut down";
      }
      enum state-change-interface-up {
        value 6;
        description "Interface Up update";
      }
      enum state-change-interface-down {
        value 7;
        description "Interface Down update";
      }
      enum state-change-active-timer {
        value 8;
        description "Active timer expired";
      }
      enum state-change-standby-timer {
        value 9;
        description "Standby timer expired";
      }
      enum state-change-resign {
        value 10;
        description "Resign received";
      }
      enum state-change-coup {
        value 11;
        description "Coup received";
      }
      enum state-change-higher-priority-speak {
        value 12;
        description "Higher priority speak received";
      }
      enum state-change-higher-priority-standby {
        value 13;
        description "Higher priority standby received";
      }
      enum state-change-lower-priority-standby {
        value 14;
        description "Lower priority standby received";
      }
      enum state-change-higher-priority-active {
        value 15;
        description "Higher priority active received";
      }
      enum state-change-lower-priority-active {
        value 16;
        description "Lower priority active received";
      }
      enum state-change-virtual-ip-configured {
        value 17;
        description "Virtual IP configured";
      }
      enum state-change-virtual-ip-lost {
        value 18;
        description "Virtual IP lost";
      }
      enum state-change-recovered-from-checkpoint {
        value 19;
        description "Recovered from checkpoint";
      }
      enum state-change-mac-update {
        value 20;
        description "MAC address update";
      }
      enum state-change-admin {
        value 21;
        description "Forwarder Admin state change";
      }
      enum state-change-parent {
        value 22;
        description "MGO parent change";
      }
      enum state-change-chkpt-update {
        value 23;
        description "Checkpoint update from Primary HSRP instance";
      }
      enum state-change-issu-resync {
        value 24;
        description "Resync following ISSU primary event";
      }
      enum state-change-max {
        value 25;
        description "Maximum reason in enumeration";
      }
    }
    description "Hsrp state change reason";
  }
  typedef Hsrp-bfd-session-state {
    type enumeration {
      enum bfd-state-none {
        value 0;
        description "None";
      }
      enum bfd-state-inactive {
        value 1;
        description "Inactive";
      }
      enum bfd-state-up {
        value 2;
        description "Up";
      }
      enum bfd-state-down {
        value 3;
        description "Down";
      }
    }
    description "Hsrp bfd session state";
  }
  typedef Standby-grp-state {
    type enumeration {
      enum state-initial {
        value 1;
        description "Initial";
      }
      enum state-learn {
        value 2;
        description "Learn";
      }
      enum state-listen {
        value 3;
        description "Listen";
      }
      enum state-speak {
        value 4;
        description "Speak";
      }
      enum state-standby {
        value 5;
        description "Standby";
      }
      enum state-active {
        value 6;
        description "Active";
      }
    }
    description "Standby grp state";
  }
  typedef Hsrp-version {
    type uint8;
    description "Hsrp version";
  }
  typedef Hsrp-b-af {
    type enumeration {
      enum ipv4 {
        description "IPv4 Address Family";
      }
      enum ipv6 {
        description "IPv6 Address Family";
      }
      enum count {
        description "The number of supported address families";
      }
    }
    description "Hsrp b af";
  }

  grouping HSRP-SUMMARY-INFO {
    description "HSRP summary statistics";
    leaf ipv4-sessions-active {
      xr:xr-xml-map "hsrp:IPv4SessionsActive";
      type uint32;
      description "Number of IPv4 sessions in ACTIVE state";
    }
    leaf ipv4-sessions-standby {
      xr:xr-xml-map "hsrp:IPv4SessionsStandby";
      type uint32;
      description "Number of IPv4 sessions in STANDBY state";
    }
    leaf ipv4-sessions-speak {
      xr:xr-xml-map "hsrp:IPv4SessionsSpeak";
      type uint32;
      description "Number of IPv4 sessions in SPEAK state";
    }
    leaf ipv4-sessions-listen {
      xr:xr-xml-map "hsrp:IPv4SessionsListen";
      type uint32;
      description "Number of IPv4 sessions in LISTEN state";
    }
    leaf ipv4-sessions-learn {
      xr:xr-xml-map "hsrp:IPv4SessionsLearn";
      type uint32;
      description "Number of IPv4 sessions in LEARN state";
    }
    leaf ipv4-sessions-init {
      xr:xr-xml-map "hsrp:IPv4SessionsInit";
      type uint32;
      description "Number of IPv4 sessions in INIT state";
    }
    leaf ipv4-slaves-active {
      xr:xr-xml-map "hsrp:IPv4SlavesActive";
      type uint32;
      description "Number of IPv4 slaves in ACTIVE state";
    }
    leaf ipv4-slaves-standby {
      xr:xr-xml-map "hsrp:IPv4SlavesStandby";
      type uint32;
      description "Number of IPv4 slaves in STANDBY state";
    }
    leaf ipv4-slaves-speak {
      xr:xr-xml-map "hsrp:IPv4SlavesSpeak";
      type uint32;
      description "Number of IPv4 slaves in SPEAK state";
    }
    leaf ipv4-slaves-listen {
      xr:xr-xml-map "hsrp:IPv4SlavesListen";
      type uint32;
      description "Number of IPv4 slaves in LISTEN state";
    }
    leaf ipv4-slaves-learn {
      xr:xr-xml-map "hsrp:IPv4SlavesLearn";
      type uint32;
      description "Number of IPv4 slaves in LEARN state";
    }
    leaf ipv4-slaves-init {
      xr:xr-xml-map "hsrp:IPv4SlavesInit";
      type uint32;
      description "Number of IPv4 slaves in INIT state";
    }
    leaf ipv4-virtual-ip-addresses-active-up {
      xr:xr-xml-map "hsrp:IPv4VirtualIPAddressesActiveUp";
      type uint32;
      description
        "Number of UP IPv4 Virtual IP Addresses on groups
        in ACTIVE state";
    }
    leaf ipv4-virtual-ip-addresses-active-down {
      xr:xr-xml-map "hsrp:IPv4VirtualIPAddressesActiveDown";
      type uint32;
      description
        "Number of DOWN IPv4 Virtual IP Addresses on
        groups in ACTIVE state";
    }
    leaf ipv4-virtual-ip-addresses-standby-up {
      xr:xr-xml-map "hsrp:IPv4VirtualIPAddressesStandbyUp";
      type uint32;
      description
        "Number of UP IPv4 Virtual IP Addresses on groups
        in STANDBY state";
    }
    leaf ipv4-virtual-ip-addresses-standby-down {
      xr:xr-xml-map "hsrp:IPv4VirtualIPAddressesStandbyDown";
      type uint32;
      description
        "Number of DOWN IPv4 Virtual IP Addresses on
        groups in STANDBY state";
    }
    leaf ipv4-virtual-ip-addresses-speak-up {
      xr:xr-xml-map "hsrp:IPv4VirtualIPAddressesSpeakUp";
      type uint32;
      description
        "Number of UP IPv4 Virtual IP Addresses on groups
        in SPEAK state";
    }
    leaf ipv4-virtual-ip-addresses-speak-down {
      xr:xr-xml-map "hsrp:IPv4VirtualIPAddressesSpeakDown";
      type uint32;
      description
        "Number of DOWN IPv4 Virtual IP Addresses on
        groups in SPEAK state";
    }
    leaf ipv4-virtual-ip-addresses-listen-up {
      xr:xr-xml-map "hsrp:IPv4VirtualIPAddressesListenUp";
      type uint32;
      description
        "Number of UP IPv4 Virtual IP Addresses on groups
        in LISTEN state";
    }
    leaf ipv4-virtual-ip-addresses-listen-down {
      xr:xr-xml-map "hsrp:IPv4VirtualIPAddressesListenDown";
      type uint32;
      description
        "Number of DOWN IPv4 Virtual IP Addresses on
        groups in LISTEN state";
    }
    leaf ipv4-virtual-ip-addresses-learn-up {
      xr:xr-xml-map "hsrp:IPv4VirtualIPAddressesLearnUp";
      type uint32;
      description
        "Number of UP IPv4 Virtual IP Addresses on groups
        in LEARN state";
    }
    leaf ipv4-virtual-ip-addresses-learn-down {
      xr:xr-xml-map "hsrp:IPv4VirtualIPAddressesLearnDown";
      type uint32;
      description
        "Number of DOWN IPv4 Virtual IP Addresses on
        groups in LEARN state";
    }
    leaf ipv4-virtual-ip-addresses-init-up {
      xr:xr-xml-map "hsrp:IPv4VirtualIPAddressesInitUp";
      type uint32;
      description
        "Number of UP IPv4 Virtual IP Addresses on groups
        in INIT state";
    }
    leaf ipv4-virtual-ip-addresses-init-down {
      xr:xr-xml-map "hsrp:IPv4VirtualIPAddressesInitDown";
      type uint32;
      description
        "Number of DOWN IPv4 Virtual IP Addresses on
        groups in INIT state";
    }
    leaf ipv6-sessions-active {
      xr:xr-xml-map "hsrp:IPv6SessionsActive";
      type uint32;
      description "Number of IPv6 sessions in ACTIVE state";
    }
    leaf ipv6-sessions-standby {
      xr:xr-xml-map "hsrp:IPv6SessionsStandby";
      type uint32;
      description "Number of IPv6 sessions in STANDBY state";
    }
    leaf ipv6-sessions-speak {
      xr:xr-xml-map "hsrp:IPv6SessionsSpeak";
      type uint32;
      description "Number of IPv6 sessions in SPEAK state";
    }
    leaf ipv6-sessions-listen {
      xr:xr-xml-map "hsrp:IPv6SessionsListen";
      type uint32;
      description "Number of IPv6 sessions in LISTEN state";
    }
    leaf ipv6-sessions-learn {
      xr:xr-xml-map "hsrp:IPv6SessionsLearn";
      type uint32;
      description "Number of IPv6 sessions in LEARN state";
    }
    leaf ipv6-sessions-init {
      xr:xr-xml-map "hsrp:IPv6SessionsInit";
      type uint32;
      description "Number of IPv6 sessions in INIT state";
    }
    leaf ipv6-slaves-active {
      xr:xr-xml-map "hsrp:IPv6SlavesActive";
      type uint32;
      description "Number of IPv6 slaves in ACTIVE state";
    }
    leaf ipv6-slaves-standby {
      xr:xr-xml-map "hsrp:IPv6SlavesStandby";
      type uint32;
      description "Number of IPv6 slaves in STANDBY state";
    }
    leaf ipv6-slaves-speak {
      xr:xr-xml-map "hsrp:IPv6SlavesSpeak";
      type uint32;
      description "Number of IPv6 slaves in SPEAK state";
    }
    leaf ipv6-slaves-listen {
      xr:xr-xml-map "hsrp:IPv6SlavesListen";
      type uint32;
      description "Number of IPv6 slaves in LISTEN state";
    }
    leaf ipv6-slaves-learn {
      xr:xr-xml-map "hsrp:IPv6SlavesLearn";
      type uint32;
      description "Number of IPv6 slaves in LEARN state";
    }
    leaf ipv6-slaves-init {
      xr:xr-xml-map "hsrp:IPv6SlavesInit";
      type uint32;
      description "Number of IPv6 slaves in INIT state";
    }
    leaf ipv6-virtual-ip-addresses-active-up {
      xr:xr-xml-map "hsrp:IPv6VirtualIPAddressesActiveUp";
      type uint32;
      description
        "Number of UP IPv6 Virtual IP Addresses on groups
        in ACTIVE state";
    }
    leaf ipv6-virtual-ip-addresses-active-down {
      xr:xr-xml-map "hsrp:IPv6VirtualIPAddressesActiveDown";
      type uint32;
      description
        "Number of DOWN IPv6 Virtual IP Addresses on
        groups in ACTIVE state";
    }
    leaf ipv6-virtual-ip-addresses-standby-up {
      xr:xr-xml-map "hsrp:IPv6VirtualIPAddressesStandbyUp";
      type uint32;
      description
        "Number of UP IPv6 Virtual IP Addresses on groups
        in STANDBY state";
    }
    leaf ipv6-virtual-ip-addresses-standby-down {
      xr:xr-xml-map "hsrp:IPv6VirtualIPAddressesStandbyDown";
      type uint32;
      description
        "Number of DOWN IPv6 Virtual IP Addresses on
        groups in STANDBY state";
    }
    leaf ipv6-virtual-ip-addresses-speak-up {
      xr:xr-xml-map "hsrp:IPv6VirtualIPAddressesSpeakUp";
      type uint32;
      description
        "Number of UP IPv6 Virtual IP Addresses on groups
        in SPEAK state";
    }
    leaf ipv6-virtual-ip-addresses-speak-down {
      xr:xr-xml-map "hsrp:IPv6VirtualIPAddressesSpeakDown";
      type uint32;
      description
        "Number of DOWN IPv6 Virtual IP Addresses on
        groups in SPEAK state";
    }
    leaf ipv6-virtual-ip-addresses-listen-up {
      xr:xr-xml-map "hsrp:IPv6VirtualIPAddressesListenUp";
      type uint32;
      description
        "Number of UP IPv6 Virtual IP Addresses on groups
        in LISTEN state";
    }
    leaf ipv6-virtual-ip-addresses-listen-down {
      xr:xr-xml-map "hsrp:IPv6VirtualIPAddressesListenDown";
      type uint32;
      description
        "Number of DOWN IPv6 Virtual IP Addresses on
        groups in LISTEN state";
    }
    leaf ipv6-virtual-ip-addresses-learn-up {
      xr:xr-xml-map "hsrp:IPv6VirtualIPAddressesLearnUp";
      type uint32;
      description
        "Number of UP IPv6 Virtual IP Addresses on groups
        in LEARN state";
    }
    leaf ipv6-virtual-ip-addresses-learn-down {
      xr:xr-xml-map "hsrp:IPv6VirtualIPAddressesLearnDown";
      type uint32;
      description
        "Number of DOWN IPv6 Virtual IP Addresses on
        groups in LEARN state";
    }
    leaf ipv6-virtual-ip-addresses-init-up {
      xr:xr-xml-map "hsrp:IPv6VirtualIPAddressesInitUp";
      type uint32;
      description
        "Number of UP IPv6 Virtual IP Addresses on groups
        in INIT state";
    }
    leaf ipv6-virtual-ip-addresses-init-down {
      xr:xr-xml-map "hsrp:IPv6VirtualIPAddressesInitDown";
      type uint32;
      description
        "Number of DOWN IPv6 Virtual IP Addresses on
        groups in INIT state";
    }
    leaf interfaces-ipv4-state-up {
      xr:xr-xml-map "hsrp:InterfacesIPv4StateUp";
      type uint32;
      description
        "Number of HSRP interfaces with IPv4 caps in UP
        state";
    }
    leaf interfaces-ipv4-state-down {
      xr:xr-xml-map "hsrp:InterfacesIPv4StateDown";
      type uint32;
      description
        "Number of HSRP interfaces with IPv4 caps in DOWN
        state";
    }
    leaf tracked-interfaces-ipv4-state-up {
      xr:xr-xml-map "hsrp:TrackedInterfacesIPv4StateUp";
      type uint32;
      description
        "Number of tracked interfaces with IPv4 caps in
        UP state";
    }
    leaf tracked-interfaces-ipv4-state-down {
      xr:xr-xml-map "hsrp:TrackedInterfacesIPv4StateDown";
      type uint32;
      description
        "Number of tracked interfaces with IPv4 caps in
        DOWN state";
    }
    leaf tracked-objects-up {
      xr:xr-xml-map "hsrp:TrackedObjectsUp";
      type uint32;
      description "Number of tracked objects in UP state";
    }
    leaf tracked-objects-down {
      xr:xr-xml-map "hsrp:TrackedObjectsDown";
      type uint32;
      description "Number of tracked objects in DOWN state";
    }
    leaf interfaces-ipv6-state-up {
      xr:xr-xml-map "hsrp:InterfacesIPv6StateUp";
      type uint32;
      description
        "Number of HSRP interfaces with IPv6 caps in UP
        state";
    }
    leaf interfaces-ipv6-state-down {
      xr:xr-xml-map "hsrp:InterfacesIPv6StateDown";
      type uint32;
      description
        "Number of HSRP interfaces with IPv6 caps in DOWN
        state";
    }
    leaf tracked-interfaces-ipv6-state-up {
      xr:xr-xml-map "hsrp:TrackedInterfacesIPv6StateUp";
      type uint32;
      description
        "Number of tracked interfaces with IPv6 caps in
        UP state";
    }
    leaf tracked-interfaces-ipv6-state-down {
      xr:xr-xml-map "hsrp:TrackedInterfacesIPv6StateDown";
      type uint32;
      description
        "Number of tracked interfaces with IPv6 caps in
        DOWN state";
    }
    leaf bfd-sessions-up {
      xr:xr-xml-map "hsrp:BFDSessionsUp";
      type uint32;
      description "Number of HSRP BFD sessions in UP state";
    }
    leaf bfd-sessions-down {
      xr:xr-xml-map "hsrp:BFDSessionsDown";
      type uint32;
      description "Number of HSRP BFD sessions in DOWN state";
    }
    leaf bfd-session-inactive {
      xr:xr-xml-map "hsrp:BFDSessionInactive";
      type uint32;
      description "Number of HSRP BFD sessions in INACTIVE state";
    }
  }

  grouping HSRP-BFD-GROUP-INFO {
    description "BFD Group Information";
    leaf interface-name {
      xr:xr-xml-map "hsrp:InterfaceName";
      type string {
        length "0..64";
      }
      description "Interface Name";
    }
    leaf hsrp-group-number {
      xr:xr-xml-map "hsrp:HSRPGroupNumber";
      type uint32;
      description "HSRP Group number";
    }
  }

  grouping STANDBY-BFD-INFO {
    description "BFD session information";
    leaf bfd-interface-name {
      xr:xr-xml-map "hsrp:BFDInterfaceName";
      type string {
        length "0..64";
      }
      description "BFD Interface Name";
    }
    leaf session-address-family {
      xr:xr-xml-map "hsrp:SessionAddressFamily";
      type Hsrp-b-af;
      description "Session Address family";
    }
    leaf destination-address {
      xr:xr-xml-map "hsrp:DestinationAddress";
      type inet:ipv4-address;
      description "BFD destination address";
    }
    leaf destination-ipv6-address {
      xr:xr-xml-map "hsrp:DestinationIPv6Address";
      type inet:ipv6-address;
      description "BFD IPv6 destination address";
    }
    leaf bfd-session-state {
      xr:xr-xml-map "hsrp:BFDSessionState";
      type Hsrp-bfd-session-state;
      description "BFD session state";
    }
    leaf bfd-interval {
      xr:xr-xml-map "hsrp:BFDInterval";
      type uint32;
      description "BFD packet send interval";
    }
    leaf bfd-multiplier {
      xr:xr-xml-map "hsrp:BFDMultiplier";
      type uint32;
      description "BFD multiplier";
    }

    list group {
      description "HSRP Groups tracking the BFD session";
      uses HSRP-BFD-GROUP-INFO;
    }
  }

  grouping HSRP-SLAVE-INFO-TYPE {
    description "Slave info";
    leaf slave-group-interface {
      xr:xr-xml-map "hsrp:SlaveGroupInterface";
      type string {
        length "0..64";
      }
      description "Interface of slave group";
    }
    leaf slave-group-number {
      xr:xr-xml-map "hsrp:SlaveGroupNumber";
      type uint32;
      description "Group number of slave group";
    }
  }

  grouping HSRP-MGO-INFO {
    description "MGO group data";
    leaf primary-session-name {
      xr:xr-xml-map "hsrp:PrimarySessionName";
      type string {
        length "0..16";
      }
      description "Session Name";
    }
    leaf primary-session-interface {
      xr:xr-xml-map "hsrp:PrimarySessionInterface";
      type xr:Interface-name;
      description "Interface of primary session";
    }
    leaf primary-af-name {
      xr:xr-xml-map "hsrp:PrimaryAFName";
      type Hsrp-b-af;
      description "Address family of primary session";
    }
    leaf primary-session-number {
      xr:xr-xml-map "hsrp:PrimarySessionNumber";
      type uint32;
      description "Group number of primary session";
    }
    leaf primary-session-state {
      xr:xr-xml-map "hsrp:PrimarySessionState";
      type Standby-grp-state;
      description "State of primary session";
    }

    list slave {
      description "List of slaves following this primary session";
      uses HSRP-SLAVE-INFO-TYPE;
    }
  }

  grouping HSRP-IF-STATS-TYPE {
    description "HSRP Interface Statistics";
    leaf advert-packets-sent {
      xr:xr-xml-map "hsrp:AdvertPacketsSent";
      type uint32;
      description "Number of advertisement packets sent";
    }
    leaf advert-packets-received {
      xr:xr-xml-map "hsrp:AdvertPacketsReceived";
      type uint32;
      description "Number of advertisement packets received";
    }
    leaf long-packets-received {
      xr:xr-xml-map "hsrp:LongPacketsReceived";
      type uint32;
      description "Number of packets received that were too Long";
    }
    leaf short-packets-received {
      xr:xr-xml-map "hsrp:ShortPacketsReceived";
      type uint32;
      description "Number of packets received that were too short";
    }
    leaf invalid-version-received {
      xr:xr-xml-map "hsrp:InvalidVersionReceived";
      type uint32;
      description "Number of packets received with invalid version";
    }
    leaf invalid-operation-code-received {
      xr:xr-xml-map "hsrp:InvalidOperationCodeReceived";
      type uint32;
      description
        "Number of packets received with invalid
        operation code";
    }
    leaf unknown-group-received {
      xr:xr-xml-map "hsrp:UnknownGroupReceived";
      type uint32;
      description
        "Number of packets received for an unknown group
        id";
    }
    leaf inoperational-group-received {
      xr:xr-xml-map "hsrp:InoperationalGroupReceived";
      type uint32;
      description
        "Number of packets received for an inoperational
        group";
    }
    leaf conflict-source-ip-address-received {
      xr:xr-xml-map "hsrp:ConflictSourceIPAddressReceived";
      type uint32;
      description
        "Number of packets received from a conflicting
        Source IP address";
    }
  }

  grouping STANDBY-IF-INFO {
    description "Use burnt in mac address information";

    container statistics {
      description "HSRP Interface Statistics";
      uses HSRP-IF-STATS-TYPE;
    }
    leaf interface {
      xr:xr-xml-map "hsrp:Interface";
      type xr:Interface-name;
      description "IM Interface";
    }
    leaf use-bia-flag {
      xr:xr-xml-map "hsrp:UseBIAFlag";
      type boolean;
      description "Use burnt in mac address flag";
    }
  }

  grouping STANDBY-TRACKEDIF-INFO {
    description "Interface tracking information";
    leaf interface {
      xr:xr-xml-map "hsrp:Interface";
      type xr:Interface-name;
      description "IM Interface";
    }
    leaf hsrp-group-number {
      xr:xr-xml-map "hsrp:HSRPGroupNumber";
      type uint32;
      description "HSRP Group number";
    }
    leaf priority-decrement {
      xr:xr-xml-map "hsrp:PriorityDecrement";
      type uint32;
      description "Priority weighting";
    }
    leaf interface-up-flag {
      xr:xr-xml-map "hsrp:InterfaceUpFlag";
      type boolean;
      description "Interface up flag";
    }
    leaf tracked-interface-name-xr {
      xr:xr-xml-map "hsrp:tracked-interface-name-xr";
      type string {
        length "0..64";
      }
      description "Tracked Interface Name";
    }
    leaf is-object {
      xr:xr-xml-map "hsrp:IsObject";
      type boolean;
      description "Tracked Object Flag";
    }
  }

  grouping HSRP-GROUP-STATS-TYPE {
    description "HSRP Group Statistics";
    leaf active-transitions {
      xr:xr-xml-map "hsrp:ActiveTransitions";
      type uint32;
      description "Number of transitions to Active State";
    }
    leaf standby-transitions {
      xr:xr-xml-map "hsrp:StandbyTransitions";
      type uint32;
      description "Number of transitions to Standby State";
    }
    leaf speak-transitions {
      xr:xr-xml-map "hsrp:SpeakTransitions";
      type uint32;
      description "Number of transitions to Speak State";
    }
    leaf listen-transitions {
      xr:xr-xml-map "hsrp:ListenTransitions";
      type uint32;
      description "Number of transitions to Listen State";
    }
    leaf learn-transitions {
      xr:xr-xml-map "hsrp:LearnTransitions";
      type uint32;
      description "Number of transitions to Learn State";
    }
    leaf init-transitions {
      xr:xr-xml-map "hsrp:InitTransitions";
      type uint32;
      description "Number of transitions to Init State";
    }
    leaf hello-packets-sent {
      xr:xr-xml-map "hsrp:HelloPacketsSent";
      type uint32;
      description "Number of Hello Packets sent (NB: Bundles only)";
    }
    leaf resign-packets-sent {
      xr:xr-xml-map "hsrp:ResignPacketsSent";
      type uint32;
      description "Number of Resign Packets sent";
    }
    leaf coup-packets-sent {
      xr:xr-xml-map "hsrp:CoupPacketsSent";
      type uint32;
      description "Number of Coup Packets sent";
    }
    leaf hello-packets-received {
      xr:xr-xml-map "hsrp:HelloPacketsReceived";
      type uint32;
      description "Number of Hello Packets received";
    }
    leaf resign-packets-received {
      xr:xr-xml-map "hsrp:ResignPacketsReceived";
      type uint32;
      description "Number of Resign Packets received";
    }
    leaf coup-packets-received {
      xr:xr-xml-map "hsrp:CoupPacketsReceived";
      type uint32;
      description "Number of Coup Packets received";
    }
    leaf auth-fail-received {
      xr:xr-xml-map "hsrp:AuthFailReceived";
      type uint32;
      description
        "Number of Packets received that failed
        authentication";
    }
    leaf invalid-timer-received {
      xr:xr-xml-map "hsrp:InvalidTimerReceived";
      type uint32;
      description
        "Number of packets received with invalid Hello
        Time value";
    }
    leaf mismatch-virtual-ip-address-received {
      xr:xr-xml-map "hsrp:MismatchVirtualIPAddressReceived";
      type uint32;
      description
        "Number of packets received with mismatching
        virtual IP address";
    }
  }

  grouping HSRP-STATE-CHANGE-INFO-TYPE {
    description "State change info";

    container time {
      description "Time of state change";
      uses HSRP-BAG-TIMESTAMP;
    }
    leaf old-state {
      xr:xr-xml-map "hsrp:OldState";
      type Standby-grp-state;
      description "Old State";
    }
    leaf new-state {
      xr:xr-xml-map "hsrp:NewState";
      type Standby-grp-state;
      description "New State";
    }
    leaf reason {
      xr:xr-xml-map "hsrp:Reason";
      type Hsrp-state-change-reason;
      description "Reason for state change";
    }
  }

  grouping HSRP-BAG-TIMESTAMP {
    description "Timestamp";
    leaf seconds {
      xr:xr-xml-map "hsrp:Seconds";
      type uint32;
      units "second";
      description "Seconds";
    }
    leaf nanoseconds {
      xr:xr-xml-map "hsrp:Nanoseconds";
      type uint32;
      units "nanosecond";
      description "Nanoseconds";
    }
  }

  grouping IPV6-BAG-ADDR {
    description "IPV6 BAG ADDR";
    leaf ipv6-address {
      xr:xr-xml-map "hsrp:IPV6Address";
      type inet:ipv6-address;
      description "IPV6Address";
    }
  }

  grouping STANDBY-GRP-INFO {
    description "Detailed group specfic information";

    container resign-sent-time {
      description "Time last resign was sent";
      uses HSRP-BAG-TIMESTAMP;
    }

    container resign-received-time {
      description "Time last resign was received";
      uses HSRP-BAG-TIMESTAMP;
    }

    container coup-sent-time {
      description "Time last coup was sent";
      uses HSRP-BAG-TIMESTAMP;
    }

    container coup-received-time {
      description "Time last coup was received";
      uses HSRP-BAG-TIMESTAMP;
    }

    container statistics {
      description "HSRP Group statistics";
      uses HSRP-GROUP-STATS-TYPE;
    }
    leaf authentication-string {
      xr:xr-xml-map "hsrp:AuthenticationString";
      type string {
        length "0..9";
      }
      description "Authentication string";
    }
    leaf virtual-mac-address {
      xr:xr-xml-map "hsrp:VirtualMACAddress";
      type yang:mac-address;
      description "Virtual mac address";
    }
    leaf hsrp-group-number {
      xr:xr-xml-map "hsrp:HSRPGroupNumber";
      type uint32;
      description "HSRP Group number";
    }
    leaf address-family {
      xr:xr-xml-map "hsrp:AddressFamily";
      type Hsrp-b-af;
      description "Address family";
    }
    leaf version {
      xr:xr-xml-map "hsrp:Version";
      type Hsrp-version;
      description "HSRP Protocol Version";
    }
    leaf session-name {
      xr:xr-xml-map "hsrp:SessionName";
      type string {
        length "0..16";
      }
      description "Session Name";
    }
    leaf slaves {
      xr:xr-xml-map "hsrp:Slaves";
      type uint32;
      description "Number of slaves following state";
    }
    leaf is-slave {
      xr:xr-xml-map "hsrp:IsSlave";
      type boolean;
      description "Group is a slave group";
    }
    leaf followed-session-name {
      xr:xr-xml-map "hsrp:FollowedSessionName";
      type string {
        length "0..16";
      }
      description "Followed Session Name";
    }
    leaf configured-priority {
      xr:xr-xml-map "hsrp:ConfiguredPriority";
      type uint8;
      description "Configured priority";
    }
    leaf preempt-delay {
      xr:xr-xml-map "hsrp:PreemptDelay";
      type uint32;
      units "second";
      description "Preempt delay time in seconds";
    }
    leaf preempt-timer-secs {
      xr:xr-xml-map "hsrp:PreemptTimerSecs";
      type uint32;
      units "second";
      description "Preempt time remaining in seconds";
    }
    leaf hello-time {
      xr:xr-xml-map "hsrp:HelloTime";
      type uint32;
      units "millisecond";
      description "Hellotime in msecs";
    }
    leaf hold-time {
      xr:xr-xml-map "hsrp:HoldTime";
      type uint32;
      units "millisecond";
      description "Holdtime in msecs";
    }
    leaf learned-hello-time {
      xr:xr-xml-map "hsrp:LearnedHelloTime";
      type uint32;
      units "millisecond";
      description "Learned hellotime in msecs";
    }
    leaf learned-hold-time {
      xr:xr-xml-map "hsrp:LearnedHoldTime";
      type uint32;
      units "millisecond";
      description "Learned holdtime in msecs";
    }
    leaf min-delay-time {
      xr:xr-xml-map "hsrp:MinDelayTime";
      type uint32;
      units "millisecond";
      description "Minimum delay time in msecs";
    }
    leaf reload-delay-time {
      xr:xr-xml-map "hsrp:ReloadDelayTime";
      type uint32;
      units "millisecond";
      description "Reload delay time in msecs";
    }
    leaf virtual-ip-address {
      xr:xr-xml-map "hsrp:VirtualIPAddress";
      type inet:ipv4-address;
      description "Configured Virtual IPv4 address";
    }
    leaf virtual-linklocal-ipv6-address {
      xr:xr-xml-map "hsrp:VirtualLinklocalIPv6Address";
      type inet:ipv6-address;
      description "Virtual linklocal IPv6 address";
    }
    leaf active-ip-address {
      xr:xr-xml-map "hsrp:ActiveIPAddress";
      type inet:ipv4-address;
      description "Active router's IP address";
    }
    leaf active-ipv6-address {
      xr:xr-xml-map "hsrp:ActiveIPv6Address";
      type inet:ipv6-address;
      description "Active router's IPv6 address";
    }
    leaf active-mac-address {
      xr:xr-xml-map "hsrp:ActiveMACAddress";
      type yang:mac-address;
      description "Active router's interface MAC address";
    }
    leaf standby-ip-address {
      xr:xr-xml-map "hsrp:StandbyIPAddress";
      type inet:ipv4-address;
      description "Standby router's IP address";
    }
    leaf standby-ipv6-address {
      xr:xr-xml-map "hsrp:StandbyIPv6Address";
      type inet:ipv6-address;
      description "Standby router's IPv6 address";
    }
    leaf standby-mac-address {
      xr:xr-xml-map "hsrp:StandbyMACAddress";
      type yang:mac-address;
      description "Standby router's interface MAC address";
    }
    leaf hsrp-router-state {
      xr:xr-xml-map "hsrp:HSRPRouterState";
      type Standby-grp-state;
      description "HSRP router state";
    }
    leaf interface-name-xr {
      xr:xr-xml-map "hsrp:interface-name-xr";
      type string {
        length "0..64";
      }
      description "Interface Name";
    }
    leaf interface {
      xr:xr-xml-map "hsrp:Interface";
      type xr:Interface-name;
      description "IM Interface";
    }
    leaf router-priority {
      xr:xr-xml-map "hsrp:RouterPriority";
      type uint8;
      description "Priority of the router";
    }
    leaf active-priority {
      xr:xr-xml-map "hsrp:ActivePriority";
      type uint8;
      description "Priority of the Active router";
    }
    leaf active-timer-flag {
      xr:xr-xml-map "hsrp:ActiveTimerFlag";
      type boolean;
      description "Active timer running flag";
    }
    leaf active-timer-secs {
      xr:xr-xml-map "hsrp:ActiveTimerSecs";
      type uint32;
      units "second";
      description "Active timer running time secs";
    }
    leaf active-timer-msecs {
      xr:xr-xml-map "hsrp:ActiveTimerMsecs";
      type uint32;
      units "millisecond";
      description "Active timer running time msecs";
    }
    leaf standby-timer-flag {
      xr:xr-xml-map "hsrp:StandbyTimerFlag";
      type boolean;
      description "Standby timer running flag";
    }
    leaf standby-timer-secs {
      xr:xr-xml-map "hsrp:StandbyTimerSecs";
      type uint32;
      units "second";
      description "Standby timer running time secs";
    }
    leaf standby-timer-msecs {
      xr:xr-xml-map "hsrp:StandbyTimerMsecs";
      type uint32;
      units "millisecond";
      description "Standby timer running time msecs";
    }
    leaf hello-timer-flag {
      xr:xr-xml-map "hsrp:HelloTimerFlag";
      type boolean;
      description "Hello timer running flag";
    }
    leaf hello-timer-secs {
      xr:xr-xml-map "hsrp:HelloTimerSecs";
      type uint32;
      units "second";
      description "Hello timer running time secs";
    }
    leaf hello-timer-msecs {
      xr:xr-xml-map "hsrp:HelloTimerMsecs";
      type uint32;
      units "millisecond";
      description "Hello timer running time msecs";
    }
    leaf delay-timer-flag {
      xr:xr-xml-map "hsrp:DelayTimerFlag";
      type boolean;
      description "Delay timer running flag";
    }
    leaf delay-timer-secs {
      xr:xr-xml-map "hsrp:DelayTimerSecs";
      type uint32;
      units "second";
      description "Delay timer running time secs";
    }
    leaf delay-timer-msecs {
      xr:xr-xml-map "hsrp:DelayTimerMsecs";
      type uint32;
      units "millisecond";
      description "Delay timer running time msecs";
    }
    leaf current-state-timer-secs {
      xr:xr-xml-map "hsrp:CurrentStateTimerSecs";
      type uint32;
      units "second";
      description "Time in current state secs";
    }
    leaf state-change-count {
      xr:xr-xml-map "hsrp:StateChangeCount";
      type uint32;
      description "Number of state changes";
    }
    leaf tracked-interface-count {
      xr:xr-xml-map "hsrp:TrackedInterfaceCount";
      type uint32;
      description "Number of tracked interfaces";
    }
    leaf tracked-interface-up-count {
      xr:xr-xml-map "hsrp:TrackedInterfaceUpCount";
      type uint32;
      description "Number of tracked interfaces up";
    }
    leaf preempt-enabled {
      xr:xr-xml-map "hsrp:PreemptEnabled";
      type boolean;
      description "Preempt enabled";
    }
    leaf use-configured-timers {
      xr:xr-xml-map "hsrp:UseConfiguredTimers";
      type boolean;
      description "Use configured timers";
    }
    leaf use-configured-virtual-ip {
      xr:xr-xml-map "hsrp:UseConfiguredVirtualIP";
      type boolean;
      description "Use configured virtual IP";
    }
    leaf use-bia-configured {
      xr:xr-xml-map "hsrp:UseBIAConfigured";
      type boolean;
      description "Use burnt in MAC address configured";
    }
    leaf configured-timers {
      xr:xr-xml-map "hsrp:ConfiguredTimers";
      type boolean;
      description "Non-default timers are configured";
    }
    leaf configured-mac-address {
      xr:xr-xml-map "hsrp:ConfiguredMACAddress";
      type boolean;
      description "MAC address configured";
    }
    leaf redirects-disabled {
      xr:xr-xml-map "hsrp:RedirectsDisabled";
      type boolean;
      description "HSRP redirects disabled";
    }
    leaf bfd-enabled {
      xr:xr-xml-map "hsrp:BFDEnabled";
      type boolean;
      description "HSRP BFD fast failover";
    }
    leaf bfd-interface {
      xr:xr-xml-map "hsrp:BFDInterface";
      type xr:Interface-name;
      description "BFD Interface";
    }
    leaf bfd-peer-ip-address {
      xr:xr-xml-map "hsrp:BFDPeerIPAddress";
      type inet:ipv4-address;
      description "BFD Peer IP address";
    }
    leaf bfd-peer-ipv6-address {
      xr:xr-xml-map "hsrp:BFDPeerIPv6Address";
      type inet:ipv6-address;
      description "BFD Peer IPv6 address";
    }
    leaf bfd-session-state {
      xr:xr-xml-map "hsrp:BFDSessionState";
      type Hsrp-bfd-session-state;
      description "BFD session state";
    }
    leaf bfd-interval {
      xr:xr-xml-map "hsrp:BFDInterval";
      type uint32;
      description "BFD packet send interval";
    }
    leaf bfd-multiplier {
      xr:xr-xml-map "hsrp:BFDMultiplier";
      type uint32;
      description "BFD multiplier";
    }
    leaf virtual-mac-address-state {
      xr:xr-xml-map "hsrp:VirtualMACAddressState";
      type Hsrp-vmac-state;
      description "Virtual mac address state";
    }
    leaf-list secondary-address {
      xr:xr-xml-map "hsrp:SecondaryAddressList";
      type inet:ipv4-address;
      description "Secondary virtual IP addresses";
    }

    list global-address {
      description "Global virtual IPv6 addresses";
      uses IPV6-BAG-ADDR;
    }

    list state-change-history {
      description "State change history";
      uses HSRP-STATE-CHANGE-INFO-TYPE;
    }
  }
}
