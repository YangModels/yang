module Cisco-IOS-XR-ipv4-igmp-cfg {

  /*** NAMESPACE / PREFIX DEFINITION ***/

  namespace "http://cisco.com/ns/yang/Cisco-IOS-XR-ipv4-igmp-cfg";


  prefix "ipv4-igmp-cfg";

  /*** LINKAGE (IMPORTS / INCLUDES) ***/

  import ietf-inet-types { prefix "inet"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ipv4-igmp package configuration.

     This module contains definitions
     for the following management objects:
       igmp: IGMPconfiguration
       amt: amt
       mld: mld

     Copyright (c) 2013-2016 by Cisco Systems, Inc.
     All rights reserved.";

  revision "2015-11-09" {
    description
      "IOS XR 6.0 revision.";
  }

  typedef Igmp-filter {
    type enumeration {
      enum include {
        value 0;
        description "Include";
      }
      enum exclude {
        value 1;
        description "Exclude";
      }
    }
    description "Igmp filter";
  }

  grouping MAXIMUM-GROUPS-PER-INTERFACE-OOR {
    description "Common node of inheritable-defaults, interface";

    container maximum-groups-per-interface-oor {
      xr:xr-xml-map "ipv4_igmp_common_cfg:MaximumGroupsPerInterface"+
        "OOR";
      description
        "Configure maximum number of groups accepted per
        interface by this router";
      leaf maximum-groups {
        xr:xr-xml-map "ipv4_igmp_common_cfg:MaximumGroups";
        type uint32 {
          range "1..40000";
        }
        default "25000";
        description
          "Maximum number of groups accepted per interface
          by this router";
      }
      leaf warning-threshold {
        xr:xr-xml-map "ipv4_igmp_common_cfg:WarningThreshold";
        type uint32 {
          range "1..40000";
        }
        default "25000";
        description
          " WarningThreshold for number of groups accepted
          per interface by this router";
      }
      leaf access-list-name {
        xr:xr-xml-map "ipv4_igmp_common_cfg:AccessListName";
        type string;
        description "Access-list to account for";
      }
    }
  }

  grouping TRAFFIC {
    description "Common node of vrf, default-context";

    container traffic {
      xr:xr-xml-map "ipv4_igmp_common_cfg:Traffic";
      description "Configure IGMP Traffic variables";
      leaf profile {
        xr:xr-xml-map "ipv4_igmp_common_cfg:Profile";
        type string;
        description "Configure the route-policy profile";
      }
    }
  }

  grouping INHERITABLE-DEFAULTS {
    description "Common node of vrf, default-context";

    container inheritable-defaults {
      xr:xr-xml-map "ipv4_igmp_common_cfg:InheritableDefaults";
      description "Inheritable Defaults";
      uses MAXIMUM-GROUPS-PER-INTERFACE-OOR;
      uses QUERY-TIMEOUT;
      uses ACCESS-GROUP;
      uses QUERY-MAX-RESPONSE-TIME;
      uses VERSION;
      uses ROUTER-ENABLE;
      uses QUERY-INTERVAL;
      uses EXPLICIT-TRACKING;
    }
  }

  grouping ROBUSTNESS {
    description "Common node of vrf, default-context";
    leaf robustness {
      xr:xr-xml-map "ipv4_igmp_common_cfg:Robustness";
      type uint32 {
        range "2..10";
      }
      default "2";
      description "Configure IGMP Robustness variable";
    }
  }

  grouping VERSION {
    description "Common node of inheritable-defaults, interface";
    leaf version {
      xr:xr-xml-map "ipv4_igmp_common_cfg:Version";
      type uint32 {
        range "1..3";
      }
      default "3";
      description "Version number";
    }
  }

  grouping MAXIMUM {
    description "Common node of vrf, default-context";

    container maximum {
      xr:xr-xml-map "ipv4_igmp_common_cfg:Maximum";
      description "Configure IGMP State Limits";
      leaf maximum-groups {
        xr:xr-xml-map "ipv4_igmp_common_cfg:MaximumGroups";
        type uint32 {
          range "1..75000";
        }
        default "50000";
        description
          "Configure maximum number of groups accepted by
          this router";
      }
    }
  }

  grouping INTERFACE-TABLE {
    description "Common node of vrf, default-context";

    container interfaces {
      xr:xr-xml-map "ipv4_igmp_common_cfg:InterfaceTable";
      description "Interface-level configuration";

      list interface {
        xr:xr-xml-map "ipv4_igmp_common_cfg:Interface";
        key "interface-name";
        description "The name of the interface";

        container join-groups {
          xr:xr-xml-map "ipv4_igmp_common_cfg:JoinGroupTable";

          grouping JOIN-GROUP-CONTENT {
            description "JOIN GROUP CONTENT";
            leaf mode {
              xr:xr-xml-map "ipv4_igmp_common_cfg:Mode";
              type Igmp-filter;
              mandatory true;
              description "Filter mode";
            }
          }

          list join-group {
            key "group-address";
            description
              "IP group address and optional source address
              to include";
            leaf group-address {
              xr:xr-xml-map "ipv4_igmp_common_cfg:GroupAddress";
              type inet:ip-address-no-zone;
              description "IP group address";
            }
            uses JOIN-GROUP-CONTENT;
          }

          list join-group-source-address {
            key "source-address group-address";
            description
              "IP group address and optional source address
              to include";
            leaf source-address {
              xr:xr-xml-map "ipv4_igmp_common_cfg:SourceAddress";
              type inet:ip-address-no-zone;
              description "IP source address";
            }
            leaf group-address {
              xr:xr-xml-map "ipv4_igmp_common_cfg:GroupAddress";
              type inet:ip-address-no-zone;
              description "IP group address";
            }
            uses JOIN-GROUP-CONTENT;
          }
          presence "Indicates a join-groups node is configured.";
          description "IGMP join multicast group";
        }

        container static-group-group-addresses {
          xr:xr-xml-map "ipv4_igmp_common_cfg:StaticGroupTable";
          description "IGMP static multicast group";

          grouping STATIC-GROUP-CONTENT {
            description "STATIC GROUP CONTENT";
            leaf group-count {
              xr:xr-xml-map "ipv4_igmp_common_cfg:GroupCount";
              type uint32 {
                range "1..512";
              }
              default "1";
              description
                "Number of groups to join if mask is present.";
            }
            leaf source-count {
              xr:xr-xml-map "ipv4_igmp_common_cfg:SourceCount";
              type uint32 {
                range "1..512";
              }
              default "1";
              description
                "Number of sources to join if mask is present
                .";
            }
            leaf suppress-report {
              xr:xr-xml-map "ipv4_igmp_common_cfg:SuppressReport";
              type boolean;
              default "false";
              description "Suppress reports";
            }
          }

          list static-group-group-address {
            key "group-address";
            description
              "IP group address and optional source address
              to include";
            leaf group-address {
              xr:xr-xml-map "ipv4_igmp_common_cfg:GroupAddress";
              type inet:ip-address-no-zone;
              description "IP group address";
            }
            uses STATIC-GROUP-CONTENT;
          }

          list static-group-group-address-source-address {
            key "group-address source-address";
            description
              "IP group address and optional source address
              to include";
            leaf group-address {
              xr:xr-xml-map "ipv4_igmp_common_cfg:GroupAddress";
              type inet:ip-address-no-zone;
              description "IP group address";
            }
            leaf source-address {
              xr:xr-xml-map "ipv4_igmp_common_cfg:SourceAddress";
              type inet:ip-address-no-zone;
              description "IP source address";
            }
            uses STATIC-GROUP-CONTENT;
          }

          list "static-group-group-address-source-address-source"+
            "-address-mask" {
            key "group-address source-address source-address-mask";
            description
              "IP group address and optional source address
              to include";
            leaf group-address {
              xr:xr-xml-map "ipv4_igmp_common_cfg:GroupAddress";
              type inet:ip-address-no-zone;
              description "IP group address";
            }
            leaf source-address {
              xr:xr-xml-map "ipv4_igmp_common_cfg:SourceAddress";
              type inet:ip-address-no-zone;
              description "IP source address";
            }
            leaf source-address-mask {
              xr:xr-xml-map "ipv4_igmp_common_cfg:SourceAddressMask";
              type inet:ip-address-no-zone;
              description "Mask for Source Address";
            }
            uses STATIC-GROUP-CONTENT;
          }

          list static-group-group-address-group-address-mask {
            key "group-address group-address-mask";
            description
              "IP group address and optional source address
              to include";
            leaf group-address {
              xr:xr-xml-map "ipv4_igmp_common_cfg:GroupAddress";
              type inet:ip-address-no-zone;
              description "IP group address";
            }
            leaf group-address-mask {
              xr:xr-xml-map "ipv4_igmp_common_cfg:GroupAddressMask";
              type inet:ip-address-no-zone;
              description "Mask for Group Address";
            }
            uses STATIC-GROUP-CONTENT;
          }

          list "static-group-group-address-group-address-mask"+
            "-source-address" {
            key "group-address group-address-mask source-address";
            description
              "IP group address and optional source address
              to include";
            leaf group-address {
              xr:xr-xml-map "ipv4_igmp_common_cfg:GroupAddress";
              type inet:ip-address-no-zone;
              description "IP group address";
            }
            leaf group-address-mask {
              xr:xr-xml-map "ipv4_igmp_common_cfg:GroupAddressMask";
              type inet:ip-address-no-zone;
              description "Mask for Group Address";
            }
            leaf source-address {
              xr:xr-xml-map "ipv4_igmp_common_cfg:SourceAddress";
              type inet:ip-address-no-zone;
              description "IP source address";
            }
            uses STATIC-GROUP-CONTENT;
          }

          list "static-group-group-address-group-address-mask"+
            "-source-address-source-address-mask" {
            key "group-address group-address-mask source-address"+
              " source-address-mask";
            description
              "IP group address and optional source address
              to include";
            leaf group-address {
              xr:xr-xml-map "ipv4_igmp_common_cfg:GroupAddress";
              type inet:ip-address-no-zone;
              description "IP group address";
            }
            leaf group-address-mask {
              xr:xr-xml-map "ipv4_igmp_common_cfg:GroupAddressMask";
              type inet:ip-address-no-zone;
              description "Mask for Group Address";
            }
            leaf source-address {
              xr:xr-xml-map "ipv4_igmp_common_cfg:SourceAddress";
              type inet:ip-address-no-zone;
              description "IP source address";
            }
            leaf source-address-mask {
              xr:xr-xml-map "ipv4_igmp_common_cfg:SourceAddressMask";
              type inet:ip-address-no-zone;
              description "Mask for Source Address";
            }
            uses STATIC-GROUP-CONTENT;
          }
        }
        leaf interface-name {
          xr:xr-xml-map "ipv4_igmp_common_cfg:InterfaceName";
          type xr:Interface-name;
          description "Name of the interface";
        }
        uses MAXIMUM-GROUPS-PER-INTERFACE-OOR;
        uses QUERY-TIMEOUT;
        uses ACCESS-GROUP;
        uses QUERY-MAX-RESPONSE-TIME;
        uses VERSION;
        uses ROUTER-ENABLE;
        uses QUERY-INTERVAL;
        uses EXPLICIT-TRACKING;
      }
    }
  }

  grouping ACCESS-GROUP {
    description "Common node of inheritable-defaults, interface";
    leaf access-group {
      xr:xr-xml-map "ipv4_igmp_common_cfg:AccessGroup";
      type string;
      description "Access list specifying access group range";
    }
  }

  grouping SSM-ACCESS-GROUP-TABLE {
    description "Common node of vrf, default-context";

    container ssm-access-groups {
      xr:xr-xml-map "ipv4_igmp_common_cfg:SSMAccessGroupTable";
      description "IGMP Source specific mode";

      list ssm-access-group {
        xr:xr-xml-map "ipv4_igmp_common_cfg:SSMAccessGroup";
        key "source-address";
        description "SSM static Access Group";
        leaf source-address {
          xr:xr-xml-map "ipv4_igmp_common_cfg:SourceAddress";
          type inet:ip-address-no-zone;
          description "IP source address";
        }
        leaf access-list-name {
          xr:xr-xml-map "ipv4_igmp_common_cfg:AccessListName";
          type string;
          mandatory true;
          description "Access list specifying access group";
        }
      }
    }
  }

  grouping ACCOUNTING {
    description "Common node of vrf, default-context";

    container accounting {
      xr:xr-xml-map "ipv4_igmp_common_cfg:Accounting";
      description
        "Configure IGMP accounting for logging join/leave
        records";
      leaf max-history {
        xr:xr-xml-map "ipv4_igmp_common_cfg:MaxHistory";
        type uint32 {
          range "0..365";
        }
        units "day";
        default "0";
        description
          "Configure IGMP accounting Maximum History
          setting";
      }
    }
  }

  grouping QUERY-MAX-RESPONSE-TIME {
    description "Common node of inheritable-defaults, interface";
    leaf query-max-response-time {
      xr:xr-xml-map "ipv4_igmp_common_cfg:QueryMaxResponseTime";
      type uint32 {
        range "1..12";
      }
      units "second";
      default "10";
      description "Query response value in seconds";
    }
  }

  grouping DEFAULT-CONTEXT {
    description "Common node of igmp, mld";

    container default-context {
      xr:xr-xml-map "ipv4_igmp_common_cfg:DefaultContext";
      presence "Indicates a default-context node is configured.";
      description "Default Context";

      container nsf {
        xr:xr-xml-map "ipv4_igmp_common_cfg:NSF";
        description "Configure NSF specific options";
        leaf lifetime {
          xr:xr-xml-map "ipv4_igmp_common_cfg:Lifetime";
          type uint32 {
            range "10..3600";
          }
          units "second";
          default "60";
          description "Maximum time for IGMP NSF mode in seconds";
        }
      }
      uses TRAFFIC;
      uses INHERITABLE-DEFAULTS;
      uses SSM-ACCESS-GROUP-TABLE;
      uses MAXIMUM;
      uses SSMDNS-QUERY-GROUP;
      uses UNICAST-QOS-ADJUST;
      uses ACCOUNTING;
      uses INTERFACE-TABLE;
      uses ROBUSTNESS;
    }
  }

  grouping QUERY-INTERVAL {
    description "Common node of inheritable-defaults, interface";
    leaf query-interval {
      xr:xr-xml-map "ipv4_igmp_common_cfg:QueryInterval";
      type uint32 {
        range "1..3600";
      }
      units "second";
      default "60";
      description "Query interval in seconds";
    }
  }

  grouping ROUTER-ENABLE {
    description "Common node of inheritable-defaults, interface";
    leaf router-enable {
      xr:xr-xml-map "ipv4_igmp_common_cfg:RouterEnable";
      type boolean;
      default "true";
      description
        "Enabled or disabled, when value is TRUE or FALSE
        respectively";
    }
  }

  grouping SSMDNS-QUERY-GROUP {
    description "Common node of vrf, default-context";
    leaf ssmdns-query-group {
      xr:xr-xml-map "ipv4_igmp_common_cfg:SSMDNSQueryGroup";
      type empty;
      description "Enable SSM mapping using DNS Query";
    }
  }

  grouping QUERY-TIMEOUT {
    description "Common node of inheritable-defaults, interface";
    leaf query-timeout {
      xr:xr-xml-map "ipv4_igmp_common_cfg:QueryTimeout";
      type uint32 {
        range "60..300";
      }
      units "second";
      description "IGMP previous querier timeout";
    }
  }

  grouping UNICAST-QOS-ADJUST {
    description "Common node of vrf, default-context";

    container unicast-qos-adjust {
      xr:xr-xml-map "ipv4_igmp_common_cfg:UnicastQoSAdjust";
      description
        "Configure IGMP QoS shapers for subscriber
        interfaces";
      leaf download-interval {
        xr:xr-xml-map "ipv4_igmp_common_cfg:DownloadInterval";
        type uint32 {
          range "10..500";
        }
        units "millisecond";
        default "100";
        description
          "Configure the QoS download interval (in
          milliseconds)";
      }
      leaf adjustment-delay {
        xr:xr-xml-map "ipv4_igmp_common_cfg:AdjustmentDelay";
        type uint32 {
          range "0..10";
        }
        units "second";
        default "1";
        description
          "Configure the QoS delay before programming (in
          seconds)";
      }
      leaf hold-off {
        xr:xr-xml-map "ipv4_igmp_common_cfg:HoldOff";
        type uint32 {
          range "5..1800";
        }
        units "second";
        default "180";
        description "Configure the QoS hold off time (in seconds)";
      }
    }
  }

  grouping EXPLICIT-TRACKING {
    description "Common node of inheritable-defaults, interface";

    container explicit-tracking {
      xr:xr-xml-map "ipv4_igmp_common_cfg:ExplicitTracking";
      presence "Indicates a explicit-tracking node is configured.";
      description "IGMPv3 explicit host tracking";
      leaf enable {
        xr:xr-xml-map "ipv4_igmp_common_cfg:Enable";
        type boolean;
        mandatory true;
        description
          "Enabled or disabled, when value is TRUE or
          FALSE respectively";
      }
      leaf access-list-name {
        xr:xr-xml-map "ipv4_igmp_common_cfg:AccessListName";
        type string;
        description "Access list specifying tracking group range";
      }
    }
  }

  container igmp {
    xr:xr-xml-map "ipv4_igmp_cfg:IGMP";
    presence "Indicates a igmp node is configured.";
    description "IGMPconfiguration";

    container vrfs {
      xr:xr-xml-map "ipv4_igmp_cfg:VRFTable";
      description "VRF related configuration";

      list vrf {
        xr:xr-xml-map "ipv4_igmp_cfg:VRF";
        key "vrf-name";
        description "Configuration for a particular vrf";
        leaf vrf-name {
          xr:xr-xml-map "ipv4_igmp_cfg:VRFName";
          type xr:Cisco-ios-xr-string;
          description "Name for this vrf";
        }
        uses TRAFFIC;
        uses INHERITABLE-DEFAULTS;
        uses SSM-ACCESS-GROUP-TABLE;
        uses MAXIMUM;
        uses SSMDNS-QUERY-GROUP;
        uses UNICAST-QOS-ADJUST;
        uses ACCOUNTING;
        uses INTERFACE-TABLE;
        uses ROBUSTNESS;
      }
    }
    uses DEFAULT-CONTEXT;
  }

  container amt {
    xr:xr-xml-map "ipv4_igmp_common_cfg:AMT";
    description "amt";

    container relay-adv-add {
      xr:xr-xml-map "ipv4_igmp_common_cfg:RelayAdvAdd";
      presence "Indicates a relay-adv-add node is configured.";
      description "Configure AMT Relay IPv4 Advertisement Address";
      leaf address {
        xr:xr-xml-map "ipv4_igmp_common_cfg:Address";
        type inet:ipv4-address-no-zone;
        mandatory true;
        description "AMT Relay IPv4 Advertisement Address";
      }
      leaf interface {
        xr:xr-xml-map "ipv4_igmp_common_cfg:Interface";
        type xr:Interface-name;
        description "Relay Advertisement Interface";
      }
    }

    container relay-anycast-prefix {
      xr:xr-xml-map "ipv4_igmp_common_cfg:RelayAnycastPrefix";
      presence "Indicates a relay-anycast-prefix node is"+
        " configured.";
      description "Configure AMT Relay IPv4 Anycast-Prefix";
      leaf address {
        xr:xr-xml-map "ipv4_igmp_common_cfg:Address";
        type inet:ipv4-address-no-zone;
        mandatory true;
        description "Anycast-Prefix Address";
      }
      leaf prefix-length {
        xr:xr-xml-map "ipv4_igmp_common_cfg:PrefixLength";
        type uint32 {
          range "1..32";
        }
        description "Mask Length for Anycast Prefix";
      }
    }
    leaf maximum-v4-route-gateway {
      xr:xr-xml-map "ipv4_igmp_common_cfg:MaximumV4RouteGateway";
      xr:xr-cli-map "amt relay ipv4 maximum route-gateway ipv4 <num"+
        "ber> ";
      type uint32 {
        range "1..4294967295";
      }
      description
        "Configure Maximum number of IPv4 route-gateways
        (Tunnels)";
    }
    leaf gateway-filter {
      xr:xr-xml-map "ipv4_igmp_common_cfg:GatewayFilter";
      xr:xr-cli-map "amt relay ipv4 gateway-filter <string> ";
      type string;
      description "Access list for Gateway Filter";
    }
    leaf maximum-v4-routes {
      xr:xr-xml-map "ipv4_igmp_common_cfg:MaximumV4Routes";
      type uint32 {
        range "1..4294967295";
      }
      description "Configure Maximum number of IPv4 Routes";
    }
    leaf amttos {
      xr:xr-xml-map "ipv4_igmp_common_cfg:AMTTOS";
      xr:xr-cli-map "amt relay ipv4 tos <number> ";
      type uint32 {
        range "1..255";
      }
      description "Configure AMT Relay TOS";
    }
    leaf amtttl {
      xr:xr-xml-map "ipv4_igmp_common_cfg:AMTTTL";
      xr:xr-cli-map "amt relay ipv4 ttl <number> ";
      type uint32 {
        range "1..255";
      }
      description "Configure AMT Relay TTL";
    }
    leaf maximum-v6-route-gateway {
      xr:xr-xml-map "ipv4_igmp_common_cfg:MaximumV6RouteGateway";
      xr:xr-cli-map "amt relay ipv4 maximum route-gateway ipv6 <num"+
        "ber> ";
      type uint32 {
        range "1..4294967295";
      }
      description
        "Configure Maximum number of IPv6 route-gateways
        (Tunnels)";
    }
    leaf maximum-gateway {
      xr:xr-xml-map "ipv4_igmp_common_cfg:MaximumGateway";
      xr:xr-cli-map "amt relay ipv4 maximum gateway <number> ";
      type uint32 {
        range "1..4294967295";
      }
      description "Configure AMT maximum number of Gateways";
    }
    leaf maximum-v6-routes {
      xr:xr-xml-map "ipv4_igmp_common_cfg:MaximumV6Routes";
      type uint32 {
        range "1..4294967295";
      }
      description "Configure Maximum number of IPv6 Routes";
    }
    leaf amtqqic {
      xr:xr-xml-map "ipv4_igmp_common_cfg:AMTQQIC";
      xr:xr-cli-map "amt relay ipv4 qqic <number> ";
      type uint32 {
        range "1..4294967295";
      }
      description "Configure AMT QQIC value";
    }
    leaf amtmtu {
      xr:xr-xml-map "ipv4_igmp_common_cfg:AMTMTU";
      xr:xr-cli-map "amt relay ipv4 mtu <number> ";
      type uint32 {
        range "100..65535";
      }
      description "Configure AMT Relay MTU";
    }
  }

  container mld {
    xr:xr-xml-map "ipv6_mld_cfg:MLD";
    presence "Indicates a mld node is configured.";
    description "mld";
    uses DEFAULT-CONTEXT;
  }
}
