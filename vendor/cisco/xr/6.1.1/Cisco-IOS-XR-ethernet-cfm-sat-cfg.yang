module Cisco-IOS-XR-ethernet-cfm-sat-cfg {

  /*** NAMESPACE / PREFIX DEFINITION ***/

  namespace "http://cisco.com/ns/yang"+
    "/Cisco-IOS-XR-ethernet-cfm-sat-cfg";


  prefix "ethernet-cfm-sat-cfg";

  /*** LINKAGE (IMPORTS / INCLUDES) ***/

  import Cisco-IOS-XR-types { prefix "xr"; }

  import Cisco-IOS-XR-ethernet-cfm-datatypes { prefix "dt1"; }

  import Cisco-IOS-XR-ifmgr-cfg { prefix "a1"; }

  import Cisco-IOS-XR-l2-eth-infra-cfg { prefix "a2"; }

  import Cisco-IOS-XR-icpe-infra-cfg { prefix "a3"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ethernet-cfm-sat package configuration.

     This YANG module augments the
       Cisco-IOS-XR-ifmgr-cfg,
       Cisco-IOS-XR-l2-eth-infra-cfg,
       Cisco-IOS-XR-icpe-infra-cfg
     modules with configuration data.

     Copyright (c) 2013-2016 by Cisco Systems, Inc.
     All rights reserved.";

  revision "2015-11-09" {
    description
      "IOS XR 6.0 revision.";
  }


  augment "/a1:interface-configurations/a1:interface-configuration"+
    "/a3:nv-satellite-fabric-link" {

    container ethernet-features {
      xr:xr-xml-map "cfm_cfg_sat:EthernetFeatures";
      description "Ethernet Satellite configuration";

      container cfm {
        xr:xr-xml-map "cfm_cfg_sat:CFM";
        description "CFM Satellite configuration";
        leaf continuity-check-interval {
          xr:xr-xml-map "cfm_cfg_sat:ContinuityCheckInterval";
          type dt1:Cfm-ccm-interval;
          description "Continuity-Check Interval";
        }
        leaf level {
          xr:xr-xml-map "cfm_cfg_sat:Level";
          type dt1:Cfm-level;
          description "Maintenance Domain Level";
        }
        leaf enable {
          xr:xr-xml-map "cfm_cfg_sat:Enable";
          type empty;
          description "Enable CFM on Satellite";
        }
      }
    }
    description
      "This augment extends the configuration data of
      'Cisco-IOS-XR-icpe-infra-cfg'";
  }
}
