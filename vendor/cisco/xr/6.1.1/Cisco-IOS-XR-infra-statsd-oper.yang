module Cisco-IOS-XR-infra-statsd-oper {

  /*** NAMESPACE / PREFIX DEFINITION ***/

  namespace "http://cisco.com/ns"+
    "/yang/Cisco-IOS-XR-infra-statsd-oper";


  prefix "infra-statsd-oper";

  /*** LINKAGE (IMPORTS / INCLUDES) ***/

  import Cisco-IOS-XR-types { prefix "xr"; }

  include Cisco-IOS-XR-infra-statsd-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR infra-statsd package operational data.

     This module contains definitions
     for the following management objects:
       infra-statistics: Statistics Infrastructure

     Copyright (c) 2013-2016 by Cisco Systems, Inc.
     All rights reserved.";

  revision "2015-11-09" {
    description
      "IOS XR 6.0 revision.";
  }


  grouping DATA-RATE {
    description "Common node of latest, cache, total, interface";

    container data-rate {
      xr:xr-xml-map "infra_statsd_oper:DataRate";
      description "Datarate information";
      uses STATSDBAG-DATARATE;
    }
  }

  grouping PROTOCOL-TABLE {
    description "Common node of latest, cache, total, interface";

    container protocols {
      xr:xr-xml-map "infra_statsd_oper:ProtocolTable";
      description "List of protocols";

      list protocol {
        xr:xr-xml-map "infra_statsd_oper:Protocol";
        key "protocol-name";
        description "Interface counters per protocol";
        leaf protocol-name {
          xr:xr-xml-map "infra_statsd_oper:ProtocolName";
          type xr:Cisco-ios-xr-string;
          description "Name of the protocol";
        }
        uses IFSTATSBAG-PROTO;
      }
    }
  }

  grouping INTERFACES-MIB-COUNTERS {
    description "Common node of latest, cache, total, interface";

    container interfaces-mib-counters {
      xr:xr-xml-map "infra_statsd_oper:InterfacesMIBCounters";
      description
        "Set of interface counters as displayed by the
        InterfacesMIB";
      uses IFSTATSBAG-GENERIC;
    }
  }

  grouping GENERIC-COUNTERS {
    description "Common node of latest, cache, total, interface";

    container generic-counters {
      xr:xr-xml-map "infra_statsd_oper:GenericCounters";
      description "Generic set of interface counters";
      uses IFSTATSBAG-GENERIC;
    }
  }

  container infra-statistics {
    xr:xr-xml-map "infra_statsd_oper:InfraStatistics";
    config false;
    description "Statistics Infrastructure";

    container interfaces {
      xr:xr-xml-map "infra_statsd_oper:InterfaceTable";
      description "List of interfaces";

      list interface {
        xr:xr-xml-map "infra_statsd_oper:Interface";
        key "interface-name";
        description "Statistics of an interface";

        container cache {
          xr:xr-xml-map "infra_statsd_oper:Cache";
          description "Cached stats data of interfaces";
          uses PROTOCOL-TABLE;
          uses INTERFACES-MIB-COUNTERS;
          uses DATA-RATE;
          uses GENERIC-COUNTERS;
        }

        container latest {
          xr:xr-xml-map "infra_statsd_oper:Latest";
          description "Latest stats data of interfaces";
          uses PROTOCOL-TABLE;
          uses INTERFACES-MIB-COUNTERS;
          uses DATA-RATE;
          uses GENERIC-COUNTERS;
        }

        container total {
          xr:xr-xml-map "infra_statsd_oper:Total";
          description "Total stats data of interfaces";
          uses PROTOCOL-TABLE;
          uses INTERFACES-MIB-COUNTERS;
          uses DATA-RATE;
          uses GENERIC-COUNTERS;
        }
        leaf interface-name {
          xr:xr-xml-map "infra_statsd_oper:InterfaceName";
          type xr:Interface-name;
          description "Name of the interface";
        }
        uses PROTOCOL-TABLE;
        uses INTERFACES-MIB-COUNTERS;
        uses DATA-RATE;
        uses GENERIC-COUNTERS;
      }
    }
  }
}
