submodule Cisco-IOS-XR-es-acl-oper-sub1 {

  belongs-to Cisco-IOS-XR-es-acl-oper {
    prefix Cisco-IOS-XR-es-acl-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR es-acl package operational data.

     Copyright (c) 2013-2016 by Cisco Systems, Inc.
     All rights reserved.";

  revision "2015-11-09" {
    description
      "IOS XR 6.0 revision.";
  }

  typedef Acl-action {
    type enumeration {
      enum deny {
        value 0;
        description "Deny";
      }
      enum permit {
        value 1;
        description "Permit";
      }
      enum encrypt {
        value 2;
        description "Encrypt";
      }
      enum bypass {
        value 3;
        description "Bypass";
      }
      enum fallthrough {
        value 4;
        description "Fallthrough";
      }
      enum invalid {
        value 5;
        description "Invalid";
      }
    }
    description "Acl action";
  }
  typedef Acl-ace1 {
    type enumeration {
      enum normal {
        description "This is Normal ACE";
      }
      enum remark {
        description "This is Remark ACE";
      }
      enum abf {
        description "This is ABF ACE";
      }
    }
    description "ACE Types";
  }
  typedef Acl-ace {
    type Acl-ace1;
    description "ACE Types";
  }

  grouping ES-ACL-EDM-ACE {
    description "ACLE bag";
    leaf ace-type {
      xr:xr-xml-map "es_acl_edm:ACEType";
      type Acl-ace;
      description "ACE type (acl, remark)";
    }
    leaf ace-sequence-number {
      xr:xr-xml-map "es_acl_edm:ACESequenceNumber";
      type uint32;
      description "ACE sequence number";
    }
    leaf hits {
      xr:xr-xml-map "es_acl_edm:Hits";
      type uint64;
      description "ACE hit number";
    }
    leaf grant {
      xr:xr-xml-map "es_acl_edm:Grant";
      type Acl-action;
      description "Grant value permit/deny ";
    }
    leaf source-address {
      xr:xr-xml-map "es_acl_edm:SourceAddress";
      type xr:Osi-system-id;
      description "Source MAC address";
    }
    leaf source-wild-card-bits {
      xr:xr-xml-map "es_acl_edm:SourceWildCardBits";
      type xr:Osi-system-id;
      description "Source wild card bits";
    }
    leaf destination-address {
      xr:xr-xml-map "es_acl_edm:DestinationAddress";
      type xr:Osi-system-id;
      description "Destination MAC address";
    }
    leaf destination-wild-card-bits {
      xr:xr-xml-map "es_acl_edm:DestinationWildCardBits";
      type xr:Osi-system-id;
      description "Destination wild card bits";
    }
    leaf ether-type-number {
      xr:xr-xml-map "es_acl_edm:EtherTypeNumber";
      type uint16;
      description "Ethernet type Number";
    }
    leaf vlan1 {
      xr:xr-xml-map "es_acl_edm:VLAN1";
      type uint16;
      description "VLAN ID/range lower limit";
    }
    leaf vlan2 {
      xr:xr-xml-map "es_acl_edm:VLAN2";
      type uint16;
      description "VLAN ID range higher limit";
    }
    leaf cos {
      xr:xr-xml-map "es_acl_edm:COS";
      type uint8;
      description "COS value";
    }
    leaf dei {
      xr:xr-xml-map "es_acl_edm:DEI";
      type uint8;
      description "DEI bit";
    }
    leaf inner-header-vlan1 {
      xr:xr-xml-map "es_acl_edm:InnerHeaderVLAN1";
      type uint16;
      description "Inner header VLAN ID/range lower limit";
    }
    leaf inner-header-vlan2 {
      xr:xr-xml-map "es_acl_edm:InnerHeaderVLAN2";
      type uint16;
      description "Inner header VLAN ID range higher limit";
    }
    leaf inner-header-cos {
      xr:xr-xml-map "es_acl_edm:InnerHeaderCOS";
      type uint8;
      description "Inner header COS value";
    }
    leaf inner-header-dei {
      xr:xr-xml-map "es_acl_edm:InnerHeaderDEI";
      type uint8;
      description "Inner header DEI bit";
    }
    leaf capture {
      xr:xr-xml-map "es_acl_edm:Capture";
      type boolean;
      description "Capture option, TRUE if enabled";
    }
    leaf log-option {
      xr:xr-xml-map "es_acl_edm:LogOption";
      type uint8;
      description "Log option";
    }
    leaf remark {
      xr:xr-xml-map "es_acl_edm:Remark";
      type string;
      description "Remark string";
    }
    leaf acl-name {
      xr:xr-xml-map "es_acl_edm:ACLName";
      type string;
      description "Acl Name";
    }
    leaf sequence-string {
      xr:xr-xml-map "es_acl_edm:SequenceString";
      type string;
      description "Sequence Sring";
    }
  }

  grouping ES-ACL-EDM-OOR-DETAIL {
    description "Oor deatil config BAG";
    leaf current-configured-ac-ls {
      xr:xr-xml-map "es_acl_edm:CurrentConfiguredACLs";
      type uint32;
      description "Current configured acls";
    }
    leaf current-configured-ac-es {
      xr:xr-xml-map "es_acl_edm:CurrentConfiguredACEs";
      type uint32;
      description "Current configured aces";
    }
    leaf maximum-configurable-ac-ls {
      xr:xr-xml-map "es_acl_edm:MaximumConfigurableACLs";
      type uint32;
      description "max configurable acls";
    }
    leaf maximum-configurable-ac-es {
      xr:xr-xml-map "es_acl_edm:MaximumConfigurableACEs";
      type uint32;
      description "max configurable aces";
    }
  }
}
