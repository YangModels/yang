submodule Cisco-IOS-XR-iedge4710-oper-sub2 {

  belongs-to Cisco-IOS-XR-iedge4710-oper {
    prefix Cisco-IOS-XR-iedge4710-oper;
  }

  /*** LINKAGE (IMPORTS / INCLUDES) ***/

  import ietf-inet-types { prefix "inet"; }

  import ietf-yang-types { prefix "yang"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR iedge4710 package operational data.

     Copyright (c) 2013-2016 by Cisco Systems, Inc.
     All rights reserved.";

  revision "2015-11-09" {
    description
      "IOS XR 6.0 revision.";
  }

  typedef Iedge-oper-session-af-state {
    type enumeration {
      enum not-started {
        description "Not started";
      }
      enum down {
        description "Down";
      }
      enum up-pending {
        description "Up Pending";
      }
      enum up {
        description "Up";
      }
    }
    description "Subscriber session address family state";
  }
  typedef Aaa-terminate-cause {
    type enumeration {
      enum none {
        description "None";
      }
      enum user-request {
        description "User request";
      }
      enum lost-carrier {
        description "Lost carrier";
      }
      enum lost-service {
        description "Lost service";
      }
      enum idle-timeout {
        description "Idle timeout";
      }
      enum session-timeout {
        description "Session timeout";
      }
      enum admin-reset {
        description "Admin reset";
      }
      enum admin-reboot {
        description "Admin reboot";
      }
      enum port-error {
        description "Port error";
      }
      enum nas-error {
        description "NAS error";
      }
      enum nas-request {
        description "NAS request";
      }
      enum nas-reboot {
        description "NAS reboot";
      }
      enum port-unneeded {
        description "Port unneeded";
      }
      enum port-preempted {
        description "Port preempted";
      }
      enum port-suspended {
        description "Port suspended";
      }
      enum service-unavailable {
        description "Service unavailable";
      }
      enum callback {
        description "Callback";
      }
      enum user-error {
        description "User error";
      }
      enum host-request {
        description "Host request";
      }
      enum supplicant-restart {
        description "Supplicant restart";
      }
      enum reauthorization-failure {
        description "Reauthorization failure";
      }
      enum port-reinitialized {
        description "Port reinitialized";
      }
      enum admin-disabled {
        description "Admin disabled";
      }
    }
    description "AAA terminate cause types";
  }
  typedef Aaa-interface {
    type enumeration {
      enum none {
        description "None";
      }
      enum primary-rate {
        description "Primary rate";
      }
      enum basic-rate {
        description "Basic rate";
      }
      enum serial {
        description "Serial";
      }
      enum asynchronous {
        description "Asynchronous";
      }
      enum vty {
        description "VTY";
      }
      enum atm {
        description "ATM";
      }
      enum ethernet {
        description "Ethernet";
      }
      enum ppp-over-atm {
        description "PPP over ATM";
      }
      enum pppoe-over-atm {
        description "PPPoE over ATM";
      }
      enum pppoe-over-ethernet {
        description "PPPoE over ethernet";
      }
      enum ppp-over-vlan {
        description "PPP over VLAN";
      }
      enum ppp-over-qinq {
        description "PPP over Q in Q";
      }
      enum v120 {
        description "V120";
      }
      enum v110 {
        description "V110";
      }
      enum piafs {
        description "PHS internet access forum standard";
      }
      enum x75 {
        description "X75";
      }
      enum ip-sec {
        description "IP sec";
      }
      enum other {
        description "Other";
      }
      enum virtual-pppoe-over-ethernet {
        description "Virtual PPPoE over ethernet";
      }
      enum virtual-pppoe-over-vlan {
        description "Virtual PPPoE over VLAN";
      }
      enum virtual-pppoe-over-qinq {
        description "Virtual PPPoE over Q in Q";
      }
      enum ipo-e-over-ethernet {
        description "IPoE over ethernet";
      }
      enum ipo-e-over-vlan {
        description "IPoE over VLAN";
      }
      enum ipo-e-over-qinq {
        description "IPoE over Q in Q";
      }
      enum virtual-i-po-e-over-ethernet {
        description "Virtual IPoE over ethernet";
      }
      enum virtual-i-po-e-over-vlan {
        description "Virtual IPoE over VLAN";
      }
      enum virtual-i-po-e-over-qinq {
        description "Virtual IPoE over Q in Q";
      }
    }
    description "AAA interface types";
  }
  typedef Aaa-tunnel-proto {
    type enumeration {
      enum none {
        description "None";
      }
      enum pptp {
        description "Point-to-point tunneling protocol";
      }
      enum l2f {
        description "Layer 2 forwarding";
      }
      enum l2tp {
        description "Layer 2 tunneling protocol";
      }
      enum atmp {
        description "Ascend tunnel management protocol";
      }
      enum vtp {
        description "VLAN trunk protocol";
      }
      enum ah {
        description "Authentication header";
      }
      enum ip-over-ip {
        description "IP over IP";
      }
      enum minimum-ip-over-ip {
        description "Minimum IP over IP";
      }
      enum esp {
        description "Encapsulating security payload";
      }
      enum gre {
        description "Generic routing encapsulation";
      }
      enum bay-dvs {
        description "Bay dial virtual services";
      }
      enum ip-in-ip {
        description "IP in IP";
      }
      enum vlan {
        description "VLAN";
      }
    }
    description "Tunnel protocol types";
  }
  typedef Aaa-tunnel-medium {
    type enumeration {
      enum none {
        description "None";
      }
      enum ipv4 {
        description "IPv4";
      }
      enum ipv6 {
        description "IPv6";
      }
      enum nsap {
        description "NSAP";
      }
      enum hdlc {
        description "HDLC";
      }
      enum bbn {
        description "BBN";
      }
      enum all802 {
        description "ALL 802";
      }
    }
    description "Tunnel medium types";
  }
  typedef Aaa-auth-service {
    type enumeration {
      enum none {
        description "None";
      }
      enum login {
        description "Login";
      }
      enum framed {
        description "Framed";
      }
      enum callback-login {
        description "Callback login";
      }
      enum callback-framed {
        description "Callback framed";
      }
      enum outbound {
        description "Outbound";
      }
      enum administrator {
        description "Administrator";
      }
      enum prompt {
        description "Prompt";
      }
      enum authentication-only {
        description "Authentication only";
      }
      enum callback-nas-prompt {
        description "Callback NAS prompt";
      }
      enum call-check {
        description "Call check";
      }
      enum callback-administrator {
        description "Callback administrator";
      }
      enum voice {
        description "Voice";
      }
      enum fax {
        description "Fax";
      }
      enum modem-relay {
        description "Modem relay";
      }
      enum eap-over-udp {
        description "EAP over UDP";
      }
    }
    description "AAA authorization service types";
  }
  typedef Iedge-oper-session-state {
    type enumeration {
      enum initialize {
        description "Initialize";
      }
      enum connecting {
        description "Connecting";
      }
      enum connected {
        description "Connected";
      }
      enum activated {
        description "Activated";
      }
      enum idle {
        description "Idle";
      }
      enum disconnecting {
        description "Disconnecting";
      }
      enum end {
        description "End";
      }
    }
    description "Subscriber session states";
  }
  typedef Mac-address {
    type yang:mac-address;
    description "MAC address type";
  }
  typedef Hex-binary {
    type yang:hex-string;
    description "Hex binary data";
  }
  typedef Ipv4-address {
    type inet:ipv4-address;
    description "IP address type";
  }
  typedef Iedge-ppp-sub {
    type enumeration {
      enum pta {
        description "PPP termination and aggregation";
      }
      enum lac {
        description "L2TP access controller";
      }
    }
    description "PPPoE sub types";
  }
  typedef Iedge-oper-session {
    type enumeration {
      enum unknown {
        description "Unknown";
      }
      enum pppoe {
        description "PPPoE/PPP client";
      }
      enum ppp {
        description "PPP serial client";
      }
      enum ip-packet-trigger {
        description "IP subscriber - packet trigger";
      }
      enum ip-packet-dhcp-trigger {
        description "IP subscriber - DHCP trigger";
      }
    }
    description "Subscriber session types";
  }

  grouping IEDGE-MOBILITY-SESSION-DATA {
    description "Mobility attributes";
    leaf mpc-protocol {
      xr:xr-xml-map "iedge_ui_data:MPCProtocol";
      type boolean;
      description "Cisco MPC Protocol";
    }
    leaf mobility-ipv4-address {
      xr:xr-xml-map "iedge_ui_data:MobilityIPv4Address";
      type string;
      description "IPv4 address of Mobility Node";
    }
    leaf mobility-default-ipv4-gateway {
      xr:xr-xml-map "iedge_ui_data:MobilityDefaultIPv4Gateway";
      type string;
      description "Default Gateway IPv4 Address";
    }
    leaf mobility-dns-server {
      xr:xr-xml-map "iedge_ui_data:MobilityDNSServer";
      type string;
      description "DNS Server Primary";
    }
    leaf mobility-dhcp-server {
      xr:xr-xml-map "iedge_ui_data:MobilityDHCPServer";
      type string;
      description "DHCP Server";
    }
    leaf mobility-ipv4-netmask {
      xr:xr-xml-map "iedge_ui_data:MobilityIPv4Netmask";
      type string;
      description "IPv4 Netmask";
    }
    leaf domain-name {
      xr:xr-xml-map "iedge_ui_data:DomainName";
      type string;
      description "Domain Name";
    }
    leaf uplink-gre-key {
      xr:xr-xml-map "iedge_ui_data:UplinkGREKey";
      type string;
      description "Uplink GRE Key";
    }
    leaf downlink-gre-key {
      xr:xr-xml-map "iedge_ui_data:DownlinkGREKey";
      type string;
      description "Downlink GRE Key";
    }
    leaf lease-time {
      xr:xr-xml-map "iedge_ui_data:LeaseTime";
      type string;
      units "second";
      description "Duration of lease in seconds";
    }
  }

  grouping IEDGE-AAA-ATTR {
    description "AAA attributes";
    leaf ipv4mtu {
      xr:xr-xml-map "iedge_ui_data:IPv4MTU";
      type uint32;
      description "IPv4 maximum transmission unit";
    }
    leaf ipv4-unnumbered {
      xr:xr-xml-map "iedge_ui_data:IPv4Unnumbered";
      type string;
      description "IPv4 unnumbered";
    }
    leaf authorization-service-type {
      xr:xr-xml-map "iedge_ui_data:AuthorizationServiceType";
      type Aaa-auth-service;
      description "Authorization service type";
    }
    leaf tunnel-client-endpoint {
      xr:xr-xml-map "iedge_ui_data:TunnelClientEndpoint";
      type Ipv4-address;
      description "Tunnel client endpoint";
    }
    leaf tunnel-server-endpoint {
      xr:xr-xml-map "iedge_ui_data:TunnelServerEndpoint";
      type Ipv4-address;
      description "Tunnel server endpoint";
    }
    leaf tunnel-tos-setting {
      xr:xr-xml-map "iedge_ui_data:TunnelTOSSetting";
      type uint32;
      description "Tunnel TOS setting";
    }
    leaf tunnel-medium {
      xr:xr-xml-map "iedge_ui_data:TunnelMedium";
      type Aaa-tunnel-medium;
      description "Tunnel medium";
    }
    leaf tunnel-preference {
      xr:xr-xml-map "iedge_ui_data:TunnelPreference";
      type uint32;
      description "Tunnel preference";
    }
    leaf tunnel-client-authentication-id {
      xr:xr-xml-map "iedge_ui_data:TunnelClientAuthenticationID";
      type string;
      description "Tunnel client authentication ID";
    }
    leaf tunnel-protocol {
      xr:xr-xml-map "iedge_ui_data:TunnelProtocol";
      type Aaa-tunnel-proto;
      description "Tunnel protocol";
    }
    leaf actual-data-rate-upstream {
      xr:xr-xml-map "iedge_ui_data:ActualDataRateUpstream";
      type uint32;
      units "Mbit/s";
      description "Actual data rate upstream (in Mbps)";
    }
    leaf actual-data-rate-downstream {
      xr:xr-xml-map "iedge_ui_data:ActualDataRateDownstream";
      type uint32;
      units "Mbit/s";
      description "Actual data rate downstream (in Mbps)";
    }
    leaf attainable-data-rate-upstream {
      xr:xr-xml-map "iedge_ui_data:AttainableDataRateUpstream";
      type uint32;
      units "Mbit/s";
      description "Attainable data rate upstream (in Mbps)";
    }
    leaf attainable-data-rate-downstream {
      xr:xr-xml-map "iedge_ui_data:AttainableDataRateDownstream";
      type uint32;
      units "Mbit/s";
      description "Attainable data rate downstream (in Mbps)";
    }
    leaf pool-address {
      xr:xr-xml-map "iedge_ui_data:PoolAddress";
      type string;
      description "IP address pool";
    }
    leaf circuit-id {
      xr:xr-xml-map "iedge_ui_data:CircuitID";
      type string;
      description "Circuit ID";
    }
    leaf connection-receive-speed {
      xr:xr-xml-map "iedge_ui_data:ConnectionReceiveSpeed";
      type uint32;
      description "Connection receive speed";
    }
    leaf connection-transmission-speed {
      xr:xr-xml-map "iedge_ui_data:ConnectionTransmissionSpeed";
      type uint32;
      description "Connection transmission speed";
    }
    leaf destination-station-id {
      xr:xr-xml-map "iedge_ui_data:DestinationStationID";
      type string;
      description "Destination station ID";
    }
    leaf primary-dns-server-address {
      xr:xr-xml-map "iedge_ui_data:PrimaryDNSServerAddress";
      type Ipv4-address;
      description "Primary DNS server address";
    }
    leaf secondary-dns-server-address {
      xr:xr-xml-map "iedge_ui_data:SecondaryDNSServerAddress";
      type Ipv4-address;
      description "Secondary DNS server address";
    }
    leaf formatted-calling-station-id {
      xr:xr-xml-map "iedge_ui_data:FormattedCallingStationID";
      type string;
      description "Formatted calling station id";
    }
    leaf interface-name {
      xr:xr-xml-map "iedge_ui_data:InterfaceName";
      type string;
      description "Interface name";
    }
    leaf interface-type {
      xr:xr-xml-map "iedge_ui_data:InterfaceType";
      type Aaa-interface;
      description "Interface type";
    }
    leaf interim-accounting-interval {
      xr:xr-xml-map "iedge_ui_data:InterimAccountingInterval";
      type uint32;
      description "Interim accounting interval";
    }
    leaf ingress-access-list {
      xr:xr-xml-map "iedge_ui_data:IngressAccessList";
      type string;
      description "Ingress access list";
    }
    leaf egress-access-list {
      xr:xr-xml-map "iedge_ui_data:EgressAccessList";
      type string;
      description "Egress access list";
    }
    leaf ip-netmask {
      xr:xr-xml-map "iedge_ui_data:IPNetmask";
      type Ipv4-address;
      description "IP netmask for the user";
    }
    leaf is-interworking-functionality {
      xr:xr-xml-map "iedge_ui_data:IsInterworkingFunctionality";
      type boolean;
      description "True, if interworking functionality";
    }
    leaf max-interleaving-delay-downstream {
      xr:xr-xml-map "iedge_ui_data:MaxInterleavingDelayDownstream";
      type uint32;
      units "Mbit/s";
      description "Maximum interleaving delay downstream (in Mbps)";
    }
    leaf max-interleaving-delay-upstream {
      xr:xr-xml-map "iedge_ui_data:MaxInterleavingDelayUpstream";
      type uint32;
      units "Mbit/s";
      description "Maximum interleaving delay upstream (in Mbps)";
    }
    leaf max-data-rate-upstream {
      xr:xr-xml-map "iedge_ui_data:MaxDataRateUpstream";
      type uint32;
      units "Mbit/s";
      description "Maximum data rate upstream (in Mbps)";
    }
    leaf max-data-rate-downstream {
      xr:xr-xml-map "iedge_ui_data:MaxDataRateDownstream";
      type uint32;
      units "Mbit/s";
      description "Maximum data rate downstream (in Mbps)";
    }
    leaf min-data-rate-downstream {
      xr:xr-xml-map "iedge_ui_data:MinDataRateDownstream";
      type uint32;
      units "Mbit/s";
      description "Minimum data rate downstream (in Mbps)";
    }
    leaf min-data-rate-downstream-low-power {
      xr:xr-xml-map "iedge_ui_data:MinDataRateDownstreamLowPower";
      type uint32;
      units "Mbit/s";
      description
        "Minimum data rate downstream low power (in Mbps)";
    }
    leaf min-data-rate-upstream-low-power {
      xr:xr-xml-map "iedge_ui_data:MinDataRateUpstreamLowPower";
      type uint32;
      units "Mbit/s";
      description "Minimum data rate upstream low power (in Mbps)";
    }
    leaf primary-net-bios-server-address {
      xr:xr-xml-map "iedge_ui_data:PrimaryNetBiosServerAddress";
      type Ipv4-address;
      description "Primary net bios server address";
    }
    leaf secondary-net-bios-server-address {
      xr:xr-xml-map "iedge_ui_data:SecondaryNetBiosServerAddress";
      type Ipv4-address;
      description "Secondary net bios server address";
    }
    leaf parent-interface-name {
      xr:xr-xml-map "iedge_ui_data:ParentInterfaceName";
      type xr:Interface-name;
      description "Parent interface name";
    }
    leaf remote-id {
      xr:xr-xml-map "iedge_ui_data:RemoteID";
      type string;
      description "Remote ID";
    }
    leaf route {
      xr:xr-xml-map "iedge_ui_data:Route";
      type string;
      description "Route information for a user session";
    }
    leaf session-timeout {
      xr:xr-xml-map "iedge_ui_data:SessionTimeout";
      type uint32;
      units "second";
      description "Session timeout (in seconds)";
    }
    leaf strict-rpf-packets {
      xr:xr-xml-map "iedge_ui_data:StrictRPFPackets";
      type uint32;
      description "Strict RPF packets";
    }
    leaf accounting-session-id {
      xr:xr-xml-map "iedge_ui_data:AccountingSessionID";
      type string;
      description "Accounting session ID";
    }
    leaf upstream-parameterized-qos-policy {
      xr:xr-xml-map "iedge_ui_data:UpstreamParameterizedQoSPolicy";
      type string;
      description
        "Upstream parameterized QoS policy to be applied
        on the subscriber side";
    }
    leaf downstream-parameterized-qos-policy {
      xr:xr-xml-map "iedge_ui_data:DownstreamParameterizedQoSPolicy";
      type string;
      description
        "Downstream parameterized QoS policy to be
        applied on the subscriber side";
    }
    leaf upstream-qos-policy {
      xr:xr-xml-map "iedge_ui_data:UpstreamQoSPolicy";
      type string;
      description
        "Upstream QoS policy to be applied on the
        subscriber side";
    }
    leaf downstream-qos-policy {
      xr:xr-xml-map "iedge_ui_data:DownstreamQoSPolicy";
      type string;
      description
        "Downstream QoS policy to be applied on the
        subscriber side";
    }
    leaf session-termination-cause {
      xr:xr-xml-map "iedge_ui_data:SessionTerminationCause";
      type Aaa-terminate-cause;
      description "Session termination cause";
    }
  }

  grouping IEDGE-OPER-COA-DATA {
    description "IEDGE OPER COA DATA";
    leaf request-acked {
      xr:xr-xml-map "iedge_ui_data:RequestAcked";
      type boolean;
      description "Coa Request Acked";
    }
    leaf request-time {
      xr:xr-xml-map "iedge_ui_data:RequestTime";
      type string;
      description
        "Request time in DDD MMM DD HH:MM:SS YYYY format
        eg: Tue Apr 11 21:30:47 2011";
    }
    leaf coa-request-attributes {
      xr:xr-xml-map "iedge_ui_data:CoaRequestAttributes";
      type yang:hex-string;
      description
        "List of Request Attributes collected in COA
        response";
    }
    leaf reply-time {
      xr:xr-xml-map "iedge_ui_data:ReplyTime";
      type string;
      description
        "Reply time in DDD MMM DD HH:MM:SS YYYY format eg
        : Tue Apr 11 21:30:47 2011";
    }
    leaf coa-reply-attributes {
      xr:xr-xml-map "iedge_ui_data:CoaReplyAttributes";
      type yang:hex-string;
      description
        "List of Reply Attributes collected in COA
        response";
    }
  }

  grouping IEDGE-OPER-ACCOUNTING-DATA {
    description "Session/Service accounting information";
    leaf accounting-state-rc {
      xr:xr-xml-map "iedge_ui_data:accounting_state_rc";
      type uint32;
      description
        "Accounting State Error Code for Accounting
        Session";
    }
    leaf accounting-stop-state {
      xr:xr-xml-map "iedge_ui_data:accounting_stop_state";
      type uint32;
      description "Accounting Stop State";
    }
    leaf record-context-name {
      xr:xr-xml-map "iedge_ui_data:RecordContextName";
      type string;
      description "Accounting record context name";
    }
    leaf method-list-name {
      xr:xr-xml-map "iedge_ui_data:MethodListName";
      type string;
      description "AAA method list name used to perform accounting";
    }
    leaf account-session-id {
      xr:xr-xml-map "iedge_ui_data:AccountSessionID";
      type string;
      description "Accounting session ID";
    }
    leaf accounting-start-time {
      xr:xr-xml-map "iedge_ui_data:AccountingStartTime";
      type string;
      description
        "Accounting start time in DDD MMM DD HH:MM:SS
        YYYY format eg: Tue Feb 15 15:12:49 2011";
    }
    leaf is-interim-accounting-enabled {
      xr:xr-xml-map "iedge_ui_data:IsInterimAccountingEnabled";
      type boolean;
      description "True if interim accounting is enabled";
    }
    leaf interim-interval {
      xr:xr-xml-map "iedge_ui_data:InterimInterval";
      type uint32;
      units "minute";
      description "Interim accounting interval (in minutes)";
    }
    leaf last-successful-interim-update-time {
      xr:xr-xml-map "iedge_ui_data:LastSuccessfulInterimUpdateTime";
      type string;
      description
        "Time of last successful interim update in DDD
        MMM DD HH:MM:SS YYYY format eg: Tue Apr 11 21:30
        :47 2011";
    }
    leaf next-interim-update-attempt-time {
      xr:xr-xml-map "iedge_ui_data:NextInterimUpdateAttemptTime";
      type uint32;
      units "second";
      description
        "Time of next interim update attempt (in seconds)";
    }
    leaf last-interim-update-attempt-time {
      xr:xr-xml-map "iedge_ui_data:LastInterimUpdateAttemptTime";
      type string;
      description
        "Time of last interim update attempt in DDD MMM
        DD HH:MM:SS YYYY format eg: Tue Apr 11 21:30:47
        2011";
    }
    leaf sent-interim-updates {
      xr:xr-xml-map "iedge_ui_data:SentInterimUpdates";
      type uint32;
      description "Number of interim updates sent";
    }
    leaf accepted-interim-updates {
      xr:xr-xml-map "iedge_ui_data:AcceptedInterimUpdates";
      type uint32;
      description "Number of interim updates accepted";
    }
    leaf rejected-interim-updates {
      xr:xr-xml-map "iedge_ui_data:RejectedInterimUpdates";
      type uint32;
      description "Number of interim updates rejected";
    }
    leaf sent-interim-update-failures {
      xr:xr-xml-map "iedge_ui_data:SentInterimUpdateFailures";
      type uint32;
      description "Number of interim update send failures";
    }
  }

  grouping IEDGE-ACCNT-DATA {
    description "Accounting information";

    list accounting-session {
      description "Accounting information";
      uses IEDGE-OPER-ACCOUNTING-DATA;
    }
  }

  grouping SUBSCRIBER-SESSION-DATA {
    description "Subscriber session information";

    container accounting {
      description "Accounting information";
      uses IEDGE-ACCNT-DATA;
    }

    container user-profile-attributes {
      description
        "List of user profile attributes collected for
        subscriber session";
      uses IEDGE-AAA-ATTR;
    }

    container mobility-attributes {
      description
        "List of mobility attributes collected for
        subscriber session";
      uses IEDGE-MOBILITY-SESSION-DATA;
    }
    leaf session-type {
      xr:xr-xml-map "iedge_ui_data:SessionType";
      type Iedge-oper-session;
      description "Subscriber session type";
    }
    leaf pppoe-sub-type {
      xr:xr-xml-map "iedge_ui_data:PPPoESubType";
      type Iedge-ppp-sub;
      description "PPPoE sub type";
    }
    leaf interface-name {
      xr:xr-xml-map "iedge_ui_data:InterfaceName";
      type xr:Interface-name;
      description "Interface name";
    }
    leaf vrf-name {
      xr:xr-xml-map "iedge_ui_data:VRFName";
      type string;
      description "VRF name";
    }
    leaf circuit-id {
      xr:xr-xml-map "iedge_ui_data:CircuitID";
      type string;
      description "Circuit ID";
    }
    leaf remote-id {
      xr:xr-xml-map "iedge_ui_data:RemoteID";
      type string;
      description "Remote ID";
    }
    leaf lns-address {
      xr:xr-xml-map "iedge_ui_data:LNSAddress";
      type Ipv4-address;
      description "PPPoE LNS address";
    }
    leaf lac-address {
      xr:xr-xml-map "iedge_ui_data:LACAddress";
      type Ipv4-address;
      description "PPPoE LAC address";
    }
    leaf tunnel-client-authentication-id {
      xr:xr-xml-map "iedge_ui_data:TunnelClientAuthenticationID";
      type string;
      description "PPPoE LAC tunnel client authentication ID";
    }
    leaf tunnel-server-authentication-id {
      xr:xr-xml-map "iedge_ui_data:TunnelServerAuthenticationID";
      type string;
      description "PPPoE LAC tunnel server authentication ID";
    }
    leaf session-ip-address {
      xr:xr-xml-map "iedge_ui_data:SessionIPAddress";
      type Ipv4-address;
      description "Session ip address";
    }
    leaf session-ipv6-address {
      xr:xr-xml-map "iedge_ui_data:SessionIPv6Address";
      type string;
      description "Session IPv6 address";
    }
    leaf session-ipv6-prefix {
      xr:xr-xml-map "iedge_ui_data:SessionIPv6Prefix";
      type string;
      description "Session IPv6 prefix";
    }
    leaf delegated-ipv6-prefix {
      xr:xr-xml-map "iedge_ui_data:DelegatedIPv6Prefix";
      type string;
      description "Session delegated IPv6 prefix";
    }
    leaf ipv6-interface-id {
      xr:xr-xml-map "iedge_ui_data:IPv6InterfaceID";
      type Hex-binary;
      description "IPv6 Interface ID";
    }
    leaf mac-address {
      xr:xr-xml-map "iedge_ui_data:MACAddress";
      type Mac-address;
      description "MAC address";
    }
    leaf account-session-id {
      xr:xr-xml-map "iedge_ui_data:AccountSessionID";
      type string;
      description "Accounting session ID";
    }
    leaf nas-port {
      xr:xr-xml-map "iedge_ui_data:NASPort";
      type string;
      description "NAS port";
    }
    leaf username {
      xr:xr-xml-map "iedge_ui_data:Username";
      type string;
      description "Username";
    }
    leaf clientname {
      xr:xr-xml-map "iedge_ui_data:Clientname";
      type string;
      description "Client Username";
    }
    leaf formattedname {
      xr:xr-xml-map "iedge_ui_data:Formattedname";
      type string;
      description "Formatted Username";
    }
    leaf is-session-authentic {
      xr:xr-xml-map "iedge_ui_data:IsSessionAuthentic";
      type boolean;
      description "If true, session is authentic";
    }
    leaf is-session-author {
      xr:xr-xml-map "iedge_ui_data:IsSessionAuthor";
      type boolean;
      description "If true, session is authorized";
    }
    leaf session-state {
      xr:xr-xml-map "iedge_ui_data:SessionState";
      type Iedge-oper-session-state;
      description "Session state";
    }
    leaf session-creation-time {
      xr:xr-xml-map "iedge_ui_data:SessionCreationTime";
      type string;
      description
        "Session creation time in DDD MMM DD HH:MM:SS
        YYYY format eg: Tue Apr 11 21:30:47 2011";
    }
    leaf idle-state-change-time {
      xr:xr-xml-map "iedge_ui_data:IdleStateChangeTime";
      type string;
      description
        "Time when idle state change occurred in DDD MMM
        DD HH:MM:SS YYYY format eg: Tue Apr 11 21:30:47
        2011";
    }
    leaf total-session-idle-time {
      xr:xr-xml-map "iedge_ui_data:TotalSessionIdleTime";
      type uint32;
      units "second";
      description "Total session idle time (in seconds)";
    }
    leaf access-interface-name {
      xr:xr-xml-map "iedge_ui_data:AccessInterfaceName";
      type xr:Interface-name;
      description
        "Access interface name associated with the
        session";
    }
    leaf pending-callbacks {
      xr:xr-xml-map "iedge_ui_data:PendingCallbacks";
      type uint64;
      description "Active pending callbacks bitmask";
    }
    leaf af-up-status {
      xr:xr-xml-map "iedge_ui_data:af_up_status";
      type uint32;
      description "AF status per Subscriber Session";
    }
    leaf session-ipv4-state {
      xr:xr-xml-map "iedge_ui_data:SessionIPv4State";
      type Iedge-oper-session-af-state;
      description "Session IPv4 state";
    }
    leaf session-ipv6-state {
      xr:xr-xml-map "iedge_ui_data:SessionIPv6State";
      type Iedge-oper-session-af-state;
      description "Session IPv6 state";
    }

    list session-change-of-authorization {
      description "Subscriber change of authorization information";
      uses IEDGE-OPER-COA-DATA;
    }
  }

  grouping SUBSCRIBER-SESSION-AF-COUNTS {
    description "Subscriber address family session counts";
    leaf in-progress-sessions {
      xr:xr-xml-map "iedge_ui_data:InProgressSessions";
      type uint32;
      description "Sessions with undecided address family";
    }
    leaf ipv4-only-sessions {
      xr:xr-xml-map "iedge_ui_data:IPv4OnlySessions";
      type uint32;
      description "IPv4 only sessions ";
    }
    leaf ipv6-only-sessions {
      xr:xr-xml-map "iedge_ui_data:IPv6OnlySessions";
      type uint32;
      description "IPv6 only sessions ";
    }
    leaf dual-part-up-sessions {
      xr:xr-xml-map "iedge_ui_data:DualPartUpSessions";
      type uint32;
      description "Dual stack partially up sessions";
    }
    leaf dual-up-sessions {
      xr:xr-xml-map "iedge_ui_data:DualUpSessions";
      type uint32;
      description "Dual stack up sessions";
    }
    leaf lac-sessions {
      xr:xr-xml-map "iedge_ui_data:LACSessions";
      type uint32;
      description "LAC sessions";
    }
  }

  grouping SUBSCRIBER-SESSION-AF-SUMMARY {
    description
      "Subscriber session address family summary
      information";

    container pppoe {
      description "PPPoE summary";
      uses SUBSCRIBER-SESSION-AF-COUNTS;
    }

    container ip-subscriber-dhcp {
      description "IP subscriber DHCP summary";
      uses SUBSCRIBER-SESSION-AF-COUNTS;
    }

    container ip-subscriber-packet {
      description "IP subscriber packet summary";
      uses SUBSCRIBER-SESSION-AF-COUNTS;
    }
  }

  grouping SUBSCRIBER-SESSION-STATE-COUNTS {
    description "Subscriber state session counts";
    leaf initialized-sessions {
      xr:xr-xml-map "iedge_ui_data:InitializedSessions";
      type uint32;
      description "Sessions in initialized state";
    }
    leaf connecting-sessions {
      xr:xr-xml-map "iedge_ui_data:ConnectingSessions";
      type uint32;
      description "Sessions in connecting state";
    }
    leaf connected-sessions {
      xr:xr-xml-map "iedge_ui_data:ConnectedSessions";
      type uint32;
      description "Sessions in connected state";
    }
    leaf activated-sessions {
      xr:xr-xml-map "iedge_ui_data:ActivatedSessions";
      type uint32;
      description "Sessions in activated state";
    }
    leaf idle-sessions {
      xr:xr-xml-map "iedge_ui_data:IdleSessions";
      type uint32;
      description "Sessions in idle state";
    }
    leaf disconnecting-sessions {
      xr:xr-xml-map "iedge_ui_data:DisconnectingSessions";
      type uint32;
      description "Sessions in disconnecting state";
    }
    leaf end-sessions {
      xr:xr-xml-map "iedge_ui_data:EndSessions";
      type uint32;
      description "Sessions in end state";
    }
  }

  grouping SUBSCRIBER-SESSION-STATE-SUMMARY {
    description "Subscriber session state summary information";

    container pppoe {
      description "PPPoE summary";
      uses SUBSCRIBER-SESSION-STATE-COUNTS;
    }

    container ip-subscriber-dhcp {
      description "IP subscriber DHCP summary";
      uses SUBSCRIBER-SESSION-STATE-COUNTS;
    }

    container ip-subscriber-packet {
      description "IP subscriber packet summary";
      uses SUBSCRIBER-SESSION-STATE-COUNTS;
    }
  }

  grouping SUBSCRIBER-SESSION-SUMMARY {
    description "Subscriber session summary information";

    container state-xr {
      description "State summary";
      uses SUBSCRIBER-SESSION-STATE-SUMMARY;
    }

    container address-family-xr {
      description "Address family summary";
      uses SUBSCRIBER-SESSION-AF-SUMMARY;
    }
  }
}
