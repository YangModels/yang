submodule Cisco-IOS-XR-ipv4-arp-oper-sub1 {

  belongs-to Cisco-IOS-XR-ipv4-arp-oper {
    prefix Cisco-IOS-XR-ipv4-arp-oper;
  }

  /*** LINKAGE (IMPORTS / INCLUDES) ***/

  import ietf-inet-types { prefix "inet"; }

  import ietf-yang-types { prefix "yang"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR ipv4-arp package operational data.

     Copyright (c) 2013-2016 by Cisco Systems, Inc.
     All rights reserved.";

  revision "2015-11-09" {
    description
      "IOS XR 6.0 revision.";
  }

  typedef Ip-arp-bag-encap {
    type enumeration {
      enum none {
        value 0;
        description "No encapsulation";
      }
      enum arpa {
        value 1;
        description "ARPA";
      }
      enum snap {
        value 2;
        description "SNAP";
      }
      enum ieee802-1q {
        value 3;
        description "802 1Q";
      }
      enum srp {
        value 4;
        description "SRP";
      }
      enum srpa {
        value 5;
        description "SRPA";
      }
      enum srpb {
        value 6;
        description "SRPB";
      }
    }
    description "ARP encapsulation";
  }
  typedef Ip-arp-bag-state {
    type enumeration {
      enum state-none {
        value 0;
        description "No state";
      }
      enum state-interface {
        value 1;
        description "Interface";
      }
      enum state-standby {
        value 2;
        description "Standby";
      }
      enum state-static {
        value 3;
        description "Static";
      }
      enum state-alias {
        value 4;
        description "Alias";
      }
      enum state-mobile {
        value 5;
        description "Mobile";
      }
      enum state-incomplete {
        value 6;
        description "Incomplete";
      }
      enum state-deleted {
        value 7;
        description "Deleted";
      }
      enum state-dynamic {
        value 8;
        description "Dynamic";
      }
      enum state-probe {
        value 9;
        description "Probe";
      }
      enum state-purge-delayed {
        value 10;
        description "Purge delayed";
      }
      enum state-dhcp {
        value 11;
        description "DHCP installed";
      }
      enum state-vxlan {
        value 12;
        description "VXLAN installed";
      }
      enum state-sat {
        value 13;
        description "Satellite installed";
      }
      enum state-r-sync {
        value 14;
        description "Geo-redundancy sync'ed";
      }
      enum state-max {
        value 15;
        description "Maximum state number";
      }
    }
    description "ARP state";
  }
  typedef Ip-arp-bag-media {
    type enumeration {
      enum media-arpa {
        value 0;
        description "ARPA";
      }
      enum media-srp {
        value 1;
        description "SRP";
      }
      enum media-unknown {
        value 2;
        description "Unknown";
      }
    }
    description "ARP media type";
  }
  typedef Arp-resolution-history-status {
    type enumeration {
      enum status-none {
        value 0;
        description "No Status";
      }
      enum status-resolution-request {
        value 1;
        description "Resolution Request Received";
      }
      enum status-resolved-reply {
        value 2;
        description "Resolved with ARP reply";
      }
      enum status-resolved-grat-arp {
        value 3;
        description "Resolved with Grat ARP";
      }
      enum status-resolved-request {
        value 4;
        description "Resolved with ARP Request";
      }
      enum status-resolved-lc-sync {
        value 5;
        description "Resolved via a Linecard sync";
      }
      enum status-resolved-lc-sync-purge-delay {
        value 6;
        description
          "Resolved via a Linecard sync while purge
          delayed";
      }
      enum status-resolved-client {
        value 7;
        description "Resolved from an ARP API client";
      }
      enum status-removed-client {
        value 8;
        description "Removed by an ARP API client";
      }
      enum status-already-resolved {
        value 9;
        description "Already Resolved";
      }
      enum status-failed {
        value 10;
        description "Resolution Failed";
      }
      enum status-dropped-interface-down {
        value 11;
        description "Dropped because the Interface was down";
      }
      enum status-dropped-broadcast-disabled {
        value 12;
        description
          "Dropped because the Interface was broadcast
          disabled";
      }
      enum status-dropped-interface-unavailable {
        value 13;
        description
          "Dropped because the Interface was unavailable
          to arp";
      }
      enum status-dropped-bad-subnet {
        value 14;
        description
          "The requested IP address didn't belong to the
          subnet";
      }
      enum status-dropped-dynamic-learning-disabled {
        value 15;
        description
          "Dynamic learning of ARP entries is disabled on
          the interface";
      }
      enum status-dropped-out-of-subnet-disabled {
        value 16;
        description
          "Out of Subnet address learning is disabled on
          the interface";
      }
      enum status-removed-client-sweep {
        value 17;
        description "Removed by an ARP API client during a resync";
      }
      enum status-added-client {
        value 18;
        description "Added by an ARP API client";
      }
      enum status-added-v1 {
        value 19;
        description "Added by replication from ARP V1 during ISSU";
      }
      enum status-removed-v1 {
        value 20;
        description
          "Removed by replication from ARP V1 during ISSU";
      }
      enum status-resolved-peer-sync {
        value 21;
        description "Resolved via a Peer Router sync";
      }
    }
    description "Arp resolution history status";
  }

  grouping IP-ARP-TABLE-ENTRY {
    description "IP ARP Table entry";
    leaf media-type {
      xr:xr-xml-map "ip_arp_show:MediaType";
      type Ip-arp-bag-media;
      description "Media type for this entry";
    }
    leaf state {
      xr:xr-xml-map "ip_arp_show:State";
      type Ip-arp-bag-state;
      description "State of this entry";
    }
    leaf age {
      xr:xr-xml-map "ip_arp_show:Age";
      type uint64;
      description "Age of this entry";
    }
    leaf encapsulation-type {
      xr:xr-xml-map "ip_arp_show:EncapsulationType";
      type Ip-arp-bag-encap;
      description "Source encapsulation type";
    }
    leaf hardware-length {
      xr:xr-xml-map "ip_arp_show:HardwareLength";
      type uint8;
      description "Source hardware length";
    }
    leaf hardware-address {
      xr:xr-xml-map "ip_arp_show:HardwareAddress";
      type yang:mac-address;
      description "Hardware address";
    }
  }

  grouping IP-ARP-STATISTICS {
    description "IP ARP Statistics information";
    leaf requests-received {
      xr:xr-xml-map "ip_arp_show:RequestsReceived";
      type uint32;
      description "Total ARP requests received";
    }
    leaf replies-received {
      xr:xr-xml-map "ip_arp_show:RepliesReceived";
      type uint32;
      description "Total ARP replies received";
    }
    leaf requests-sent {
      xr:xr-xml-map "ip_arp_show:RequestsSent";
      type uint32;
      description "Total ARP requests sent";
    }
    leaf replies-sent {
      xr:xr-xml-map "ip_arp_show:RepliesSent";
      type uint32;
      description "Total ARP replies sent";
    }
    leaf proxy-replies-sent {
      xr:xr-xml-map "ip_arp_show:ProxyRepliesSent";
      type uint32;
      description "Total Proxy ARP replies sent";
    }
    leaf subscr-requests-received {
      xr:xr-xml-map "ip_arp_show:SubscrRequestsReceived";
      type uint32;
      description
        "Total ARP requests received over subscriber
        interface";
    }
    leaf subscr-replies-sent {
      xr:xr-xml-map "ip_arp_show:SubscrRepliesSent";
      type uint32;
      description
        "Total ARP replies sent over subscriber interface";
    }
    leaf subscr-replies-gratg-sent {
      xr:xr-xml-map "ip_arp_show:SubscrRepliesGratgSent";
      type uint32;
      description
        "Total ARP grat replies sent over subscriber
        interface";
    }
    leaf local-proxy-replies-sent {
      xr:xr-xml-map "ip_arp_show:LocalProxyRepliesSent";
      type uint32;
      description "Total Local Proxy ARP replies sent";
    }
    leaf gratuitous-replies-sent {
      xr:xr-xml-map "ip_arp_show:GratuitousRepliesSent";
      type uint32;
      description "Total Gratuituous ARP replies sent";
    }
    leaf resolution-requests-received {
      xr:xr-xml-map "ip_arp_show:ResolutionRequestsReceived";
      type uint32;
      description "Total ARP resolution requests received";
    }
    leaf resolution-replies-received {
      xr:xr-xml-map "ip_arp_show:ResolutionRepliesReceived";
      type uint32;
      description "Total ARP resolution replies received";
    }
    leaf resolution-requests-dropped {
      xr:xr-xml-map "ip_arp_show:ResolutionRequestsDropped";
      type uint32;
      description "total ARP resolution requests dropped";
    }
    leaf out-of-memory-errors {
      xr:xr-xml-map "ip_arp_show:OutOfMemoryErrors";
      type uint32;
      description "Total errors for out of memory";
    }
    leaf no-buffer-errors {
      xr:xr-xml-map "ip_arp_show:NoBufferErrors";
      type uint32;
      description "Total errors for no buffer";
    }
    leaf total-entries {
      xr:xr-xml-map "ip_arp_show:TotalEntries";
      type uint32;
      description "Total ARP entries in the cache";
    }
    leaf dynamic-entries {
      xr:xr-xml-map "ip_arp_show:DynamicEntries";
      type uint32;
      description "Total dynamic entries in the cache";
    }
    leaf static-entries {
      xr:xr-xml-map "ip_arp_show:StaticEntries";
      type uint32;
      description "Total static entries in the cache";
    }
    leaf alias-entries {
      xr:xr-xml-map "ip_arp_show:AliasEntries";
      type uint32;
      description "Total alias entries in the cache";
    }
    leaf interface-entries {
      xr:xr-xml-map "ip_arp_show:InterfaceEntries";
      type uint32;
      description "Total interface entries in the cache";
    }
    leaf standby-entries {
      xr:xr-xml-map "ip_arp_show:StandbyEntries";
      type uint32;
      description "Total standby entries in the cache";
    }
    leaf dhcp-entries {
      xr:xr-xml-map "ip_arp_show:DHCPEntries";
      type uint32;
      description "Total DHCP entries in the cache";
    }
    leaf vxlan-entries {
      xr:xr-xml-map "ip_arp_show:VXLANEntries";
      type uint32;
      description "Total VXLAN entries in the cache";
    }
    leaf ip-packets-dropped-node {
      xr:xr-xml-map "ip_arp_show:IPPacketsDroppedNode";
      type uint32;
      description "Total ip packets droped on this node";
    }
    leaf arp-packet-node-out-of-subnet {
      xr:xr-xml-map "ip_arp_show:ARPPacketNodeOutOfSubnet";
      type uint32;
      description "Total ARP packets on node due to out of subnet";
    }
    leaf ip-packets-dropped-interface {
      xr:xr-xml-map "ip_arp_show:IPPacketsDroppedInterface";
      type uint32;
      description "Total ip packets droped on this interface";
    }
    leaf arp-packet-interface-out-of-subnet {
      xr:xr-xml-map "ip_arp_show:ARPPacketInterfaceOutOfSubnet";
      type uint32;
      description
        "Total arp packets on interface due to out of
        subnet";
    }
    leaf idb-structures {
      xr:xr-xml-map "ip_arp_show:IDBStructures";
      type uint32;
      description "Total idb structures on this node";
    }
  }

  grouping ARP-RESHIST-ENTRY {
    description "ARP resolution history entry";
    leaf nsec-timestamp {
      xr:xr-xml-map "ip_arp_show:NsecTimestamp";
      type uint64;
      units "nanosecond";
      description
        "Timestamp for entry in nanoseconds since Epoch,
        i.e. since 00:00:00 UTC, January 1, 1970";
    }
    leaf idb-interface-name {
      xr:xr-xml-map "ip_arp_show:IDBInterfaceName";
      type xr:Interface-name;
      description "Interface";
    }
    leaf ipv4-address {
      xr:xr-xml-map "ip_arp_show:IPv4Address";
      type inet:ipv4-address;
      description "IPv4 address";
    }
    leaf mac-address {
      xr:xr-xml-map "ip_arp_show:MACAddress";
      type yang:mac-address;
      description "MAC address";
    }
    leaf status {
      xr:xr-xml-map "ip_arp_show:Status";
      type Arp-resolution-history-status;
      description "Resolution status";
    }
    leaf client-id {
      xr:xr-xml-map "ip_arp_show:ClientID";
      type int32;
      description "Resolving Client ID";
    }
    leaf entry-state {
      xr:xr-xml-map "ip_arp_show:EntryState";
      type int32;
      description "ARP entry state";
    }
    leaf resolution-request-count {
      xr:xr-xml-map "ip_arp_show:ResolutionRequestCount";
      type uint32;
      description "Resolution Request count";
    }
  }

  grouping ARP-RESHIST {
    description "ARP Resolution History";

    list arp-entry {
      description "Resolution history array";
      uses ARP-RESHIST-ENTRY;
    }
  }
}
