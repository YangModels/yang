module Cisco-IOS-XR-ipv4-igmp-oper {

  /*** NAMESPACE / PREFIX DEFINITION ***/

  namespace "http://cisco.com/ns/yang/Cisco-IOS-XR-ipv4-igmp-oper";


  prefix "ipv4-igmp-oper";

  /*** LINKAGE (IMPORTS / INCLUDES) ***/

  import ietf-inet-types { prefix "inet"; }

  import Cisco-IOS-XR-types { prefix "xr"; }

  include Cisco-IOS-XR-ipv4-igmp-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ipv4-igmp package operational data.

     This module contains definitions
     for the following management objects:
       mld: MLD operational data
       igmp: igmp

     Copyright (c) 2013-2016 by Cisco Systems, Inc.
     All rights reserved.";

  revision "2015-11-09" {
    description
      "IOS XR 6.0 revision.";
  }

  typedef Igmpssm-map {
    type enumeration {
      enum static {
        value 0;
        description "Static";
      }
      enum dns {
        value 1;
        description "Dns";
      }
      enum all {
        value 2;
        description "All";
      }
    }
    description "Igmpssm map";
  }

  grouping INTERFACE-STATE-OFF-TABLE {
    description "Common node of vrf, default-context";

    container interface-state-offs {
      xr:xr-xml-map "ipv4_igmp_common_oper:InterfaceStateOffTable";
      description "IGMP Interface state off";

      list interface-state-off {
        xr:xr-xml-map "ipv4_igmp_common_oper:InterfaceStateOff";
        key "interface-name";
        description "IGMP Interface";
        leaf interface-name {
          xr:xr-xml-map "ipv4_igmp_common_oper:InterfaceName";
          type xr:Interface-name;
          description "Interface Name";
        }
        uses IGMP-EDM-IDB-BAG;
      }
    }
  }

  grouping RANGE-TABLE {
    description "Common node of vrf, default-context";

    container ranges {
      xr:xr-xml-map "ipv4_igmp_common_oper:RangeTable";
      description "Range table";

      list range {
        xr:xr-xml-map "ipv4_igmp_common_oper:Range";
        description "Range information";
        leaf group-address {
          xr:xr-xml-map "ipv4_igmp_common_oper:GroupAddress";
          type inet:ip-address-no-zone;
          description "Group address";
        }
        leaf group-mask {
          xr:xr-xml-map "ipv4_igmp_common_oper:GroupMask";
          type int32;
          description "Group Mask";
        }
        uses IGMP-GROUP-RANGE;
      }
    }
  }

  grouping SSM-MAP-DETAIL-TABLE {
    description "Common node of vrf, default-context";

    container ssm-map-details {
      xr:xr-xml-map "ipv4_igmp_common_oper:SSMMapDetailTable";
      description "SSM Map Detail";

      list ssm-map-detail {
        xr:xr-xml-map "ipv4_igmp_common_oper:SSMMapDetail";
        description "SSM Map Detail Table information";
        leaf ssm-map-type {
          xr:xr-xml-map "ipv4_igmp_common_oper:SSMMapType";
          type Igmpssm-map;
          description "SSM Map Type";
        }
        leaf group-address {
          xr:xr-xml-map "ipv4_igmp_common_oper:GroupAddress";
          type inet:ip-address-no-zone;
          description "Group address";
        }
        uses IGMP-EDM-SSM-MAP-DETAIL-BAG;
      }
    }
  }

  grouping EXPLICIT-GROUP-TABLE {
    description "Common node of vrf, default-context";

    container explicit-groups {
      xr:xr-xml-map "ipv4_igmp_common_oper:ExplicitGroupTable";
      description "IGMP Explicit Group Database";

      list explicit-group {
        xr:xr-xml-map "ipv4_igmp_common_oper:ExplicitGroup";
        description "IGMP Explicit Group Entry Information";
        leaf group-address {
          xr:xr-xml-map "ipv4_igmp_common_oper:GroupAddress";
          type inet:ip-address-no-zone;
          description "Group Address";
        }
        leaf interface-name {
          xr:xr-xml-map "ipv4_igmp_common_oper:InterfaceName";
          type xr:Interface-name;
          description "Interface Name";
        }
        leaf source-address {
          xr:xr-xml-map "ipv4_igmp_common_oper:SourceAddress";
          type inet:ip-address-no-zone;
          description "Source/Host Address";
        }
        uses IGMP-EDM-GROUPS-ET-BAG;
      }
    }
  }

  grouping INTERFACE-STATE-OFF-OLD-FORMAT-TABLE {
    description "Common node of vrf, default-context";

    container interface-state-off-old-formats {
      xr:xr-xml-map "ipv4_igmp_common_oper:InterfaceStateOffOldForm"+
        "atTable";
      description "IGMP Interface state off old format";

      list interface-state-off-old-format {
        xr:xr-xml-map "ipv4_igmp_common_oper:InterfaceStateOffOldFo"+
          "rmat";
        key "interface-name";
        description "IGMP Interface";
        leaf interface-name {
          xr:xr-xml-map "ipv4_igmp_common_oper:InterfaceName";
          type xr:Interface-name;
          description "Interface Name";
        }
        uses IGMP-EDM-IDB-BAG;
      }
    }
  }

  grouping ALL-JOINED {
    description "Common node of vrf, default-context";

    container join-tables {
      xr:xr-xml-map "ipv4_igmp_common_oper:AllJoined";
      description "IGMP show all joins on the interface";

      list join-table {
        xr:xr-xml-map "ipv4_igmp_common_oper:JoinTable";
        key "interface-name";
        description "IGMP Joins grouped by interface";
        leaf interface-name {
          xr:xr-xml-map "ipv4_igmp_common_oper:InterfaceName";
          type xr:Interface-name;
          description "Interface Name";
        }

        list join {
          xr:xr-xml-map "ipv4_igmp_common_oper:Join";
          key "interface-name";
          description "IGMP show all joins on the interface";
          leaf interface-name {
            xr:xr-xml-map "ipv4_igmp_common_oper:InterfaceName";
            type xr:Interface-name;
            description "Interface Name";
          }
          uses IGMP-EDM-GROUPS-DETAIL-BAG;
        }
      }
    }
  }

  grouping GROUP-TABLE {
    description "Common node of vrf, default-context";

    container groups {
      xr:xr-xml-map "ipv4_igmp_common_oper:GroupTable";
      description "IGMP Group Database Table";

      list group {
        xr:xr-xml-map "ipv4_igmp_common_oper:Group";
        description "IGMP Group Entry Information";
        leaf group-address {
          xr:xr-xml-map "ipv4_igmp_common_oper:GroupAddress";
          type inet:ip-address-no-zone;
          description "Group Address";
        }
        leaf interface-name {
          xr:xr-xml-map "ipv4_igmp_common_oper:InterfaceName";
          type xr:Interface-name;
          description "Interface Name";
        }
        uses IGMP-EDM-GROUPS-BAG;
      }
    }
  }

  grouping GROUP-SUMMARY {
    description "Common node of vrf, default-context";

    container group-summary {
      xr:xr-xml-map "ipv4_igmp_common_oper:GroupSummary";
      description "IGMP Groups Summary";
      uses IGMP-EDM-GROUPS-SUMMARY-BAG;
    }
  }

  grouping VRF-TABLE {
    description "Common node of active, standby";

    container vrfs {
      xr:xr-xml-map "ipv4_igmp_common_oper:VRFTable";
      description "VRF Table";

      list vrf {
        xr:xr-xml-map "ipv4_igmp_common_oper:VRF";
        key "vrf-name";
        description "VRF table Names";
        leaf vrf-name {
          xr:xr-xml-map "ipv4_igmp_common_oper:VRFName";
          type xr:Cisco-ios-xr-string;
          description "VRF name";
        }
        uses SUMMARY;
        uses INTERFACE-STATE-ON-TABLE;
        uses DETAIL-GROUP-TABLE;
        uses NON-ACTIVE-GROUPS;
        uses SSM-MAP-TABLE;
        uses EXPLICIT-GROUP-TABLE;
        uses INTERFACE-TABLE;
        uses INTERFACE-OLD-FORMAT-TABLE;
        uses INTERFACE-STATE-OFF-OLD-FORMAT-TABLE;
        uses INTERFACE-UNICAST-QOS-ADJUST-TABLE;
        uses RANGE-TABLE;
        uses IFRS-INTERFACE-TABLE;
        uses TRAFFIC-COUNTERS;
        uses GROUP-TABLE;
        uses GROUP-SUMMARY;
        uses IFRS-INTERFACE-SUMMARY;
        uses GLOBAL-INTERFACE-TABLE;
        uses SSM-MAP-DETAIL-TABLE;
        uses ALL-JOINED;
        uses INTERFACE-STATE-OFF-TABLE;
        uses INTERFACE-STATE-ON-OLD-FORMAT-TABLE;
      }
    }
  }

  grouping INTERFACE-STATE-ON-TABLE {
    description "Common node of vrf, default-context";

    container interface-state-ons {
      xr:xr-xml-map "ipv4_igmp_common_oper:InterfaceStateOnTable";
      description "IGMP Interface state on";

      list interface-state-on {
        xr:xr-xml-map "ipv4_igmp_common_oper:InterfaceStateOn";
        key "interface-name";
        description "IGMP Interface";
        leaf interface-name {
          xr:xr-xml-map "ipv4_igmp_common_oper:InterfaceName";
          type xr:Interface-name;
          description "Interface Name";
        }
        uses IGMP-EDM-IDB-BAG;
      }
    }
  }

  grouping INTERFACE {
    description
      "Common node of interface-table,
      global-interface-table";

    list interface {
      xr:xr-xml-map "ipv4_igmp_common_oper:Interface";
      key "interface-name";
      description "IGMP Interface";
      leaf interface-name {
        xr:xr-xml-map "ipv4_igmp_common_oper:InterfaceName";
        type xr:Interface-name;
        description "Interface Name";
      }
      uses IGMP-EDM-IDB-BAG;
    }
  }

  grouping IFRS-INTERFACE-TABLE {
    description "Common node of vrf, default-context";

    container ifrs-interfaces {
      xr:xr-xml-map "ipv4_igmp_common_oper:IFRSInterfaceTable";
      description "IGMP Interface specific";

      list ifrs-interface {
        xr:xr-xml-map "ipv4_igmp_common_oper:IFRSInterface";
        key "interface-name";
        description "IGMP IFRS Interface";
        leaf interface-name {
          xr:xr-xml-map "ipv4_igmp_common_oper:InterfaceName";
          type xr:Interface-name;
          description "IFRS Interface Name";
        }
        uses IGMP-EDM-IDB-IFRS-BAG;
      }
    }
  }

  grouping PROCESS {
    description "Common node of active, standby";

    container process {
      xr:xr-xml-map "ipv4_igmp_role_lvl_oper:Process";
      description "Process";

      container amt-summary {
        xr:xr-xml-map "ipv4_igmp_common_oper:AMTSummary";
        description "MRIB RouteDB Expiry Information";
        uses AMT-SUMMARY-BAG;
      }

      container nsr {
        xr:xr-xml-map "ipv4_igmp_common_oper:NSR";
        description "NSR Information";
        uses IGMP-EDM-NSR-BAG;
      }

      container amt-gatewaies {
        xr:xr-xml-map "ipv4_igmp_common_oper:AMTGatewayTable";
        description
          "Table containing AMT Gateway DataBase
          information";

        list amt-gateway {
          xr:xr-xml-map "ipv4_igmp_common_oper:AMTGateway";
          description "AMT Gateway DataBase information";
          leaf gateway-address {
            xr:xr-xml-map "ipv4_igmp_common_oper:GatewayAddress";
            type inet:ip-address-no-zone;
            description "Gateway Address";
          }
          leaf port {
            xr:xr-xml-map "ipv4_igmp_common_oper:Port";
            type int32;
            description "Port";
          }
          uses AMT-GW-BAG;
        }
      }

      container unicast-qos-adjust-stats {
        xr:xr-xml-map "ipv4_igmp_common_oper:UnicastQosAdjustStats";
        description "IGMP Unicast-Qos-Adjust Statistics";
        uses IGMP-EDM-I2Q-STATS-BAG;
      }

      container bvi-statistics {
        xr:xr-xml-map "ipv4_igmp_common_oper:BVIStatistics";
        description "IGMP BVI Stats";
        uses IGMP-EDM-BVI-STATS-BAG;
      }

      container nsf {
        xr:xr-xml-map "ipv4_igmp_common_oper:NSF";
        description "NSF Information";
        uses IGMP-EDM-NSF-BAG;
      }
    }
  }

  grouping INTERFACE-STATE-ON-OLD-FORMAT-TABLE {
    description "Common node of vrf, default-context";

    container interface-old-format-state-ons {
      xr:xr-xml-map "ipv4_igmp_common_oper:InterfaceStateOnOldForma"+
        "tTable";
      description "IGMP Interface state on old format";

      list interface-old-format-state-on {
        xr:xr-xml-map "ipv4_igmp_common_oper:InterfaceOldFormatStat"+
          "eOn";
        key "interface-name";
        description "IGMP Interface";
        leaf interface-name {
          xr:xr-xml-map "ipv4_igmp_common_oper:InterfaceName";
          type xr:Interface-name;
          description "Interface Name";
        }
        uses IGMP-EDM-IDB-BAG;
      }
    }
  }

  grouping TRAFFIC-COUNTERS {
    description "Common node of vrf, default-context";

    container traffic-counters {
      xr:xr-xml-map "ipv4_igmp_common_oper:TrafficCounters";
      description "IGMP Message Traffic Counters";
      uses IGMP-EDM-TRAFFIC-BAG;
    }
  }

  grouping GLOBAL-INTERFACE-TABLE {
    description "Common node of vrf, default-context";

    container global-interface-table {
      xr:xr-xml-map "ipv4_igmp_common_oper:GlobalInterfaceTable";
      description "IGMP Global Interface ";
      uses INTERFACE;
    }
  }

  grouping ACTIVE {
    description "Common node of igmp, mld";

    container active {
      xr:xr-xml-map "ipv4_igmp_role_lvl_oper:Active";
      description "Active Process";
      uses VRF-TABLE;
      uses PROCESS;
      uses DEFAULT-CONTEXT;
    }
  }

  grouping INTERFACE-UNICAST-QOS-ADJUST-TABLE {
    description "Common node of vrf, default-context";

    container interface-unicast-qos-adjusts {
      xr:xr-xml-map "ipv4_igmp_common_oper:InterfaceUnicastQosAdjus"+
        "tTable";
      description "IGMP Interface Unicast-Qos-Adjust";

      list interface-unicast-qos-adjust {
        xr:xr-xml-map "ipv4_igmp_common_oper:InterfaceUnicastQosAdj"+
          "ust";
        key "interface-name";
        description "IGMP Interface";
        leaf interface-name {
          xr:xr-xml-map "ipv4_igmp_common_oper:InterfaceName";
          type xr:Interface-name;
          description "Interface Name";
        }
        uses IGMP-EDM-I2Q-INTF-STATS-BAG;
      }
    }
  }

  grouping INTERFACE-OLD-FORMAT-TABLE {
    description "Common node of vrf, default-context";

    container interface-old-formats {
      xr:xr-xml-map "ipv4_igmp_common_oper:InterfaceOldFormatTable";
      description "IGMP Interface specific Table in old format";

      list interface-old-format {
        xr:xr-xml-map "ipv4_igmp_common_oper:InterfaceOldFormat";
        key "interface-name";
        description "IGMP Interface";
        leaf interface-name {
          xr:xr-xml-map "ipv4_igmp_common_oper:InterfaceName";
          type xr:Interface-name;
          description "Interface Name";
        }
        uses IGMP-EDM-IDB-BAG;
      }
    }
  }

  grouping INTERFACE-TABLE {
    description "Common node of vrf, default-context";

    container interface-table {
      xr:xr-xml-map "ipv4_igmp_common_oper:InterfaceTable";
      description "IGMP Interface specific Table";
      uses INTERFACE;
    }
  }

  grouping SUMMARY {
    description "Common node of vrf, default-context";

    container summary {
      xr:xr-xml-map "ipv4_igmp_common_oper:Summary";
      description "IGMP Summary Information";
      uses IGMP-EDM-SUMMARY-BAG;
    }
  }

  grouping NON-ACTIVE-GROUPS {
    description "Common node of vrf, default-context";

    container non-active-groups {
      xr:xr-xml-map "ipv4_igmp_common_oper:NonActiveGroups";
      description "IGMP Non-Active Groups Information";
      uses IGMP-EDM-NOT-ACTIVE-ALLGROUPS-BAG;
    }
  }

  grouping DETAIL-GROUP-TABLE {
    description "Common node of vrf, default-context";

    container detail-groups {
      xr:xr-xml-map "ipv4_igmp_common_oper:DetailGroupTable";
      description "IGMP Detail Group Database";

      list detail-group {
        xr:xr-xml-map "ipv4_igmp_common_oper:DetailGroup";
        description "IGMP Detail Group Entry Information";
        leaf group-address {
          xr:xr-xml-map "ipv4_igmp_common_oper:GroupAddress";
          type inet:ip-address-no-zone;
          description "Group Address";
        }
        leaf interface-name {
          xr:xr-xml-map "ipv4_igmp_common_oper:InterfaceName";
          type xr:Interface-name;
          description "Interface Name";
        }
        leaf source-address {
          xr:xr-xml-map "ipv4_igmp_common_oper:SourceAddress";
          type inet:ip-address-no-zone;
          description "Source/Host Address";
        }
        uses IGMP-EDM-GROUPS-DETAIL-BAG;
      }
    }
  }

  grouping SSM-MAP-TABLE {
    description "Common node of vrf, default-context";

    container ssm-maps {
      xr:xr-xml-map "ipv4_igmp_common_oper:SSMMapTable";
      description "SSM Map Table";

      list ssm-map {
        xr:xr-xml-map "ipv4_igmp_common_oper:SSMMap";
        description "SSM Map information";
        leaf ssm-map-type {
          xr:xr-xml-map "ipv4_igmp_common_oper:SSMMapType";
          type Igmpssm-map;
          description "SSM Map Type";
        }
        leaf group-address {
          xr:xr-xml-map "ipv4_igmp_common_oper:GroupAddress";
          type inet:ip-address-no-zone;
          description "Group address";
        }
        uses IGMP-EDM-SSM-MAP-BAG;
      }
    }
  }

  grouping DEFAULT-CONTEXT {
    description "Common node of active, standby";

    container default-context {
      xr:xr-xml-map "ipv4_igmp_common_oper:DefaultContext";
      description "Default Context";
      uses SUMMARY;
      uses INTERFACE-STATE-ON-TABLE;
      uses DETAIL-GROUP-TABLE;
      uses NON-ACTIVE-GROUPS;
      uses SSM-MAP-TABLE;
      uses EXPLICIT-GROUP-TABLE;
      uses INTERFACE-TABLE;
      uses INTERFACE-OLD-FORMAT-TABLE;
      uses INTERFACE-STATE-OFF-OLD-FORMAT-TABLE;
      uses INTERFACE-UNICAST-QOS-ADJUST-TABLE;
      uses RANGE-TABLE;
      uses IFRS-INTERFACE-TABLE;
      uses TRAFFIC-COUNTERS;
      uses GROUP-TABLE;
      uses GROUP-SUMMARY;
      uses IFRS-INTERFACE-SUMMARY;
      uses GLOBAL-INTERFACE-TABLE;
      uses SSM-MAP-DETAIL-TABLE;
      uses ALL-JOINED;
      uses INTERFACE-STATE-OFF-TABLE;
      uses INTERFACE-STATE-ON-OLD-FORMAT-TABLE;
    }
  }

  grouping IFRS-INTERFACE-SUMMARY {
    description "Common node of vrf, default-context";

    container ifrs-interface-summary {
      xr:xr-xml-map "ipv4_igmp_common_oper:IFRSInterfaceSummary";
      description "IGMP IFRS Interface summary";
      uses IGMP-EDM-IDB-SUMM-BAG;
    }
  }

  grouping STANDBY {
    description "Common node of igmp, mld";

    container standby {
      xr:xr-xml-map "ipv4_igmp_role_lvl_oper:Standby";
      description "Standby Process";
      uses VRF-TABLE;
      uses PROCESS;
      uses DEFAULT-CONTEXT;
    }
  }

  container mld {
    xr:xr-xml-map "ipv6_mld_oper:MLD";
    config false;
    description "MLD operational data";
    uses STANDBY;
    uses ACTIVE;
  }

  container igmp {
    xr:xr-xml-map "ipv4_igmp_oper:IGMP";
    config false;
    description "igmp";
    uses STANDBY;
    uses ACTIVE;
  }
}
