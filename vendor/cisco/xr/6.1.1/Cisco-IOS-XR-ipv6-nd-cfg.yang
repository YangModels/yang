module Cisco-IOS-XR-ipv6-nd-cfg {

  /*** NAMESPACE / PREFIX DEFINITION ***/

  namespace "http://cisco.com/ns/yang/Cisco-IOS-XR-ipv6-nd-cfg";


  prefix "ipv6-nd-cfg";

  /*** LINKAGE (IMPORTS / INCLUDES) ***/

  import ietf-inet-types { prefix "inet"; }

  import ietf-yang-types { prefix "yang"; }

  import Cisco-IOS-XR-types { prefix "xr"; }

  import Cisco-IOS-XR-ifmgr-cfg { prefix "a1"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ipv6-nd package configuration.

     This module contains definitions
     for the following management objects:
       ipv6-neighbor: IPv6 neighbor or neighbor discovery
         configuration

     This YANG module augments the
       Cisco-IOS-XR-ifmgr-cfg
     module with configuration data.

     Copyright (c) 2013-2016 by Cisco Systems, Inc.
     All rights reserved.";

  revision "2015-11-09" {
    description
      "IOS XR 6.0 revision.";
  }

  typedef Ipv6srp-encapsulation {
    type enumeration {
      enum srpa {
        value 5;
        description "Encapsulation type SRP, prefer side A";
      }
      enum srpb {
        value 6;
        description "Encapsulation type SRP, prefer side B";
      }
    }
    description "Ipv6srp encapsulation";
  }
  typedef Ipv6nd-month {
    type enumeration {
      enum january {
        value 0;
        description "January";
      }
      enum february {
        value 1;
        description "February";
      }
      enum march {
        value 2;
        description "March";
      }
      enum april {
        value 3;
        description "April";
      }
      enum may {
        value 4;
        description "May";
      }
      enum june {
        value 5;
        description "June";
      }
      enum july {
        value 6;
        description "July";
      }
      enum august {
        value 7;
        description "August";
      }
      enum september {
        value 8;
        description "September";
      }
      enum october {
        value 9;
        description "October";
      }
      enum november {
        value 10;
        description "November";
      }
      enum december {
        value 11;
        description "December";
      }
    }
    description "Ipv6nd month";
  }
  typedef Ipv6-nd-router-pref {
    type enumeration {
      enum high {
        value 1;
        description "High preference";
      }
      enum medium {
        value 2;
        description "Medium preference";
      }
      enum low {
        value 3;
        description "Low preference";
      }
    }
    description "Ipv6 nd router pref";
  }

  container ipv6-neighbor {
    xr:xr-xml-map "ipv6_nd_cfg:IPv6Neighbor";
    description "IPv6 neighbor or neighbor discovery configuration";

    container neighbors {
      xr:xr-xml-map "ipv6_nd_cfg:NeighborTable";
      description "IPv6 neighbors";

      list neighbor {
        xr:xr-xml-map "ipv6_nd_cfg:Neighbor";
        xr:xr-cli-map "neighbor <IPv6 address> <interface> <MAC add"+
          "ress> [<enum>] ";
        key "neighbor-address interface-name";
        description "IPv6 neighbor configuration";
        leaf neighbor-address {
          xr:xr-xml-map "ipv6_nd_cfg:NeighborAddress";
          type inet:ipv6-address-no-zone;
          description "IPv6 address";
        }
        leaf interface-name {
          xr:xr-xml-map "ipv6_nd_cfg:InterfaceName";
          type xr:Interface-name;
          description "Interface name";
        }
        leaf zone {
          xr:xr-xml-map "ipv6_nd_cfg:Zone";
          type string;
          default "0";
          description "IPv6 address zone";
        }
        leaf mac-address {
          xr:xr-xml-map "ipv6_nd_cfg:MACAddress";
          type yang:mac-address;
          mandatory true;
          description "48-bit hardware address H.H.H";
        }
        leaf encapsulation {
          xr:xr-xml-map "ipv6_nd_cfg:Encapsulation";
          type Ipv6srp-encapsulation;
          description
            "Encapsulation type only if interface type is
            SRP";
        }
      }
    }
    leaf scavenge-timeout {
      xr:xr-xml-map "ipv6_nd_cfg:ScavengeTimeout";
      xr:xr-cli-map "scavenge-timeout <number> ";
      type uint32 {
        range "1..43200";
      }
      units "second";
      description "Set lifetime for stale neighbor";
    }
  }

  augment "/a1:interface-configurations/a1:interface-configuration" {

    container ipv6-neighbor {
      xr:xr-xml-map "ipv6_nd_interface_cfg:IPv6Neighbor";
      description
        "IPv6 interface neighbor or neighbor discovery
        configuration";

      container raspecific-route-s {
        xr:xr-xml-map "ipv6_nd_interface_cfg:RASPECIFICROUTETable";
        description "IPv6 Router Advertisement (RA) Specific Route";

        list raspecific-route {
          xr:xr-xml-map "ipv6_nd_interface_cfg:RASPECIFICROUTE";
          key "specific-route";
          description
            "IPv6 Router Advertisement (RA) Specific Route";
          leaf specific-route {
            xr:xr-xml-map "ipv6_nd_interface_cfg:SpecificRoute";
            type inet:ipv6-address-no-zone;
            description "IPv6 Address";
          }
          leaf prefix-length {
            xr:xr-xml-map "ipv6_nd_interface_cfg:PrefixLength";
            type xr:Ipv6-prefix-length;
            description "Prefix mask length";
          }
          leaf lifetime {
            xr:xr-xml-map "ipv6_nd_interface_cfg:Lifetime";
            type uint32 {
              range "0..4294967295";
            }
            description "Lifetime (seconds)";
          }
          leaf preference {
            xr:xr-xml-map "ipv6_nd_interface_cfg:Preference";
            type Ipv6-nd-router-pref;
            description "Preference";
          }
        }
      }

      container duplicate-address-detection {
        xr:xr-xml-map "ipv6_nd_interface_cfg:DuplicateAddressDetect"+
          "ion";
        description "Duplicate Address Detection (DAD)";
        leaf attempts {
          xr:xr-xml-map "ipv6_nd_interface_cfg:Attempts";
          type uint32 {
            range "0..600";
          }
          description
            "Set IPv6 duplicate address detection transmits";
        }
      }

      container radns-searches {
        xr:xr-xml-map "ipv6_nd_interface_cfg:RADNSSearchListTable";
        description
          "IPv6 Router Advertisement (RA) DNS Search List";

        list radns-search {
          xr:xr-xml-map "ipv6_nd_interface_cfg:RADNSSearchList";
          key "dns-search-list";
          description
            "IPv6 Router Advertisement (RA) DNS Search List";
          leaf dns-search-list {
            xr:xr-xml-map "ipv6_nd_interface_cfg:DNSSearchList";
            type xr:Cisco-ios-xr-string;
            description "Search List";
          }
          leaf lifetime {
            xr:xr-xml-map "ipv6_nd_interface_cfg:Lifetime";
            type uint32 {
              range "4..3600";
            }
            mandatory true;
            description "Lifetime value in seconds";
          }
        }
      }

      container radns-servers {
        xr:xr-xml-map "ipv6_nd_interface_cfg:RADNSServerTable";
        description "IPv6 Router Advertisement (RA) DNS Servre";

        list radns-server {
          xr:xr-xml-map "ipv6_nd_interface_cfg:RADNSServer";
          key "dns-server";
          description "IPv6 Router Advertisement (RA) DNS Servre";
          leaf dns-server {
            xr:xr-xml-map "ipv6_nd_interface_cfg:DNSServer";
            type inet:ipv6-address-no-zone;
            description "IPv6 Address";
          }
          leaf lifetime {
            xr:xr-xml-map "ipv6_nd_interface_cfg:Lifetime";
            type uint32 {
              range "4..3600";
            }
            mandatory true;
            description "Lifetime value in seconds";
          }
        }
      }

      container ra-interval {
        xr:xr-xml-map "ipv6_nd_interface_cfg:RAInterval";
        presence "Indicates a ra-interval node is configured.";
        description
          "Set IPv6 Router Advertisement (RA) interval in
          seconds";
        leaf maximum {
          xr:xr-xml-map "ipv6_nd_interface_cfg:Maximum";
          type uint32 {
            range "4..1800";
          }
          mandatory true;
          description "Maximum RA interval in seconds";
        }
        leaf minimum {
          xr:xr-xml-map "ipv6_nd_interface_cfg:Minimum";
          type uint32 {
            range "3..1800";
          }
          description "Minimum RA interval in seconds";
        }
      }

      container ipv6-prefixes {
        xr:xr-xml-map "ipv6_nd_interface_cfg:IPv6PrefixTable";
        description "Prefixes ";

        list ipv6-prefix {
          xr:xr-xml-map "ipv6_nd_interface_cfg:IPv6Prefix";
          key "prefix";
          description "Configure prefix with paramemters";
          leaf prefix {
            xr:xr-xml-map "ipv6_nd_interface_cfg:Prefix";
            type inet:ipv6-address-no-zone;
            description "IPv6 prefix";
          }
          leaf prefix-zone {
            xr:xr-xml-map "ipv6_nd_interface_cfg:PrefixZone";
            type string {
              length "0..9";
            }
            description "Prefix zone";
          }
          leaf prefix-length {
            xr:xr-xml-map "ipv6_nd_interface_cfg:PrefixLength";
            type xr:Ipv6-prefix-length;
            mandatory true;
            description "Prefix mask length";
          }
          leaf valid-lifetime {
            xr:xr-xml-map "ipv6_nd_interface_cfg:ValidLifetime";
            type uint32 {
              range "0..4294967295";
            }
            description "Valid Lifetime (seconds)";
          }
          leaf preferred-lifetime {
            xr:xr-xml-map "ipv6_nd_interface_cfg:PreferredLifetime";
            type uint32 {
              range "0..4294967295";
            }
            description
              "Preferred Lifetime (seconds) must be <= Valid
              Lifetime";
          }
          leaf off-link {
            xr:xr-xml-map "ipv6_nd_interface_cfg:OffLink";
            type boolean;
            description
              "If set, prefix will not be used for onlink
              determination";
          }
          leaf no-auto-config {
            xr:xr-xml-map "ipv6_nd_interface_cfg:NoAutoConfig";
            type boolean;
            description
              "If set, prefix will not be used for auto
              configuration";
          }
          leaf no-advertize {
            xr:xr-xml-map "ipv6_nd_interface_cfg:NoAdvertize";
            type boolean;
            description "If set, prefix will not be advertized";
          }
          leaf expiry-month {
            xr:xr-xml-map "ipv6_nd_interface_cfg:ExpiryMonth";
            type Ipv6nd-month;
            description "Month to expire valid lifetime";
          }
          leaf expiry-date {
            xr:xr-xml-map "ipv6_nd_interface_cfg:ExpiryDate";
            type uint32 {
              range "1..31";
            }
            description "Date to expire valid lifetime";
          }
          leaf expiry-year {
            xr:xr-xml-map "ipv6_nd_interface_cfg:ExpiryYear";
            type uint32 {
              range "2003..2035";
            }
            description "Year to expire valid lifetime";
          }
          leaf expiry-hour {
            xr:xr-xml-map "ipv6_nd_interface_cfg:ExpiryHour";
            type uint32 {
              range "0..23";
            }
            description "Hour to expire valid lifetime";
          }
          leaf expiry-minute {
            xr:xr-xml-map "ipv6_nd_interface_cfg:ExpiryMinute";
            type uint32 {
              range "0..59";
            }
            description "Minute to expire valid lifetime";
          }
          leaf pref-expiry-month {
            xr:xr-xml-map "ipv6_nd_interface_cfg:PrefExpiryMonth";
            type Ipv6nd-month;
            description "Month to expire preferred lifetime";
          }
          leaf pref-expiry-date {
            xr:xr-xml-map "ipv6_nd_interface_cfg:PrefExpiryDate";
            type uint32 {
              range "1..31";
            }
            description "Date to expire preferred lifetime";
          }
          leaf pref-expiry-year {
            xr:xr-xml-map "ipv6_nd_interface_cfg:PrefExpiryYear";
            type uint32 {
              range "2003..2035";
            }
            description "Year to expire preferred lifetime";
          }
          leaf pref-expiry-hour {
            xr:xr-xml-map "ipv6_nd_interface_cfg:PrefExpiryHour";
            type uint32 {
              range "0..23";
            }
            description "Hour to expire preferred lifetime";
          }
          leaf pref-expiry-minute {
            xr:xr-xml-map "ipv6_nd_interface_cfg:PrefExpiryMinute";
            type uint32 {
              range "0..59";
            }
            description "Minute to expire preferred lifetime";
          }
        }
      }
      leaf reachable-time {
        xr:xr-xml-map "ipv6_nd_interface_cfg:ReachableTime";
        type uint32 {
          range "0..3600000";
        }
        units "millisecond";
        description
          "Set advertised reachability time in
          milliseconds";
      }
      leaf ra-unspecify-hoplimit {
        xr:xr-xml-map "ipv6_nd_interface_cfg:RAUnspecifyHoplimit";
        type empty;
        description
          "Unspecify IPv6 Router Advertisement (RA)
          hop-limit";
      }
      leaf srp-multicast-encapsulation {
        xr:xr-xml-map "ipv6_nd_interface_cfg:SRPMulticastEncapsulat"+
          "ion";
        type Ipv6srp-encapsulation;
        description "Set SRP multicast prefer encapsulation";
      }
      leaf ns-interval {
        xr:xr-xml-map "ipv6_nd_interface_cfg:NSInterval";
        type uint32 {
          range "1000..4294967295";
        }
        units "millisecond";
        description
          "Set advertised NS retransmission interval in
          milliseconds";
      }
      leaf cache-limit {
        xr:xr-xml-map "ipv6_nd_interface_cfg:CacheLimit";
        type uint32 {
          range "0..128000";
        }
        description "Set the cache limit for neighbor entries";
      }
      leaf redirect {
        xr:xr-xml-map "ipv6_nd_interface_cfg:Redirect";
        type empty;
        description "Enable sending of ICMP Redirect messages";
      }
      leaf srp-unicast-encapsulation {
        xr:xr-xml-map "ipv6_nd_interface_cfg:SRPUnicastEncapsulatio"+
          "n";
        type Ipv6srp-encapsulation;
        description "Set SRP unicast prefer encapsulation";
      }
      leaf ramtu-suppress {
        xr:xr-xml-map "ipv6_nd_interface_cfg:RAMTUSuppress";
        type empty;
        description
          "Enable suppress MTU in IPv6 router
          advertisement";
      }
      leaf managed-config {
        xr:xr-xml-map "ipv6_nd_interface_cfg:ManagedConfig";
        type empty;
        description
          "Host to use stateful protocol for address
          configuration";
      }
      leaf ra-lifetime {
        xr:xr-xml-map "ipv6_nd_interface_cfg:RALifetime";
        type uint32 {
          range "0..9000";
        }
        units "second";
        description
          "Set IPv6 Router Advertisement (RA) lifetime in
          seconds";
      }
      leaf other-config {
        xr:xr-xml-map "ipv6_nd_interface_cfg:OtherConfig";
        type empty;
        description
          "Host to use stateful protocol for non-address
          configuration";
      }
      leaf ra-suppress {
        xr:xr-xml-map "ipv6_nd_interface_cfg:RASuppress";
        type empty;
        description "Enable suppress IPv6 router advertisement";
      }
      leaf router-preference {
        xr:xr-xml-map "ipv6_nd_interface_cfg:RouterPreference";
        type Ipv6-nd-router-pref;
        description "RA Router Preference";
      }
    }
    description
      "This augment extends the configuration data of
      'Cisco-IOS-XR-ifmgr-cfg'";
  }
}
