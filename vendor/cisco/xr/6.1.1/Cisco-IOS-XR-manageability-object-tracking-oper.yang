module Cisco-IOS-XR-manageability-object-tracking-oper {

  /*** NAMESPACE / PREFIX DEFINITION ***/

  namespace "http://cisco.com/ns/yang"+
    "/Cisco-IOS-XR-manageability-object-tracking-oper";


  prefix "manageability-object-tracking-oper";

  /*** LINKAGE (IMPORTS / INCLUDES) ***/

  import Cisco-IOS-XR-types { prefix "xr"; }

  import Cisco-IOS-XR-manageability-object-tracking-datatypes {
    prefix "dt1";
  }

  include Cisco-IOS-XR-manageability-object-tracking-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR manageability-object-tracking package operational data.

     This module contains definitions
     for the following management objects:
       object-tracking: Object Tracking operational data

     Copyright (c) 2013-2016 by Cisco Systems, Inc.
     All rights reserved.";

  revision "2015-11-09" {
    description
      "IOS XR 6.0 revision.";
  }


  container object-tracking {
    xr:xr-xml-map "manageability-object-tracking_oper:ObjectTrackin"+
      "g";
    config false;
    description "Object Tracking operational data";

    container track-type-interface {
      xr:xr-xml-map "manageability-object-tracking_oper:TrackTypeIn"+
        "terface";
      description "Object Tracking Type interface info";
      uses TRACK-INFO;
    }

    container track-briefs {
      xr:xr-xml-map "manageability-object-tracking_oper:TrackBriefT"+
        "able";
      description "Object Tracking Track table brief";

      list track-brief {
        xr:xr-xml-map "manageability-object-tracking_oper:TrackBrie"+
          "f";
        key "track-name";
        description "Track name - maximum 32 characters";
        leaf track-name {
          xr:xr-xml-map "manageability-object-tracking_oper:TrackNa"+
            "me";
          type dt1:Object-tracking-name-string;
          description "Track name";
        }
        uses TRACK-INFO-BRIEF;
      }
    }

    container track-type-rtr-reachability {
      xr:xr-xml-map "manageability-object-tracking_oper:TrackTypeRT"+
        "RReachability";
      description "Object Tracking Type RTR Reachability info";
      uses TRACK-INFO;
    }

    container track-type-rtr-reachability-brief {
      xr:xr-xml-map "manageability-object-tracking_oper:TrackTypeRT"+
        "RReachabilityBrief";
      description
        "Object Tracking Type RTR Reachability brief info";
      uses TRACK-INFO-BRIEF;
    }

    container tracks {
      xr:xr-xml-map "manageability-object-tracking_oper:TrackTable";
      description "Object Tracking Track table";

      list track {
        xr:xr-xml-map "manageability-object-tracking_oper:Track";
        key "track-name";
        description "Track name - maximum 32 characters";
        leaf track-name {
          xr:xr-xml-map "manageability-object-tracking_oper:TrackNa"+
            "me";
          type dt1:Object-tracking-name-string;
          description "Track name";
        }
        uses TRACK-INFO;
      }
    }

    container track-type-ipv4-route-brief {
      xr:xr-xml-map "manageability-object-tracking_oper:TrackTypeIP"+
        "V4RouteBrief";
      description "Object Tracking Type Ipv4 Route brief info";
      uses TRACK-INFO-BRIEF;
    }

    container track-type-ipv4-route {
      xr:xr-xml-map "manageability-object-tracking_oper:TrackTypeIP"+
        "V4Route";
      description "Object Tracking Type IPV4 route info";
      uses TRACK-INFO;
    }

    container track-type-interface-brief {
      xr:xr-xml-map "manageability-object-tracking_oper:TrackTypeIn"+
        "terfaceBrief";
      description "Object Tracking Type Interface brief info";
      uses TRACK-INFO-BRIEF;
    }
  }
}
