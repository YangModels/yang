module Cisco-IOS-XR-crypto-ssh-cfg {

  /*** NAMESPACE / PREFIX DEFINITION ***/

  namespace "http://cisco.com/ns/yang/Cisco-IOS-XR-crypto-ssh-cfg";


  prefix "crypto-ssh-cfg";

  /*** LINKAGE (IMPORTS / INCLUDES) ***/

  import Cisco-IOS-XR-types { prefix "xr"; }

  import Cisco-IOS-XR-crypto-sam-cfg { prefix "a1"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR crypto-ssh package configuration.

     This YANG module augments the
       Cisco-IOS-XR-crypto-sam-cfg
     module with configuration data.

     Copyright (c) 2013-2016 by Cisco Systems, Inc.
     All rights reserved.";

  revision "2015-07-30" {
    description
      "Descriptions updated.";
  }

  revision "2015-07-13" {
    description
      "IOS XR 5.3.2 revision.";
  }

  revision "2015-01-07" {
    description
      "IOS XR 5.3.1 revision.";
  }


  grouping DSCP {
    description "Common node of client, server";
    leaf dscp {
      xr:xr-xml-map "crypto_ssh_cfg:DSCP";
      type uint32 {
        range "0..63";
      }
      description "Cisco sshd DSCP value";
    }
  }

  grouping VRF {
    description "Common node of vrf-table, netconf-vrf-table";

    list vrf {
      xr:xr-xml-map "crypto_ssh_cfg:VRF";
      key "vrf-name";
      description "Enter VRF name";
      leaf vrf-name {
        xr:xr-xml-map "crypto_ssh_cfg:VRFName";
        type xr:Cisco-ios-xr-string {
          length "0..32";
        }
        description "Enter VRF name";
      }
      leaf enable {
        xr:xr-xml-map "crypto_ssh_cfg:Enable";
        type empty;
        mandatory true;
        description "Enable to use VRF";
      }
      leaf ipv4-access-list {
        xr:xr-xml-map "crypto_ssh_cfg:IPv4AccessList";
        type xr:Cisco-ios-xr-string {
          length "0..32";
        }
        description "SSH v4 access-list name";
      }
      leaf ipv6-access-list {
        xr:xr-xml-map "crypto_ssh_cfg:IPv6AccessList";
        type xr:Cisco-ios-xr-string {
          length "0..32";
        }
        description "SSH v6 access-list name";
      }
    }
  }

  augment "/a1:crypto" {

    container ssh {
      xr:xr-xml-map "crypto_ssh_cfg:SSH";
      description "Secure Shell configuration";

      container client {
        xr:xr-xml-map "crypto_ssh_cfg:Client";
        description "Provide SSH client service";
        leaf host-public-key {
          xr:xr-xml-map "crypto_ssh_cfg:HostPublicKey";
          type string;
          description "Filename - where to store known host file";
        }
        leaf client-vrf {
          xr:xr-xml-map "crypto_ssh_cfg:ClientVRF";
          type xr:Cisco-ios-xr-string {
            length "0..32";
          }
          description
            "Source interface VRF for ssh client sessions";
        }
        leaf source-interface {
          xr:xr-xml-map "crypto_ssh_cfg:SourceInterface";
          type xr:Interface-name;
          description "Source interface for ssh client sessions";
        }
        uses DSCP;
      }

      container server {
        xr:xr-xml-map "crypto_ssh_cfg:Server";
        description "Provide SSH server service";

        container vrf-table {
          xr:xr-xml-map "crypto_ssh_cfg:VRFTable";
          description "Cisco sshd VRF name";
          uses VRF;
        }

        container netconf-vrf-table {
          xr:xr-xml-map "crypto_ssh_cfg:NetconfVRFTable";
          description "Cisco sshd Netconf VRF name";
          uses VRF;
        }
        leaf session-limit {
          xr:xr-xml-map "crypto_ssh_cfg:SessionLimit";
          type uint32 {
            range "1..1024";
          }
          description
            "Cisco sshd session-limit of service requests";
        }
        leaf netconf {
          xr:xr-xml-map "crypto_ssh_cfg:Netconf";
          type uint32 {
            range "1..65535";
          }
          default "830";
          description
            "port number on which ssh service to be started
            for netconf";
        }
        leaf v2 {
          xr:xr-xml-map "crypto_ssh_cfg:V2";
          type empty;
          description "Cisco sshd force protocol version 2 only";
        }
        leaf logging {
          xr:xr-xml-map "crypto_ssh_cfg:Logging";
          type empty;
          description "Enable ssh server logging";
        }
        leaf rate-limit {
          xr:xr-xml-map "crypto_ssh_cfg:RateLimit";
          type uint32 {
            range "1..600";
          }
          default "60";
          description "Cisco sshd rate-limit of service requests";
        }
        leaf timeout {
          xr:xr-xml-map "crypto_ssh_cfg:Timeout";
          type uint32 {
            range "5..120";
          }
          default "30";
          description
            "Timeout value between 5-120 seconds defalut 30";
        }
        uses DSCP;
      }
    }
    description
      "This augment extends the configuration data of
      'Cisco-IOS-XR-crypto-sam-cfg'";
  }
}
