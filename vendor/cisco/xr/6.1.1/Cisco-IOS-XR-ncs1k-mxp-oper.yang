module Cisco-IOS-XR-ncs1k-mxp-oper {

  /*** NAMESPACE / PREFIX DEFINITION ***/

  namespace "http://cisco.com/ns/yang/Cisco-IOS-XR-ncs1k-mxp-oper";


  prefix "ncs1k-mxp-oper";

  /*** LINKAGE (IMPORTS / INCLUDES) ***/

  import Cisco-IOS-XR-types { prefix "xr"; }

  include Cisco-IOS-XR-ncs1k-mxp-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ncs1k-mxp package operational data.

     This module contains definitions
     for the following management objects:
       hw-module: mxp hw-module command chain

     Copyright (c) 2013-2016 by Cisco Systems, Inc.
     All rights reserved.";

  revision "2015-11-09" {
    description
      "IOS XR 6.0 revision.";
  }


  container hw-module {
    xr:xr-xml-map "mxp_show_oper:HwModule";
    config false;
    description "mxp hw-module command chain";

    container slice-ids {
      xr:xr-xml-map "mxp_show_hwmod:SliceTable";
      description "Slice information";

      list slice-id {
        xr:xr-xml-map "mxp_show_hwmod:SliceId";
        key "slice-num";
        description "Per slice num data";
        leaf slice-num {
          xr:xr-xml-map "mxp_show_hwmod:SliceNum";
          type int32;
          description
            "Details associated with a particular slice
            number";
        }
        uses MXP-HWMOD-OP;
      }
    }

    container slice-all {
      xr:xr-xml-map "mxp_show_hwmod:SliceAll";
      description "Information for all slices";
      uses MXP-HWMOD-OP;
    }
  }
}
