module Cisco-IOS-XR-controller-optics-oper {

  /*** NAMESPACE / PREFIX DEFINITION ***/

  namespace "http://cisco.com/ns/yang"+
    "/Cisco-IOS-XR-controller-optics-oper";


  prefix "controller-optics-oper";

  /*** LINKAGE (IMPORTS / INCLUDES) ***/

  import Cisco-IOS-XR-types { prefix "xr"; }

  include Cisco-IOS-XR-controller-optics-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR controller-optics package operational data.

     This module contains definitions
     for the following management objects:
       optics-oper: Optics operational data

     Copyright (c) 2013-2016 by Cisco Systems, Inc.
     All rights reserved.";

  revision "2015-11-09" {
    description
      "IOS XR 6.0 revision.";
  }


  container optics-oper {
    xr:xr-xml-map "optics_controller_oper:OpticsOper";
    config false;
    description "Optics operational data";

    container optics-ports {
      xr:xr-xml-map "optics_controller_oper:OpticsPortTable";
      description "All Optics Port operational data";

      list optics-port {
        xr:xr-xml-map "optics_controller_oper:OpticsPort";
        key "name";
        description "Optics operational data";

        container optics-dwdm-carrrier-channel-map {
          xr:xr-xml-map "optics_controller_oper:OpticsDWDMCarrrierC"+
            "hannelMap";
          description "Optics operational data";
          uses OPTICS-EDM-WAVE-INFO;
        }

        container optics-info {
          xr:xr-xml-map "optics_controller_oper:OpticsInfo";
          description "Optics operational data";
          uses OPTICS-EDM-INFO;
        }

        container optics-lanes {
          xr:xr-xml-map "optics_controller_oper:OpticsLaneTable";
          description "All Optics Port operational data";

          list optics-lane {
            xr:xr-xml-map "optics_controller_oper:OpticsLane";
            key "number";
            description "Lane Information";
            leaf number {
              xr:xr-xml-map "optics_controller_oper:Number";
              type int32;
              description "Lane Index";
            }
            uses OPTICS-EDM-LANE-DATA;
          }
        }

        container optics-db-info {
          xr:xr-xml-map "optics_controller_oper:OpticsDbInfo";
          description "Optics operational data";
          uses OPTICS-DB-INFO;
        }
        leaf name {
          xr:xr-xml-map "optics_controller_oper:Name";
          type xr:Interface-name;
          description "Port name";
        }
      }
    }
  }
}
