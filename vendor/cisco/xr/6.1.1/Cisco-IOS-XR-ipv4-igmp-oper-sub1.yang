submodule Cisco-IOS-XR-ipv4-igmp-oper-sub1 {

  belongs-to Cisco-IOS-XR-ipv4-igmp-oper {
    prefix Cisco-IOS-XR-ipv4-igmp-oper;
  }

  /*** LINKAGE (IMPORTS / INCLUDES) ***/

  import ietf-inet-types { prefix "inet"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR ipv4-igmp package operational data.

     Copyright (c) 2013-2016 by Cisco Systems, Inc.
     All rights reserved.";

  revision "2015-11-09" {
    description
      "IOS XR 6.0 revision.";
  }

  typedef Igmp-edm-protocol {
    type enumeration {
      enum no-route {
        value 0;
        description "no route";
      }
      enum sm {
        value 1;
        description "sm";
      }
      enum dm {
        value 2;
        description "dm";
      }
      enum bidir {
        value 3;
        description "bidir";
      }
      enum ssm {
        value 4;
        description "ssm";
      }
      enum any {
        value 6;
        description "any";
      }
    }
    description "IGMP Protocol";
  }
  typedef Ipv6-address {
    type inet:ipv6-address;
    description "IPV6 Address type";
  }
  typedef Igmp-afi {
    type enumeration {
      enum ipv4-unicast {
        value 0;
        description "IP v4 unicast";
      }
      enum ipv6-unicast {
        value 1;
        description "IP v6 unicast";
      }
    }
    description "Address family";
  }
  typedef Im-state {
    type uint32;
    description "Im state";
  }

  grouping IGMP-EDM-NSF-BAG {
    description "IGMP NSF state";
    leaf is-multicast-nsf-active {
      xr:xr-xml-map "ipv4_igmp:IsMulticastNSFActive";
      type boolean;
      description "Is Multicast NSF active";
    }
    leaf multicast-nsf-timeout {
      xr:xr-xml-map "ipv4_igmp:MulticastNSFTimeout";
      type uint32;
      units "second";
      description "Multicast NSF timeout in secs";
    }
    leaf multicast-nsf-time-left {
      xr:xr-xml-map "ipv4_igmp:MulticastNSFTimeLeft";
      type uint32;
      units "second";
      description "Multicast NSF time remaining in secs";
    }
    leaf respawn-count {
      xr:xr-xml-map "ipv4_igmp:RespawnCount";
      type uint32;
      description "Respawn Count";
    }
    leaf last-nsf-on {
      xr:xr-xml-map "ipv4_igmp:LastNSFOn";
      type int64;
      description "Last NSF time ON";
    }
    leaf last-nsf-off {
      xr:xr-xml-map "ipv4_igmp:LastNSFOff";
      type int64;
      description "Last NSF time off";
    }
    leaf last-nsf-on-min {
      xr:xr-xml-map "ipv4_igmp:LastNSFOnMin";
      type int32;
      units "second";
      description "Last NSF time ON in Seconds";
    }
    leaf last-nsf-off-min {
      xr:xr-xml-map "ipv4_igmp:LastNSFOffMin";
      type int32;
      units "second";
      description "Last NSF time OFF in Seconds";
    }
    leaf last-icd-notif-recv {
      xr:xr-xml-map "ipv4_igmp:LastICDNotifRecv";
      type int64;
      description "Last ICD Notif Recv";
    }
    leaf last-icd-notif-recv-min {
      xr:xr-xml-map "ipv4_igmp:LastICDNotifRecvMin";
      type int32;
      units "second";
      description "Last ICD Notif Recv in Seconds";
    }
  }

  grouping IGMP-EDM-BVI-STATS-BAG {
    description "IGMP EDM BVI STATS BAG";
    leaf receive-buffers {
      xr:xr-xml-map "ipv4_igmp:ReceiveBuffers";
      type uint32;
      description "Number of AIPC buffers received";
    }
    leaf release-buffers {
      xr:xr-xml-map "ipv4_igmp:ReleaseBuffers";
      type uint32;
      description "Number of AIPC buffers released";
    }
    leaf send-blocks {
      xr:xr-xml-map "ipv4_igmp:SendBlocks";
      type uint32;
      description "Number of AIPC buffers send blocked";
    }
    leaf release-fail-buffers {
      xr:xr-xml-map "ipv4_igmp:ReleaseFailBuffers";
      type uint32;
      description "Number of AIPC buffers release failed";
    }
    leaf null-buffer-handles {
      xr:xr-xml-map "ipv4_igmp:NullBufferHandles";
      type uint32;
      description "Number of AIPC NULL buffer handles";
    }
    leaf rx-ipc-open-notif {
      xr:xr-xml-map "ipv4_igmp:RxIPCOpenNotif";
      type uint32;
      description "Number of AIPC open notifications received";
    }
    leaf rx-ipc-close-notif {
      xr:xr-xml-map "ipv4_igmp:RxIPCCloseNotif";
      type uint32;
      description "Number of AIPC close notifications received";
    }
    leaf rx-ipc-error-notif {
      xr:xr-xml-map "ipv4_igmp:RxIPCErrorNotif";
      type uint32;
      description "Number of AIPC error notifications received";
    }
    leaf rx-ipc-lwm-notif {
      xr:xr-xml-map "ipv4_igmp:RxIPC_LWMNotif";
      type uint32;
      description "Number of AIPC LWM notifications received";
    }
    leaf rx-ipc-input-wait-notif {
      xr:xr-xml-map "ipv4_igmp:RxIPCInputWaitNotif";
      type uint32;
      description
        "Number of AIPC input waiting notifications
        received";
    }
    leaf rx-ipc-send-status-notif {
      xr:xr-xml-map "ipv4_igmp:RxIPCSendStatusNotif";
      type uint32;
      description
        "Number of AIPC send status notifications
        received";
    }
    leaf rx-ipc-publish-notif {
      xr:xr-xml-map "ipv4_igmp:RxIPCPublishNotif";
      type uint32;
      description "Number of AIPC publish notifications received";
    }
    leaf rx-ipc-q-full-notif {
      xr:xr-xml-map "ipv4_igmp:RxIPC_QFullNotif";
      type uint32;
      description
        "Number of AIPC queue full notifications received";
    }
    leaf rx-ipc-output-notif {
      xr:xr-xml-map "ipv4_igmp:RxIPCOutputNotif";
      type uint32;
      description "Number of AIPC output notifications received";
    }
    leaf rx-ipc-connect-notif {
      xr:xr-xml-map "ipv4_igmp:RxIPCConnectNotif";
      type uint32;
      description "Number of AIPC connect notifications received";
    }
    leaf rx-igmp-packet-success {
      xr:xr-xml-map "ipv4_igmp:RxIGMPPacketSuccess";
      type uint32;
      description "Number of IGMP protocol messages received";
    }
    leaf rx-add-mrouter-msg {
      xr:xr-xml-map "ipv4_igmp:RxAddMrouterMsg";
      type uint32;
      description "Number of IGMP Mrouter Add messages received";
    }
    leaf rx-delete-mrouter-msg {
      xr:xr-xml-map "ipv4_igmp:RxDeleteMrouterMsg";
      type uint32;
      description "Number of IGMP Mrouter Delete messages received";
    }
    leaf rx-sweep-mrouter-msg {
      xr:xr-xml-map "ipv4_igmp:RxSweepMrouterMsg";
      type uint32;
      description "Number of IGMP Mrouter Sweep messages received";
    }
    leaf tx-add-mrouter-msg {
      xr:xr-xml-map "ipv4_igmp:TxAddMrouterMsg";
      type uint32;
      description "Number of IGMP Mrouter Add messages transmitted";
    }
    leaf tx-delete-mrouter-msg {
      xr:xr-xml-map "ipv4_igmp:TxDeleteMrouterMsg";
      type uint32;
      description
        "Number of IGMP Mrouter Delete messages
        transmitted";
    }
    leaf tx-sweep-mrouter-msg {
      xr:xr-xml-map "ipv4_igmp:TxSweepMrouterMsg";
      type uint32;
      description "Number of IGMP Mrouter Sweep messages received";
    }
    leaf rx-unknown-mrouter-msg {
      xr:xr-xml-map "ipv4_igmp:RxUnknownMrouterMsg";
      type uint32;
      description
        "Number of IGMP Mrouter Unknown messages received";
    }
    leaf tx-unknown-mrouter-msg {
      xr:xr-xml-map "ipv4_igmp:TxUnknownMrouterMsg";
      type uint32;
      description
        "Number of IGMP Mrouter Unknown messages
        transmitted";
    }
    leaf tx-buffer-errors {
      xr:xr-xml-map "ipv4_igmp:TxBufferErrors";
      type uint32;
      description "Number of AIPC transmission errors";
    }
    leaf tx-buffers {
      xr:xr-xml-map "ipv4_igmp:TxBuffers";
      type uint32;
      description "Number of AIPC buffers transmited";
    }
    leaf tx-protocol-buffers {
      xr:xr-xml-map "ipv4_igmp:TxProtocolBuffers";
      type uint32;
      description "Number of IGMP protocol buffers transmitted";
    }
    leaf tx-mrouter-buffers {
      xr:xr-xml-map "ipv4_igmp:TxMrouterBuffers";
      type uint32;
      description "Number of IGMP Mrouter buffers transmitted";
    }
    leaf tx-unknown-buffers {
      xr:xr-xml-map "ipv4_igmp:TxUnknownBuffers";
      type uint32;
      description "Number of IGMP Unknown buffers transmited";
    }
    leaf wtx-msg-recvd {
      xr:xr-xml-map "ipv4_igmp:WtxMsgRecvd";
      type uint32;
      description "Number of WTX messages received";
    }
    leaf wtx-msg-sent {
      xr:xr-xml-map "ipv4_igmp:WtxMsgSent";
      type uint32;
      description "Number of WTX messages sent";
    }
    leaf wtx-msg-proto-sent {
      xr:xr-xml-map "ipv4_igmp:WtxMsgProtoSent";
      type uint32;
      description "Number of WTX messages sent to Protocol";
    }
    leaf wtx-msg-drop-dc {
      xr:xr-xml-map "ipv4_igmp:WtxMsgDropDc";
      type uint32;
      description
        "Number of WTX messages dropped due to disconnect";
    }
    leaf wtx-msg-drop-nomem {
      xr:xr-xml-map "ipv4_igmp:WtxMsgDropNomem";
      type uint32;
      description "Number of WTX messages dropped to memory";
    }
  }

  grouping IGMP-EDM-I2Q-STATS-BAG {
    description "IGMP Rate Adjust Stats";
    leaf queues {
      xr:xr-xml-map "ipv4_igmp:Queues";
      type uint16;
      description "I2Q Queue count";
    }
    leaf batches {
      xr:xr-xml-map "ipv4_igmp:Batches";
      type uint16;
      description "I2Q Rate Batch count";
    }
    leaf add-to-batches {
      xr:xr-xml-map "ipv4_igmp:AddToBatches";
      type uint32;
      description "Add to batch count";
    }
    leaf delete-to-batches {
      xr:xr-xml-map "ipv4_igmp:DeleteToBatches";
      type uint32;
      description "Delete to batch count";
    }
    leaf send-success {
      xr:xr-xml-map "ipv4_igmp:SendSuccess";
      type uint32;
      description "Send Success count";
    }
    leaf send-errors {
      xr:xr-xml-map "ipv4_igmp:SendErrors";
      type uint32;
      description "Number of Send errors in batch";
    }
    leaf send-comm-errors {
      xr:xr-xml-map "ipv4_igmp:SendCommErrors";
      type uint32;
      description "Send Error due to comms count";
    }
    leaf send-partial-errors {
      xr:xr-xml-map "ipv4_igmp:SendPartialErrors";
      type uint32;
      description "Send Error due to partial issue count";
    }
    leaf received-resync-requests {
      xr:xr-xml-map "ipv4_igmp:ReceivedResyncRequests";
      type uint32;
      description "Number of Resync request received";
    }
    leaf sent-resync-bulks {
      xr:xr-xml-map "ipv4_igmp:SentResyncBulks";
      type uint32;
      description "Number of bulks sent for last resync received";
    }
    leaf is-resync-received {
      xr:xr-xml-map "ipv4_igmp:IsResyncReceived";
      type boolean;
      description "Is Resync request received";
    }
    leaf is-resync-required {
      xr:xr-xml-map "ipv4_igmp:IsResyncRequired";
      type boolean;
      description "Is Resync required";
    }
    leaf is-resync-start-sent {
      xr:xr-xml-map "ipv4_igmp:IsResyncStartSent";
      type boolean;
      description "Is Resync Start message sent";
    }
    leaf is-qos-s-sweeped {
      xr:xr-xml-map "ipv4_igmp:IsQosSSweeped";
      type boolean;
      description "Is QOS Sweeped once ";
    }
    leaf last-sweep-time {
      xr:xr-xml-map "ipv4_igmp:LastSweepTime";
      type uint64;
      units "second";
      description
        "Time elapsed since Last mark and sweep in
        seconds";
    }
    leaf last-download-time {
      xr:xr-xml-map "ipv4_igmp:LastDownloadTime";
      type uint64;
      units "second";
      description
        "Time elapsed since Last download to QOS in
        seconds";
    }
  }

  grouping AMT-GW-BAG {
    description "AMT GW info";
    leaf amtgw {
      xr:xr-xml-map "ipv4_igmp:AMTGW";
      type inet:ipv4-address;
      description "GW";
    }
    leaf amt-port {
      xr:xr-xml-map "ipv4_igmp:AMTPort";
      type uint32;
      description "Port";
    }
    leaf key-len {
      xr:xr-xml-map "ipv4_igmp:KeyLen";
      type uint32;
      description "Len";
    }
    leaf amtnh {
      xr:xr-xml-map "ipv4_igmp:AMTNH";
      type uint32;
      description "AMT NH";
    }
    leaf amt-nonce {
      xr:xr-xml-map "ipv4_igmp:AMTNonce";
      type uint32;
      description "Nonce";
    }
    leaf idb {
      xr:xr-xml-map "ipv4_igmp:IDB";
      type uint64;
      description "IDB";
    }
    leaf mem-upd-in {
      xr:xr-xml-map "ipv4_igmp:MemUpdIn";
      type uint32;
      description "UpdIn";
    }
    leaf mem-upd-out {
      xr:xr-xml-map "ipv4_igmp:MemUpdOut";
      type uint32;
      description "UpdOut";
    }
  }

  grouping IGMP-EDM-NSR-BAG {
    description "IGMP NSR state";
    leaf state {
      xr:xr-xml-map "ipv4_igmp:State";
      type uint8;
      description "NSR state";
    }
    leaf partner-proc-connected {
      xr:xr-xml-map "ipv4_igmp:PartnerProcConnected";
      type boolean;
      description "Partner process connected";
    }
    leaf collab-conv-done {
      xr:xr-xml-map "ipv4_igmp:CollabConvDone";
      type boolean;
      description "Collaborators convergence done";
    }
    leaf rmf-notification-done {
      xr:xr-xml-map "ipv4_igmp:RMFNotificationDone";
      type boolean;
      description "RMF Notification done";
    }
    leaf last-proc {
      xr:xr-xml-map "ipv4_igmp:LastProc";
      type uint64;
      description "Time when process came up";
    }
    leaf last-proc-connection-up {
      xr:xr-xml-map "ipv4_igmp:LastProcConnectionUp";
      type uint64;
      description "Time when process connection went up";
    }
    leaf last-proc-connection-dn {
      xr:xr-xml-map "ipv4_igmp:LastProcConnectionDn";
      type uint64;
      description "Time when process connection went down";
    }
    leaf last-rmf-ready {
      xr:xr-xml-map "ipv4_igmp:LastRMFReady";
      type uint64;
      description "Time when RMF Rdy notif was sent";
    }
    leaf last-rmf-not-ready {
      xr:xr-xml-map "ipv4_igmp:LastRMFNotReady";
      type uint64;
      description "Time when RMF Not-Rdy notif was sent";
    }
    leaf count-proc-connection-up {
      xr:xr-xml-map "ipv4_igmp:CountProcConnectionUp";
      type uint32;
      description "No. of times process connection went up";
    }
    leaf count-proc-connection-dn {
      xr:xr-xml-map "ipv4_igmp:CountProcConnectionDn";
      type uint32;
      description "No. of times process connection went down";
    }
    leaf count-rmf-ready {
      xr:xr-xml-map "ipv4_igmp:CountRMFReady";
      type uint32;
      description "No. of times RMF Ready notif was sent";
    }
    leaf count-rmf-not-ready {
      xr:xr-xml-map "ipv4_igmp:CountRMFNotReady";
      type uint32;
      description "No. of times RMF Not Ready notif was sent";
    }
  }

  grouping AMT-SUMMARY-BAG {
    description "AMT summary info";
    leaf anycast-prefix {
      xr:xr-xml-map "ipv4_igmp:AnycastPrefix";
      type inet:ipv4-address;
      description "Robustness variable";
    }
    leaf prefix-length {
      xr:xr-xml-map "ipv4_igmp:PrefixLength";
      type uint32;
      description "Advertize AMT prefix length";
    }
    leaf relay-address {
      xr:xr-xml-map "ipv4_igmp:RelayAddress";
      type inet:ipv4-address;
      description "Advertaisment for AMT Relay address";
    }
    leaf mtu {
      xr:xr-xml-map "ipv4_igmp:MTU";
      type uint32;
      description "AMT Tunnel MTU";
    }
    leaf tos {
      xr:xr-xml-map "ipv4_igmp:TOS";
      type uint32;
      description "Type Of Service value in AMT header";
    }
    leaf ttl {
      xr:xr-xml-map "ipv4_igmp:TTL";
      type uint32;
      description "Time To Live value in AMT header";
    }
    leaf query-interval {
      xr:xr-xml-map "ipv4_igmp:QueryInterval";
      type uint32;
      description "AMT Query interval";
    }
    leaf gateway-count {
      xr:xr-xml-map "ipv4_igmp:GatewayCount";
      type uint32;
      description "Number of AMT Gateway";
    }
    leaf max-gateway {
      xr:xr-xml-map "ipv4_igmp:MaxGateway";
      type uint32;
      description "Maximum Gateway allowed";
    }
    leaf tunnel-count {
      xr:xr-xml-map "ipv4_igmp:TunnelCount";
      type uint32;
      description "AMT Tunnel Count";
    }
    leaf tunnel-configured-maximum {
      xr:xr-xml-map "ipv4_igmp:TunnelConfiguredMaximum";
      type uint32;
      description "AMT Tunnel configured Maximum";
    }
    leaf is-acl-configured {
      xr:xr-xml-map "ipv4_igmp:IsACLConfigured";
      type boolean;
      description "ACL configured under AMT";
    }
    leaf is-gateway-simulation {
      xr:xr-xml-map "ipv4_igmp:IsGatewaySimulation";
      type boolean;
      description "AMT Gateway Simulation";
    }
    leaf is-ou-of-resource {
      xr:xr-xml-map "ipv4_igmp:IsOuOfResource";
      type boolean;
      description "AMT Out Of Resource";
    }
  }

  grouping IGMP-EDM-SSM-MAP-DETAIL-BAG {
    description "IGMP SSM Map Detail List";

    container map-info {
      description "Basic Map Info";
      uses IGMP-EDM-SSM-MAP-BAG;
    }
    leaf expiration-time {
      xr:xr-xml-map "ipv4_igmp:ExpirationTime";
      type uint32;
      units "second";
      description "Expiration Time in Seconds";
    }
    leaf response-pending {
      xr:xr-xml-map "ipv4_igmp:ResponsePending";
      type boolean;
      description "Response Pending";
    }
    leaf query-interval {
      xr:xr-xml-map "ipv4_igmp:QueryInterval";
      type uint32;
      description "Query interval";
    }
    leaf elapsed-time {
      xr:xr-xml-map "ipv4_igmp:ElapsedTime";
      type uint64;
      description "Elapsed time";
    }

    list sources {
      description "List of sources";
      uses IGMP-ADDRTYPE;
    }
  }

  grouping IGMP-EDM-IDB-SUMM-BAG {
    description "IGMP Interface DB summary";
    leaf interface-count {
      xr:xr-xml-map "ipv4_igmp:InterfaceCount";
      type uint32;
      description "Interface Count";
    }
    leaf configuration-count {
      xr:xr-xml-map "ipv4_igmp:ConfigurationCount";
      type uint32;
      description "Configuration count";
    }
  }

  grouping IGMP-EDM-GROUPS-SUMMARY-BAG {
    description "IGMP group summary entry";
    leaf groutes {
      xr:xr-xml-map "ipv4_igmp:GRoutes";
      type uint32;
      description "No. of (*,G) routes";
    }
    leaf sg-routes {
      xr:xr-xml-map "ipv4_igmp:SGRoutes";
      type uint32;
      description "No. of (S,G) routes";
    }
    leaf group-count {
      xr:xr-xml-map "ipv4_igmp:GroupCount";
      type uint32;
      description "Current groups accepted";
    }
    leaf is-low-memory {
      xr:xr-xml-map "ipv4_igmp:IsLowMemory";
      type boolean;
      description "Node is running low on memory";
    }
  }

  grouping IGMP-EDM-TRAFFIC-BAG {
    description "IGMP Traffic Counters bag";
    leaf elapsed-time {
      xr:xr-xml-map "ipv4_igmp:ElapsedTime";
      type uint32;
      description "Running time for counters";
    }
    leaf packets-in {
      xr:xr-xml-map "ipv4_igmp:PacketsIn";
      type uint32;
      description "Packets in";
    }
    leaf packets-out {
      xr:xr-xml-map "ipv4_igmp:PacketsOut";
      type uint32;
      description "Packets out";
    }
    leaf format-errors {
      xr:xr-xml-map "ipv4_igmp:FormatErrors";
      type uint32;
      description "Malformed packets in";
    }
    leaf packet-manager-input-errors {
      xr:xr-xml-map "ipv4_igmp:PacketManagerInputErrors";
      type uint32;
      description "Incoming Packet Manager packets dropped";
    }
    leaf packet-manager-output-errors {
      xr:xr-xml-map "ipv4_igmp:PacketManagerOutputErrors";
      type uint32;
      description "Outgoing Packet Manager packets dropped";
    }
    leaf checksum-errors {
      xr:xr-xml-map "ipv4_igmp:ChecksumErrors";
      type uint32;
      description "Checksum errors";
    }
    leaf receive-socket-errors {
      xr:xr-xml-map "ipv4_igmp:ReceiveSocketErrors";
      type uint32;
      description "Socket errors on reception";
    }
    leaf socket-errors {
      xr:xr-xml-map "ipv4_igmp:SocketErrors";
      type uint32;
      description "Socket errors on send";
    }
    leaf bad-scope-errors {
      xr:xr-xml-map "ipv4_igmp:BadScopeErrors";
      type uint32;
      description "BadScope errors";
    }
    leaf auxillary-data-length-errors {
      xr:xr-xml-map "ipv4_igmp:AuxillaryDataLengthErrors";
      type uint32;
      description "AuxDataLen errors";
    }
    leaf invalid-source-address-errors {
      xr:xr-xml-map "ipv4_igmp:InvalidSourceAddressErrors";
      type uint32;
      description "Invalid Source Address errors";
    }
    leaf no-socket-connection {
      xr:xr-xml-map "ipv4_igmp:NoSocketConnection";
      type uint32;
      description "Packets dropped since no socket connection";
    }
    leaf miscellaneous-errors {
      xr:xr-xml-map "ipv4_igmp:MiscellaneousErrors";
      type uint32;
      description "Packets dropped for other reasons";
    }
    leaf input-queries {
      xr:xr-xml-map "ipv4_igmp:InputQueries";
      type uint32;
      description "Query packets in";
    }
    leaf input-reports {
      xr:xr-xml-map "ipv4_igmp:InputReports";
      type uint32;
      description "Reports in";
    }
    leaf input-leaves {
      xr:xr-xml-map "ipv4_igmp:InputLeaves";
      type uint32;
      description "Leaves in";
    }
    leaf input-mtrace {
      xr:xr-xml-map "ipv4_igmp:InputMtrace";
      type uint32;
      description "Mtrace packets in";
    }
    leaf input-dvmrp {
      xr:xr-xml-map "ipv4_igmp:InputDVMRP";
      type uint32;
      description "DVMRP packets in";
    }
    leaf input-pim {
      xr:xr-xml-map "ipv4_igmp:InputPIM";
      type uint32;
      description "PIM packets in";
    }
    leaf output-queries {
      xr:xr-xml-map "ipv4_igmp:OutputQueries";
      type uint32;
      description "Query packets out";
    }
    leaf output-reports {
      xr:xr-xml-map "ipv4_igmp:OutputReports";
      type uint32;
      description "Reports out";
    }
    leaf output-leaves {
      xr:xr-xml-map "ipv4_igmp:OutputLeaves";
      type uint32;
      description "Leaves out";
    }
    leaf output-mtrace {
      xr:xr-xml-map "ipv4_igmp:OutputMtrace";
      type uint32;
      description "Mtrace packets out";
    }
    leaf output-dvmrp {
      xr:xr-xml-map "ipv4_igmp:OutputDVMRP";
      type uint32;
      description "DVMRP packets out";
    }
    leaf output-pim {
      xr:xr-xml-map "ipv4_igmp:OutputPIM";
      type uint32;
      description "PIM packets out";
    }
    leaf get-packet-failure {
      xr:xr-xml-map "ipv4_igmp:GetPacketFailure";
      type uint32;
      description "Packet get failed";
    }
    leaf output-no-parent-interface-handle {
      xr:xr-xml-map "ipv4_igmp:OutputNoParentInterfaceHandle";
      type uint32;
      description "Failures setting 2nd ifhandle";
    }
    leaf input-no-idb {
      xr:xr-xml-map "ipv4_igmp:InputNoIDB";
      type uint32;
      description "Packets received without idb";
    }
    leaf input-no-vrf-in-idb {
      xr:xr-xml-map "ipv4_igmp:InputNoVRFInIDB";
      type uint32;
      description "Packets received on idb without VRF";
    }
    leaf input-disabled-idb {
      xr:xr-xml-map "ipv4_igmp:InputDisabledIDB";
      type uint32;
      description "Packet received on disabled idb";
    }
    leaf input-martian-address {
      xr:xr-xml-map "ipv4_igmp:InputMartianAddress";
      type uint32;
      description "Packets received with Martian Address";
    }
    leaf input-no-assigned-vrf-id {
      xr:xr-xml-map "ipv4_igmp:InputNoAssignedVRF_ID";
      type uint32;
      description "Packets received with no assigned vrf id";
    }
    leaf input-no-vrf-mtrace {
      xr:xr-xml-map "ipv4_igmp:InputNoVRFMtrace";
      type uint32;
      description "mtrace packets with no vrf associated";
    }
    leaf input-no-platform-support-mtrace {
      xr:xr-xml-map "ipv4_igmp:InputNoPlatformSupportMtrace";
      type uint32;
      description "mtrace packets without platform support";
    }
  }

  grouping IGMP-EDM-IDB-IFRS-BAG {
    description "IGMP IFRS interface entry";

    container igmp-interface-entry {
      description "IGMP interface entry";
      uses IGMP-EDM-IDB-BAG;
    }
    leaf join-group-count {
      xr:xr-xml-map "ipv4_igmp:JoinGroupCount";
      type uint32;
      description "Join group count";
    }
  }

  grouping IGMP-GROUP-RANGE {
    description "IGMP Group-Map Range";

    container group-address-xr {
      description "Group address";
      uses IGMP-ADDRTYPE;
    }
    leaf prefix-length {
      xr:xr-xml-map "ipv4_igmp:PrefixLength";
      type uint32;
      description "Prefix length";
    }
    leaf protocol {
      xr:xr-xml-map "ipv4_igmp:Protocol";
      type Igmp-edm-protocol;
      description "Protocol";
    }
    leaf is-stale {
      xr:xr-xml-map "ipv4_igmp:IsStale";
      type boolean;
      description "Is the entry stale";
    }
  }

  grouping IGMP-EDM-I2Q-INTF-RATE-BAG {
    description "IGMP-QOS Interface Rate";

    container source-address {
      description "Source address";
      uses IGMP-ADDRTYPE;
    }

    container group-address {
      description "Group address";
      uses IGMP-ADDRTYPE;
    }
    leaf is-add {
      xr:xr-xml-map "ipv4_igmp:IsAdd";
      type boolean;
      description "Is this a rate increment";
    }
    leaf weight {
      xr:xr-xml-map "ipv4_igmp:Weight";
      type uint32;
      description "Weight from policy";
    }
    leaf received-time {
      xr:xr-xml-map "ipv4_igmp:ReceivedTime";
      type uint64;
      description "Time this update is received";
    }
  }

  grouping IGMP-EDM-I2Q-INTF-STATS-BAG {
    description "IGMP-QOS Interface Stats";
    leaf is-virtual-access {
      xr:xr-xml-map "ipv4_igmp:IsVirtualAccess";
      type boolean;
      description "Is VirtualAccess Interface";
    }
    leaf rate {
      xr:xr-xml-map "ipv4_igmp:Rate";
      type uint32;
      units "kbit/s";
      description "Overall rate in Kbps";
    }
    leaf rate-increments {
      xr:xr-xml-map "ipv4_igmp:RateIncrements";
      type uint32;
      description "Count of rate increments";
    }
    leaf rate-decrements {
      xr:xr-xml-map "ipv4_igmp:RateDecrements";
      type uint32;
      description "Count of rate decrements";
    }

    list update {
      max-elements "5";
      description "List of updates";
      uses IGMP-EDM-I2Q-INTF-RATE-BAG;
    }
  }

  grouping IGMP-EDM-GROUPS-HOST-BAG {
    description "IGMP Groups host entry";

    container address {
      description "Host Address";
      uses IGMP-ADDRTYPE;
    }
    leaf uptime {
      xr:xr-xml-map "ipv4_igmp:Uptime";
      type uint32;
      units "second";
      description "Uptime in seconds";
    }
    leaf is-exclude {
      xr:xr-xml-map "ipv4_igmp:IsExclude";
      type boolean;
      description "Exclude flag set";
    }
    leaf expiration-time {
      xr:xr-xml-map "ipv4_igmp:ExpirationTime";
      type uint32;
      units "second";
      description "Expiration time in seconds";
    }
    leaf source-count {
      xr:xr-xml-map "ipv4_igmp:SourceCount";
      type uint32;
      description "No. of sources in entry";
    }

    list source-address {
      max-elements "3";
      description "First 3 source addresses";
      uses IGMP-ADDRTYPE;
    }
  }

  grouping IGMP-EDM-GROUPS-ET-BAG {
    description "IGMP group explicit-tracking entry";

    container group-info {
      description "Basic Group information";
      uses IGMP-EDM-GROUPS-BAG;
    }
    leaf include-hosts {
      xr:xr-xml-map "ipv4_igmp:IncludeHosts";
      type uint32;
      description "No. of hosts who are included";
    }
    leaf exclude-hosts {
      xr:xr-xml-map "ipv4_igmp:ExcludeHosts";
      type uint32;
      description "No. of hosts who are excluded";
    }

    list host {
      description "List of hosts";
      uses IGMP-EDM-GROUPS-HOST-BAG;
    }
  }

  grouping IGMP-EDM-SSM-MAP-BAG {
    description "IGMP SSM Map List";

    container group-address-xr {
      description "Group Address";
      uses IGMP-ADDRTYPE;
    }
    leaf map-type {
      xr:xr-xml-map "ipv4_igmp:MapType";
      type uint32;
      description "Map Type of group";
    }
    leaf source-counts {
      xr:xr-xml-map "ipv4_igmp:SourceCounts";
      type uint32;
      description "Count of Sources";
    }
  }

  grouping IGMP-EDM-NOT-ACTIVE-GROUP-BAG {
    description "IGMP Non active group";

    container group-address {
      description "Group Address";
      uses IGMP-ADDRTYPE;
    }

    container source-address {
      description "Source Address";
      uses IGMP-ADDRTYPE;
    }
    leaf interface {
      xr:xr-xml-map "ipv4_igmp:Interface";
      type string {
        length "0..65";
      }
      description "Interface Name";
    }
    leaf reason-for-non-activity {
      xr:xr-xml-map "ipv4_igmp:ReasonForNonActivity";
      type string {
        length "0..257";
      }
      description "Reason for group join not being processed";
    }
  }

  grouping IGMP-EDM-NOT-ACTIVE-ALLGROUPS-BAG {
    description "IGMP Non active groups list";

    list non-active-groups {
      description "List of non-active groups";
      uses IGMP-EDM-NOT-ACTIVE-GROUP-BAG;
    }
  }

  grouping IGMP-EDM-GROUPS-SOURCE-BAG {
    description "IGMP Groups source entry";

    container source-address {
      description "Source Address";
      uses IGMP-ADDRTYPE;
    }
    leaf uptime {
      xr:xr-xml-map "ipv4_igmp:Uptime";
      type uint64;
      units "second";
      description "Uptime in seconds";
    }
    leaf expiration-time {
      xr:xr-xml-map "ipv4_igmp:ExpirationTime";
      type int32;
      units "second";
      description "Expiration time in seconds";
    }
    leaf is-local {
      xr:xr-xml-map "ipv4_igmp:IsLocal";
      type boolean;
      description "Is this a local source";
    }
    leaf is-remote {
      xr:xr-xml-map "ipv4_igmp:IsRemote";
      type boolean;
      description "Is this a remote source";
    }
    leaf is-forward {
      xr:xr-xml-map "ipv4_igmp:IsForward";
      type boolean;
      description "Should we forward on this entry";
    }
    leaf is-we-report {
      xr:xr-xml-map "ipv4_igmp:IsWeReport";
      type boolean;
      description "Should we report the source";
    }
    leaf flags {
      xr:xr-xml-map "ipv4_igmp:Flags";
      type int32;
      description "Source flags";
    }
    leaf is-added {
      xr:xr-xml-map "ipv4_igmp:IsAdded";
      type boolean;
      description "Joined";
    }
  }

  grouping IGMP-EDM-GROUPS-BAG {
    description "IGMP group entry";

    container group-address-xr {
      description "Group Address";
      uses IGMP-ADDRTYPE;
    }

    container last-reporter {
      description "Last reporter address";
      uses IGMP-ADDRTYPE;
    }

    container source-address {
      description "Source Address";
      uses IGMP-ADDRTYPE;
    }
    leaf interface-name-xr {
      xr:xr-xml-map "ipv4_igmp:interface-name-xr";
      type xr:Interface-name;
      description "Interface";
    }
    leaf uptime {
      xr:xr-xml-map "ipv4_igmp:Uptime";
      type uint64;
      units "second";
      description "Uptime in seconds";
    }
    leaf expiration-time {
      xr:xr-xml-map "ipv4_igmp:ExpirationTime";
      type int32;
      units "second";
      description "Expiration time in seconds";
    }
    leaf explicit-tracking-enabled {
      xr:xr-xml-map "ipv4_igmp:ExplicitTrackingEnabled";
      type boolean;
      description "Is explicit tracking enabled";
    }
    leaf is-self-join {
      xr:xr-xml-map "ipv4_igmp:IsSelfJoin";
      type boolean;
      description
        "If local system is member of this group on this
        interface";
    }
    leaf row-status {
      xr:xr-xml-map "ipv4_igmp:RowStatus";
      type string {
        length "0..16";
      }
      description "interface on or off for the group";
    }
    leaf is-low-memory {
      xr:xr-xml-map "ipv4_igmp:IsLowMemory";
      type boolean;
      description "Node is running low on memory";
    }
    leaf router-filter-mode {
      xr:xr-xml-map "ipv4_igmp:RouterFilterMode";
      type uint8;
      description "Filter mode";
    }
    leaf older-host-version1-timer {
      xr:xr-xml-map "ipv4_igmp:OlderHostVersion1Timer";
      type uint32;
      description "IGMP Hostversion1timer";
    }
    leaf older-host-version2-timer {
      xr:xr-xml-map "ipv4_igmp:OlderHostVersion2Timer";
      type uint32;
      description "IGMP Hostversion2timer";
    }
    leaf is-added {
      xr:xr-xml-map "ipv4_igmp:IsAdded";
      type boolean;
      description "Joined";
    }
    leaf is-suppressed {
      xr:xr-xml-map "ipv4_igmp:IsSuppressed";
      type boolean;
      description "Suppressed";
    }
  }

  grouping IGMP-EDM-GROUPS-DETAIL-BAG {
    description "IGMP group detail entry";

    container group-info {
      description "Basic Group information";
      uses IGMP-EDM-GROUPS-BAG;
    }
    leaf is-router-exclude-mode {
      xr:xr-xml-map "ipv4_igmp:IsRouterExcludeMode";
      type boolean;
      description "Group router filter mode";
    }
    leaf is-host-exclude-mode {
      xr:xr-xml-map "ipv4_igmp:IsHostExcludeMode";
      type boolean;
      description "Group host filter mode";
    }

    list source {
      description "List of sources";
      uses IGMP-EDM-GROUPS-SOURCE-BAG;
    }
  }

  grouping IGMP-ADDRTYPE {
    description "IGMP ADDRTYPE";
    leaf af-name {
      xr:xr-xml-map "ipv4_igmp:AFName";
      type Igmp-afi;
      description "AFName";
    }
    leaf ipv4-address {
      xr:xr-xml-map "ipv4_igmp:IPV4Address";
      when "../af-name = 'ipv4-unicast'" {
        description "../AFName = 'IPv4Unicast'";
      }
      type inet:ipv4-address;
      description "IPv4 Addr";
    }
    leaf ipv6-address {
      xr:xr-xml-map "ipv4_igmp:IPV6Address";
      when "../af-name = 'ipv6-unicast'" {
        description "../AFName = 'IPv6Unicast'";
      }
      type Ipv6-address;
      description "IPV6 Addr";
    }
  }

  grouping IGMP-EDM-IDB-BAG {
    description "IGMP interface entry";

    container address {
      description "IP address";
      uses IGMP-ADDRTYPE;
    }

    container querier-address {
      description "Address of the Querier";
      uses IGMP-ADDRTYPE;
    }

    container subscriber-address {
      description "Address of subscriber";
      uses IGMP-ADDRTYPE;
    }
    leaf interface-name-xr {
      xr:xr-xml-map "ipv4_igmp:interface-name-xr";
      type xr:Interface-name;
      description "Interface";
    }
    leaf state {
      xr:xr-xml-map "ipv4_igmp:State";
      type Im-state;
      description "Interface state";
    }
    leaf prefix-length {
      xr:xr-xml-map "ipv4_igmp:PrefixLength";
      type uint32;
      description "Prefix length";
    }
    leaf is-interface-up {
      xr:xr-xml-map "ipv4_igmp:IsInterfaceUp";
      type boolean;
      description "Is interface up";
    }
    leaf is-ip-enabled {
      xr:xr-xml-map "ipv4_igmp:IsIPEnabled";
      type boolean;
      description "Is IP enabled";
    }
    leaf is-router-enabled {
      xr:xr-xml-map "ipv4_igmp:IsRouterEnabled";
      type boolean;
      description "Is Router functionality enabled";
    }
    leaf igmp-version {
      xr:xr-xml-map "ipv4_igmp:IGMPVersion";
      type uint8;
      description "IGMP Router version";
    }
    leaf host-version {
      xr:xr-xml-map "ipv4_igmp:HostVersion";
      type uint8;
      description "IGMP Host version";
    }
    leaf query-interval {
      xr:xr-xml-map "ipv4_igmp:QueryInterval";
      type uint16;
      units "second";
      description "Query Interval value in seconds";
    }
    leaf query-timeout {
      xr:xr-xml-map "ipv4_igmp:QueryTimeout";
      type uint16;
      description "Query Timeout value";
    }
    leaf query-maximum-response-time {
      xr:xr-xml-map "ipv4_igmp:QueryMaximumResponseTime";
      type uint16;
      description "Max Response Timeout value";
    }
    leaf last-member-query-interval {
      xr:xr-xml-map "ipv4_igmp:LastMemberQueryInterval";
      type uint16;
      description "Last Member Query Interval";
    }
    leaf group-joins {
      xr:xr-xml-map "ipv4_igmp:GroupJoins";
      type uint32;
      description "No. of group joins";
    }
    leaf group-leaves {
      xr:xr-xml-map "ipv4_igmp:GroupLeaves";
      type uint32;
      description "No. of group leaves";
    }
    leaf is-querier {
      xr:xr-xml-map "ipv4_igmp:IsQuerier";
      type boolean;
      description "Are we querier";
    }
    leaf total-active-groups {
      xr:xr-xml-map "ipv4_igmp:TotalActiveGroups";
      type uint32;
      description "Actual number of groups on interface";
    }
    leaf robustness {
      xr:xr-xml-map "ipv4_igmp:Robustness";
      type uint32;
      description "Robustness Variable value";
    }
    leaf proxy-interface {
      xr:xr-xml-map "ipv4_igmp:ProxyInterface";
      type xr:Interface-name;
      description "Proxy interface index";
    }
    leaf querier-uptime {
      xr:xr-xml-map "ipv4_igmp:QuerierUptime";
      type uint16;
      description "Time since the last querier took over";
    }
    leaf las-ll-registration-count {
      xr:xr-xml-map "ipv4_igmp:LAS_LLRegistrationCount";
      type uint32;
      description "LAS reg count";
    }
    leaf las-get-address-count {
      xr:xr-xml-map "ipv4_igmp:LASGetAddressCount";
      type uint32;
      description "LAS get addr count";
    }
    leaf las-update-count {
      xr:xr-xml-map "ipv4_igmp:LASUpdateCount";
      type uint32;
      description "LAS Update count";
    }
    leaf las-ll-remove-update-count {
      xr:xr-xml-map "ipv4_igmp:LAS_LLRemoveUpdateCount";
      type uint32;
      description "LAS LL remove update count";
    }
    leaf las-ll-add-update-count {
      xr:xr-xml-map "ipv4_igmp:LAS_LLAddUpdateCount";
      type uint32;
      description "LAS LL add update count";
    }
    leaf las-null-update-count {
      xr:xr-xml-map "ipv4_igmp:LASNullUpdateCount";
      type uint32;
      description "LAS Null update count";
    }
    leaf las-unregistration-count {
      xr:xr-xml-map "ipv4_igmp:LASUnregistrationCount";
      type uint32;
      description "LAS unreg count";
    }
    leaf is-las-request {
      xr:xr-xml-map "ipv4_igmp:IsLASRequest";
      type boolean;
      description "LAS req";
    }
    leaf is-las-registered {
      xr:xr-xml-map "ipv4_igmp:IsLASRegistered";
      type boolean;
      description "LAS registered";
    }
    leaf vrf-id {
      xr:xr-xml-map "ipv4_igmp:VRF_ID";
      type uint32;
      description "VRF id";
    }
    leaf mte-vrf-id {
      xr:xr-xml-map "ipv4_igmp:MTE_VRF_ID";
      type uint32;
      description "MTE VRF id";
    }
    leaf location {
      xr:xr-xml-map "ipv4_igmp:Location";
      type uint32;
      description "Location";
    }
    leaf mtu {
      xr:xr-xml-map "ipv4_igmp:MTU";
      type uint32;
      description "MTU";
    }
    leaf vrf-state {
      xr:xr-xml-map "ipv4_igmp:VRFState";
      type uint32;
      description "Vrf State";
    }
    leaf is-configurationverify {
      xr:xr-xml-map "ipv4_igmp:IsConfigurationVerify";
      type boolean;
      description "CFG verify";
    }
    leaf configurationvrf-set {
      xr:xr-xml-map "ipv4_igmp:ConfigurationVRFSet";
      type boolean;
      description "CFG vrf set";
    }
    leaf configurationvrf-error {
      xr:xr-xml-map "ipv4_igmp:ConfigurationVRFError";
      type boolean;
      description "CFG vrf error";
    }
    leaf configuration-mcast-vrf-set {
      xr:xr-xml-map "ipv4_igmp:ConfigurationMcastVRFSet";
      type boolean;
      description "Is mcast set";
    }
    leaf configuration-mcast-vrf-error {
      xr:xr-xml-map "ipv4_igmp:ConfigurationMcastVRFError";
      type boolean;
      description "Is mcast error";
    }
    leaf is-im-state-registered {
      xr:xr-xml-map "ipv4_igmp:IsIMStateRegistered";
      type boolean;
      description "Im state registered";
    }
    leaf is-subscriber {
      xr:xr-xml-map "ipv4_igmp:IsSubscriber";
      type boolean;
      description "Subscriber interface";
    }
    leaf subscriber-mode {
      xr:xr-xml-map "ipv4_igmp:SubscriberMode";
      type uint32;
      description "Subscriber mode";
    }
    leaf is-identity-present {
      xr:xr-xml-map "ipv4_igmp:IsIdentityPresent";
      type boolean;
      description "Subscriber ID or Address available from AAA";
    }
    leaf subscriber-id {
      xr:xr-xml-map "ipv4_igmp:SubscriberID";
      type string {
        length "0..257";
      }
      description "ID string of subscriber";
    }
    leaf parent-ifhandle {
      xr:xr-xml-map "ipv4_igmp:ParentIfhandle";
      type xr:Interface-name;
      description "Parent If Handle";
    }
    leaf time-since-last-query-in-seconds {
      xr:xr-xml-map "ipv4_igmp:TimeSinceLastQueryInSeconds";
      type uint32;
      description "Time elapsed since last query";
    }
    leaf time-since-last-report-in-seconds {
      xr:xr-xml-map "ipv4_igmp:TimeSinceLastReportInSeconds";
      type uint32;
      description "Time elapsed since last report";
    }
    leaf router-uptime-in-seconds {
      xr:xr-xml-map "ipv4_igmp:RouterUptimeInSeconds";
      type uint32;
      description "Uptime since router enabled event";
    }
    leaf mte-tuple-count {
      xr:xr-xml-map "ipv4_igmp:MteTupleCount";
      type uint32;
      description "MTE Tuple count";
    }
  }

  grouping IGMP-EDM-INTF-SUMMARY-BAG {
    description "IGMP interface summary info";
    leaf interface-name {
      xr:xr-xml-map "ipv4_igmp:InterfaceName";
      type xr:Interface-name;
      description "Interface";
    }
    leaf group-limit {
      xr:xr-xml-map "ipv4_igmp:GroupLimit";
      type uint32;
      description "Maximum groups accepted per interface";
    }
    leaf group-count {
      xr:xr-xml-map "ipv4_igmp:GroupCount";
      type uint32;
      description "Current groups accepted per interface";
    }
    leaf parent-ifhandle {
      xr:xr-xml-map "ipv4_igmp:ParentIfhandle";
      type xr:Interface-name;
      description "Parent if handle";
    }
    leaf on-off {
      xr:xr-xml-map "ipv4_igmp:OnOff";
      type boolean;
      description "Enabled/Disabled";
    }
    leaf time-since-last-query-in-seconds {
      xr:xr-xml-map "ipv4_igmp:TimeSinceLastQueryInSeconds";
      type uint32;
      description "Time elapsed since last query";
    }
    leaf time-since-last-report-in-seconds {
      xr:xr-xml-map "ipv4_igmp:TimeSinceLastReportInSeconds";
      type uint32;
      description "Time elapsed since last report";
    }
    leaf router-uptime-in-seconds {
      xr:xr-xml-map "ipv4_igmp:RouterUptimeInSeconds";
      type uint32;
      description "Time elapsed since router enabled event";
    }
  }

  grouping IGMP-EDM-SUMMARY-BAG {
    description "IGMP summary info";
    leaf robustness {
      xr:xr-xml-map "ipv4_igmp:Robustness";
      type uint32;
      description "Robustness variable";
    }
    leaf group-limit {
      xr:xr-xml-map "ipv4_igmp:GroupLimit";
      type uint32;
      description "Maximum groups accepted";
    }
    leaf group-count {
      xr:xr-xml-map "ipv4_igmp:GroupCount";
      type uint32;
      description "Current groups accepted";
    }
    leaf is-disabled {
      xr:xr-xml-map "ipv4_igmp:IsDisabled";
      type boolean;
      description "Is maximum enforcement disabled";
    }
    leaf supported-interfaces {
      xr:xr-xml-map "ipv4_igmp:SupportedInterfaces";
      type uint32;
      description "No. of supported interfaces";
    }
    leaf unsupported-interfaces {
      xr:xr-xml-map "ipv4_igmp:UnsupportedInterfaces";
      type uint32;
      description "No. of unsupported interfaces";
    }
    leaf enabled-interface-count {
      xr:xr-xml-map "ipv4_igmp:EnabledInterfaceCount";
      type uint32;
      description "No. of enabled interfaces";
    }
    leaf disabled-interface-count {
      xr:xr-xml-map "ipv4_igmp:DisabledInterfaceCount";
      type uint32;
      description "No. of disabled interfaces";
    }
    leaf tunnel-mte-config-count {
      xr:xr-xml-map "ipv4_igmp:TunnelMTEConfigCount";
      type uint32;
      description "No. of static group commands";
    }
    leaf node-low-memory {
      xr:xr-xml-map "ipv4_igmp:NodeLowMemory";
      type boolean;
      description "Is node in low memory condition";
    }

    list interface {
      description
        "Maximum and current groups accepted for each
        interface";
      uses IGMP-EDM-INTF-SUMMARY-BAG;
    }
  }
}
