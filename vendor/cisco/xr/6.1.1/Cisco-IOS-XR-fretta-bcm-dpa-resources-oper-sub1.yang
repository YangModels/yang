submodule Cisco-IOS-XR-fretta-bcm-dpa-resources-oper-sub1 {

  belongs-to Cisco-IOS-XR-fretta-bcm-dpa-resources-oper {
    prefix Cisco-IOS-XR-fretta-bcm-dpa-resources-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR fretta-bcm-dpa-resources package operational data.

     Copyright (c) 2013-2016 by Cisco Systems, Inc.
     All rights reserved.";

  revision "2015-11-09" {
    description
      "IOS XR 6.0 revision.";
  }


  grouping DPA-SYSDB-NPU-TABLE-RESOURCE {
    description "DPA SYSDB NPU TABLE RESOURCE";
    leaf npu-id {
      xr:xr-xml-map "dpa_resources:npu_id";
      type uint32;
      description "npu id";
    }
    leaf num-objs {
      xr:xr-xml-map "dpa_resources:num_objs";
      type uint32;
      description "num objs";
    }
    leaf create-req {
      xr:xr-xml-map "dpa_resources:create_req";
      type uint32;
      description "create req";
    }
    leaf create-ok {
      xr:xr-xml-map "dpa_resources:create_ok";
      type uint32;
      description "create ok";
    }
    leaf delete-req {
      xr:xr-xml-map "dpa_resources:delete_req";
      type uint32;
      description "delete req";
    }
    leaf delete-ok {
      xr:xr-xml-map "dpa_resources:delete_ok";
      type uint32;
      description "delete ok";
    }
    leaf update-req {
      xr:xr-xml-map "dpa_resources:update_req";
      type uint32;
      description "update req";
    }
    leaf update-ok {
      xr:xr-xml-map "dpa_resources:update_ok";
      type uint32;
      description "update ok";
    }
    leaf eod-req {
      xr:xr-xml-map "dpa_resources:eod_req";
      type uint32;
      description "eod req";
    }
    leaf eod-ok {
      xr:xr-xml-map "dpa_resources:eod_ok";
      type uint32;
      description "eod ok";
    }
    leaf err-hw-fail {
      xr:xr-xml-map "dpa_resources:err_hw_fail";
      type uint32;
      description "err hw fail";
    }
    leaf err-ref-resolve {
      xr:xr-xml-map "dpa_resources:err_ref_resolve";
      type uint32;
      description "err ref resolve";
    }
    leaf err-db-notfound {
      xr:xr-xml-map "dpa_resources:err_db_notfound";
      type uint32;
      description "err db notfound";
    }
    leaf err-db-exists {
      xr:xr-xml-map "dpa_resources:err_db_exists";
      type uint32;
      description "err db exists";
    }
    leaf err-db-nomem {
      xr:xr-xml-map "dpa_resources:err_db_nomem";
      type uint32;
      description "err db nomem";
    }
  }

  grouping DPA-SYSDB-TABLE-RESOURCE {
    description "DPA SYSDB TABLE RESOURCE";
    leaf table-id {
      xr:xr-xml-map "dpa_resources:table_id";
      type uint32;
      description "table id";
    }
    leaf name {
      xr:xr-xml-map "dpa_resources:name";
      type string {
        length "0..64";
      }
      description "name";
    }
    leaf is-global {
      xr:xr-xml-map "dpa_resources:is_global";
      type boolean;
      description "is global";
    }
    leaf num-npus {
      xr:xr-xml-map "dpa_resources:num_npus";
      type uint32;
      description "num npus";
    }
    leaf table-specific-list {
      xr:xr-xml-map "dpa_resources:table_specific_list";
      type string;
      description "table specific list";
    }

    list npu-tblr {
      description "npu tblr";
      uses DPA-SYSDB-NPU-TABLE-RESOURCE;
    }
  }
}
