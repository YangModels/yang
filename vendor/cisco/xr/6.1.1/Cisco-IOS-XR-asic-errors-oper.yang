module Cisco-IOS-XR-asic-errors-oper {

  /*** NAMESPACE / PREFIX DEFINITION ***/

  namespace "http://cisco.com/ns/yang/Cisco-IOS-XR-asic-errors-oper";


  prefix "asic-errors-oper";

  /*** LINKAGE (IMPORTS / INCLUDES) ***/

  import Cisco-IOS-XR-types { prefix "xr"; }

  include Cisco-IOS-XR-asic-errors-oper-sub2 {
    revision-date 2015-11-09;
  }

  include Cisco-IOS-XR-asic-errors-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR asic-errors package operational data.

     This module contains definitions
     for the following management objects:
       asic-errors: Error summary of all asics

     Copyright (c) 2013-2016 by Cisco Systems, Inc.
     All rights reserved.";

  revision "2015-11-09" {
    description
      "IOS XR 6.0 revision.";
  }


  container asic-errors {
    xr:xr-xml-map "asic_errors_oper:AsicErrors";
    config false;
    description "Error summary of all asics";

    container nodes {
      xr:xr-xml-map "asic_errors_oper:NodeTable";
      description "Asic errors for each available nodes";

      list node {
        xr:xr-xml-map "asic_errors_oper:Node";
        key "node-name";
        description "Asic error for a particular node";
        leaf node-name {
          xr:xr-xml-map "asic_errors_oper:NodeName";
          type xr:Node-id;
          description "Node ID";
        }

        list asic-information {
          xr:xr-xml-map "asic_errors_oper:AsicInformation";
          key "asic";
          description "Asic on the node";

          container all-instances {
            xr:xr-xml-map "asic_errors_oper:AllInstances";
            description "All asic instance on the node";

            container all-error-path {
              xr:xr-xml-map "asic_errors_oper:AllErrorPath";
              description "Error path of all instances";

              container summary {
                xr:xr-xml-map "asic_errors_oper:Summary";
                description "Summary of all instances errors";
                uses ASIC-SUMMARY-BG;
              }
            }
          }

          container instances {
            xr:xr-xml-map "asic_errors_oper:AsicInstance";
            description "All asic errors  on the node";

            list instance {
              xr:xr-xml-map "asic_errors_oper:Instance";
              key "asic-instance";
              description "Particular asic instance on the node";

              container error-path {
                xr:xr-xml-map "asic_errors_oper:ErrorPath";
                description "Error path of the instances";

                container multiple-bit-soft-errors {
                  xr:xr-xml-map "asic_errors_oper:MultipleBitSoftEr"+
                    "rors";
                  description "Multiple bit soft error information";
                  uses CIHERR-NODES-BG;
                }

                container asic-error-generic-soft {
                  xr:xr-xml-map "asic_errors_oper:AsicErrorGenericS"+
                    "oft";
                  description "Indirect hard error information";
                  uses CIHERR-NODES-BG;
                }

                container crc-hard-errors {
                  xr:xr-xml-map "asic_errors_oper:CRCHardErrors";
                  description "CRC hard error information";
                  uses CIHERR-NODES-BG;
                }

                container asic-error-sbe-soft {
                  xr:xr-xml-map "asic_errors_oper:AsicErrorSBESoft";
                  description "Indirect hard error information";
                  uses CIHERR-NODES-BG;
                }

                container hardware-soft-errors {
                  xr:xr-xml-map "asic_errors_oper:HardwareSoftError"+
                    "s";
                  description "Hardware soft error information";
                  uses CIHERR-NODES-BG;
                }

                container asic-error-crc-soft {
                  xr:xr-xml-map "asic_errors_oper:AsicErrorCRCSoft";
                  description "Indirect hard error information";
                  uses CIHERR-NODES-BG;
                }

                container asic-error-parity-soft {
                  xr:xr-xml-map "asic_errors_oper:AsicErrorParitySo"+
                    "ft";
                  description "Indirect hard error information";
                  uses CIHERR-NODES-BG;
                }

                container io-soft-errors {
                  xr:xr-xml-map "asic_errors_oper:IOSoftErrors";
                  description "IO soft error information";
                  uses CIHERR-NODES-BG;
                }

                container reset-soft-errors {
                  xr:xr-xml-map "asic_errors_oper:ResetSoftErrors";
                  description "Reset soft error information";
                  uses CIHERR-NODES-BG;
                }

                container barrier-hard-errors {
                  xr:xr-xml-map "asic_errors_oper:BarrierHardErrors";
                  description "Barrier hard error information";
                  uses CIHERR-NODES-BG;
                }

                container ucode-soft-errors {
                  xr:xr-xml-map "asic_errors_oper:UCodeSoftErrors";
                  description "Ucode soft error information";
                  uses CIHERR-NODES-BG;
                }

                container asic-error-reset-hard {
                  xr:xr-xml-map "asic_errors_oper:AsicErrorResetHar"+
                    "d";
                  description "Indirect hard error information";
                  uses CIHERR-NODES-BG;
                }

                container single-bit-hard-errors {
                  xr:xr-xml-map "asic_errors_oper:SingleBitHardErro"+
                    "rs";
                  description "Single bit hard error information";
                  uses CIHERR-NODES-BG;
                }

                container indirect-hard-errors {
                  xr:xr-xml-map "asic_errors_oper:IndirectHardError"+
                    "s";
                  description "Indirect hard error information";
                  uses CIHERR-NODES-BG;
                }

                container outof-resource-soft {
                  xr:xr-xml-map "asic_errors_oper:OutofResourceSoft";
                  description "OOR thresh information";
                  uses CIHERR-NODES-BG;
                }

                container crc-soft-errors {
                  xr:xr-xml-map "asic_errors_oper:CRCSoftErrors";
                  description "CRC soft error information";
                  uses CIHERR-NODES-BG;
                }

                container time-out-hard-errors {
                  xr:xr-xml-map "asic_errors_oper:TimeOutHardErrors";
                  description "Time out hard error information";
                  uses CIHERR-NODES-BG;
                }

                container barrier-soft-errors {
                  xr:xr-xml-map "asic_errors_oper:BarrierSoftErrors";
                  description "Barrier soft error information";
                  uses CIHERR-NODES-BG;
                }

                container asic-error-mbe-soft {
                  xr:xr-xml-map "asic_errors_oper:AsicErrorMBESoft";
                  description "Indirect hard error information";
                  uses CIHERR-NODES-BG;
                }

                container back-pressure-hard-errors {
                  xr:xr-xml-map "asic_errors_oper:BackPressureHardE"+
                    "rrors";
                  description "BP hard error information";
                  uses CIHERR-NODES-BG;
                }

                container single-bit-soft-errors {
                  xr:xr-xml-map "asic_errors_oper:SingleBitSoftErro"+
                    "rs";
                  description "Single bit soft error information";
                  uses CIHERR-NODES-BG;
                }

                container indirect-soft-errors {
                  xr:xr-xml-map "asic_errors_oper:IndirectSoftError"+
                    "s";
                  description "Indirect soft error information";
                  uses CIHERR-NODES-BG;
                }

                container generic-hard-errors {
                  xr:xr-xml-map "asic_errors_oper:GenericHardErrors";
                  description "Generic hard error information";
                  uses CIHERR-NODES-BG;
                }

                container link-hard-errors {
                  xr:xr-xml-map "asic_errors_oper:LinkHardErrors";
                  description "Link hard error information";
                  uses CIHERR-NODES-BG;
                }

                container configuration-hard-errors {
                  xr:xr-xml-map "asic_errors_oper:ConfigurationHard"+
                    "Errors";
                  description
                    "Configuration hard error information";
                  uses CIHERR-NODES-BG;
                }

                container instance-summary {
                  xr:xr-xml-map "asic_errors_oper:InstanceSummary";
                  description "Summary for a specific instance";
                  uses ASIC-SUMMARY-BG;
                }

                container unexpected-hard-errors {
                  xr:xr-xml-map "asic_errors_oper:UnexpectedHardErr"+
                    "ors";
                  description "Unexpected hard error information";
                  uses CIHERR-NODES-BG;
                }

                container time-out-soft-errors {
                  xr:xr-xml-map "asic_errors_oper:TimeOutSoftErrors";
                  description "Time out soft error information";
                  uses CIHERR-NODES-BG;
                }

                container asic-error-generic-hard {
                  xr:xr-xml-map "asic_errors_oper:AsicErrorGenericH"+
                    "ard";
                  description "Indirect hard error information";
                  uses CIHERR-NODES-BG;
                }

                container parity-hard-errors {
                  xr:xr-xml-map "asic_errors_oper:ParityHardErrors";
                  description "Parity hard error information";
                  uses CIHERR-NODES-BG;
                }

                container descriptor-hard-errors {
                  xr:xr-xml-map "asic_errors_oper:DescriptorHardErr"+
                    "ors";
                  description "Descriptor hard error information";
                  uses CIHERR-NODES-BG;
                }

                container interface-hard-errors {
                  xr:xr-xml-map "asic_errors_oper:InterfaceHardErro"+
                    "rs";
                  description "Interface hard error information";
                  uses CIHERR-NODES-BG;
                }

                container asic-error-sbe-hard {
                  xr:xr-xml-map "asic_errors_oper:AsicErrorSBEHard";
                  description "Indirect hard error information";
                  uses CIHERR-NODES-BG;
                }

                container asic-error-crc-hard {
                  xr:xr-xml-map "asic_errors_oper:AsicErrorCRCHard";
                  description "Indirect hard error information";
                  uses CIHERR-NODES-BG;
                }

                container asic-error-parity-hard {
                  xr:xr-xml-map "asic_errors_oper:AsicErrorParityHa"+
                    "rd";
                  description "Indirect hard error information";
                  uses CIHERR-NODES-BG;
                }

                container asic-error-reset-soft {
                  xr:xr-xml-map "asic_errors_oper:AsicErrorResetSof"+
                    "t";
                  description "Indirect hard error information";
                  uses CIHERR-NODES-BG;
                }

                container back-pressure-soft-errors {
                  xr:xr-xml-map "asic_errors_oper:BackPressureSoftE"+
                    "rrors";
                  description "BP soft error information";
                  uses CIHERR-NODES-BG;
                }

                container generic-soft-errors {
                  xr:xr-xml-map "asic_errors_oper:GenericSoftErrors";
                  description "Generic soft error information";
                  uses CIHERR-NODES-BG;
                }

                container link-soft-errors {
                  xr:xr-xml-map "asic_errors_oper:LinkSoftErrors";
                  description "Link soft error information";
                  uses CIHERR-NODES-BG;
                }

                container configuration-soft-errors {
                  xr:xr-xml-map "asic_errors_oper:ConfigurationSoft"+
                    "Errors";
                  description
                    "Configuration soft error information";
                  uses CIHERR-NODES-BG;
                }

                container multiple-bit-hard-errors {
                  xr:xr-xml-map "asic_errors_oper:MultipleBitHardEr"+
                    "rors";
                  description "Multiple bit hard error information";
                  uses CIHERR-NODES-BG;
                }

                container unexpected-soft-errors {
                  xr:xr-xml-map "asic_errors_oper:UnexpectedSoftErr"+
                    "ors";
                  description "Unexpected soft error information";
                  uses CIHERR-NODES-BG;
                }

                container outof-resource-hard {
                  xr:xr-xml-map "asic_errors_oper:OutofResourceHard";
                  description "OOR thresh information";
                  uses CIHERR-NODES-BG;
                }

                container hardware-hard-errors {
                  xr:xr-xml-map "asic_errors_oper:HardwareHardError"+
                    "s";
                  description "Hardware hard error information";
                  uses CIHERR-NODES-BG;
                }

                container parity-soft-errors {
                  xr:xr-xml-map "asic_errors_oper:ParitySoftErrors";
                  description "Parity soft error information";
                  uses CIHERR-NODES-BG;
                }

                container descriptor-soft-errors {
                  xr:xr-xml-map "asic_errors_oper:DescriptorSoftErr"+
                    "ors";
                  description "Descriptor soft error information";
                  uses CIHERR-NODES-BG;
                }

                container interface-soft-errors {
                  xr:xr-xml-map "asic_errors_oper:InterfaceSoftErro"+
                    "rs";
                  description "Interface soft error information";
                  uses CIHERR-NODES-BG;
                }

                container io-hard-errors {
                  xr:xr-xml-map "asic_errors_oper:IOHardErrors";
                  description "IO hard error information";
                  uses CIHERR-NODES-BG;
                }

                container reset-hard-errors {
                  xr:xr-xml-map "asic_errors_oper:ResetHardErrors";
                  description "Reset hard error information";
                  uses CIHERR-NODES-BG;
                }

                container ucode-hard-errors {
                  xr:xr-xml-map "asic_errors_oper:UCodeHardErrors";
                  description "UCode hard error information";
                  uses CIHERR-NODES-BG;
                }

                container asic-error-mbe-hard {
                  xr:xr-xml-map "asic_errors_oper:AsicErrorMBEHard";
                  description "Indirect hard error information";
                  uses CIHERR-NODES-BG;
                }
              }
              leaf asic-instance {
                xr:xr-xml-map "asic_errors_oper:AsicInstance";
                type int32;
                description "asic instance";
              }
            }
          }
          leaf asic {
            xr:xr-xml-map "asic_errors_oper:Asic";
            type xr:Cisco-ios-xr-string;
            description "Asic string";
          }
        }
      }
    }
  }
}
