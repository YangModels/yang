module Cisco-IOS-XR-ethernet-link-oam-oper {

  /*** NAMESPACE / PREFIX DEFINITION ***/

  namespace "http://cisco.com/ns/yang"+
    "/Cisco-IOS-XR-ethernet-link-oam-oper";


  prefix "ethernet-link-oam-oper";

  /*** LINKAGE (IMPORTS / INCLUDES) ***/

  import Cisco-IOS-XR-types { prefix "xr"; }

  include Cisco-IOS-XR-ethernet-link-oam-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ethernet-link-oam package operational data.

     This module contains definitions
     for the following management objects:
       ether-link-oam: Ethernet Link OAM operational data

     Copyright (c) 2013-2016 by Cisco Systems, Inc.
     All rights reserved.";

  revision "2015-11-09" {
    description
      "IOS XR 6.0 revision.";
  }


  container ether-link-oam {
    xr:xr-xml-map "ethernet_link_oam_oper:EtherLinkOAM";
    config false;
    description "Ethernet Link OAM operational data";

    container discovery-info-interfaces {
      xr:xr-xml-map "ethernet_link_oam_oper:DiscoveryInfoInterfaceT"+
        "able";
      description
        "Table of Ethernet Link OAM enabled interfaces
        within Discovery Info container";

      list discovery-info-interface {
        xr:xr-xml-map "ethernet_link_oam_oper:DiscoveryInfoInterfac"+
          "e";
        key "member-interface";
        description
          "Ethernet Link OAM interface to get Discovery
          Info for";
        leaf member-interface {
          xr:xr-xml-map "ethernet_link_oam_oper:MemberInterface";
          type xr:Interface-name;
          description "Member Interface";
        }
        uses ELOD-DISCOVERY-INFO;
      }
    }

    container interface-state-interfaces {
      xr:xr-xml-map "ethernet_link_oam_oper:InterfaceStateInterface"+
        "Table";
      description
        "Table of Ethernet Link OAM enabled interfaces
        within Interface State container";

      list interface-state-interface {
        xr:xr-xml-map "ethernet_link_oam_oper:InterfaceStateInterfa"+
          "ce";
        key "member-interface";
        description
          "Ethernet Link OAM interface to get Interface
          State for";
        leaf member-interface {
          xr:xr-xml-map "ethernet_link_oam_oper:MemberInterface";
          type xr:Interface-name;
          description "Member Interface";
        }
        uses ELOD-INTERFACE-STATE;
      }
    }

    container running-config-interfaces {
      xr:xr-xml-map "ethernet_link_oam_oper:RunningConfigInterfaceT"+
        "able";
      description
        "Table of Ethernet Link OAM enabled interfaces
        within Running Config container";

      list running-config-interface {
        xr:xr-xml-map "ethernet_link_oam_oper:RunningConfigInterfac"+
          "e";
        key "member-interface";
        description
          "Ethernet Link OAM interface to get Running
          Config for";
        leaf member-interface {
          xr:xr-xml-map "ethernet_link_oam_oper:MemberInterface";
          type xr:Interface-name;
          description "Member Interface";
        }
        uses ELOD-RUNNING-CONFIG;
      }
    }

    container nodes {
      xr:xr-xml-map "ethernet_link_oam_oper:NodeTable";
      description "Node table for node-specific operational data";

      list node {
        xr:xr-xml-map "ethernet_link_oam_oper:Node";
        key "node-name";
        description "Node-specific data for a particular node";

        container summary {
          xr:xr-xml-map "ethernet_link_oam_oper:Summary";
          description
            "Ethernet Link OAM Summary information for the
            entire node";
          uses ELOD-SUMMARY-INFO;
        }
        leaf node-name {
          xr:xr-xml-map "ethernet_link_oam_oper:NodeName";
          type xr:Node-id;
          description "Node";
        }
      }
    }

    container event-log-entry-interfaces {
      xr:xr-xml-map "ethernet_link_oam_oper:EventLogEntryInterfaceT"+
        "able";
      description
        "Table of Ethernet Link OAM enabled interfaces
        within Event Log Entry container";

      list event-log-entry-interface {
        xr:xr-xml-map "ethernet_link_oam_oper:EventLogEntryInterfac"+
          "e";
        key "member-interface";
        description
          "Ethernet Link OAM enabled interface to get
          Event Log Entry for";

        container event-log-entry-indexes {
          xr:xr-xml-map "ethernet_link_oam_oper:EventLogEntryIndexT"+
            "able";
          description
            "Table of Ethernet Link OAM Event Log entries
            on the interface";

          list event-log-entry-index {
            xr:xr-xml-map "ethernet_link_oam_oper:EventLogEntryInde"+
              "x";
            key "event-log-entry-index";
            description
              "Ethernet Link OAM Event Log Entry Index to
              get data for";
            leaf event-log-entry-index {
              xr:xr-xml-map "ethernet_link_oam_oper:EventLogEntryIn"+
                "dex";
              type xr:Cisco-ios-xr-string;
              description "Event Log Entry index";
            }
            uses ELOD-LOG-ENTRY;
          }
        }
        leaf member-interface {
          xr:xr-xml-map "ethernet_link_oam_oper:MemberInterface";
          type xr:Interface-name;
          description "Member Interface";
        }
      }
    }

    container stats-interfaces {
      xr:xr-xml-map "ethernet_link_oam_oper:StatsInterfaceTable";
      description
        "Table of Ethernet Link OAM enabled interfaces
        within Stats container";

      list stats-interface {
        xr:xr-xml-map "ethernet_link_oam_oper:StatsInterface";
        key "member-interface";
        description "Ethernet Link OAM interface to get Stats for";
        leaf member-interface {
          xr:xr-xml-map "ethernet_link_oam_oper:MemberInterface";
          type xr:Interface-name;
          description "Member Interface";
        }
        uses ELOD-STATS;
      }
    }
  }
}
