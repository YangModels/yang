module Cisco-IOS-XR-alarmgr-server-oper {

  /*** NAMESPACE / PREFIX DEFINITION ***/

  namespace "http://cisco.com/ns/yang"+
    "/Cisco-IOS-XR-alarmgr-server-oper";


  prefix "alarmgr-server-oper";

  /*** LINKAGE (IMPORTS / INCLUDES) ***/

  import Cisco-IOS-XR-types { prefix "xr"; }

  include Cisco-IOS-XR-alarmgr-server-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR alarmgr-server package operational data.

     This module contains definitions
     for the following management objects:
       alarms: Show Alarms associated with XR

     Copyright (c) 2013-2016 by Cisco Systems, Inc.
     All rights reserved.";

  revision "2015-11-09" {
    description
      "IOS XR 6.0 revision.";
  }


  container alarms {
    xr:xr-xml-map "alarm_mgr_oper:Alarms";
    config false;
    description "Show Alarms associated with XR";

    container detail {
      xr:xr-xml-map "alarm_mgr_oper:Detail";
      description "A set of detail alarm commands.";

      container detail-system {
        xr:xr-xml-map "alarm_mgr_oper:DetailSystem";
        description "show detail system scope alarm related data.";

        container active {
          xr:xr-xml-map "alarm_mgr_oper:Active";
          description "Show the active alarms at this scope.";
          uses ALARM-MGR-SHOW-ALARM-INFO-CLI;
        }

        container history {
          xr:xr-xml-map "alarm_mgr_oper:History";
          description "Show the history alarms at this scope.";
          uses ALARM-MGR-SHOW-ALARM-INFO-CLI;
        }

        container suppressed {
          xr:xr-xml-map "alarm_mgr_oper:Suppressed";
          description "Show the suppressed alarms at this scope.";
          uses ALARM-MGR-SHOW-ALARM-INFO-SUPPR-CLI;
        }

        container stats {
          xr:xr-xml-map "alarm_mgr_oper:Stats";
          description "Show the service statistics.";
          uses ALARM-MGR-SHOW-ALARM-STATS;
        }

        container clients {
          xr:xr-xml-map "alarm_mgr_oper:Clients";
          description
            "Show the clients associated with this service.";
          uses ALARM-MGR-SHOW-CLIENT-INFO;
        }
      }

      container detail-card {
        xr:xr-xml-map "alarm_mgr_oper:DetailCard";
        description "Show detail card scope alarm related data.";

        container detail-locations {
          xr:xr-xml-map "alarm_mgr_oper:DetailLocationTable";
          description "Table of DetailLocation";

          list detail-location {
            xr:xr-xml-map "alarm_mgr_oper:DetailLocation";
            key "node-id";
            description "Specify a card location for alarms.";

            container active {
              xr:xr-xml-map "alarm_mgr_oper:Active";
              description "Show the active alarms at this scope.";
              uses ALARM-MGR-SHOW-ALARM-INFO-CLI;
            }

            container history {
              xr:xr-xml-map "alarm_mgr_oper:History";
              description "Show the history alarms at this scope.";
              uses ALARM-MGR-SHOW-ALARM-INFO-CLI;
            }

            container suppressed {
              xr:xr-xml-map "alarm_mgr_oper:Suppressed";
              description
                "Show the suppressed alarms at this scope.";
              uses ALARM-MGR-SHOW-ALARM-INFO-SUPPR-CLI;
            }

            container stats {
              xr:xr-xml-map "alarm_mgr_oper:Stats";
              description "Show the service statistics.";
              uses ALARM-MGR-SHOW-ALARM-STATS;
            }

            container clients {
              xr:xr-xml-map "alarm_mgr_oper:Clients";
              description
                "Show the clients associated with this
                service.";
              uses ALARM-MGR-SHOW-CLIENT-INFO;
            }
            leaf node-id {
              xr:xr-xml-map "alarm_mgr_oper:NodeID";
              type xr:Node-id;
              description "NodeID of the Location";
            }
          }
        }
      }
    }

    container brief {
      xr:xr-xml-map "alarm_mgr_oper:Brief";
      description "A set of brief alarm commands.";

      container brief-card {
        xr:xr-xml-map "alarm_mgr_oper:BriefCard";
        description "Show brief card scope alarm related data.";

        container brief-locations {
          xr:xr-xml-map "alarm_mgr_oper:BriefLocationTable";
          description "Table of BriefLocation";

          list brief-location {
            xr:xr-xml-map "alarm_mgr_oper:BriefLocation";
            key "node-id";
            description "Specify a card location for alarms.";

            container active {
              xr:xr-xml-map "alarm_mgr_oper:Active";
              description "Show the active alarms at this scope.";
              uses ALARM-MGR-SHOW-ALARM-BRIEF-INFO;
            }

            container history {
              xr:xr-xml-map "alarm_mgr_oper:History";
              description "Show the history alarms at this scope.";
              uses ALARM-MGR-SHOW-ALARM-BRIEF-INFO;
            }

            container suppressed {
              xr:xr-xml-map "alarm_mgr_oper:Suppressed";
              description
                "Show the suppressed alarms at this scope.";
              uses ALARM-MGR-SHOW-ALARM-BRIEF-SUPPR-INFO;
            }
            leaf node-id {
              xr:xr-xml-map "alarm_mgr_oper:NodeID";
              type xr:Node-id;
              description "NodeID of the Location";
            }
          }
        }
      }

      container brief-system {
        xr:xr-xml-map "alarm_mgr_oper:BriefSystem";
        description "Show brief system scope alarm related data.";

        container active {
          xr:xr-xml-map "alarm_mgr_oper:Active";
          description "Show the active alarms at this scope.";
          uses ALARM-MGR-SHOW-ALARM-BRIEF-INFO;
        }

        container history {
          xr:xr-xml-map "alarm_mgr_oper:History";
          description "Show the history alarms at this scope.";
          uses ALARM-MGR-SHOW-ALARM-BRIEF-INFO;
        }

        container suppressed {
          xr:xr-xml-map "alarm_mgr_oper:Suppressed";
          description "Show the suppressed alarms at this scope.";
          uses ALARM-MGR-SHOW-ALARM-BRIEF-SUPPR-INFO;
        }
      }
    }
  }
}
