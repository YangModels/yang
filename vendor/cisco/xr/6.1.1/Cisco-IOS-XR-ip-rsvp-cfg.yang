module Cisco-IOS-XR-ip-rsvp-cfg {

  /*** NAMESPACE / PREFIX DEFINITION ***/

  namespace "http://cisco.com/ns/yang/Cisco-IOS-XR-ip-rsvp-cfg";


  prefix "ip-rsvp-cfg";

  /*** LINKAGE (IMPORTS / INCLUDES) ***/

  import ietf-inet-types { prefix "inet"; }

  import Cisco-IOS-XR-types { prefix "xr"; }

  import Cisco-IOS-XR-snmp-agent-cfg { prefix "a1"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ip-rsvp package configuration.

     This module contains definitions
     for the following management objects:
       rsvp: Global RSVP configuration commands

     This YANG module augments the
       Cisco-IOS-XR-snmp-agent-cfg
     module with configuration data.

     Copyright (c) 2013-2016 by Cisco Systems, Inc.
     All rights reserved.";

  revision "2015-11-09" {
    description
      "IOS XR 6.0 revision.";
  }

  typedef Rsvp-rdm {
    type enumeration {
      enum rdm {
        value 1;
        description "RDM Keyword Specified";
      }
      enum not-specified {
        value 2;
        description "RDM Keyword Not Specified";
      }
      enum use-default-bandwidth {
        value 3;
        description "Use Default Bandwidth - 75% Link Bandwidth";
      }
    }
    description "Rsvp rdm";
  }
  typedef Rsvp-bc0 {
    type enumeration {
      enum bc0 {
        value 1;
        description "Keyword is bc0";
      }
      enum global-pool {
        value 2;
        description "Keyword is global-pool";
      }
      enum not-specified {
        value 3;
        description "Keyword is not specified";
      }
    }
    description "Rsvp bc0";
  }
  typedef Rsvp-bw-cfg {
    type enumeration {
      enum absolute {
        value 0;
        description "Configuration is in absolute bandwidth values";
      }
      enum percentage {
        value 1;
        description
          "Configuration is in percentage of physical
          bandwidth values";
      }
    }
    description "Rsvp bw cfg";
  }
  typedef Rsvp-bc1 {
    type enumeration {
      enum bc1 {
        value 1;
        description "Keyword is bc1";
      }
      enum sub-pool {
        value 2;
        description "Keyword is sub-pool";
      }
    }
    description "Rsvp bc1";
  }

  grouping AUTHENTICATION {
    description "Common node of rsvp, interface, neighbor";

    container authentication {
      xr:xr-xml-map "ip_rsvp_cfg:Authentication";
      description "Configure RSVP authentication";
      leaf life-time {
        xr:xr-xml-map "ip_rsvp_cfg:LifeTime";
        xr:xr-cli-map "rsvp neighbor <IPv4 address> authentication "+
          "life-time <number> ";
        xr:xr-cli-map "rsvp interface <interface> authentication li"+
          "fe-time <number> ";
        xr:xr-cli-map "rsvp authentication life-time <number> ";
        type uint32 {
          range "30..86400";
        }
        units "second";
        description
          "Life time (in seconds) for each security
          association";
      }
      leaf enable {
        xr:xr-xml-map "ip_rsvp_cfg:Enable";
        type boolean;
        description "Enable or disable RSVP authentication";
      }
      leaf window-size {
        xr:xr-xml-map "ip_rsvp_cfg:WindowSize";
        xr:xr-cli-map "rsvp neighbor <IPv4 address> authentication "+
          "window-size <number> ";
        xr:xr-cli-map "rsvp interface <interface> authentication wi"+
          "ndow-size <number> ";
        xr:xr-cli-map "rsvp authentication window-size <number> ";
        type uint32 {
          range "1..64";
        }
        description
          "Window-size to limit number of out-of-order
          messages";
      }
      leaf key-chain {
        xr:xr-xml-map "ip_rsvp_cfg:KeyChain";
        xr:xr-cli-map "rsvp neighbor <IPv4 address> authentication "+
          "key-source key-chain <string> ";
        xr:xr-cli-map "rsvp interface <interface> authentication ke"+
          "y-source key-chain <string> ";
        xr:xr-cli-map "rsvp authentication key-source key-chain <st"+
          "ring> ";
        type xr:Cisco-ios-xr-string {
          length "0..32";
        }
        description
          "Key chain to authenticate RSVP signalling
          messages";
      }
    }
  }

  grouping OUT-OF-BAND {
    description "Common node of cntl-signalling, if-signalling";

    container out-of-band {
      xr:xr-xml-map "ip_rsvp_cfg:OutOfBand";
      description
        "Configure RSVP out-of-band signalling parameters";
      leaf missed-messages {
        xr:xr-xml-map "ip_rsvp_cfg:MissedMessages";
        xr:xr-cli-map "rsvp controller signalling refresh out-of-ba"+
          "nd missed <number> ";
        xr:xr-cli-map "rsvp interface <interface> signalling refres"+
          "h out-of-band missed <number> ";
        type uint32 {
          range "1..110000";
        }
        default "38000";
        description
          "Configure max number of consecutive missed
          messages for state expiry for out-of-band
          tunnels";
      }
      leaf refresh-interval {
        xr:xr-xml-map "ip_rsvp_cfg:RefreshInterval";
        xr:xr-cli-map "rsvp controller signalling refresh out-of-ba"+
          "nd interval <number> ";
        xr:xr-cli-map "rsvp interface <interface> signalling refres"+
          "h out-of-band interval <number> ";
        type uint32 {
          range "180..86400";
        }
        units "second";
        description
          "Configure interval between successive refreshes
          for out-of-band tunnels";
      }
    }
  }

  container rsvp {
    xr:xr-xml-map "ip_rsvp_cfg:RSVP";
    description "Global RSVP configuration commands";

    container neighbors {
      xr:xr-xml-map "ip_rsvp_cfg:NeighborTable";
      description "RSVP Neighbor Table";

      list neighbor {
        xr:xr-xml-map "ip_rsvp_cfg:Neighbor";
        key "neighbor";
        description "RSVP neighbor configuration";
        leaf neighbor {
          xr:xr-xml-map "ip_rsvp_cfg:Neighbor";
          type inet:ipv4-address-no-zone;
          description "Neighbor IP address";
        }
        uses AUTHENTICATION;
      }
    }

    container controllers {
      xr:xr-xml-map "ip_rsvp_cfg:ControllerTable";
      description "Controller table";

      list controller {
        xr:xr-xml-map "ip_rsvp_cfg:Controller";
        key "controller-name";
        description "Controller configuration";

        container cntl-signalling {
          xr:xr-xml-map "ip_rsvp_cfg:CNTLSignalling";
          description "Configure RSVP signalling parameters";
          uses OUT-OF-BAND;
        }
        leaf enable {
          xr:xr-xml-map "ip_rsvp_cfg:Enable";
          type empty;
          description "Enable RSVP on an interface";
        }
        leaf controller-name {
          xr:xr-xml-map "ip_rsvp_cfg:ControllerName";
          type xr:Interface-name;
          description "Name of controller";
        }
      }
    }

    container global-logging {
      xr:xr-xml-map "ip_rsvp_cfg:GlobalLogging";
      description "Global Logging";
      leaf log-nsr-status {
        xr:xr-xml-map "ip_rsvp_cfg:LogNSRStatus";
        type empty;
        description "Enable NSR Status Logging";
      }
      leaf log-issu-status {
        xr:xr-xml-map "ip_rsvp_cfg:LogISSUStatus";
        type empty;
        description "Enable ISSU Status Logging";
      }
    }

    container global-bandwidth {
      xr:xr-xml-map "ip_rsvp_cfg:GlobalBandwidth";
      description "Configure Global Bandwidth Parameters";

      container default-interface-percent {
        xr:xr-xml-map "ip_rsvp_cfg:DefaultInterfacePercent";
        description "Configure Global RSVP signalling parameters";

        container mam {
          xr:xr-xml-map "ip_rsvp_cfg:MAM";
          description
            "Configure global default MAM I/F percent
            bandwidth parameters";
          leaf max-res-percent {
            xr:xr-xml-map "ip_rsvp_cfg:MaxResPercent";
            type uint32 {
              range "0..10000";
            }
            description "Default maximum reservable I/F % B/W ";
          }
          leaf bc0-percent {
            xr:xr-xml-map "ip_rsvp_cfg:BC0Percent";
            type uint32 {
              range "0..10000";
            }
            description "Default BC0 pool I/F % B/W ";
          }
          leaf bc1-percent {
            xr:xr-xml-map "ip_rsvp_cfg:BC1Percent";
            type uint32 {
              range "0..10000";
            }
            description "Default BC1 pool I/F % B/W ";
          }
        }

        container rdm {
          xr:xr-xml-map "ip_rsvp_cfg:RDM";
          description
            "Configure global default RDM I/F percent
            bandwidth parameters";
          leaf bc0-percent {
            xr:xr-xml-map "ip_rsvp_cfg:BC0Percent";
            type uint32 {
              range "0..10000";
            }
            description "Default BC0 pool I/F % B/W ";
          }
          leaf bc1-percent {
            xr:xr-xml-map "ip_rsvp_cfg:BC1Percent";
            type uint32 {
              range "0..10000";
            }
            description "Default BC1 pool I/F % B/W ";
          }
        }
      }
    }

    container interfaces {
      xr:xr-xml-map "ip_rsvp_cfg:InterfaceTable";
      description "Interface table";

      list interface {
        xr:xr-xml-map "ip_rsvp_cfg:Interface";
        key "name";
        description "Interface configuration";

        container if-signalling {
          xr:xr-xml-map "ip_rsvp_cfg:IfSignalling";
          description "Configure RSVP signalling parameters";

          container refresh-reduction {
            xr:xr-xml-map "ip_rsvp_cfg:RefreshReduction";
            description
              "Configure RSVP Refresh Reduction parameters";
            leaf disable {
              xr:xr-xml-map "ip_rsvp_cfg:Disable";
              xr:xr-cli-map "rsvp interface <interface> signalling "+
                "refresh reduction disable ";
              type empty;
              description "Disable refresh reduction";
            }
            leaf reliable-ack-max-size {
              xr:xr-xml-map "ip_rsvp_cfg:ReliableAckMaxSize";
              xr:xr-cli-map "rsvp interface <interface> signalling "+
                "refresh reduction reliable ack-max-size <number> ";
              type uint32 {
                range "20..65000";
              }
              units "byte";
              default "4096";
              description
                "Configure max size of a single RSVP ACK
                message";
            }
            leaf reliable-ack-hold-time {
              xr:xr-xml-map "ip_rsvp_cfg:ReliableAckHoldTime";
              xr:xr-cli-map "rsvp interface <interface> signalling "+
                "refresh reduction reliable ack-hold-time <number> ";
              type uint32 {
                range "100..5000";
              }
              units "millisecond";
              default "400";
              description
                "Configure hold time for sending RSVP ACK
                message(s)";
            }
            leaf reliable-retransmit-time {
              xr:xr-xml-map "ip_rsvp_cfg:ReliableRetransmitTime";
              xr:xr-cli-map "rsvp interface <interface> signalling "+
                "refresh reduction reliable retransmit-time <number"+
                "> ";
              type uint32 {
                range "100..10000";
              }
              units "millisecond";
              default "2100";
              description
                "Configure min delay to wait for an ACK
                before a retransmit";
            }
            leaf reliable-s-refresh {
              xr:xr-xml-map "ip_rsvp_cfg:ReliableSRefresh";
              xr:xr-cli-map "rsvp interface <interface> signalling "+
                "refresh reduction reliable summary-refresh ";
              type empty;
              description
                "Configure use of reliable messaging for
                summary refresh";
            }
            leaf summary-max-size {
              xr:xr-xml-map "ip_rsvp_cfg:SummaryMaxSize";
              xr:xr-cli-map "rsvp interface <interface> signalling "+
                "refresh reduction summary max-size <number> ";
              type uint32 {
                range "20..65000";
              }
              units "byte";
              default "4096";
              description
                "Configure max size of a single RSVP summary
                refresh message";
            }
            leaf bundle-message-max-size {
              xr:xr-xml-map "ip_rsvp_cfg:BundleMessageMaxSize";
              xr:xr-cli-map "rsvp interface <interface> signalling "+
                "refresh reduction bundle-max-size <number> ";
              type uint32 {
                range "512..65000";
              }
              units "byte";
              default "4096";
              description
                "Configure maximum size of a single RSVP
                Bundle message";
            }
          }

          container interval-rate {
            xr:xr-xml-map "ip_rsvp_cfg:IntervalRate";
            description
              "Configure number of messages to be sent per
              interval";
            leaf messages-per-interval {
              xr:xr-xml-map "ip_rsvp_cfg:MessagesPerInterval";
              type uint32 {
                range "1..500";
              }
              default "100";
              description
                "Number of messages to be sent per interval";
            }
            leaf interval-size {
              xr:xr-xml-map "ip_rsvp_cfg:IntervalSize";
              type uint32 {
                range "250..2000";
              }
              units "millisecond";
              default "1000";
              description "Size of an interval (milliseconds)";
            }
          }
          leaf dscp {
            xr:xr-xml-map "ip_rsvp_cfg:DSCP";
            xr:xr-cli-map "rsvp interface <interface> signalling ds"+
              "cp <number> ";
            type uint32 {
              range "0..63";
            }
            description "Differentiated Services Code Point (DSCP)";
          }
          leaf missed-messages {
            xr:xr-xml-map "ip_rsvp_cfg:MissedMessages";
            xr:xr-cli-map "rsvp interface <interface> signalling re"+
              "fresh missed <number> ";
            type uint32 {
              range "1..8";
            }
            default "4";
            description
              "Configure max number of consecutive missed
              messages for state expiry";
          }
          leaf hello-graceful-restart-if-based {
            xr:xr-xml-map "ip_rsvp_cfg:HelloGracefulRestartIfBased";
            xr:xr-cli-map "rsvp interface <interface> signalling he"+
              "llo graceful-restart interface-based ";
            type empty;
            description
              "Enable IF-based Hello adjacency on a RSVP
              interface";
          }
          leaf pacing {
            xr:xr-xml-map "ip_rsvp_cfg:Pacing";
            xr:xr-cli-map "rsvp interface <interface> signalling ra"+
              "te-limit ";
            type empty;
            description "Enable rate-limiting on the interface";
          }
          leaf refresh-interval {
            xr:xr-xml-map "ip_rsvp_cfg:RefreshInterval";
            xr:xr-cli-map "rsvp interface <interface> signalling re"+
              "fresh interval <number> ";
            type uint32 {
              range "10..180";
            }
            units "second";
            default "45";
            description
              "Configure interval between successive
              refreshes";
          }
          uses OUT-OF-BAND;
        }

        container bandwidth {
          xr:xr-xml-map "ip_rsvp_cfg:Bandwidth";
          description "Configure Bandwidth";

          container mam {
            xr:xr-xml-map "ip_rsvp_cfg:MAM";
            description "Configure MAM bandwidth parameters";
            leaf max-resv-bandwidth {
              xr:xr-xml-map "ip_rsvp_cfg:MaxResvBandwidth";
              type uint32 {
                range "0..4294967295";
              }
              description
                "Maximum reservable bandwidth (Kbps or
                percent of physical bandwidth)";
            }
            leaf max-resv-flow {
              xr:xr-xml-map "ip_rsvp_cfg:MaxResvFlow";
              type uint32 {
                range "0..4294967295";
              }
              description
                "Largest reservable flow (Kbps or percent of
                physical bandwidth)";
            }
            leaf bc0-bandwidth {
              xr:xr-xml-map "ip_rsvp_cfg:BC0Bandwidth";
              type uint32 {
                range "0..4294967295";
              }
              description
                "Reservable bandwidth in BC0 (Kbps or percent
                of physical bandwidth)";
            }
            leaf bc1-bandwidth {
              xr:xr-xml-map "ip_rsvp_cfg:BC1Bandwidth";
              type uint32 {
                range "0..4294967295";
              }
              description
                "Reservable bandwidth in BC1 (Kbps or percent
                of physical bandwidth)";
            }
            leaf bandwidth-mode {
              xr:xr-xml-map "ip_rsvp_cfg:BandwidthMode";
              type Rsvp-bw-cfg;
              units "percentage";
              description "Absolute or Percentage bandwidth mode";
            }
          }

          container rdm {
            xr:xr-xml-map "ip_rsvp_cfg:RDM";
            description "Configure RDM bandwidth parameters";
            leaf max-resv-flow {
              xr:xr-xml-map "ip_rsvp_cfg:MaxResvFlow";
              when "../rdm-keyword = 'rdm' or ../rdm-keyword ="+
                " 'not-specified'" {
                  description
                    "../RDMKeyword = RDM or ../RDMKeyword =
                    NotSpecified";
              }
              type uint32 {
                range "0..4294967295";
              }
              description
                "Largest reservable flow (Kbps or percent of
                physical bandwidth)";
            }
            leaf bc0-bandwidth {
              xr:xr-xml-map "ip_rsvp_cfg:BC0Bandwidth";
              when "../rdm-keyword = 'rdm' or ../rdm-keyword ="+
                " 'not-specified'" {
                  description
                    "../RDMKeyword = RDM or ../RDMKeyword =
                    NotSpecified";
              }
              type uint32 {
                range "0..4294967295";
              }
              description
                "Reservable bandwidth in BC0 (Kbps or percent
                of physical bandwidth)";
            }
            leaf bc1-bandwidth {
              xr:xr-xml-map "ip_rsvp_cfg:BC1Bandwidth";
              when "../rdm-keyword = 'rdm' or ../rdm-keyword ="+
                " 'not-specified'" {
                  description
                    "../RDMKeyword = RDM or ../RDMKeyword =
                    NotSpecified";
              }
              type uint32 {
                range "0..4294967295";
              }
              description
                "Reservable bandwidth in BC1 (Kbps or percent
                of physical bandwidth)";
            }
            leaf rdm-keyword {
              xr:xr-xml-map "ip_rsvp_cfg:RDMKeyword";
              type Rsvp-rdm;
              description "Set requests should always use RDM";
            }
            leaf bc0-keyword {
              xr:xr-xml-map "ip_rsvp_cfg:BC0Keyword";
              when "../rdm-keyword = 'rdm' or ../rdm-keyword ="+
                " 'not-specified'" {
                  description
                    "../RDMKeyword = RDM or ../RDMKeyword =
                    NotSpecified";
              }
              type Rsvp-bc0;
              description "Set requests should always use BC0";
            }
            leaf bc1-keyword {
              xr:xr-xml-map "ip_rsvp_cfg:BC1Keyword";
              when "../rdm-keyword = 'rdm' or ../rdm-keyword ="+
                " 'not-specified'" {
                  description
                    "../RDMKeyword = RDM or ../RDMKeyword =
                    NotSpecified";
              }
              type Rsvp-bc1;
              description "Set requests should always use BC1";
            }
            leaf bandwidth-mode {
              xr:xr-xml-map "ip_rsvp_cfg:BandwidthMode";
              when "../rdm-keyword = 'rdm' or ../rdm-keyword ="+
                " 'not-specified'" {
                  description
                    "../RDMKeyword = RDM or ../RDMKeyword =
                    NotSpecified";
              }
              type Rsvp-bw-cfg;
              units "percentage";
              description "Absolute or Percentage bandwidth mode";
            }
          }
        }
        leaf enable {
          xr:xr-xml-map "ip_rsvp_cfg:Enable";
          type empty;
          description "Enable RSVP on an interface";
        }
        leaf name {
          xr:xr-xml-map "ip_rsvp_cfg:Name";
          type xr:Interface-name;
          description "Name of interface";
        }
        uses AUTHENTICATION;
      }
    }

    container signalling {
      xr:xr-xml-map "ip_rsvp_cfg:Signalling";
      description "Configure Global RSVP signalling parameters";

      container global-out-of-band {
        xr:xr-xml-map "ip_rsvp_cfg:GlobalOutOfBand";
        description "Configure out-of-band signalling parameters";
        leaf vrf {
          xr:xr-xml-map "ip_rsvp_cfg:VRF";
          xr:xr-cli-map "rsvp signalling out-of-band vrf <string> ";
          type xr:Cisco-ios-xr-string {
            length "0..32";
          }
          description "VRF used for out-of-band control signalling";
        }
      }

      container graceful-restart {
        xr:xr-xml-map "ip_rsvp_cfg:GracefulRestart";
        description "Configure RSVP Graceful-Restart parameters";
        leaf enable {
          xr:xr-xml-map "ip_rsvp_cfg:Enable";
          xr:xr-cli-map "rsvp signalling graceful-restart ";
          type boolean;
          description "Enable RSVP graceful restart";
        }
        leaf restart-time {
          xr:xr-xml-map "ip_rsvp_cfg:RestartTime";
          xr:xr-cli-map "rsvp signalling graceful-restart restart-t"+
            "ime <number> ";
          type uint32 {
            range "60..3600";
          }
          units "second";
          default "120";
          description "Graceful restart time (seconds)";
        }
        leaf recovery-time {
          xr:xr-xml-map "ip_rsvp_cfg:RecoveryTime";
          xr:xr-cli-map "rsvp signalling graceful-restart recovery-"+
            "time <number> ";
          type uint32 {
            range "0..3600";
          }
          units "second";
          default "120";
          description "Graceful restart recovery time (seconds)";
        }
      }

      container prefix-filtering {
        xr:xr-xml-map "ip_rsvp_prefix_filtering_cfg:PrefixFiltering";
        description "Configure prefix filtering parameters";

        container default-deny-action {
          xr:xr-xml-map "ip_rsvp_prefix_filtering_cfg:DefaultDenyAc"+
            "tion";
          description
            "Configure RSVP behaviour for scenarios where
            ACL match yields a default (implicit) deny";
          leaf drop {
            xr:xr-xml-map "ip_rsvp_prefix_filtering_cfg:Drop";
            xr:xr-cli-map "rsvp signalling prefix-filtering default"+
              "-deny-action drop ";
            type empty;
            description
              "Configure RSVP to drop packets when ACL match
              yields a default (implicit) deny";
          }
        }
        leaf acl {
          xr:xr-xml-map "ip_rsvp_prefix_filtering_cfg:ACL";
          xr:xr-cli-map "rsvp signalling prefix-filtering access-li"+
            "st <string> ";
          type string {
            length "0..65";
          }
          description
            "Configure an ACL to perform prefix filtering
            of RSVP Router Alert messages";
        }
      }

      container pesr {
        xr:xr-xml-map "ip_rsvp_cfg:PESR";
        description "Sending Path Error with State-Removal flag";
        leaf disable {
          xr:xr-xml-map "ip_rsvp_cfg:Disable";
          xr:xr-cli-map "rsvp signalling patherr state-removal disa"+
            "ble ";
          type empty;
          description "Disable RSVP PESR";
        }
      }

      container checksum {
        xr:xr-xml-map "ip_rsvp_cfg:Checksum";
        description "RSVP message checksum computation";
        leaf disable {
          xr:xr-xml-map "ip_rsvp_cfg:Disable";
          xr:xr-cli-map "rsvp signalling checksum disable ";
          type empty;
          description "Disable RSVP message checksum computation";
        }
      }
      leaf hello-graceful-restart-misses {
        xr:xr-xml-map "ip_rsvp_cfg:HelloGracefulRestartMisses";
        xr:xr-cli-map "rsvp signalling hello graceful-restart refre"+
          "sh misses <number> ";
        type uint32 {
          range "1..10";
        }
        default "3";
        description
          "Configure max number of consecutive missed
          Hello messages";
      }
      leaf hello-graceful-restart-interval {
        xr:xr-xml-map "ip_rsvp_cfg:HelloGracefulRestartInterval";
        xr:xr-cli-map "rsvp signalling hello graceful-restart refre"+
          "sh interval <number> ";
        type uint32 {
          range "3000..30000";
        }
        units "millisecond";
        default "5000";
        description
          "Configure interval between successive Hello
          messages";
      }
    }
    uses AUTHENTICATION;
  }

  augment "/a1:snmp/a1:notification" {

    container rsvp {
      xr:xr-xml-map "rsvpmib_cfg:RSVP";
      description "Enable RSVP-MIB notifications";
      leaf lost-flow {
        xr:xr-xml-map "rsvpmib_cfg:LostFlow";
        type empty;
        description "Enable lostFlow notification";
      }
      leaf new-flow {
        xr:xr-xml-map "rsvpmib_cfg:NewFlow";
        type empty;
        description "Enable newFlow notification";
      }
      leaf enable {
        xr:xr-xml-map "rsvpmib_cfg:Enable";
        type empty;
        description "Enable all RSVP notifications";
      }
    }
    description
      "This augment extends the configuration data of
      'Cisco-IOS-XR-snmp-agent-cfg'";
  }
}
