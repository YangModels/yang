module Cisco-IOS-XR-ip-tcp-cfg {

  /*** NAMESPACE / PREFIX DEFINITION ***/

  namespace "http://cisco.com/ns/yang/Cisco-IOS-XR-ip-tcp-cfg";


  prefix "ip-tcp-cfg";

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ip-tcp package configuration.

     This module contains definitions
     for the following management objects:
       ip-tcp: Global IP TCP configuration
       ip: ip

     Copyright (c) 2013-2016 by Cisco Systems, Inc.
     All rights reserved.";

  revision "2016-02-26" {
    description
      "Descriptions updated.";
  }

  revision "2015-11-09" {
    description
      "IOS XR 6.0 revision.";
  }


  grouping TFTP {
    description "Common node of ipv4, ipv6";

    container tftp {
      xr:xr-xml-map "ip_tcp_services_vrf_cfg:TFTP";
      description "TFTP server configuration commands";

      container udp {
        xr:xr-xml-map "ip_tcp_services_vrf_cfg:UDP";
        presence "Indicates a udp node is configured.";
        description "UDP details";
        leaf access-list-name {
          xr:xr-xml-map "ip_tcp_services_vrf_cfg:AccessListName";
          type string;
          description "Access list";
        }
        leaf maximum-server {
          xr:xr-xml-map "ip_tcp_services_vrf_cfg:MaximumServer";
          type uint32 {
            range "0..2147483647";
          }
          description
            "Set number of allowable servers, 0 for
            no-limit";
        }
        leaf home-directory {
          xr:xr-xml-map "ip_tcp_services_vrf_cfg:HomeDirectory";
          type string;
          mandatory true;
          description
            "Specify device name where file is read from (e
            .g. flash:)";
        }
        leaf dscp-value {
          xr:xr-xml-map "ip_tcp_services_vrf_cfg:DSCPValue";
          type int32;
          description
            "Set IP DSCP (DiffServ CodePoint) for TFTP
            Server Packets";
        }
      }
    }
  }

  grouping SMALL-SERVERS {
    description "Common node of ipv4, ipv6";

    container small-servers {
      xr:xr-xml-map "ip_tcp_services_cfg:SmallServers";
      description "Describing IPV4 and IPV6 small servers";

      container tcp-small-servers {
        xr:xr-xml-map "ip_tcp_services_cfg:TCPSmallServers";
        presence "Indicates a tcp-small-servers node is configured.";
        description
          "Describing TCP related IPV4 and IPV6 small
          servers";
        leaf access-control-list-name {
          xr:xr-xml-map "ip_tcp_services_cfg:AccessControlListName";
          type string;
          description "Access list";
        }
        leaf small-server {
          xr:xr-xml-map "ip_tcp_services_cfg:SmallServer";
          type int32;
          mandatory true;
          description
            "Set number of allowable TCP small servers,
            specify 0 for no-limit";
        }
      }
    }
  }

  grouping TELNET {
    description "Common node of ipv4, ipv6";

    container telnet {
      xr:xr-xml-map "ip_tcp_services_vrf_cfg:TELNET";
      description "TELNET server configuration commands";

      container tcp {
        xr:xr-xml-map "ip_tcp_services_vrf_cfg:TCP";
        presence "Indicates a tcp node is configured.";
        description "TCP details";
        leaf access-list-name {
          xr:xr-xml-map "ip_tcp_services_vrf_cfg:AccessListName";
          type string;
          description "Access list";
        }
        leaf maximum-server {
          xr:xr-xml-map "ip_tcp_services_vrf_cfg:MaximumServer";
          type uint32 {
            range "1..100";
          }
          mandatory true;
          description "Set number of allowable servers";
        }
      }
    }
  }

  container ip-tcp {
    xr:xr-xml-map "ip_tcp_cfg:IP_TCP";
    description "Global IP TCP configuration";

    container directory {
      xr:xr-xml-map "ip_tcp_cfg:Directory";
      presence "Indicates a directory node is configured.";
      description "TCP directory details";
      leaf directoryname {
        xr:xr-xml-map "ip_tcp_cfg:Directoryname";
        type string;
        mandatory true;
        description "Directory name ";
      }
      leaf max-debug-files {
        xr:xr-xml-map "ip_tcp_cfg:MaxDebugFiles";
        type uint32 {
          range "1..10000";
        }
        mandatory true;
        description "Set number of Debug files";
      }
      leaf max-file-size-files {
        xr:xr-xml-map "ip_tcp_cfg:MaxFileSizeFiles";
        type uint32 {
          range "1024..4294967295";
        }
        units "byte";
        mandatory true;
        description "Set size of debug files in bytes";
      }
    }

    container throttle {
      xr:xr-xml-map "ip_tcp_cfg:Throttle";
      presence "Indicates a throttle node is configured.";
      description "Throttle TCP receive buffer (in percentage)";
      leaf tcpmin-throttle {
        xr:xr-xml-map "ip_tcp_cfg:tcpminThrottle";
        type uint32 {
          range "0..100";
        }
        mandatory true;
        description "Min throttle";
      }
      leaf tcpmaxthrottle {
        xr:xr-xml-map "ip_tcp_cfg:tcpmaxthrottle";
        type uint32 {
          range "0..100";
        }
        mandatory true;
        description "Max throttle";
      }
    }

    container num-thread {
      xr:xr-xml-map "ip_tcp_cfg:NumThread";
      presence "Indicates a num-thread node is configured.";
      description "TCP InQueue and OutQueue threads";
      leaf tcp-in-q-threads {
        xr:xr-xml-map "ip_tcp_cfg:tcpInQThreads";
        type uint32 {
          range "1..16";
        }
        mandatory true;
        description "InQ Threads";
      }
      leaf tcp-out-q-threads {
        xr:xr-xml-map "ip_tcp_cfg:tcpOutQThreads";
        type uint32 {
          range "1..16";
        }
        mandatory true;
        description "OutQ Threads";
      }
    }
    leaf accept-rate {
      xr:xr-xml-map "ip_tcp_cfg:AcceptRate";
      xr:xr-cli-map "tcp accept-rate <number> ";
      type uint32 {
        range "1..1000";
      }
      default "500";
      description "TCP connection accept rate";
    }
    leaf selective-ack {
      xr:xr-xml-map "ip_tcp_cfg:SelectiveAck";
      xr:xr-cli-map "tcp selective-ack ";
      type empty;
      description "Enable TCP selective-ACK";
    }
    leaf window-size {
      xr:xr-xml-map "ip_tcp_cfg:WindowSize";
      xr:xr-cli-map "tcp window-size <number> ";
      type uint32 {
        range "2048..65535";
      }
      units "byte";
      description "TCP receive window size (bytes)";
    }
    leaf receive-q {
      xr:xr-xml-map "ip_tcp_cfg:ReceiveQ";
      xr:xr-cli-map "tcp receive-queue <number> ";
      type uint32 {
        range "40..800";
      }
      description "TCP receive Queue Size";
    }
    leaf maximum-segment-size {
      xr:xr-xml-map "ip_tcp_cfg:MaximumSegmentSize";
      xr:xr-cli-map "tcp mss <number> ";
      type uint32 {
        range "68..10000";
      }
      description "TCP initial maximum segment size";
    }
    leaf syn-wait-time {
      xr:xr-xml-map "ip_tcp_cfg:SynWaitTime";
      xr:xr-cli-map "tcp synwait-time <number> ";
      type uint32 {
        range "5..30";
      }
      units "second";
      description "Time to wait on new TCP connections in seconds";
    }
    leaf timestamp {
      xr:xr-xml-map "ip_tcp_cfg:Timestamp";
      xr:xr-cli-map "tcp timestamp ";
      type empty;
      description "Enable TCP timestamp option";
    }
    leaf path-mtu-discovery {
      xr:xr-xml-map "ip_tcp_cfg:PathMTUDiscovery";
      xr:xr-cli-map "tcp path-mtu-discovery [age-timer <enum>] ";
      type int32;
      units "minute";
      default "10";
      description
        "Aging time; 0 for infinite, and range be (10,30)";
    }
  }

  container ip {
    xr:xr-xml-map "ip_tcp_services_cfg:IP";
    description "ip";

    container cinetd {
      xr:xr-xml-map "ip_tcp_services_cfg:Cinetd";
      description "Cinetd configuration data";

      container services {
        xr:xr-xml-map "ip_tcp_services_cfg:Services";
        description "Describing services of cinetd";

        container ipv4 {
          xr:xr-xml-map "ip_tcp_services_cfg:IPV4";
          description "IPV4 related services";
          uses SMALL-SERVERS;
        }

        container vrfs {
          xr:xr-xml-map "ip_tcp_services_vrf_cfg:VRFTable";
          description "VRF table";

          list vrf {
            xr:xr-xml-map "ip_tcp_services_vrf_cfg:VRF";
            key "vrf-name";
            description "VRF specific data";

            container ipv6 {
              xr:xr-xml-map "ip_tcp_services_vrf_cfg:IPV6";
              description "IPV6 related services";
              uses TELNET;
              uses TFTP;
            }

            container ipv4 {
              xr:xr-xml-map "ip_tcp_services_vrf_cfg:IPV4";
              description "IPV4 related services";
              uses TELNET;
              uses TFTP;
            }
            leaf vrf-name {
              xr:xr-xml-map "ip_tcp_services_vrf_cfg:VRFName";
              type xr:Cisco-ios-xr-string;
              description "Name of the VRF instance";
            }
          }
        }

        container ipv6 {
          xr:xr-xml-map "ip_tcp_services_cfg:IPV6";
          description "IPV6 related services";
          uses SMALL-SERVERS;
        }
      }
    }
  }
}
