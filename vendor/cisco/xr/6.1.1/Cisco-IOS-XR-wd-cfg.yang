module Cisco-IOS-XR-wd-cfg {

  /*** NAMESPACE / PREFIX DEFINITION ***/

  namespace "http://cisco.com/ns/yang/Cisco-IOS-XR-wd-cfg";


  prefix "wd-cfg";

  /*** LINKAGE (IMPORTS / INCLUDES) ***/

  import Cisco-IOS-XR-types { prefix "xr"; }

  import Cisco-IOS-XR-config-mda-cfg { prefix "node"; }

  import Cisco-IOS-XR-config-mda-cfg { prefix "a1"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR wd package configuration.

     This module contains definitions
     for the following management objects:
       watchdog: watchdog

     This YANG module augments the
       Cisco-IOS-XR-config-mda-cfg
       Cisco-IOS-XR-config-mda-cfg
     modules with configuration data.

     Copyright (c) 2013-2016 by Cisco Systems, Inc.
     All rights reserved.";

  revision "2015-11-09" {
    description
      "IOS XR 6.0 revision.";
  }

  revision "2015-10-12" {
    description
      "Descriptions updated.";
  }


  grouping NODE-CFG {
    description "active/preconfigured nodes configuration";

    container watchdog-node-threshold {
      xr:xr-xml-map "wd_cfg:WatchdogNodeThreshold";
      description "Watchdog threshold configuration";

      container memory-threshold {
        xr:xr-xml-map "wd_cfg:MemoryThreshold";
        description "Memory thresholds";
        leaf minor {
          xr:xr-xml-map "wd_cfg:minor";
          type uint32 {
            range "5..40";
          }
          description "Threshold, Range(5, 40)";
        }
        leaf severe {
          xr:xr-xml-map "wd_cfg:severe";
          type uint32 {
            range "4..40";
          }
          description "Threshold, Range(4, minor)";
        }
        leaf critical {
          xr:xr-xml-map "wd_cfg:critical";
          type uint32 {
            range "3..40";
          }
          description "Threshold, Range(3, severe)";
        }
      }
    }
  }

  container watchdog {
    xr:xr-xml-map "wd_cfg:Watchdog";
    description "watchdog";

    container threshold-memory {
      xr:xr-xml-map "wd_cfg:ThresholdMemory";
      description "Memory thresholds";
      leaf minor {
        xr:xr-xml-map "wd_cfg:minor";
        type uint32 {
          range "5..40";
        }
        description "Threshold, Range(5, 40)";
      }
      leaf severe {
        xr:xr-xml-map "wd_cfg:severe";
        type uint32 {
          range "4..40";
        }
        description "Threshold, Range(4, minor)";
      }
      leaf critical {
        xr:xr-xml-map "wd_cfg:critical";
        type uint32 {
          range "3..40";
        }
        description "Threshold, Range(3, severe)";
      }
    }
    leaf threshold-memory-switchover {
      xr:xr-xml-map "wd_cfg:ThresholdMemorySwitchover";
      xr:xr-cli-map "threshold memory switchover (minor)|(severe)|("+
        "critical) ";
      type uint32 {
        range "2..4";
      }
      description "switchover the RP at configured memory state";
    }
    leaf restart-deadlock-disable {
      xr:xr-xml-map "wd_cfg:RestartDeadlockDisable";
      xr:xr-cli-map "restart deadlock disable ";
      type empty;
      description "Disable watchdog restart deadlock";
    }
    leaf monitor-qnet-timeout {
      xr:xr-xml-map "wd_cfg:MonitorQnetTimeout";
      xr:xr-cli-map "monitor transport qnet timeout <number> ";
      type uint32 {
        range "10..3600";
      }
      units "second";
      description "Watchdog monitor transport qnet timeout";
    }
    leaf monitor-cpuhog-timeout {
      xr:xr-xml-map "wd_cfg:MonitorCpuhogTimeout";
      xr:xr-cli-map "monitor cpu-hog persistent timeout <number> ";
      type uint32 {
        range "10..3600";
      }
      units "second";
      description
        "Watchdog monitor cpu-hog persistent timeout
        configuration";
    }
    leaf monitor-procnto-timeout {
      xr:xr-xml-map "wd_cfg:MonitorProcntoTimeout";
      xr:xr-cli-map "monitor procnto timeout <number> ";
      type uint32 {
        range "60..3600";
      }
      units "second";
      description "Watchdog monitor procnto timeout configuration";
    }
    leaf overload-notification {
      xr:xr-xml-map "wd_cfg:OverloadNotification";
      xr:xr-cli-map "overload notification disable ";
      type empty;
      description "Disable critical event notification";
    }
    leaf restart-cpuhog-disable {
      xr:xr-xml-map "wd_cfg:RestartCpuhogDisable";
      xr:xr-cli-map "restart cpu-hog disable ";
      type empty;
      description "Disable watchdog restart cpu-hog";
    }
    leaf restart-memoryhog-disable {
      xr:xr-xml-map "wd_cfg:RestartMemoryhogDisable";
      xr:xr-cli-map "restart memory-hog disable ";
      type empty;
      description "Disable watchdog restart memory-hog";
    }
    leaf overload-throttle-timeout {
      xr:xr-xml-map "wd_cfg:OverloadThrottleTimeout";
      xr:xr-cli-map "overload throttle-timeout <number> ";
      type uint32 {
        range "5..120";
      }
      units "second";
      description
        "Watchdog overload throttle timeout configuration";
    }
  }

  augment "/node:active-nodes/node:active-node" {
    uses NODE-CFG;
    description "This augment extends active nodes configuration";
  }

  augment "/node:preconfigured-nodes/node:preconfigured-node" {
    uses NODE-CFG;
    description
      "This augment extends preconfigured nodes
      configuration";
  }
}
