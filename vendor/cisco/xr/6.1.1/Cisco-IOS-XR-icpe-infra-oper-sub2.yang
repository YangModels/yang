submodule Cisco-IOS-XR-icpe-infra-oper-sub2 {

  belongs-to Cisco-IOS-XR-icpe-infra-oper {
    prefix Cisco-IOS-XR-icpe-infra-oper;
  }

  /*** LINKAGE (IMPORTS / INCLUDES) ***/

  import Cisco-IOS-XR-types { prefix "xr"; }

  include Cisco-IOS-XR-icpe-infra-oper-sub5 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR icpe-infra package operational data.

     Copyright (c) 2013-2016 by Cisco Systems, Inc.
     All rights reserved.";

  revision "2015-11-09" {
    description
      "IOS XR 6.0 revision.";
  }


  grouping ICPE-RELOAD-STATUS-DETAIL {
    description "Detailed breakdown of reload status";
    leaf satellite-range-xr {
      xr:xr-xml-map "icpe_reload_data_gen:satellite-range-xr";
      type Xr-yang-string;
      description "Satellite range";
    }
    leaf-list sats-not-initiated {
      xr:xr-xml-map "icpe_reload_data_gen:SatsNotInitiated";
      type uint16;
      description "Sats not initiated";
    }
    leaf-list sats-reloading {
      xr:xr-xml-map "icpe_reload_data_gen:SatsReloading";
      type uint16;
      description "Sats reloading";
    }
    leaf-list sats-reloaded {
      xr:xr-xml-map "icpe_reload_data_gen:SatsReloaded";
      type uint16;
      description "Sats reloaded";
    }
    leaf-list sats-reload-failed {
      xr:xr-xml-map "icpe_reload_data_gen:SatsReloadFailed";
      type uint16;
      description "Sats reload failed";
    }
  }
}
