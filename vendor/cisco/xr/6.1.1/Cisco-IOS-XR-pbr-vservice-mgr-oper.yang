module Cisco-IOS-XR-pbr-vservice-mgr-oper {

  /*** NAMESPACE / PREFIX DEFINITION ***/

  namespace "http://cisco.com/ns/yang"+
    "/Cisco-IOS-XR-pbr-vservice-mgr-oper";


  prefix "pbr-vservice-mgr-oper";

  /*** LINKAGE (IMPORTS / INCLUDES) ***/

  import Cisco-IOS-XR-types { prefix "xr"; }

  import Cisco-IOS-XR-pbr-datatypes { prefix "dt1"; }

  include Cisco-IOS-XR-pbr-vservice-mgr-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR pbr-vservice-mgr package operational data.

     This module contains definitions
     for the following management objects:
       global-service-function-chaining: NSH Service Function
         Chaining global operational data

     Copyright (c) 2013-2016 by Cisco Systems, Inc.
     All rights reserved.";

  revision "2015-11-09" {
    description
      "IOS XR 6.0 revision.";
  }


  container global-service-function-chaining {
    xr:xr-xml-map "vservice_mgr_nsh_oper:GlobalServiceFunctionChain"+
      "ing";
    config false;
    description
      "NSH Service Function Chaining global operational
      data";

    container service-function-path {
      xr:xr-xml-map "vservice_mgr_nsh_oper:ServiceFunctionPath";
      description "Service Function Path operational data";

      container path-ids {
        xr:xr-xml-map "vservice_mgr_nsh_oper:PathIdTable";
        description "Service Function Path Id ";

        list path-id {
          xr:xr-xml-map "vservice_mgr_nsh_oper:PathId";
          key "id";
          description "Specific Service-Function-Path identifier ";

          container stats {
            xr:xr-xml-map "vservice_mgr_nsh_oper:Stats";
            description "SFP Statistics";

            container detail {
              xr:xr-xml-map "vservice_mgr_nsh_oper:Detail";
              description "Detail statistics per service index ";
              uses VSERVICE-EDM-NSH-STATS-INFO;
            }

            container summarized {
              xr:xr-xml-map "vservice_mgr_nsh_oper:Summarized";
              description
                "Combined statistics of all service index in
                service functionpath";
              uses VSERVICE-EDM-NSH-STATS-INFO;
            }
          }

          container service-indexes {
            xr:xr-xml-map "vservice_mgr_nsh_oper:ServiceIndexTable";
            description "Service Index Belonging to Path";

            list service-index {
              xr:xr-xml-map "vservice_mgr_nsh_oper:ServiceIndex";
              key "index";
              description
                "Service index operational data belonging to
                this path";
              leaf index {
                xr:xr-xml-map "vservice_mgr_nsh_oper:Index";
                type dt1:Vservice-nsh-service-index-range;
                description "Service Index";
              }
              uses VSERVICE-EDM-NSH-STATS-INFO;
            }
          }
          leaf id {
            xr:xr-xml-map "vservice_mgr_nsh_oper:Id";
            type dt1:Vservice-nsh-path-id-range;
            description "Specific Service-Function-Path identifier";
          }
        }
      }
    }

    container service-function {
      xr:xr-xml-map "vservice_mgr_nsh_oper:ServiceFunction";
      description "Service Function operational data";

      container sf-names {
        xr:xr-xml-map "vservice_mgr_nsh_oper:SFNameListTable";
        description "List of Service Function Names";

        list sf-name {
          xr:xr-xml-map "vservice_mgr_nsh_oper:SFName";
          key "name";
          description "Name of Service Function";
          leaf name {
            xr:xr-xml-map "vservice_mgr_nsh_oper:Name";
            type xr:Cisco-ios-xr-string {
              length "0..32";
            }
            description "Name";
          }
          uses VSERVICE-EDM-NSH-STATS-INFO;
        }
      }
    }

    container service-function-forwarder {
      xr:xr-xml-map "vservice_mgr_nsh_oper:ServiceFunctionForwarder";
      description "Service Function Forwarder operational data";

      container sff-names {
        xr:xr-xml-map "vservice_mgr_nsh_oper:SFFNameListTable";
        description "List of Service Function Forwarder Names";

        list sff-name {
          xr:xr-xml-map "vservice_mgr_nsh_oper:SFFName";
          key "name";
          description "Name of Service Function Forwarder";
          leaf name {
            xr:xr-xml-map "vservice_mgr_nsh_oper:Name";
            type xr:Cisco-ios-xr-string {
              length "0..32";
            }
            description "Name";
          }
          uses VSERVICE-EDM-NSH-STATS-INFO;
        }
      }

      container local {
        xr:xr-xml-map "vservice_mgr_nsh_oper:Local";
        description
          "Local Service Function Forwarder operational
          data";

        container error {
          xr:xr-xml-map "vservice_mgr_nsh_oper:Error";
          description
            "Error Statistics for local service function
            forwarder";
          uses VSERVICE-EDM-NSH-STATS-INFO;
        }
      }
    }
  }
}
