submodule Cisco-IOS-XR-atm-vcm-oper-sub1 {

  belongs-to Cisco-IOS-XR-atm-vcm-oper {
    prefix Cisco-IOS-XR-atm-vcm-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR atm-vcm package operational data.

     Copyright (c) 2013-2016 by Cisco Systems, Inc.
     All rights reserved.";

  revision "2015-11-09" {
    description
      "IOS XR 6.0 revision.";
  }

  typedef Vp-state {
    type enumeration {
      enum vp-initialized {
        value 0;
        description "VP-Tunnel State: Initialized";
      }
      enum vp-modifying {
        value 1;
        description "VP-Tunnel State: Modifying";
      }
      enum vp-ready {
        value 2;
        description "VP-Tunnel State: Ready";
      }
      enum vp-mgd-down {
        value 3;
        description "VP-Tunnel State: Managed Down";
      }
      enum vp-deleting {
        value 4;
        description "VP-Tunnel State: Deleting";
      }
      enum vp-deleted {
        value 5;
        description "VP-Tunnel State: Deleted";
      }
      enum vp-state-unknown {
        value 6;
        description "VP-Tunnel State: Unknown";
      }
    }
    description "VP-Tunnel State";
  }
  typedef Vp-traf-shaping {
    type enumeration {
      enum vp-cbr {
        value 1;
        description "VP-Tunnel traffic shaping type CBR";
      }
      enum vp-vbr-nrt {
        value 2;
        description "VP-Tunnel traffic shaping type VBR-NR";
      }
      enum vp-vbr-rt {
        value 3;
        description "VP-Tunnel traffic shaping type VBR-RT";
      }
      enum vp-abr {
        value 4;
        description "VP-Tunnel traffic shaping type ABR";
      }
      enum vp-ubr-plus {
        value 5;
        description "VP-Tunnel traffic shaping type UBR+";
      }
      enum vp-ubr {
        value 6;
        description "VP-Tunnel traffic shaping type UBR";
      }
      enum vp-traf-shaping-unknown {
        value 7;
        description
          "VP-Tunnel traffic shaping type Unknown
          (invalid)";
      }
    }
    description "VP-Tunnel traffic shaping type";
  }

  grouping ATM-VCM-VP {
    description "ATM VP-Tunnel data";
    leaf main-interface {
      xr:xr-xml-map "atm_vcm_vp:MainInterface";
      type xr:Interface-name;
      description "Main Interface handle";
    }
    leaf vp-interface {
      xr:xr-xml-map "atm_vcm_vp:VPInterface";
      type xr:Interface-name;
      description "VP Interfcace handle";
    }
    leaf vpi-xr {
      xr:xr-xml-map "atm_vcm_vp:vpi-xr";
      type uint16;
      description "VP-Tunnel VPI value";
    }
    leaf shape {
      xr:xr-xml-map "atm_vcm_vp:Shape";
      type Vp-traf-shaping;
      description "ATM VP traffic shaping type";
    }
    leaf peak-cell-rate {
      xr:xr-xml-map "atm_vcm_vp:PeakCellRate";
      type uint32;
      units "kbit/s";
      description "Peak cell rate in Kbps";
    }
    leaf sustained-cell-rate {
      xr:xr-xml-map "atm_vcm_vp:SustainedCellRate";
      type uint32;
      units "kbit/s";
      description "Sustained cell rate in Kbps";
    }
    leaf burst-rate {
      xr:xr-xml-map "atm_vcm_vp:BurstRate";
      type uint32;
      description "Burst size in cells";
    }
    leaf f4oam-enabled {
      xr:xr-xml-map "atm_vcm_vp:F4OAMEnabled";
      type boolean;
      description "F4OAM Enabled flag";
    }
    leaf data-vc-count {
      xr:xr-xml-map "atm_vcm_vp:DataVCCount";
      type uint32;
      description "Number of Data PVCs under this VP-tunnel";
    }
    leaf oper-status {
      xr:xr-xml-map "atm_vcm_vp:OperStatus";
      type boolean;
      description
        "TRUE value indicates that the VP is
        operationally UP";
    }
    leaf amin-status {
      xr:xr-xml-map "atm_vcm_vp:AminStatus";
      type boolean;
      description
        "TRUE value indicates that the VP is
        administratively UP";
    }
    leaf internal-state {
      xr:xr-xml-map "atm_vcm_vp:InternalState";
      type Vp-state;
      description "Internal state";
    }
    leaf last-vp-state-change-time {
      xr:xr-xml-map "atm_vcm_vp:LastVPStateChangeTime";
      type uint32;
      description "Time when VP-Tunnel state was last changed";
    }
  }
}
