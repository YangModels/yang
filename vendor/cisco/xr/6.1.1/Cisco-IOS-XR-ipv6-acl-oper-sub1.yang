submodule Cisco-IOS-XR-ipv6-acl-oper-sub1 {

  belongs-to Cisco-IOS-XR-ipv6-acl-oper {
    prefix Cisco-IOS-XR-ipv6-acl-oper;
  }

  /*** LINKAGE (IMPORTS / INCLUDES) ***/

  import ietf-inet-types { prefix "inet"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR ipv6-acl package operational data.

     Copyright (c) 2013-2016 by Cisco Systems, Inc.
     All rights reserved.";

  revision "2015-11-09" {
    description
      "IOS XR 6.0 revision.";
  }

  typedef Bag-acl-nh-at-status {
    type enumeration {
      enum unknown {
        description "AT State Unknown";
      }
      enum up {
        description "AT State UP";
      }
      enum down {
        description "AT State DOWN";
      }
      enum not-present {
        description "AT State Not Present";
      }
      enum max {
        description "invalid status";
      }
    }
    description "Bag acl nh at status";
  }
  typedef Bag-acl-nh-status {
    type enumeration {
      enum not-present {
        description "State Not Present";
      }
      enum unknown {
        description "State Unknown";
      }
      enum down {
        description "State DOWN";
      }
      enum up {
        description "State UP";
      }
      enum max {
        description "invalid status";
      }
    }
    description "Bag acl nh status";
  }
  typedef Bag-acl-nh {
    type enumeration {
      enum nexthop-none {
        description "Next Hop None";
      }
      enum nexthop-default {
        description "Nexthop Default";
      }
      enum nexthop {
        description "Nexthop";
      }
    }
    description "Bag acl nh";
  }
  typedef Acl-ttl-operator {
    type Acl-port-operator;
    description "Acl ttl operator";
  }
  typedef Acl-plen-operator {
    type Acl-port-operator;
    description "Acl plen operator";
  }
  typedef Acl-tcpflags-operator {
    type enumeration {
      enum match-none {
        description "Match None";
      }
      enum match-all {
        description "Match All";
      }
      enum match-any-old {
        description "Match any old";
      }
      enum match-any {
        description "Match any";
      }
    }
    description "Acl tcpflags operator";
  }
  typedef Acl-log {
    type enumeration {
      enum log-none {
        value 0;
        description "Log None";
      }
      enum log {
        value 1;
        description "Log Regular";
      }
      enum log-input {
        value 2;
        description "Log Input";
      }
    }
    description "Acl log";
  }
  typedef Acl-port-operator {
    type enumeration {
      enum none {
        value 0;
        description "None";
      }
      enum eq {
        value 1;
        description "Equal";
      }
      enum gt {
        value 2;
        description "Greater than";
      }
      enum lt {
        value 3;
        description "Less than";
      }
      enum neq {
        value 4;
        description "Not Equal";
      }
      enum range {
        value 5;
        description "Range";
      }
      enum onebyte {
        value 8;
        description "One Byte";
      }
      enum twobytes {
        value 9;
        description "Two Bytes";
      }
    }
    description "Acl port operator";
  }
  typedef Acl-action {
    type enumeration {
      enum deny {
        value 0;
        description "Deny";
      }
      enum permit {
        value 1;
        description "Permit";
      }
      enum encrypt {
        value 2;
        description "Encrypt";
      }
      enum bypass {
        value 3;
        description "Bypass";
      }
      enum fallthrough {
        value 4;
        description "Fallthrough";
      }
      enum invalid {
        value 5;
        description "Invalid";
      }
    }
    description "Acl action";
  }
  typedef Acl-ace1 {
    type enumeration {
      enum normal {
        description "This is Normal ACE";
      }
      enum remark {
        description "This is Remark ACE";
      }
      enum abf {
        description "This is ABF ACE";
      }
    }
    description "ACE Types";
  }
  typedef Acl-ace {
    type Acl-ace1;
    description "ACE Types";
  }

  grouping IPV6-ACL-EDM-OOR-DETAIL {
    description "Oor deatil config BAG";
    leaf is-default-maximum-configurable-ac-ls {
      xr:xr-xml-map "ipv6_acl_edm:IsDefaultMaximumConfigurableACLs";
      type uint32;
      description "default max configurable acls";
    }
    leaf is-default-maximum-configurable-ac-es {
      xr:xr-xml-map "ipv6_acl_edm:IsDefaultMaximumConfigurableACEs";
      type uint32;
      description "default max configurable aces";
    }
    leaf is-current-configured-ac-ls {
      xr:xr-xml-map "ipv6_acl_edm:IsCurrentConfiguredACLs";
      type uint32;
      description "Current configured acls";
    }
    leaf is-current-configured-aces {
      xr:xr-xml-map "ipv6_acl_edm:IsCurrentConfiguredACES";
      type uint32;
      description "Current configured aces";
    }
    leaf is-current-maximum-configurable-acls {
      xr:xr-xml-map "ipv6_acl_edm:IsCurrentMaximumConfigurableACLS";
      type uint32;
      description "Current max configurable acls";
    }
    leaf is-current-maximum-configurable-aces {
      xr:xr-xml-map "ipv6_acl_edm:IsCurrentMaximumConfigurableACES";
      type uint32;
      description "Current max configurable aces";
    }
    leaf is-maximum-configurable-ac-ls {
      xr:xr-xml-map "ipv6_acl_edm:IsMaximumConfigurableACLs";
      type uint32;
      description "max configurable acls";
    }
    leaf is-maximum-configurable-ac-es {
      xr:xr-xml-map "ipv6_acl_edm:IsMaximumConfigurableACEs";
      type uint32;
      description "max configurable aces";
    }
  }

  grouping IPV6-ACL-BAG-HW-NH-INFO {
    description "HW_NH_Info structure";
    leaf type {
      xr:xr-xml-map "ipv6_acl_edm:Type";
      type Bag-acl-nh;
      description "The next-hop type";
    }
    leaf next-hop {
      xr:xr-xml-map "ipv6_acl_edm:NextHop";
      type inet:ipv6-address;
      description "The Next Hop";
    }
    leaf table-id {
      xr:xr-xml-map "ipv6_acl_edm:TableID";
      type uint32;
      description "Table ID";
    }
    leaf vrf-name {
      xr:xr-xml-map "ipv6_acl_edm:VRFName";
      type string {
        length "0..32";
      }
      description "Vrf Name";
    }
  }

  grouping IPV6-ACL-BAG-NH-INFO {
    description "NH_Info structure";
    leaf next-hop {
      xr:xr-xml-map "ipv6_acl_edm:NextHop";
      type inet:ipv6-address;
      description "The next hop";
    }
    leaf vrf-name {
      xr:xr-xml-map "ipv6_acl_edm:VrfName";
      type string {
        length "0..32";
      }
      description "Vrf Name";
    }
    leaf track-name {
      xr:xr-xml-map "ipv6_acl_edm:TrackName";
      type string {
        length "0..33";
      }
      description "Track name";
    }
    leaf status {
      xr:xr-xml-map "ipv6_acl_edm:Status";
      type Bag-acl-nh-status;
      description "The next hop status";
    }
    leaf at-status {
      xr:xr-xml-map "ipv6_acl_edm:ATStatus";
      type Bag-acl-nh-at-status;
      description "The next hop at status";
    }
    leaf acl-nh-exist {
      xr:xr-xml-map "ipv6_acl_edm:AclNhExist";
      type int32;
      description "The nexthop exist";
    }
  }

  grouping IPV6-ACL-EDM-ACE {
    description "ACLE bag";

    container hw-next-hop-info {
      description "HW Next hop info";
      uses IPV6-ACL-BAG-HW-NH-INFO;
    }
    leaf is-ace-type {
      xr:xr-xml-map "ipv6_acl_edm:IsACEType";
      type Acl-ace;
      description "ACE type (acl, remark)";
    }
    leaf is-ace-sequence-number {
      xr:xr-xml-map "ipv6_acl_edm:IsACESequenceNumber";
      type uint32;
      description "ACLE sequence number";
    }
    leaf is-packet-allow-or-deny {
      xr:xr-xml-map "ipv6_acl_edm:IsPacketAllowOrDeny";
      type Acl-action;
      description "Grant value permit/deny ";
    }
    leaf is-ipv6-protocol-type {
      xr:xr-xml-map "ipv6_acl_edm:IsIPV6ProtocolType";
      type int32;
      description "IsIPV6ProtocolType";
    }
    leaf is-source-address-in-numbers {
      xr:xr-xml-map "ipv6_acl_edm:IsSourceAddressInNumbers";
      type inet:ipv6-address;
      description "IsSourceAddressInNumbers";
    }
    leaf is-source-address-prefix-length {
      xr:xr-xml-map "ipv6_acl_edm:IsSourceAddressPrefixLength";
      type uint32;
      description "IsSourceAddressPrefixLength";
    }
    leaf source-mask {
      xr:xr-xml-map "ipv6_acl_edm:SourceMask";
      type inet:ipv6-address;
      description "Source Mask";
    }
    leaf is-destination-address-in-numbers {
      xr:xr-xml-map "ipv6_acl_edm:IsDestinationAddressInNumbers";
      type inet:ipv6-address;
      description "IsDestinationAddressInNumbers";
    }
    leaf is-destination-address-prefix-length {
      xr:xr-xml-map "ipv6_acl_edm:IsDestinationAddressPrefixLength";
      type uint32;
      description "IsDestinationAddressPrefixLength";
    }
    leaf destination-mask {
      xr:xr-xml-map "ipv6_acl_edm:DestinationMask";
      type inet:ipv6-address;
      description "Destination Mask";
    }
    leaf is-source-operator {
      xr:xr-xml-map "ipv6_acl_edm:IsSourceOperator";
      type Acl-port-operator;
      description "eq, ne, lt, etc...";
    }
    leaf is-source-port1 {
      xr:xr-xml-map "ipv6_acl_edm:IsSourcePort1";
      type uint32;
      description "IsSourcePort1";
    }
    leaf is-source-port2 {
      xr:xr-xml-map "ipv6_acl_edm:IsSourcePort2";
      type uint32;
      description "IsSourcePort2";
    }
    leaf is-destination-operator {
      xr:xr-xml-map "ipv6_acl_edm:IsDestinationOperator";
      type Acl-port-operator;
      description "eq, ne, lt, etc...";
    }
    leaf is-destination-port1 {
      xr:xr-xml-map "ipv6_acl_edm:IsDestinationPort1";
      type uint32;
      description "IsDestinationPort1";
    }
    leaf is-destination-port2 {
      xr:xr-xml-map "ipv6_acl_edm:IsDestinationPort2";
      type uint32;
      description "IsDestinationPort2";
    }
    leaf is-log-option {
      xr:xr-xml-map "ipv6_acl_edm:IsLogOption";
      type Acl-log;
      description "IsLogOption";
    }
    leaf counter-name {
      xr:xr-xml-map "ipv6_acl_edm:CounterName";
      type string;
      description "Counter name";
    }
    leaf is-tcp-bits-operator {
      xr:xr-xml-map "ipv6_acl_edm:IsTCPBitsOperator";
      type Acl-tcpflags-operator;
      description "IsTCPBitsOperator";
    }
    leaf is-tcp-bits {
      xr:xr-xml-map "ipv6_acl_edm:IsTCPBits";
      type uint32;
      description "IsTCPBits";
    }
    leaf is-tcp-bits-mask {
      xr:xr-xml-map "ipv6_acl_edm:IsTCPBitsMask";
      type uint32;
      description "IsTCPBitsMask";
    }
    leaf is-dscp-present {
      xr:xr-xml-map "ipv6_acl_edm:IsDSCPPresent";
      type int32;
      description "IsDSCPPresent";
    }
    leaf is-dscp-valu {
      xr:xr-xml-map "ipv6_acl_edm:IsDSCPValu";
      type uint32;
      description "IsDSCPValu";
    }
    leaf is-precedence-present {
      xr:xr-xml-map "ipv6_acl_edm:IsPrecedencePresent";
      type int32;
      description "IsPrecedencePresent";
    }
    leaf is-precedence-value {
      xr:xr-xml-map "ipv6_acl_edm:IsPrecedenceValue";
      type uint32;
      description "range from 0 to 7";
    }
    leaf is-header-matches {
      xr:xr-xml-map "ipv6_acl_edm:IsHeaderMatches";
      type uint32;
      description "Match if routing header is presant";
    }
    leaf is-packet-length-operator {
      xr:xr-xml-map "ipv6_acl_edm:IsPacketLengthOperator";
      type Acl-plen-operator;
      description "Match if routing header is presant";
    }
    leaf is-packet-length-start {
      xr:xr-xml-map "ipv6_acl_edm:IsPacketLengthStart";
      type uint32;
      description "IsPacketLengthStart";
    }
    leaf is-packet-length-end {
      xr:xr-xml-map "ipv6_acl_edm:IsPacketLengthEnd";
      type uint32;
      description "IsPacketLengthEnd";
    }
    leaf is-time-to-live-operator {
      xr:xr-xml-map "ipv6_acl_edm:IsTimeToLiveOperator";
      type Acl-ttl-operator;
      description "IsTimeToLiveOperator";
    }
    leaf is-time-to-live-start {
      xr:xr-xml-map "ipv6_acl_edm:IsTimeToLiveStart";
      type uint32;
      description "IsTimeToLiveStart";
    }
    leaf is-time-to-live-end {
      xr:xr-xml-map "ipv6_acl_edm:IsTimeToLiveEnd";
      type uint32;
      description "IsTimeToLiveEnd";
    }
    leaf no-stats {
      xr:xr-xml-map "ipv6_acl_edm:no_stats";
      type int32;
      description "no stats";
    }
    leaf hits {
      xr:xr-xml-map "ipv6_acl_edm:hits";
      type uint64;
      description "hits";
    }
    leaf capture {
      xr:xr-xml-map "ipv6_acl_edm:Capture";
      type boolean;
      description "Capture option, TRUE if enabled";
    }
    leaf is-icmp-message-off {
      xr:xr-xml-map "ipv6_acl_edm:IsICMPMessageOff";
      type int32;
      description "Don't generate the icmp message";
    }
    leaf is-comment-for-entry {
      xr:xr-xml-map "ipv6_acl_edm:IsCommentForEntry";
      type string;
      description "IsCommentForEntry";
    }
    leaf next-hop-type {
      xr:xr-xml-map "ipv6_acl_edm:NextHopType";
      type Bag-acl-nh;
      description "Next hop type";
    }
    leaf is-flow-id {
      xr:xr-xml-map "ipv6_acl_edm:IsFlowId";
      type uint32;
      description "IsFlowId";
    }
    leaf source-prefix-group {
      xr:xr-xml-map "ipv6_acl_edm:SourcePrefixGroup";
      type string;
      description "Source prefix object-group";
    }
    leaf destination-prefix-group {
      xr:xr-xml-map "ipv6_acl_edm:DestinationPrefixGroup";
      type string;
      description "Destination prefix object-group";
    }
    leaf source-port-group {
      xr:xr-xml-map "ipv6_acl_edm:SourcePortGroup";
      type string;
      description "Source port object-group";
    }
    leaf destination-port-group {
      xr:xr-xml-map "ipv6_acl_edm:DestinationPortGroup";
      type string;
      description "Destination port object-group";
    }
    leaf acl-name {
      xr:xr-xml-map "ipv6_acl_edm:ACLName";
      type string;
      description "ACL Name";
    }
    leaf sequence-str {
      xr:xr-xml-map "ipv6_acl_edm:SequenceStr";
      type string;
      description "Sequence String";
    }

    list next-hop-info {
      max-elements "3";
      description "Next hop info";
      uses IPV6-ACL-BAG-NH-INFO;
    }
  }

  grouping IPV6-PFX-EDM-ACE {
    description "Prefix list entry BAG";
    leaf is-ace-type {
      xr:xr-xml-map "ipv6_acl_edm:IsACEType";
      type Acl-ace;
      description "ACE type (acl, remark)";
    }
    leaf is-ace-sequence-number {
      xr:xr-xml-map "ipv6_acl_edm:IsACESequenceNumber";
      type uint32;
      description "ACLE sequence number";
    }
    leaf is-packet-allow-or-deny {
      xr:xr-xml-map "ipv6_acl_edm:IsPacketAllowOrDeny";
      type Acl-action;
      description "Grant value permit/deny ";
    }
    leaf is-address-in-numbers {
      xr:xr-xml-map "ipv6_acl_edm:IsAddressInNumbers";
      type inet:ipv6-address;
      description "IPv6 prefix";
    }
    leaf is-address-mask-length {
      xr:xr-xml-map "ipv6_acl_edm:IsAddressMaskLength";
      type uint32;
      description "Prefix length ";
    }
    leaf is-length-operator {
      xr:xr-xml-map "ipv6_acl_edm:IsLengthOperator";
      type Acl-port-operator;
      description "Port Operator";
    }
    leaf is-packet-minimum-length {
      xr:xr-xml-map "ipv6_acl_edm:IsPacketMinimumLength";
      type uint32;
      description "Min length";
    }
    leaf is-packet-maximum-length {
      xr:xr-xml-map "ipv6_acl_edm:IsPacketMaximumLength";
      type uint32;
      description "Maximum length";
    }
    leaf hits {
      xr:xr-xml-map "ipv6_acl_edm:hits";
      type uint32;
      description "Number of hits";
    }
    leaf is-comment-for-entry {
      xr:xr-xml-map "ipv6_acl_edm:IsCommentForEntry";
      type string;
      description "Remark String";
    }
    leaf acl-name {
      xr:xr-xml-map "ipv6_acl_edm:ACLName";
      type string;
      description "ACL Name";
    }
  }
}
