submodule Cisco-IOS-XR-invmgr-oper-sub2 {

  belongs-to Cisco-IOS-XR-invmgr-oper {
    prefix Cisco-IOS-XR-invmgr-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR invmgr package operational data.

     Copyright (c) 2013-2016 by Cisco Systems, Inc.
     All rights reserved.";

  revision "2015-11-09" {
    description
      "IOS XR 6.0 revision.";
  }

  typedef Inv-card-state {
    type enumeration {
      enum inv-card-not-present {
        value 0;
        description "inv card not present";
      }
      enum inv-card-present {
        value 1;
        description "inv card present";
      }
      enum inv-card-reset {
        value 2;
        description "inv card reset";
      }
      enum inv-card-booting {
        value 3;
        description "inv card booting";
      }
      enum inv-card-mbi-booting {
        value 4;
        description "inv card mbi booting";
      }
      enum inv-card-running-mbi {
        value 5;
        description "inv card running mbi";
      }
      enum inv-card-running-ena {
        value 6;
        description "inv card running ena";
      }
      enum inv-card-bring-down {
        value 7;
        description "inv card bring down";
      }
      enum inv-card-ena-failure {
        value 8;
        description "inv card ena failure";
      }
      enum inv-card-f-diag-run {
        value 9;
        description "inv card f diag run";
      }
      enum inv-card-f-diag-failure {
        value 10;
        description "inv card f diag failure";
      }
      enum inv-card-powered {
        value 11;
        description "inv card powered";
      }
      enum inv-card-unpowered {
        value 12;
        description "inv card unpowered";
      }
      enum inv-card-mdr {
        value 13;
        description "inv card mdr";
      }
      enum inv-card-mdr-running-mbi {
        value 14;
        description "inv card mdr running mbi";
      }
      enum inv-card-main-t-mode {
        value 15;
        description "inv card main t mode";
      }
      enum inv-card-admin-down {
        value 16;
        description "inv card admin down";
      }
      enum inv-card-no-mon {
        value 17;
        description "inv card no mon";
      }
      enum inv-card-unknown {
        value 18;
        description "inv card unknown";
      }
      enum inv-card-failed {
        value 19;
        description "inv card failed";
      }
      enum inv-card-ok {
        value 20;
        description "inv card ok";
      }
      enum inv-card-missing {
        value 21;
        description "inv card missing";
      }
      enum inv-card-field-diag-downloading {
        value 22;
        description "inv card field diag downloading";
      }
      enum inv-card-field-diag-unmonitor {
        value 23;
        description "inv card field diag unmonitor";
      }
      enum inv-card-fabric-field-diag-unmonitor {
        value 24;
        description "inv card fabric field diag unmonitor";
      }
      enum inv-card-field-diag-rp-launching {
        value 25;
        description "inv card field diag rp launching";
      }
      enum inv-card-field-diag-running {
        value 26;
        description "inv card field diag running";
      }
      enum inv-card-field-diag-pass {
        value 27;
        description "inv card field diag pass";
      }
      enum inv-card-field-diag-fail {
        value 28;
        description "inv card field diag fail";
      }
      enum inv-card-field-diag-timeout {
        value 29;
        description "inv card field diag timeout";
      }
      enum inv-card-disabled {
        value 30;
        description "inv card disabled";
      }
      enum inv-card-spa-booting {
        value 31;
        description "inv card spa booting";
      }
      enum inv-card-not-allowed-online {
        value 32;
        description "inv card not allowed online";
      }
      enum inv-card-stopped {
        value 33;
        description "inv card stopped";
      }
      enum inv-card-incompatible-fw-ver {
        value 34;
        description "inv card incompatible fw ver";
      }
      enum inv-card-fpd-hold {
        value 35;
        description "inv card fpd hold";
      }
      enum inv-card-node-prep {
        value 36;
        description "inv card node prep";
      }
      enum inv-card-updating-fpd {
        value 37;
        description "inv card updating fpd";
      }
      enum inv-card-num-states {
        value 38;
        description "inv card num states";
      }
    }
    description "Inv card state";
  }

  grouping INV-PHY-ENTITY-BASIC-INFO {
    description
      "Bag contains all the basic inventory information
      for each entity";
    leaf description {
      xr:xr-xml-map "inv:Description";
      type string {
        length "0..255";
      }
      description
        "describes in user-readable terms 						what the
        entity in question does";
    }
    leaf vendor-type {
      xr:xr-xml-map "inv:VendorType";
      type string {
        length "0..255";
      }
      description "maps to the vendor OID string";
    }
    leaf name {
      xr:xr-xml-map "inv:Name";
      type string {
        length "0..255";
      }
      description "name string for the entity";
    }
    leaf hardware-revision {
      xr:xr-xml-map "inv:HardwareRevision";
      type string {
        length "0..255";
      }
      description "hw revision string";
    }
    leaf firmware-revision {
      xr:xr-xml-map "inv:FirmwareRevision";
      type string {
        length "0..255";
      }
      description "firmware revision string";
    }
    leaf software-revision {
      xr:xr-xml-map "inv:SoftwareRevision";
      type string {
        length "0..255";
      }
      description "software revision string";
    }
    leaf chip-hardware-revision {
      xr:xr-xml-map "inv:ChipHardwareRevision";
      type string {
        length "0..255";
      }
      description "chip module hw revision string";
    }
    leaf serial-number {
      xr:xr-xml-map "inv:SerialNumber";
      type string {
        length "0..255";
      }
      description "serial number";
    }
    leaf manufacturer-name {
      xr:xr-xml-map "inv:ManufacturerName";
      type string {
        length "0..255";
      }
      description "manufacturer's name";
    }
    leaf model-name {
      xr:xr-xml-map "inv:ModelName";
      type string {
        length "0..255";
      }
      description "model name";
    }
    leaf asset-id-str {
      xr:xr-xml-map "inv:assetIdStr";
      type string {
        length "0..255";
      }
      description "asset Identification string";
    }
    leaf asset-identification {
      xr:xr-xml-map "inv:AssetIdentification";
      type int32;
      description "asset Identification";
    }
    leaf is-field-replaceable-unit {
      xr:xr-xml-map "inv:IsFieldReplaceableUnit";
      type boolean;
      description "1 if Field Replaceable Unit 0, if not";
    }
    leaf manufacturer-asset-tags {
      xr:xr-xml-map "inv:ManufacturerAssetTags";
      type int32;
      description "Manufacture Asset Tags";
    }
    leaf composite-class-code {
      xr:xr-xml-map "inv:CompositeClassCode";
      type int32;
      description "Major&minor class of the entity";
    }
    leaf memory-size {
      xr:xr-xml-map "inv:MemorySize";
      type int32;
      description
        "Size of memory associated with 						the entity
        where applicable";
    }
    leaf environmental-monitor-path {
      xr:xr-xml-map "inv:EnvironmentalMonitorPath";
      type string {
        length "0..255";
      }
      description "sysdb name of sensor in the envmon EDM";
    }
    leaf alias {
      xr:xr-xml-map "inv:Alias";
      type string {
        length "0..255";
      }
      description "useful for storing an entity alias ";
    }
    leaf group-flag {
      xr:xr-xml-map "inv:GroupFlag";
      type boolean;
      description "indicates if this entity is group 						or not";
    }
    leaf new-deviation-number {
      xr:xr-xml-map "inv:NewDeviationNumber";
      type int32;
      description "integer value for New Deviation Number 0x88";
    }
    leaf physical-layer-interface-module-type {
      xr:xr-xml-map "inv:PhysicalLayerInterfaceModuleType";
      type int32;
      description
        "integer value for plim type if     applicable to
        this entity";
    }
    leaf unrecognized-fru {
      xr:xr-xml-map "inv:UnrecognizedFRU";
      type boolean;
      description "1 if UnrecognizedFRU and 0 for recognizedFRU";
    }
    leaf redundancystate {
      xr:xr-xml-map "inv:Redundancystate";
      type int32;
      description
        "integer value for Redundancy State if    
        applicable to this entity";
    }
    leaf ceport {
      xr:xr-xml-map "inv:CEport";
      type boolean;
      description "1 if ce port found, 0 if not";
    }
    leaf xr-scoped {
      xr:xr-xml-map "inv:XRScoped";
      type boolean;
      description "1 if xr scoped, 0 if not";
    }
  }

  grouping INV-TIMESPEC {
    description "Inventory FRU Info Time Spec";
    leaf time-in-seconds {
      xr:xr-xml-map "inv:TimeInSeconds";
      type int32;
      units "second";
      description "Time Value in Seconds";
    }
    leaf time-in-nano-seconds {
      xr:xr-xml-map "inv:TimeInNanoSeconds";
      type int32;
      units "nanosecond";
      description "Time Value in Nano-seconds";
    }
  }

  grouping INV-CARD-FRU-INFO-SPIRIT {
    description
      "card (FRU) operation state bag for spirit
      platforms";

    container last-operational-state-change {
      description "last card oper change state";
      uses INV-TIMESPEC;
    }

    container card-up-time {
      description "card up time";
      uses INV-TIMESPEC;
    }
    leaf card-administrative-state {
      xr:xr-xml-map "inv:CardAdministrativeState";
      type int32;
      description "card admin state: shutdown or not";
    }
    leaf power-administrative-state {
      xr:xr-xml-map "inv:PowerAdministrativeState";
      type int32;
      description "power admin state: up or down";
    }
    leaf card-operational-state {
      xr:xr-xml-map "inv:CardOperationalState";
      type int32;
      description "card operation state";
    }
    leaf card-monitor-state {
      xr:xr-xml-map "inv:CardMonitorState";
      type int32;
      description
        "card is monitored by a manager or left
        unmonitored";
    }
    leaf card-reset-reason {
      xr:xr-xml-map "inv:CardResetReason";
      type int32;
      description "card reset reason enum";
    }
    leaf power-current-measurement {
      xr:xr-xml-map "inv:PowerCurrentMeasurement";
      type int32;
      description "power current: not implemented";
    }
    leaf power-operational-state {
      xr:xr-xml-map "inv:PowerOperationalState";
      type int32;
      description "Power operation state";
    }
  }

  grouping INV-PHY-ENTITY-ASSET-INFO {
    description "The physical entity detaled asset attribute bag";
    leaf part-number {
      xr:xr-xml-map "inv:PartNumber";
      type string {
        length "0..255";
      }
      description "";
    }
    leaf manufacturer-assembly-number {
      xr:xr-xml-map "inv:ManufacturerAssemblyNumber";
      type string {
        length "0..255";
      }
      description "Manufacture Assembly number";
    }
    leaf manufacturer-assembly-revision {
      xr:xr-xml-map "inv:ManufacturerAssemblyRevision";
      type string {
        length "0..255";
      }
      description "Manufacture assembly revision";
    }
    leaf manufacturer-firmware-identifier {
      xr:xr-xml-map "inv:ManufacturerFirmwareIdentifier";
      type string {
        length "0..255";
      }
      description "";
    }
    leaf manufacturer-software-identifier {
      xr:xr-xml-map "inv:ManufacturerSoftwareIdentifier";
      type string {
        length "0..255";
      }
      description "";
    }
    leaf manufacturer-common-language-equipment-identifier {
      xr:xr-xml-map "inv:ManufacturerCommonLanguageEquipmentIdentif"+
        "ier";
      type string {
        length "0..255";
      }
      description
        "Common Language Equipment 						    Identifier
        number";
    }
    leaf original-equipment-manufacturer-string {
      xr:xr-xml-map "inv:OriginalEquipmentManufacturerString";
      type string {
        length "0..255";
      }
      description
        "String containing OEM information 						    if
        applicable";
    }
  }

  grouping INV-PWG-INFO {
    description "Power supply group bag";
    leaf power-group-redundancy-mode {
      xr:xr-xml-map "inv:PowerGroupRedundancyMode";
      type int32;
      description "redundancy mode";
    }
    leaf power-group-power-units {
      xr:xr-xml-map "inv:PowerGroupPowerUnits";
      type string;
      description "power units";
    }
    leaf power-group-available-current {
      xr:xr-xml-map "inv:PowerGroupAvailableCurrent";
      type int32;
      description "available current";
    }
    leaf power-group-drawn-current {
      xr:xr-xml-map "inv:PowerGroupDrawnCurrent";
      type int32;
      description "drawn current";
    }
  }

  grouping INV-NODE-STATE-INFO {
    description "node state bag";
    leaf node-administrative-state {
      xr:xr-xml-map "inv:NodeAdministrativeState";
      type int32;
      description "node admin state: shutdown or not";
    }
    leaf power-administrative-state {
      xr:xr-xml-map "inv:PowerAdministrativeState";
      type int32;
      description "power admin state: up or down";
    }
    leaf node-operational-state {
      xr:xr-xml-map "inv:NodeOperationalState";
      type Inv-card-state;
      description "node operation state";
    }
    leaf node-monitor-state {
      xr:xr-xml-map "inv:NodeMonitorState";
      type int32;
      description
        "node is monitored by a manager or left
        unmonitored";
    }
    leaf card-type {
      xr:xr-xml-map "inv:CardType";
      type int32;
      description "enumeration of the card type";
    }
  }
}
