module Cisco-IOS-XR-sdr-invmgr-oper {

  /*** NAMESPACE / PREFIX DEFINITION ***/

  namespace "http://cisco.com/ns/yang/Cisco-IOS-XR-sdr-invmgr-oper";


  prefix "sdr-invmgr-oper";

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR sdr-invmgr package operational data.

     This module contains definitions
     for the following management objects:
       sdr-inventory: SDR information

     Copyright (c) 2013-2016 by Cisco Systems, Inc.
     All rights reserved.";

  revision "2015-11-09" {
    description
      "IOS XR 6.0 revision.";
  }


  container sdr-inventory {
    xr:xr-xml-map "inv_sdr_adminoper:SDRInventory";
    config false;
    description "SDR information";

    container racks {
      xr:xr-xml-map "inv_sdr_adminoper:RackTable";
      description "RackTable";

      list rack {
        xr:xr-xml-map "inv_sdr_adminoper:Rack";
        key "name";
        description "Rack name";
        leaf name {
          xr:xr-xml-map "inv_sdr_adminoper:Name";
          type xr:Cisco-ios-xr-string;
          description "Rack name";
        }

        list slot {
          xr:xr-xml-map "inv_sdr_adminoper:Slot";
          key "name";
          description "Slot name";
          leaf name {
            xr:xr-xml-map "inv_sdr_adminoper:Name";
            type xr:Cisco-ios-xr-string;
            description "Slot name";
          }

          list card {
            xr:xr-xml-map "inv_sdr_adminoper:Card";
            key "name";
            description "Card";

            container attributes {
              xr:xr-xml-map "inv_sdr_adminoper:Attributes";
              description "Attributes";
              leaf power {
                xr:xr-xml-map "inv_sdr_adminoper:Power";
                type int32;
                default "0";
                description "Power";
              }
              leaf config-state {
                xr:xr-xml-map "inv_sdr_adminoper:ConfigState";
                type int32;
                default "0";
                description "ConfigState";
              }
              leaf card-state {
                xr:xr-xml-map "inv_sdr_adminoper:CardState";
                type int32;
                default "0";
                description "CardState";
              }
              leaf vm-state {
                xr:xr-xml-map "inv_sdr_adminoper:VMState";
                type int32;
                default "0";
                description "VM State information";
              }
              leaf card-admin-state {
                xr:xr-xml-map "inv_sdr_adminoper:CardAdminState";
                type int32;
                default "0";
                description "Card Admin State";
              }
              leaf card-type {
                xr:xr-xml-map "inv_sdr_adminoper:CardType";
                type int32;
                default "0";
                description "CardType";
              }
              leaf pi-slot-number {
                xr:xr-xml-map "inv_sdr_adminoper:PiSlotNumber";
                type int32;
                default "0";
                description "Pi Slot Number";
              }
              leaf shutdown {
                xr:xr-xml-map "inv_sdr_adminoper:Shutdown";
                type int32;
                default "0";
                description "Shutdown";
              }
              leaf ctype {
                xr:xr-xml-map "inv_sdr_adminoper:CType";
                type int32;
                default "0";
                description "CType";
              }
              leaf monitor {
                xr:xr-xml-map "inv_sdr_adminoper:Monitor";
                type int32;
                default "0";
                description "Monitor";
              }
            }
            leaf name {
              xr:xr-xml-map "inv_sdr_adminoper:Name";
              type xr:Cisco-ios-xr-string;
              description "Card";
            }
          }
        }
      }
    }
  }
}
