module Cisco-IOS-XR-spirit-install-instmgr-oper {

  /*** NAMESPACE / PREFIX DEFINITION ***/

  namespace "http://cisco.com/ns/yang"+
    "/Cisco-IOS-XR-spirit-install-instmgr-oper";


  prefix "spirit-install-instmgr-oper";

  /*** LINKAGE (IMPORTS / INCLUDES) ***/

  import Cisco-IOS-XR-types { prefix "xr"; }

  include Cisco-IOS-XR-spirit-install-instmgr-oper-sub2 {
    revision-date 2015-11-09;
  }

  include Cisco-IOS-XR-spirit-install-instmgr-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR spirit-install-instmgr package operational data.

     This module contains definitions
     for the following management objects:
       software-install: Install operations info

     Copyright (c) 2013-2016 by Cisco Systems, Inc.
     All rights reserved.";

  revision "2015-11-09" {
    description
      "IOS XR 6.0 revision.";
  }


  container software-install {
    xr:xr-xml-map "instmgr_show_oper:SoftwareInstall";
    config false;
    description "Install operations info";

    container files {
      xr:xr-xml-map "instmgr_show_oper:FileTable";
      description "Show information about an installed file";

      list file {
        xr:xr-xml-map "instmgr_show_oper:File";
        key "file-name";
        description "Show information about an installed file";

        container brief {
          xr:xr-xml-map "instmgr_show_oper:Brief";
          description "Show information about an installed file";
          uses INSTALL-LOG;
        }

        container detail {
          xr:xr-xml-map "instmgr_show_oper:Detail";
          description
            "Show detail information about an installed
            file";
          uses INSTALL-LOG;
        }
        leaf file-name {
          xr:xr-xml-map "instmgr_show_oper:FileName";
          type string;
          description "File name";
        }
      }
    }

    container last-n-operation-logs {
      xr:xr-xml-map "instmgr_show_oper:LastNOperationLogTable";
      description "Show log file for last n operations";

      list last-n-operation-log {
        xr:xr-xml-map "instmgr_show_oper:LastNOperationLog";
        key "last-n-logs";
        description "Show log file of last n operations";

        container summary {
          xr:xr-xml-map "instmgr_show_oper:Summary";
          description "Show summary log file for last n operations";
          uses INSTALL-LOG;
        }

        container detail {
          xr:xr-xml-map "instmgr_show_oper:Detail";
          description
            "Show detailed log file for last n operations";
          uses INSTALL-LOG;
        }
        leaf last-n-logs {
          xr:xr-xml-map "instmgr_show_oper:LastNLogs";
          type int32;
          description "Last N opeartion logs";
        }
      }
    }

    container prepare {
      xr:xr-xml-map "instmgr_show_oper:Prepare";
      description "Show prepared packages ready for activation";
      uses INSTALL-LOG;
    }

    container active {
      xr:xr-xml-map "instmgr_show_oper:Active";
      description "Show active packages installed";
      uses INSTMGR-CALV-SHOW-INST-ACT;
    }

    container version {
      xr:xr-xml-map "instmgr_show_oper:Version";
      description "Show install version";
      uses INSTALL-LOG;
    }

    container inactive {
      xr:xr-xml-map "instmgr_show_oper:Inactive";
      description "Show XR inactive packages";
      uses INSTALL-LOG;
    }

    container request {
      xr:xr-xml-map "instmgr_show_oper:Request";
      description "Show current request";
      uses INSTALL-LOG;
    }

    container issu {
      xr:xr-xml-map "instmgr_show_oper:ISSU";
      description "ISSU operation";

      container stage {
        xr:xr-xml-map "instmgr_show_oper:Stage";
        description "Show XR install issu stage";
        uses ISD-STAGE-INFO;
      }

      container inventory {
        xr:xr-xml-map "instmgr_show_oper:Inventory";
        description "Show XR install issu inventory";
        uses ISD-INV-INFO-CONTAINER;
      }
    }

    container committed {
      xr:xr-xml-map "instmgr_show_oper:Committed";
      description "Show Committed packages installed";
      uses INSTMGR-CALV-SHOW-INST-COMMIT;
    }

    container all-operations-log {
      xr:xr-xml-map "instmgr_show_oper:AllOperationsLog";
      description "Show log file for all operations";

      container summary {
        xr:xr-xml-map "instmgr_show_oper:Summary";
        description "Show summary log file for all operations";
        uses INSTALL-LOG;
      }

      container detail {
        xr:xr-xml-map "instmgr_show_oper:Detail";
        description "Show detailed log file for all operations";
        uses INSTALL-LOG;
      }
    }

    container packages {
      xr:xr-xml-map "instmgr_show_oper:PackageTable";
      description "Show the list of installed packages";

      list package {
        xr:xr-xml-map "instmgr_show_oper:Package";
        key "package-name";
        description "Show the info for a installed package";

        container verbose {
          xr:xr-xml-map "instmgr_show_oper:Verbose";
          description
            "Show the verbose info for a installed package";
          uses INSTALL-LOG;
        }

        container brief {
          xr:xr-xml-map "instmgr_show_oper:Brief";
          description "Show the info for a installed package";
          uses INSTALL-LOG;
        }

        container detail {
          xr:xr-xml-map "instmgr_show_oper:Detail";
          description
            "Show the deatil info for a installed package";
          uses INSTALL-LOG;
        }
        leaf package-name {
          xr:xr-xml-map "instmgr_show_oper:PackageName";
          type string;
          description "Package name";
        }
      }
    }

    container operation-logs {
      xr:xr-xml-map "instmgr_show_oper:OperationLogTable";
      description "Show log file";

      list operation-log {
        xr:xr-xml-map "instmgr_show_oper:OperationLog";
        key "log-id";
        description "Show log file for the specified install ID";

        container summary {
          xr:xr-xml-map "instmgr_show_oper:Summary";
          description
            "Show summary log file for the specified
            install ID";
          uses INSTALL-LOG;
        }

        container detail {
          xr:xr-xml-map "instmgr_show_oper:Detail";
          description
            "Show detailed log file for the specified
            install ID";
          uses INSTALL-LOG;
        }
        leaf log-id {
          xr:xr-xml-map "instmgr_show_oper:LogID";
          type int32;
          description "Log ID number";
        }
      }
    }

    container repository {
      xr:xr-xml-map "instmgr_show_oper:Repository";
      description
        "Show packages stored in install software
        repositories";

      container xr {
        xr:xr-xml-map "instmgr_show_oper:XR";
        description "Show install software repository for XR";
        uses INSTALL-LOG;
      }

      container all {
        xr:xr-xml-map "instmgr_show_oper:All";
        description
          "Show contents of all install software
          repositories";
        uses INSTALL-LOG;
      }
    }
  }
}
