module Cisco-IOS-XR-dnx-port-mapper-oper {

  /*** NAMESPACE / PREFIX DEFINITION ***/

  namespace "http://cisco.com/ns/yang"+
    "/Cisco-IOS-XR-dnx-port-mapper-oper";


  prefix "dnx-port-mapper-oper";

  /*** LINKAGE (IMPORTS / INCLUDES) ***/

  import Cisco-IOS-XR-types { prefix "xr"; }

  include Cisco-IOS-XR-dnx-port-mapper-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR dnx-port-mapper package operational data.

     This module contains definitions
     for the following management objects:
       oor: DPA operational data

     Copyright (c) 2013-2016 by Cisco Systems, Inc.
     All rights reserved.";

  revision "2015-11-09" {
    description
      "IOS XR 6.0 revision.";
  }


  container oor {
    xr:xr-xml-map "dnx_port_mapper_oor_edm_oper:OOR";
    config false;
    description "DPA operational data";

    container nodes {
      xr:xr-xml-map "dnx_port_mapper_oor_edm_oper:NodeTable";
      description "OOR data for available nodes";

      list node {
        xr:xr-xml-map "dnx_port_mapper_oor_edm_oper:Node";
        key "node-name";
        description "DPA operational data for a particular node";

        container bundle-interface-details {
          xr:xr-xml-map "dnx_port_mapper_oor_edm_oper:BundleInterfa"+
            "ce";
          description "OOR Bundle Interface Detail";

          list bundle-interface-detail {
            xr:xr-xml-map "dnx_port_mapper_oor_edm_oper:BundleInter"+
              "faceDetail";
            key "interface";
            description "OOR Data for particular Bundle interface";
            leaf interface {
              xr:xr-xml-map "dnx_port_mapper_oor_edm_oper:Interface";
              type int32;
              description "Interface Name";
            }
            uses OOR-BUNDLE-INTERFACE-DETAIL;
          }
        }

        container interface-details {
          xr:xr-xml-map "dnx_port_mapper_oor_edm_oper:Interface";
          description "OOR Interface Detail";

          list interface-detail {
            xr:xr-xml-map "dnx_port_mapper_oor_edm_oper:InterfaceDe"+
              "tail";
            key "interface";
            description "OOR Data for particular interface";
            leaf interface {
              xr:xr-xml-map "dnx_port_mapper_oor_edm_oper:Interface";
              type int32;
              description "Interface Name";
            }
            uses OOR-INTERFACE-DETAIL;
          }
        }

        container interface-summary-datas {
          xr:xr-xml-map "dnx_port_mapper_oor_edm_oper:OORAllInterfa"+
            "ceSummary";
          description "OOR Per Interface Summary";

          list interface-summary-data {
            xr:xr-xml-map "dnx_port_mapper_oor_edm_oper:InterfaceSu"+
              "mmaryData";
            key "interface";
            description "OOR Data for particular interface";
            leaf interface {
              xr:xr-xml-map "dnx_port_mapper_oor_edm_oper:Interface";
              type int32;
              description "Interface Number";
            }
            uses OOR-INTERFACE-SUMMARY;
          }
        }

        container oor-summary {
          xr:xr-xml-map "dnx_port_mapper_oor_edm_oper:OORSummary";
          description "OOR Summary";
          uses OOR-SUMMARY;
        }
        leaf node-name {
          xr:xr-xml-map "dnx_port_mapper_oor_edm_oper:NodeName";
          type xr:Node-id;
          description "Node ID";
        }
      }
    }
  }
}
