module Cisco-IOS-XR-infra-tc-oper {

  /*** NAMESPACE / PREFIX DEFINITION ***/

  namespace "http://cisco.com/ns/yang/Cisco-IOS-XR-infra-tc-oper";


  prefix "infra-tc-oper";

  /*** LINKAGE (IMPORTS / INCLUDES) ***/

  import Cisco-IOS-XR-types { prefix "xr"; }

  include Cisco-IOS-XR-infra-tc-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR infra-tc package operational data.

     This module contains definitions
     for the following management objects:
       traffic-collector: Global Traffic Collector configuration
         commands

     Copyright (c) 2013-2016 by Cisco Systems, Inc.
     All rights reserved.";

  revision "2015-11-09" {
    description
      "IOS XR 6.0 revision.";
  }

  typedef Tc-oper-af-name {
    type enumeration {
      enum ipv4 {
        value 0;
        description "IPv4";
      }
      enum ipv6 {
        value 1;
        description "IPv6";
      }
    }
    description "Tc oper af name";
  }
  typedef Tc-oper-local-label {
    type uint32 {
      range "16..1048575";
    }
    description "Tc oper local label";
  }

  grouping AF-TABLE {
    description "Common node of default-vrf, traffic-collector";

    container afs {
      xr:xr-xml-map "tc_oper:AFTable";
      description "Address Family specific operational data";

      list af {
        xr:xr-xml-map "tc_oper:AF";
        key "af-name";
        description "Operational data for given Address Family";

        container counters {
          xr:xr-xml-map "tc_oper:Counters";
          description "Show Counters";

          container prefixes {
            xr:xr-xml-map "tc_oper:PrefixTable";
            description "Prefix Database";

            list prefix {
              xr:xr-xml-map "tc_oper:Prefix";
              description "Show Prefix Counter";
              leaf ipaddr {
                xr:xr-xml-map "tc_oper:IPaddr";
                type xr:Cisco-ios-xr-string;
                description "IP Address";
              }
              leaf mask {
                xr:xr-xml-map "tc_oper:Mask";
                type xr:Cisco-ios-xr-string;
                description "Prefix Mask";
              }
              leaf label {
                xr:xr-xml-map "tc_oper:Label";
                type Tc-oper-local-label;
                description "Local Label";
              }
              uses TC-MGMT-PREFIX-DATA;
            }
          }

          container tunnels {
            xr:xr-xml-map "tc_oper:TunnelTable";
            description "Tunnels";

            list tunnel {
              xr:xr-xml-map "tc_oper:Tunnel";
              key "interface-name";
              description "Tunnel information";
              leaf interface-name {
                xr:xr-xml-map "tc_oper:InterfaceName";
                type xr:Interface-name;
                description "The Interface Name";
              }
              uses TC-MGMT-TUNNEL-DATA;
            }
          }
        }
        leaf af-name {
          xr:xr-xml-map "tc_oper:AFName";
          type Tc-oper-af-name;
          description "Address Family name";
        }
      }
    }
  }

  container traffic-collector {
    xr:xr-xml-map "tc_oper:TrafficCollector";
    config false;
    description "Global Traffic Collector configuration commands";

    container external-interfaces {
      xr:xr-xml-map "tc_oper:ExternalInterfaceTable";
      description "External Interface";

      list external-interface {
        xr:xr-xml-map "tc_oper:ExternalInterface";
        key "interface-name";
        description "External Interface ";
        leaf interface-name {
          xr:xr-xml-map "tc_oper:InterfaceName";
          type xr:Interface-name;
          description "The Interface Name";
        }
        uses TC-MGMT-EXT-IF-DATA;
      }
    }

    container summary {
      xr:xr-xml-map "tc_oper:Summary";
      description "Traffic Collector summary";
      uses TC-MGMT-SUMMARY;
    }

    container vrf-table {
      xr:xr-xml-map "tc_oper:VRFTable";
      description "VRF specific operational data";

      container default-vrf {
        xr:xr-xml-map "tc_oper:DefaultVRF";
        description "DefaultVRF specific operational data";
        uses AF-TABLE;
      }
    }
    uses AF-TABLE;
  }
}
