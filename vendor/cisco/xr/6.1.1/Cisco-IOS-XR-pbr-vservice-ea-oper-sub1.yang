submodule Cisco-IOS-XR-pbr-vservice-ea-oper-sub1 {

  belongs-to Cisco-IOS-XR-pbr-vservice-ea-oper {
    prefix Cisco-IOS-XR-pbr-vservice-ea-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR pbr-vservice-ea package operational data.

     Copyright (c) 2013-2016 by Cisco Systems, Inc.
     All rights reserved.";

  revision "2015-11-09" {
    description
      "IOS XR 6.0 revision.";
  }

  typedef Vs-nsh-stats {
    type enumeration {
      enum vs-nsh-stats-spi-si {
        description "vs nsh stats spi si";
      }
      enum vs-nsh-stats-ter-min-ate {
        description "vs nsh stats ter min ate";
      }
      enum vs-nsh-stats-sf {
        description "vs nsh stats sf";
      }
      enum vs-nsh-stats-sff {
        description "vs nsh stats sff";
      }
      enum vs-nsh-stats-sff-local {
        description "vs nsh stats sff local";
      }
      enum vs-nsh-stats-sfp {
        description "vs nsh stats sfp";
      }
      enum vs-nsh-stats-sfp-detail {
        description "vs nsh stats sfp detail";
      }
      enum vs-nsh-stats-max {
        description "vs nsh stats max";
      }
    }
    description "Vs nsh stats";
  }

  grouping VS-NSH-SI-DATA {
    description "Service index stats counters";

    container spi-si {
      when "../type = 'vs-nsh-stats-spi-si'" {
        description "../type = 'VS_NSH_STATS_SPI_SI'";
      }
      description "SF/SFF stats";
      uses VSERVICE-NSH-SPI-SI;
    }

    container term {
      when "../type = 'vs-nsh-stats-ter-min-ate'" {
        description "../type = 'VS_NSH_STATS_TERMINATE'";
      }
      description "Terminate stats";
      uses VSERVICE-NSH-SPI-SI-TERMINATE;
    }
    leaf type {
      xr:xr-xml-map "vservice_stats_edm:type";
      type Vs-nsh-stats;
      description "type";
    }
  }

  grouping VSERVICE-NSH-SI {
    description "si supported counters";

    container data {
      description "Stats counter for this index";
      uses VS-NSH-SI-DATA;
    }
    leaf si {
      xr:xr-xml-map "vservice_stats_edm:si";
      type uint8;
      description "Service index";
    }
  }

  grouping VSERVICE-NSH-SFF-LOCAL {
    description "Local service-function-forwarder counters";
    leaf malformed-err-pkts {
      xr:xr-xml-map "vservice_stats_edm:malformed_err_pkts";
      type uint64;
      description "Number of packets with invalid NSH header";
    }
    leaf lookup-err-pkts {
      xr:xr-xml-map "vservice_stats_edm:lookup_err_pkts";
      type uint64;
      description "Number of packets with unknown spi-si";
    }
    leaf malformed-err-bytes {
      xr:xr-xml-map "vservice_stats_edm:malformed_err_bytes";
      type uint64;
      units "byte";
      description "Total bytes with invalid NSH header";
    }
    leaf lookup-err-bytes {
      xr:xr-xml-map "vservice_stats_edm:lookup_err_bytes";
      type uint64;
      units "byte";
      description "Total bytes with unknown spi-si";
    }
  }

  grouping VSERVICE-NSH-SF {
    description "Service function/forwarder counters";
    leaf processed-pkts {
      xr:xr-xml-map "vservice_stats_edm:processed_pkts";
      type uint64;
      description "Number of packets processed";
    }
    leaf processed-bytes {
      xr:xr-xml-map "vservice_stats_edm:processed_bytes";
      type uint64;
      units "byte";
      description "Total bytes processed";
    }
  }

  grouping VSERVICE-NSH-SPI-SI-TERMINATE {
    description "spi-si supported counters";
    leaf terminated-pkts {
      xr:xr-xml-map "vservice_stats_edm:terminated_pkts";
      type uint64;
      description "Number of terminated packets";
    }
    leaf terminated-bytes {
      xr:xr-xml-map "vservice_stats_edm:terminated_bytes";
      type uint64;
      units "byte";
      description "Total bytes terminated";
    }
  }

  grouping VSERVICE-NSH-SPI-SI {
    description "spi-si supported counters";
    leaf processed-pkts {
      xr:xr-xml-map "vservice_stats_edm:processed_pkts";
      type uint64;
      description "Number of packets processed";
    }
    leaf processed-bytes {
      xr:xr-xml-map "vservice_stats_edm:processed_bytes";
      type uint64;
      units "byte";
      description "Total bytes processed";
    }
  }

  grouping VSERVICE-NSH-SFP {
    description "spf supported counters";

    container spi-si {
      description "Service index counters";
      uses VSERVICE-NSH-SPI-SI;
    }

    container term {
      description "Terminate counters";
      uses VSERVICE-NSH-SPI-SI-TERMINATE;
    }
  }

  grouping VS-NSH-STATS-DATA {
    description "Union for stats counter";

    container sfp {
      when "../type = 'vs-nsh-stats-sfp'" {
        description "../type = 'VS_NSH_STATS_SFP'";
      }
      description "SFP stats";
      uses VSERVICE-NSH-SFP;
    }

    container spi-si {
      when "../type = 'vs-nsh-stats-spi-si'" {
        description "../type = 'VS_NSH_STATS_SPI_SI'";
      }
      description "SPI SI stats";
      uses VSERVICE-NSH-SPI-SI;
    }

    container term {
      when "../type = 'vs-nsh-stats-ter-min-ate'" {
        description "../type = 'VS_NSH_STATS_TERMINATE'";
      }
      description "Terminate stats";
      uses VSERVICE-NSH-SPI-SI-TERMINATE;
    }

    container sf {
      when "../type = 'vs-nsh-stats-sf'" {
        description "../type = 'VS_NSH_STATS_SF'";
      }
      description "Service function stats";
      uses VSERVICE-NSH-SF;
    }

    container sff {
      when "../type = 'vs-nsh-stats-sff'" {
        description "../type = 'VS_NSH_STATS_SFF'";
      }
      description "Service function forwarder stats";
      uses VSERVICE-NSH-SF;
    }

    container sff-local {
      when "../type = 'vs-nsh-stats-sff-local'" {
        description "../type = 'VS_NSH_STATS_SFF_LOCAL'";
      }
      description "Local service function forwarder stats";
      uses VSERVICE-NSH-SFF-LOCAL;
    }
    leaf type {
      xr:xr-xml-map "vservice_stats_edm:type";
      type Vs-nsh-stats;
      description "type";
    }
  }

  grouping VSERVICE-EDM-NSH-STATS-INFO {
    description "NSH stats bag";

    container data {
      description "Statistics data";
      uses VS-NSH-STATS-DATA;
    }

    list si-arr {
      description "SI array in case of detail stats";
      uses VSERVICE-NSH-SI;
    }
  }
}
