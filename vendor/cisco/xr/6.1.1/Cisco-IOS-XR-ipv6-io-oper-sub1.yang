submodule Cisco-IOS-XR-ipv6-io-oper-sub1 {

  belongs-to Cisco-IOS-XR-ipv6-io-oper {
    prefix Cisco-IOS-XR-ipv6-io-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR ipv6-io package operational data.

     Copyright (c) 2013-2016 by Cisco Systems, Inc.
     All rights reserved.";

  revision "2015-11-09" {
    description
      "IOS XR 6.0 revision.";
  }

  revision "2015-08-27" {
    description
      "IOS XR 6.0.0 revision.";
  }


  grouping IPV6-ND-TRAFFIC {
    description "IPV6 ND Traffic";
    leaf sent-router-solicitation-messages {
      xr:xr-xml-map "ipv6_traffic:SentRouterSolicitationMessages";
      type uint32;
      description "ICMP Router Solicitations Sent";
    }
    leaf sent-router-advertisement-messages {
      xr:xr-xml-map "ipv6_traffic:SentRouterAdvertisementMessages";
      type uint32;
      description "ICMP Router Advertisements Sent";
    }
    leaf sent-neighbor-solicitation-messages {
      xr:xr-xml-map "ipv6_traffic:SentNeighborSolicitationMessages";
      type uint32;
      description "ICMP Neighbor Solicitations Sent";
    }
    leaf sent-neighbor-advertisement-messages {
      xr:xr-xml-map "ipv6_traffic:SentNeighborAdvertisementMessages";
      type uint32;
      description "ICMP Neighbor Advertisements Sent";
    }
    leaf sent-redirect-messages {
      xr:xr-xml-map "ipv6_traffic:SentRedirectMessages";
      type uint32;
      description "ICMP Redirect Sent";
    }
    leaf received-router-solicitation-messages {
      xr:xr-xml-map "ipv6_traffic:ReceivedRouterSolicitationMessage"+
        "s";
      type uint32;
      description "ICMP Router Solicitations Received";
    }
    leaf received-router-advertisement-messages {
      xr:xr-xml-map "ipv6_traffic:ReceivedRouterAdvertisementMessag"+
        "es";
      type uint32;
      description "ICMP Router Advertisements Received";
    }
    leaf received-neighbor-solicitation-messages {
      xr:xr-xml-map "ipv6_traffic:ReceivedNeighborSolicitationMessa"+
        "ges";
      type uint32;
      description "ICMP Neighbor Solicitations Received";
    }
    leaf received-neighbor-advertisement-messages {
      xr:xr-xml-map "ipv6_traffic:ReceivedNeighborAdvertisementMess"+
        "ages";
      type uint32;
      description "ICMP Neighbor Advertisements Received";
    }
    leaf received-redirect-messages {
      xr:xr-xml-map "ipv6_traffic:ReceivedRedirectMessages";
      type uint32;
      description "ICMP Redirect Received";
    }
  }

  grouping IPV6-IO-ICMP-TRAFFIC {
    description "ICMPv6 Traffic Information";
    leaf total-messages {
      xr:xr-xml-map "ipv6_traffic:TotalMessages";
      type uint32;
      description "ICMP Received";
    }
    leaf too-short-error-messages {
      xr:xr-xml-map "ipv6_traffic:TooShortErrorMessages";
      type uint32;
      description "ICMP Too Short Errors";
    }
    leaf checksum-error-messages {
      xr:xr-xml-map "ipv6_traffic:ChecksumErrorMessages";
      type uint32;
      description "ICMP Checksum Errors";
    }
    leaf unknown-error-type-messages {
      xr:xr-xml-map "ipv6_traffic:UnknownErrorTypeMessages";
      type uint32;
      description "ICMP Unknown Error";
    }
    leaf output-messages {
      xr:xr-xml-map "ipv6_traffic:OutputMessages";
      type uint32;
      description "ICMP Transmitted";
    }
    leaf sent-rate-limited-packets {
      xr:xr-xml-map "ipv6_traffic:SentRateLimitedPackets";
      type uint32;
      description "ICMP Sent Packets Ratelimited";
    }
    leaf sent-unreachable-routing-messages {
      xr:xr-xml-map "ipv6_traffic:SentUnreachableRoutingMessages";
      type uint32;
      description "ICMP Route Unreachable Sent";
    }
    leaf sent-unreachable-admin-messages {
      xr:xr-xml-map "ipv6_traffic:SentUnreachableAdminMessages";
      type uint32;
      description "ICMP Admin Unreachable Sent";
    }
    leaf sent-unreachable-neighbor-messages {
      xr:xr-xml-map "ipv6_traffic:SentUnreachableNeighborMessages";
      type uint32;
      description "ICMP Host Unreachable Sent";
    }
    leaf sent-unreachable-address-messages {
      xr:xr-xml-map "ipv6_traffic:SentUnreachableAddressMessages";
      type uint32;
      description "ICMP Addr Unreachable Sent";
    }
    leaf sent-unreachable-port-messages {
      xr:xr-xml-map "ipv6_traffic:SentUnreachablePortMessages";
      type uint32;
      description "ICMP Port Unreachable Sent";
    }
    leaf received-unreachable-routing-messages {
      xr:xr-xml-map "ipv6_traffic:ReceivedUnreachableRoutingMessage"+
        "s";
      type uint32;
      description "ICMP Route Unreachable Received";
    }
    leaf received-unreachable-admin-messages {
      xr:xr-xml-map "ipv6_traffic:ReceivedUnreachableAdminMessages";
      type uint32;
      description "ICMP Admin Unreachable Received";
    }
    leaf received-unreachable-neighbor-messages {
      xr:xr-xml-map "ipv6_traffic:ReceivedUnreachableNeighborMessag"+
        "es";
      type uint32;
      description "ICMP Host Unreachable Received";
    }
    leaf received-unreachable-address-messages {
      xr:xr-xml-map "ipv6_traffic:ReceivedUnreachableAddressMessage"+
        "s";
      type uint32;
      description "ICMP Addr Unreachable Received";
    }
    leaf received-unreachable-port-messages {
      xr:xr-xml-map "ipv6_traffic:ReceivedUnreachablePortMessages";
      type uint32;
      description "ICMP Port Unreachable Received";
    }
    leaf sent-hop-count-expired-messages {
      xr:xr-xml-map "ipv6_traffic:SentHopCountExpiredMessages";
      type uint32;
      description "ICMP Hop Count Expired Sent";
    }
    leaf sent-reassembly-timeouts {
      xr:xr-xml-map "ipv6_traffic:SentReassemblyTimeouts";
      type uint32;
      description "ICMP Reassembly Timeouts";
    }
    leaf received-hop-count-expired-messages {
      xr:xr-xml-map "ipv6_traffic:ReceivedHopCountExpiredMessages";
      type uint32;
      description "ICMP Hop Count Expired Received";
    }
    leaf received-reassembly-timeouts {
      xr:xr-xml-map "ipv6_traffic:ReceivedReassemblyTimeouts";
      type uint32;
      description "ICMP Reassembly Timeouts";
    }
    leaf sent-too-big-messages {
      xr:xr-xml-map "ipv6_traffic:SentTooBigMessages";
      type uint32;
      description "ICMP Too Big Messages Sent";
    }
    leaf received-too-big-messages {
      xr:xr-xml-map "ipv6_traffic:ReceivedTooBigMessages";
      type uint32;
      description "ICMP Too Big Messages Received";
    }
    leaf sent-parameter-error-messages {
      xr:xr-xml-map "ipv6_traffic:SentParameterErrorMessages";
      type uint32;
      description "ICMP Parameter Error Messages Sent";
    }
    leaf sent-parameter-header-messages {
      xr:xr-xml-map "ipv6_traffic:SentParameterHeaderMessages";
      type uint32;
      description "ICMP Parameter Next Header Messages Sent";
    }
    leaf sent-parameter-option-messages {
      xr:xr-xml-map "ipv6_traffic:SentParameterOptionMessages";
      type uint32;
      description "ICMP Parameter Option Messages Sent";
    }
    leaf received-parameter-error-messages {
      xr:xr-xml-map "ipv6_traffic:ReceivedParameterErrorMessages";
      type uint32;
      description "ICMP Parameter Error Messages Received";
    }
    leaf received-parameter-header-messages {
      xr:xr-xml-map "ipv6_traffic:ReceivedParameterHeaderMessages";
      type uint32;
      description "ICMP Parameter Next Header Messages Received";
    }
    leaf received-parameter-option-messages {
      xr:xr-xml-map "ipv6_traffic:ReceivedParameterOptionMessages";
      type uint32;
      description "ICMP Parameter Option Problem Received";
    }
    leaf sent-echo-request-messages {
      xr:xr-xml-map "ipv6_traffic:SentEchoRequestMessages";
      type uint32;
      description "ICMP Echo Request Sent";
    }
    leaf sent-echo-reply-messages {
      xr:xr-xml-map "ipv6_traffic:SentEchoReplyMessages";
      type uint32;
      description "ICMP Echo Reply Sent";
    }
    leaf received-echo-request-messages {
      xr:xr-xml-map "ipv6_traffic:ReceivedEchoRequestMessages";
      type uint32;
      description "ICMP Echo Request Received";
    }
    leaf received-echo-reply-messages {
      xr:xr-xml-map "ipv6_traffic:ReceivedEchoReplyMessages";
      type uint32;
      description "ICMP Echo Reply Received";
    }
    leaf sent-unknown-timeout-messages {
      xr:xr-xml-map "ipv6_traffic:SentUnknownTimeoutMessages";
      type uint32;
      description "ICMP Unknown Timeout Messages Sent";
    }
    leaf received-unknown-timeout-messages {
      xr:xr-xml-map "ipv6_traffic:ReceivedUnknownTimeoutMessages";
      type uint32;
      description "ICMP Unknown Timeout Messages Received";
    }
    leaf sent-parameter-unknown-type-messages {
      xr:xr-xml-map "ipv6_traffic:SentParameterUnknownTypeMessages";
      type uint32;
      description "ICMP Parameter Unknown Type Messages Sent";
    }
    leaf received-parameter-unknown-type-messages {
      xr:xr-xml-map "ipv6_traffic:ReceivedParameterUnknownTypeMessa"+
        "ges";
      type uint32;
      description "ICMP Parameter Unknown Type Messages Received";
    }
    leaf sent-unreachable-unknown-type-messages {
      xr:xr-xml-map "ipv6_traffic:SentUnreachableUnknownTypeMessage"+
        "s";
      type uint32;
      description "ICMP Unreachable Unknown Messages Sent";
    }
    leaf received-unreachable-unknown-type-messages {
      xr:xr-xml-map "ipv6_traffic:ReceivedUnreachableUnknownTypeMes"+
        "sages";
      type uint32;
      description "ICMP Unreachable Unknown Messages Received";
    }
  }

  grouping IPV6-IO-TRAFFIC {
    description "IPv6 Traffic Information";
    leaf total-packets {
      xr:xr-xml-map "ipv6_traffic:TotalPackets";
      type uint32;
      description "Total Packets";
    }
    leaf local-destination-packets {
      xr:xr-xml-map "ipv6_traffic:LocalDestinationPackets";
      type uint32;
      description "Local Destination Packets";
    }
    leaf format-errors {
      xr:xr-xml-map "ipv6_traffic:FormatErrors";
      type uint32;
      description "Format Errors";
    }
    leaf truncated-packets {
      xr:xr-xml-map "ipv6_traffic:TruncatedPackets";
      type uint32;
      description "Truncated Packets";
    }
    leaf hop-count-exceeded-packets {
      xr:xr-xml-map "ipv6_traffic:HopCountExceededPackets";
      type uint32;
      description "Hop Count Exceeded Packets";
    }
    leaf bad-source-address-packets {
      xr:xr-xml-map "ipv6_traffic:BadSourceAddressPackets";
      type uint32;
      description "Bad Source Address Packets";
    }
    leaf bad-header-packets {
      xr:xr-xml-map "ipv6_traffic:BadHeaderPackets";
      type uint32;
      description "Bad Header Packets";
    }
    leaf unknown-option-type-packets {
      xr:xr-xml-map "ipv6_traffic:UnknownOptionTypePackets";
      type uint32;
      description "Unknown Option Type Packets";
    }
    leaf unknown-protocol-packets {
      xr:xr-xml-map "ipv6_traffic:UnknownProtocolPackets";
      type uint32;
      description "Unknown Protocol Packets";
    }
    leaf fragments {
      xr:xr-xml-map "ipv6_traffic:Fragments";
      type uint32;
      description "Fragments";
    }
    leaf reassembled-packets {
      xr:xr-xml-map "ipv6_traffic:ReassembledPackets";
      type uint32;
      description "Reassembled Packets";
    }
    leaf reassembly-timeouts {
      xr:xr-xml-map "ipv6_traffic:ReassemblyTimeouts";
      type uint32;
      description "Reassembly Timeouts";
    }
    leaf reassembly-failures {
      xr:xr-xml-map "ipv6_traffic:ReassemblyFailures";
      type uint32;
      description "Reassembly Failures";
    }
    leaf reassembly-maximum-drops {
      xr:xr-xml-map "ipv6_traffic:ReassemblyMaximumDrops";
      type uint32;
      description "Reassembly Reach Maximum Drop";
    }
    leaf generated-packets {
      xr:xr-xml-map "ipv6_traffic:GeneratedPackets";
      type uint32;
      description "Packets Output";
    }
    leaf forwarded-packets {
      xr:xr-xml-map "ipv6_traffic:ForwardedPackets";
      type uint32;
      description "Packets Forwarded";
    }
    leaf source-routed-packets {
      xr:xr-xml-map "ipv6_traffic:SourceRoutedPackets";
      type uint32;
      description "Packets Source Routed";
    }
    leaf fragmented-packets {
      xr:xr-xml-map "ipv6_traffic:FragmentedPackets";
      type uint32;
      description "Packets Fragmented";
    }
    leaf fragment-count {
      xr:xr-xml-map "ipv6_traffic:FragmentCount";
      type uint32;
      description "Fragmented Packet Count";
    }
    leaf fragment-failures {
      xr:xr-xml-map "ipv6_traffic:FragmentFailures";
      type uint32;
      description "Fragment Failures";
    }
    leaf no-route-packets {
      xr:xr-xml-map "ipv6_traffic:NoRoutePackets";
      type uint32;
      description "No Route Packets";
    }
    leaf too-big-packets {
      xr:xr-xml-map "ipv6_traffic:TooBigPackets";
      type uint32;
      description "Packet Too Big";
    }
    leaf received-multicast-packets {
      xr:xr-xml-map "ipv6_traffic:ReceivedMulticastPackets";
      type uint32;
      description "Multicast In";
    }
    leaf sent-multicast-packets {
      xr:xr-xml-map "ipv6_traffic:SentMulticastPackets";
      type uint32;
      description "Multicast Out";
    }
    leaf miscellaneous-drops {
      xr:xr-xml-map "ipv6_traffic:MiscellaneousDrops";
      type uint32;
      description "Misc. drops";
    }
    leaf lisp-v4-encap-packets {
      xr:xr-xml-map "ipv6_traffic:LispV4EncapPackets";
      type uint32;
      description "Lisp IPv4 Encapped packets";
    }
    leaf lisp-v4-decap-packets {
      xr:xr-xml-map "ipv6_traffic:LispV4DecapPackets";
      type uint32;
      description "Lisp IPv4 Decapped packets";
    }
    leaf lisp-v6-encap-packets {
      xr:xr-xml-map "ipv6_traffic:LispV6EncapPackets";
      type uint32;
      description "Lisp IPv6 Encapped packets";
    }
    leaf lisp-v6-decap-packets {
      xr:xr-xml-map "ipv6_traffic:LispV6DecapPackets";
      type uint32;
      description "Lisp IPv6 Decapped packets";
    }
    leaf lisp-encap-errors {
      xr:xr-xml-map "ipv6_traffic:LispEncapErrors";
      type uint32;
      description "Lisp Encap errors";
    }
    leaf lisp-decap-errors {
      xr:xr-xml-map "ipv6_traffic:LispDecapErrors";
      type uint32;
      description "Lisp Decap errors";
    }
  }

  grouping IPV6-TRAFFIC {
    description "IPv6 and ICMPv6 Traffic Information";

    container ipv6 {
      description "IPv6 Statistics";
      uses IPV6-IO-TRAFFIC;
    }

    container icmp {
      description "ICMP Statistics";
      uses IPV6-IO-ICMP-TRAFFIC;
    }

    container ipv6-node-discovery {
      description "IPv6 Node Discovery Statistics";
      uses IPV6-ND-TRAFFIC;
    }
  }
}
