module Cisco-IOS-XR-segment-routing-ms-cfg {

  /*** NAMESPACE / PREFIX DEFINITION ***/

  namespace "http://cisco.com/ns/yang"+
    "/Cisco-IOS-XR-segment-routing-ms-cfg";


  prefix "segment-routing-ms-cfg";

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR segment-routing-ms package configuration.

     This module contains definitions
     for the following management objects:
       sr: Segment Routing

     Copyright (c) 2013-2016 by Cisco Systems, Inc.
     All rights reserved.";

  revision "2015-11-09" {
    description
      "IOS XR 6.0 revision.";
  }

  typedef Srms-mi-flag {
    type enumeration {
      enum disable {
        value 0;
        description "Disable flag";
      }
      enum enable {
        value 1;
        description "Enable flag";
      }
    }
    description "Srms mi flag";
  }

  container sr {
    xr:xr-xml-map "srms_config:SR";
    description "Segment Routing";

    container global-block {
      xr:xr-xml-map "srms_config:GlobalBlock";
      presence "Indicates a global-block node is configured.";
      description "Global Block Segment Routing";
      leaf lower-bound {
        xr:xr-xml-map "srms_config:LowerBound";
        type uint32 {
          range "16000..1048574";
        }
        mandatory true;
        description "SRGB Lower Bound";
      }
      leaf upper-bound {
        xr:xr-xml-map "srms_config:UpperBound";
        type uint32 {
          range "16001..1048575";
        }
        mandatory true;
        description "SRGB Upper Bound";
      }
    }

    container mappings {
      xr:xr-xml-map "srms_config:MS";
      description "Mapping Server";

      list mapping {
        xr:xr-xml-map "srms_config:Mapping";
        xr:xr-cli-map "segment-routing mapping-server prefix-sid-ma"+
          "p address-family (ipv4)|(ipv6) (<IPv4 address>)|(<IPv6 a"+
          "ddress>) <number> [range <number>] [attached] ";
        key "af ip mask";
        description "IP prefix to SID mapping";
        leaf af {
          xr:xr-xml-map "srms_config:AF";
          type xr:Cisco-ios-xr-string;
          description "Address Family";
        }
        leaf ip {
          xr:xr-xml-map "srms_config:IP";
          type xr:Cisco-ios-xr-string;
          description "IP prefix";
        }
        leaf mask {
          xr:xr-xml-map "srms_config:Mask";
          type int32;
          description "Mask";
        }
        leaf sid-start {
          xr:xr-xml-map "srms_config:SidStart";
          type uint32 {
            range "0..1048575";
          }
          description "Start of SID index range";
        }
        leaf sid-range {
          xr:xr-xml-map "srms_config:SidRange";
          type int32;
          description "Range (number of SIDs)";
        }
        leaf flag-attached {
          xr:xr-xml-map "srms_config:FlagAttached";
          type Srms-mi-flag;
          description "Enable/Disable Attached flag";
        }
      }
    }
    leaf enable {
      xr:xr-xml-map "srms_config:Enable";
      type empty;
      description "enable SR";
    }
  }
}
