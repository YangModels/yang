submodule Cisco-IOS-XR-ipv4-vrrp-oper-sub1 {

  belongs-to Cisco-IOS-XR-ipv4-vrrp-oper {
    prefix Cisco-IOS-XR-ipv4-vrrp-oper;
  }

  /*** LINKAGE (IMPORTS / INCLUDES) ***/

  import ietf-inet-types { prefix "inet"; }

  import ietf-yang-types { prefix "yang"; }

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR ipv4-vrrp package operational data.

     Copyright (c) 2013-2016 by Cisco Systems, Inc.
     All rights reserved.";

  revision "2015-11-09" {
    description
      "IOS XR 6.0 revision.";
  }

  typedef Vrrp-vmac-state {
    type enumeration {
      enum stored {
        value 0;
        description "VMAC stored locally";
      }
      enum reserved {
        value 1;
        description "VMAC reserved in mac table";
      }
      enum active {
        value 2;
        description "VMAC active in mac table";
      }
      enum reserving {
        value 3;
        description "VMAC not yet reserved in mac table";
      }
    }
    description "Vrrp vmac state";
  }
  typedef Vrrp-state-change-reason {
    type enumeration {
      enum state-change-bfd-down {
        value 0;
        description "BFD session down";
      }
      enum state-change-virtual-ip-configured {
        value 1;
        description "Virtual IP configured";
      }
      enum state-change-interface-ip {
        value 2;
        description "Interface IP update";
      }
      enum state-change-delay-timer {
        value 3;
        description "Delay timer expired";
      }
      enum state-change-startup {
        value 4;
        description "Ready on startup";
      }
      enum state-change-interface-up {
        value 5;
        description "Interface Up update";
      }
      enum state-change-interface-down {
        value 6;
        description "Interface Down update";
      }
      enum state-change-master-down-timer {
        value 7;
        description "Master down timer expired";
      }
      enum state-change-higher-priority-master {
        value 8;
        description "Higher priority advert received";
      }
      enum state-change-fhrp-admin {
        value 9;
        description "FHRP Admin state change";
      }
      enum state-change-mgo-parent {
        value 10;
        description "Change of MGO parent session";
      }
      enum state-change-chkpt-update {
        value 11;
        description "Checkpoint update from Primary VRRP instance";
      }
      enum state-change-issu-resync {
        value 12;
        description "Resync following ISSU primary event";
      }
    }
    description "Vrrp state change reason";
  }
  typedef Vrrp-bfd-session-state {
    type enumeration {
      enum bfd-state-none {
        value 0;
        description "None";
      }
      enum bfd-state-inactive {
        value 1;
        description "Inactive";
      }
      enum bfd-state-up {
        value 2;
        description "Up";
      }
      enum bfd-state-down {
        value 3;
        description "Down";
      }
    }
    description "Vrrp bfd session state";
  }
  typedef Vrrp-prot-auth {
    type enumeration {
      enum authentication-none {
        value 0;
        description "Down";
      }
      enum authentication-text {
        value 1;
        description "Simple Text";
      }
      enum authentication-ip {
        value 2;
        description "IP header";
      }
    }
    description "Vrrp prot auth";
  }
  typedef Vrrp-bag-protocol-state {
    type enumeration {
      enum state-initial {
        value 1;
        description "Initial";
      }
      enum state-backup {
        value 2;
        description "Backup";
      }
      enum state-master {
        value 3;
        description "Master";
      }
    }
    description "VRRP protocol state";
  }
  typedef Vrrp-vip-state {
    type enumeration {
      enum virtual-ip-state-down {
        value 0;
        description "Down";
      }
      enum virtual-ip-state-up {
        value 1;
        description "Up";
      }
    }
    description "Vrrp vip state";
  }
  typedef Vrrp-b-af {
    type enumeration {
      enum address-family-ipv4 {
        description "IPv4 Address Family";
      }
      enum address-family-ipv6 {
        description "IPv6 Address Family";
      }
      enum vrrp-baf-count {
        description "Number of Adddress Families";
      }
    }
    description "Vrrp b af";
  }
  typedef Vrrp-version {
    type uint8;
    description "Vrrp version";
  }

  grouping VRRP-SLAVE-INFO-TYPE {
    description "Slave info";
    leaf slave-interface {
      xr:xr-xml-map "vrrp:SlaveInterface";
      type string {
        length "0..64";
      }
      description "Interface of slave";
    }
    leaf slave-virtual-router-id {
      xr:xr-xml-map "vrrp:SlaveVirtualRouterID";
      type uint32;
      description "VRID of slave";
    }
  }

  grouping VRRP-MGO-INFO {
    description "MGO group data";
    leaf primary-session-name {
      xr:xr-xml-map "vrrp:PrimarySessionName";
      type string {
        length "0..16";
      }
      description "Session Name";
    }
    leaf primary-session-interface {
      xr:xr-xml-map "vrrp:PrimarySessionInterface";
      type xr:Interface-name;
      description "Interface of primary session";
    }
    leaf primary-af-name {
      xr:xr-xml-map "vrrp:PrimaryAFName";
      type Vrrp-b-af;
      description "Address family of primary session";
    }
    leaf primary-session-number {
      xr:xr-xml-map "vrrp:PrimarySessionNumber";
      type uint32;
      description "VRID of primary session";
    }
    leaf primary-session-state {
      xr:xr-xml-map "vrrp:PrimarySessionState";
      type Vrrp-bag-protocol-state;
      description "State of primary session";
    }

    list slave {
      description "List of slaves following this primary session";
      uses VRRP-SLAVE-INFO-TYPE;
    }
  }

  grouping VRRP-INTERFACE-INFO {
    description "VRRP Interface statistics";
    leaf interface {
      xr:xr-xml-map "vrrp:Interface";
      type xr:Interface-name;
      description "IM Interface";
    }
    leaf invalid-checksum-count {
      xr:xr-xml-map "vrrp:InvalidChecksumCount";
      type uint32;
      description "Invalid checksum";
    }
    leaf invalid-version-count {
      xr:xr-xml-map "vrrp:InvalidVersionCount";
      type uint32;
      description "Unknown/unsupported version";
    }
    leaf invalid-vrid-count {
      xr:xr-xml-map "vrrp:InvalidVRIDCount";
      type uint32;
      description "Invalid vrID";
    }
    leaf invalid-packet-length-count {
      xr:xr-xml-map "vrrp:InvalidPacketLengthCount";
      type uint32;
      description "Bad packet lengths";
    }
  }

  grouping VRRP-STATE-CHANGE-INFO-TYPE {
    description "State change info";

    container time {
      description "Time of state change";
      uses VRRP-BAG-TIMESTAMP;
    }
    leaf old-state {
      xr:xr-xml-map "vrrp:OldState";
      type Vrrp-bag-protocol-state;
      description "Old State";
    }
    leaf new-state {
      xr:xr-xml-map "vrrp:NewState";
      type Vrrp-bag-protocol-state;
      description "New State";
    }
    leaf reason {
      xr:xr-xml-map "vrrp:Reason";
      type Vrrp-state-change-reason;
      description "Reason for state change";
    }
  }

  grouping VRRP-BAG-TIMESTAMP {
    description "Timestamp";
    leaf seconds {
      xr:xr-xml-map "vrrp:Seconds";
      type uint32;
      units "second";
      description "Seconds";
    }
    leaf nanoseconds {
      xr:xr-xml-map "vrrp:Nanoseconds";
      type uint32;
      units "nanosecond";
      description "Nanoseconds";
    }
  }

  grouping IPV6-BAG-ADDR {
    description "IPV6 BAG ADDR";
    leaf ipv6-address {
      xr:xr-xml-map "vrrp:IPV6Address";
      type inet:ipv6-address;
      description "IPV6Address";
    }
  }

  grouping VRRP-VROUTER-INFO {
    description "Detailed vrID specific information";

    container resign-sent-time {
      description "Time last resign was sent";
      uses VRRP-BAG-TIMESTAMP;
    }

    container resign-received-time {
      description "Time last resign was received";
      uses VRRP-BAG-TIMESTAMP;
    }
    leaf interface-name-xr {
      xr:xr-xml-map "vrrp:interface-name-xr";
      type string {
        length "0..64";
      }
      description "IM Interface Name";
    }
    leaf virtual-router-id-xr {
      xr:xr-xml-map "vrrp:virtual-router-id-xr";
      type uint32;
      description "Virtual Router ID";
    }
    leaf version {
      xr:xr-xml-map "vrrp:Version";
      type Vrrp-version;
      description "VRRP Protocol Version";
    }
    leaf address-family {
      xr:xr-xml-map "vrrp:AddressFamily";
      type Vrrp-b-af;
      description "Address family";
    }
    leaf session-name {
      xr:xr-xml-map "vrrp:SessionName";
      type string {
        length "0..16";
      }
      description "Session Name";
    }
    leaf slaves {
      xr:xr-xml-map "vrrp:Slaves";
      type uint32;
      description "Number of slaves following state";
    }
    leaf is-slave {
      xr:xr-xml-map "vrrp:IsSlave";
      type boolean;
      description "Group is a slave group";
    }
    leaf followed-session-name {
      xr:xr-xml-map "vrrp:FollowedSessionName";
      type string {
        length "0..16";
      }
      description "Followed Session Name";
    }
    leaf secondary-address-count {
      xr:xr-xml-map "vrrp:SecondaryAddressCount";
      type uint8;
      description "Configured VRRP secondary address count";
    }
    leaf operational-address-count {
      xr:xr-xml-map "vrrp:OperationalAddressCount";
      type uint8;
      description "Operational VRRP address count";
    }
    leaf primary-virtual-ip {
      xr:xr-xml-map "vrrp:PrimaryVirtualIP";
      type inet:ipv4-address;
      description "Configured IPv4 Primary address";
    }
    leaf configured-down-address-count {
      xr:xr-xml-map "vrrp:ConfiguredDownAddressCount";
      type uint8;
      description " Configured but Down VRRP address count";
    }
    leaf virtual-linklocal-ipv6-address {
      xr:xr-xml-map "vrrp:VirtualLinklocalIPv6Address";
      type inet:ipv6-address;
      description "Virtual linklocal IPv6 address";
    }
    leaf primary-state {
      xr:xr-xml-map "vrrp:PrimaryState";
      type Vrrp-vip-state;
      description "State of primary IP address";
    }
    leaf master-ip-address {
      xr:xr-xml-map "vrrp:MasterIPAddress";
      type inet:ipv4-address;
      description "Master router real IP address";
    }
    leaf master-ipv6-address {
      xr:xr-xml-map "vrrp:MasterIPv6Address";
      type inet:ipv6-address;
      description "Master router real IPv6 address";
    }
    leaf master-priority {
      xr:xr-xml-map "vrrp:MasterPriority";
      type uint8;
      description "Master router priority";
    }
    leaf vrrp-state {
      xr:xr-xml-map "vrrp:VRRPState";
      type Vrrp-bag-protocol-state;
      description "VRRP state";
    }
    leaf authentication-type {
      xr:xr-xml-map "vrrp:AuthenticationType";
      type Vrrp-prot-auth;
      description "Authentication type";
    }
    leaf configured-advertize-time {
      xr:xr-xml-map "vrrp:ConfiguredAdvertizeTime";
      type uint32;
      description "Configured advertize time";
    }
    leaf oper-advertize-time {
      xr:xr-xml-map "vrrp:OperAdvertizeTime";
      type uint32;
      description "Operational advertize time";
    }
    leaf min-delay-time {
      xr:xr-xml-map "vrrp:MinDelayTime";
      type uint32;
      units "millisecond";
      description "Minimum delay time in msecs";
    }
    leaf reload-delay-time {
      xr:xr-xml-map "vrrp:ReloadDelayTime";
      type uint32;
      units "millisecond";
      description "Reload delay time in msecs";
    }
    leaf delay-timer-flag {
      xr:xr-xml-map "vrrp:DelayTimerFlag";
      type boolean;
      description "Delay timer running flag";
    }
    leaf delay-timer-secs {
      xr:xr-xml-map "vrrp:DelayTimerSecs";
      type uint32;
      units "second";
      description "Delay timer running time secs";
    }
    leaf delay-timer-msecs {
      xr:xr-xml-map "vrrp:DelayTimerMsecs";
      type uint32;
      units "millisecond";
      description "Delay timer running time msecs";
    }
    leaf authentication-flag {
      xr:xr-xml-map "vrrp:AuthenticationFlag";
      type boolean;
      description "Text authentication configured flag";
    }
    leaf force-timer-flag {
      xr:xr-xml-map "vrrp:ForceTimerFlag";
      type boolean;
      description "Configured timers forced flag";
    }
    leaf preempt-flag {
      xr:xr-xml-map "vrrp:PreemptFlag";
      type boolean;
      description "Preempt configured flag";
    }
    leaf ip-address-owner-flag {
      xr:xr-xml-map "vrrp:IPAddressOwnerFlag";
      type boolean;
      description "IP address owner flag";
    }
    leaf is-accept-mode {
      xr:xr-xml-map "vrrp:IsAcceptMode";
      type boolean;
      description "Is accept mode";
    }
    leaf preempt-delay-time {
      xr:xr-xml-map "vrrp:PreemptDelayTime";
      type uint16;
      description "Preempt delay time";
    }
    leaf configured-priority {
      xr:xr-xml-map "vrrp:ConfiguredPriority";
      type uint8;
      description "Configured priority";
    }
    leaf operational-priority {
      xr:xr-xml-map "vrrp:OperationalPriority";
      type uint8;
      description "Operational priority";
    }
    leaf priority-decrement {
      xr:xr-xml-map "vrrp:PriorityDecrement";
      type uint32;
      description "Priority decrement";
    }
    leaf tracked-interface-count {
      xr:xr-xml-map "vrrp:TrackedInterfaceCount";
      type uint32;
      description "Number of items tracked";
    }
    leaf tracked-interface-up-count {
      xr:xr-xml-map "vrrp:TrackedInterfaceUpCount";
      type uint32;
      description "Number of tracked items up";
    }
    leaf tracked-item-count {
      xr:xr-xml-map "vrrp:TrackedItemCount";
      type uint32;
      description "Number of tracked items";
    }
    leaf tracked-item-up-count {
      xr:xr-xml-map "vrrp:TrackedItemUpCount";
      type uint32;
      description "Number of tracked items in UP state";
    }
    leaf time-in-current-state {
      xr:xr-xml-map "vrrp:TimeInCurrentState";
      type uint32;
      units "second";
      description "Time in current state secs";
    }
    leaf state-change-count {
      xr:xr-xml-map "vrrp:StateChangeCount";
      type uint32;
      description "Number of state changes";
    }
    leaf time-vrouter-up {
      xr:xr-xml-map "vrrp:TimeVrouterUp";
      type uint32;
      description "Time vrouter is up in ticks (10ns units)";
    }
    leaf master-count {
      xr:xr-xml-map "vrrp:MasterCount";
      type uint32;
      description "No. of times become Master";
    }
    leaf adverts-received-count {
      xr:xr-xml-map "vrrp:AdvertsReceivedCount";
      type uint32;
      description "No. of advertisements received";
    }
    leaf advert-interval-error-count {
      xr:xr-xml-map "vrrp:AdvertIntervalErrorCount";
      type uint32;
      description "Advertise interval errors";
    }
    leaf adverts-sent-count {
      xr:xr-xml-map "vrrp:AdvertsSentCount";
      type uint32;
      description "No. of advertisements sent";
    }
    leaf authentication-fail-count {
      xr:xr-xml-map "vrrp:AuthenticationFailCount";
      type uint32;
      description "Authentication failures";
    }
    leaf ttl-error-count {
      xr:xr-xml-map "vrrp:TTLErrorCount";
      type uint32;
      description "TTL errors";
    }
    leaf priority-zero-received-count {
      xr:xr-xml-map "vrrp:PriorityZeroReceivedCount";
      type uint32;
      description "No. priority 0 received";
    }
    leaf priority-zero-sent-count {
      xr:xr-xml-map "vrrp:PriorityZeroSentCount";
      type uint32;
      description "No. priority 0 sent";
    }
    leaf invalid-packet-count {
      xr:xr-xml-map "vrrp:InvalidPacketCount";
      type uint32;
      description "Invalid packets received";
    }
    leaf address-list-error-count {
      xr:xr-xml-map "vrrp:AddressListErrorCount";
      type uint32;
      description "Address list errors";
    }
    leaf invalid-auth-type-count {
      xr:xr-xml-map "vrrp:InvalidAuthTypeCount";
      type uint32;
      description "Invalid authentication type";
    }
    leaf auth-type-mismatch-count {
      xr:xr-xml-map "vrrp:AuthTypeMismatchCount";
      type uint32;
      description "Authentication type mismatches";
    }
    leaf pkt-length-errors-count {
      xr:xr-xml-map "vrrp:PktLengthErrorsCount";
      type uint32;
      description "Packet length errors";
    }
    leaf time-stats-discontinuity {
      xr:xr-xml-map "vrrp:TimeStatsDiscontinuity";
      type uint32;
      description
        "Time since a statistics discontinuity in ticks
        (10ns units)";
    }
    leaf bfd-session-state {
      xr:xr-xml-map "vrrp:BFDSessionState";
      type Vrrp-bfd-session-state;
      description "BFD session state";
    }
    leaf bfd-interval {
      xr:xr-xml-map "vrrp:BFDInterval";
      type uint32;
      description "BFD packet send interval";
    }
    leaf bfd-multiplier {
      xr:xr-xml-map "vrrp:BFDMultiplier";
      type uint32;
      description "BFD multiplier";
    }
    leaf bfd-cfg-remote-ip {
      xr:xr-xml-map "vrrp:BFDCfgRemoteIP";
      type inet:ipv4-address;
      description "BFD configured remote IP";
    }
    leaf bfd-configured-remote-ipv6-address {
      xr:xr-xml-map "vrrp:BFDConfiguredRemoteIPv6Address";
      type inet:ipv6-address;
      description "BFD configured remote IPv6";
    }
    leaf state-from-checkpoint {
      xr:xr-xml-map "vrrp:StateFromCheckpoint";
      type boolean;
      description "Whether state recovered from checkpoint";
    }
    leaf interface-ipv4-address {
      xr:xr-xml-map "vrrp:InterfaceIPv4Address";
      type inet:ipv4-address;
      description "The Interface Primary IPv4 address";
    }
    leaf interface-ipv6-address {
      xr:xr-xml-map "vrrp:InterfaceIPv6Address";
      type inet:ipv6-address;
      description "The Interface linklocal IPv6 address";
    }
    leaf virtual-mac-address {
      xr:xr-xml-map "vrrp:VirtualMACAddress";
      type yang:mac-address;
      description "Virtual mac address";
    }
    leaf virtual-mac-address-state {
      xr:xr-xml-map "vrrp:VirtualMACAddressState";
      type Vrrp-vmac-state;
      description "Virtual mac address state";
    }
    leaf-list operational-address {
      xr:xr-xml-map "vrrp:OperationalAddressList";
      type inet:ipv4-address;
      description "Operational IPv4 VRRP addresses";
    }
    leaf-list ipv4-configured-down-address {
      xr:xr-xml-map "vrrp:IPv4ConfiguredDownAddressList";
      type inet:ipv4-address;
      description "IPv4 Configured but Down VRRP addresses";
    }
    leaf-list authentication-string {
      xr:xr-xml-map "vrrp:AuthenticationString";
      type uint8;
      description "Authentication data";
    }

    list ipv6-operational-address {
      description "IPv6 Operational VRRP addresses";
      uses IPV6-BAG-ADDR;
    }

    list ipv6-configured-down-address {
      description "IPv6 Configured but Down VRRP addresses";
      uses IPV6-BAG-ADDR;
    }

    list state-change-history {
      description "State change history";
      uses VRRP-STATE-CHANGE-INFO-TYPE;
    }
  }

  grouping VRRP-TRACKITEM-INFO {
    description "Tracked item information";
    leaf interface {
      xr:xr-xml-map "vrrp:Interface";
      type xr:Interface-name;
      description "IM Interface";
    }
    leaf virtual-router-id-xr {
      xr:xr-xml-map "vrrp:virtual-router-id-xr";
      type uint32;
      description "Virtual Router ID";
    }
    leaf tracked-item-type {
      xr:xr-xml-map "vrrp:TrackedItemType";
      type uint16;
      description "Type of tracked item";
    }
    leaf tracked-item-index {
      xr:xr-xml-map "vrrp:TrackedItemIndex";
      type string {
        length "0..32";
      }
      description "Tracked item index";
    }
    leaf state {
      xr:xr-xml-map "vrrp:State";
      type uint8;
      description "State of the tracked item";
    }
    leaf priority {
      xr:xr-xml-map "vrrp:Priority";
      type uint8;
      description "Priority weight of item";
    }
  }

  grouping VRRP-SUMMARY-INFO {
    description "VRRP summary statistics";
    leaf ipv4-sessions-master-owner {
      xr:xr-xml-map "vrrp:IPv4SessionsMasterOwner";
      type uint32;
      description "Number of IPv4 sessions in MASTER (owner) state";
    }
    leaf ipv4-sessions-master {
      xr:xr-xml-map "vrrp:IPv4SessionsMaster";
      type uint32;
      description "Number of IPv4 sessions in MASTER state";
    }
    leaf ipv4-sessions-backup {
      xr:xr-xml-map "vrrp:IPv4SessionsBackup";
      type uint32;
      description "Number of IPv4 sessions in BACKUP state";
    }
    leaf ipv4-sessions-init {
      xr:xr-xml-map "vrrp:IPv4SessionsInit";
      type uint32;
      description "Number of IPv4 sessions in INIT state";
    }
    leaf ipv4-slaves-master {
      xr:xr-xml-map "vrrp:IPv4SlavesMaster";
      type uint32;
      description "Number of IPv4 slaves in MASTER state";
    }
    leaf ipv4-slaves-backup {
      xr:xr-xml-map "vrrp:IPv4SlavesBackup";
      type uint32;
      description "Number of IPv4 slaves in BACKUP state";
    }
    leaf ipv4-slaves-init {
      xr:xr-xml-map "vrrp:IPv4SlavesInit";
      type uint32;
      description "Number of IPv4 slaves in INIT state";
    }
    leaf ipv4-virtual-ip-addresses-master-owner-up {
      xr:xr-xml-map "vrrp:IPv4VirtualIPAddressesMasterOwnerUp";
      type uint32;
      description
        "Number of UP IPv4 Virtual IP Addresses on
        virtual routers in MASTER (owner) state";
    }
    leaf ipv4-virtual-ip-addresses-master-owner-down {
      xr:xr-xml-map "vrrp:IPv4VirtualIPAddressesMasterOwnerDown";
      type uint32;
      description
        "Number of DOWN IPv4 Virtual IP Addresses on
        virtual routers in MASTER (owner) state";
    }
    leaf ipv4-virtual-ip-addresses-master-up {
      xr:xr-xml-map "vrrp:IPv4VirtualIPAddressesMasterUp";
      type uint32;
      description
        "Number of UP IPv4 Virtual IP Addresses on
        virtual routers in MASTER state";
    }
    leaf ipv4-virtual-ip-addresses-master-down {
      xr:xr-xml-map "vrrp:IPv4VirtualIPAddressesMasterDown";
      type uint32;
      description
        "Number of DOWN IPv4 Virtual IP Addresses on
        virtual routers in MASTER state";
    }
    leaf ipv4-virtual-ip-addresses-backup-up {
      xr:xr-xml-map "vrrp:IPv4VirtualIPAddressesBackupUp";
      type uint32;
      description
        "Number of UP IPv4 Virtual IP Addresses on
        virtual routers in BACKUP state";
    }
    leaf ipv4-virtual-ip-addresses-backup-down {
      xr:xr-xml-map "vrrp:IPv4VirtualIPAddressesBackupDown";
      type uint32;
      description
        "Number of DOWN IPv4 Virtual IP Addresses on
        virtual routers in BACKUP state";
    }
    leaf ipv4-virtual-ip-addresses-init-up {
      xr:xr-xml-map "vrrp:IPv4VirtualIPAddressesInitUp";
      type uint32;
      description
        "Number of UP IPv4 Virtual IP Addresses on
        virtual routers in INIT state";
    }
    leaf ipv4-virtual-ip-addresses-init-down {
      xr:xr-xml-map "vrrp:IPv4VirtualIPAddressesInitDown";
      type uint32;
      description
        "Number of DOWN IPv4 Virtual IP Addresses on
        virtual routers in INIT state";
    }
    leaf ipv6-sessions-master-owner {
      xr:xr-xml-map "vrrp:IPv6SessionsMasterOwner";
      type uint32;
      description "Number of IPv6 sessions in MASTER (owner) state";
    }
    leaf ipv6-sessions-master {
      xr:xr-xml-map "vrrp:IPv6SessionsMaster";
      type uint32;
      description "Number of IPv6 sessions in MASTER state";
    }
    leaf ipv6-sessions-backup {
      xr:xr-xml-map "vrrp:IPv6SessionsBackup";
      type uint32;
      description "Number of IPv6 sessions in BACKUP state";
    }
    leaf ipv6-sessions-init {
      xr:xr-xml-map "vrrp:IPv6SessionsInit";
      type uint32;
      description "Number of IPv6 sessions in INIT state";
    }
    leaf ipv6-slaves-master {
      xr:xr-xml-map "vrrp:IPv6SlavesMaster";
      type uint32;
      description "Number of IPv6 slaves in MASTER state";
    }
    leaf ipv6-slaves-backup {
      xr:xr-xml-map "vrrp:IPv6SlavesBackup";
      type uint32;
      description "Number of IPv6 slaves in BACKUP state";
    }
    leaf ipv6-slaves-init {
      xr:xr-xml-map "vrrp:IPv6SlavesInit";
      type uint32;
      description "Number of IPv6 slaves in INIT state";
    }
    leaf ipv6-virtual-ip-addresses-master-owner-up {
      xr:xr-xml-map "vrrp:IPv6VirtualIPAddressesMasterOwnerUp";
      type uint32;
      description
        "Number of UP IPv6 Virtual IP Addresses on
        virtual routers in MASTER (owner) state";
    }
    leaf ipv6-virtual-ip-addresses-master-owner-down {
      xr:xr-xml-map "vrrp:IPv6VirtualIPAddressesMasterOwnerDown";
      type uint32;
      description
        "Number of DOWN IPv6 Virtual IP Addresses on
        virtual routers in MASTER (owner) state";
    }
    leaf ipv6-virtual-ip-addresses-master-up {
      xr:xr-xml-map "vrrp:IPv6VirtualIPAddressesMasterUp";
      type uint32;
      description
        "Number of UP IPv6 Virtual IP Addresses on
        virtual routers in MASTER state";
    }
    leaf ipv6-virtual-ip-addresses-master-down {
      xr:xr-xml-map "vrrp:IPv6VirtualIPAddressesMasterDown";
      type uint32;
      description
        "Number of DOWN IPv6 Virtual IP Addresses on
        virtual routers in MASTER state";
    }
    leaf ipv6-virtual-ip-addresses-backup-up {
      xr:xr-xml-map "vrrp:IPv6VirtualIPAddressesBackupUp";
      type uint32;
      description
        "Number of UP IPv6 Virtual IP Addresses on
        virtual routers in BACKUP state";
    }
    leaf ipv6-virtual-ip-addresses-backup-down {
      xr:xr-xml-map "vrrp:IPv6VirtualIPAddressesBackupDown";
      type uint32;
      description
        "Number of DOWN IPv6 Virtual IP Addresses on
        virtual routers in BACKUP state";
    }
    leaf ipv6-virtual-ip-addresses-init-up {
      xr:xr-xml-map "vrrp:IPv6VirtualIPAddressesInitUp";
      type uint32;
      description
        "Number of UP IPv6 Virtual IP Addresses on
        virtual routers in INIT state";
    }
    leaf ipv6-virtual-ip-addresses-init-down {
      xr:xr-xml-map "vrrp:IPv6VirtualIPAddressesInitDown";
      type uint32;
      description
        "Number of DOWN IPv6 Virtual IP Addresses on
        virtual routers in INIT state";
    }
    leaf interfaces-ipv4-state-up {
      xr:xr-xml-map "vrrp:InterfacesIPv4StateUp";
      type uint32;
      description
        "Number of VRRP interfaces with IPv4 caps in UP
        state";
    }
    leaf interfaces-ipv4-state-down {
      xr:xr-xml-map "vrrp:InterfacesIPv4StateDown";
      type uint32;
      description
        "Number of VRRP interfaces with IPv4 caps in DOWN
        state";
    }
    leaf tracked-interfaces-ipv4-state-up {
      xr:xr-xml-map "vrrp:TrackedInterfacesIPv4StateUp";
      type uint32;
      description
        "Number of tracked interfaces with IPv4 caps in
        UP state";
    }
    leaf tracked-interfaces-ipv4-state-down {
      xr:xr-xml-map "vrrp:TrackedInterfacesIPv4StateDown";
      type uint32;
      description
        "Number of tracked interfaces with IPv4 caps in
        DOWN state";
    }
    leaf interfaces-ipv6-state-up {
      xr:xr-xml-map "vrrp:InterfacesIPv6StateUp";
      type uint32;
      description
        "Number of VRRP interfaces with IPv6 caps in UP
        state";
    }
    leaf interfaces-ipv6-state-down {
      xr:xr-xml-map "vrrp:InterfacesIPv6StateDown";
      type uint32;
      description
        "Number of VRRP interfaces with IPv6 caps in DOWN
        state";
    }
    leaf tracked-interfaces-ipv6-state-up {
      xr:xr-xml-map "vrrp:TrackedInterfacesIPv6StateUp";
      type uint32;
      description
        "Number of tracked interfaces with IPv6 caps in
        UP state";
    }
    leaf tracked-interfaces-ipv6-state-down {
      xr:xr-xml-map "vrrp:TrackedInterfacesIPv6StateDown";
      type uint32;
      description
        "Number of tracked interfaces with IPv6 caps in
        DOWN state";
    }
    leaf tracked-objects-state-up {
      xr:xr-xml-map "vrrp:TrackedObjectsStateUp";
      type uint32;
      description "Number of tracked objects in UP state";
    }
    leaf tracked-objects-state-down {
      xr:xr-xml-map "vrrp:TrackedObjectsStateDown";
      type uint32;
      description "Number of tracked objects in DOWN state";
    }
    leaf bfd-sessions-up {
      xr:xr-xml-map "vrrp:BFDSessionsUp";
      type uint32;
      description "Number of VRRP IPv4 BFD sessions in UP state";
    }
    leaf bfd-sessions-down {
      xr:xr-xml-map "vrrp:BFDSessionsDown";
      type uint32;
      description "Number of VRRP IPv4 BFD sessions in DOWN state";
    }
    leaf bfd-session-inactive {
      xr:xr-xml-map "vrrp:BFDSessionInactive";
      type uint32;
      description
        "Number of VRRP IPv4 BFD sessions in INACTIVE
        state";
    }
    leaf ipv6bfd-sessions-up {
      xr:xr-xml-map "vrrp:IPv6BFDSessionsUp";
      type uint32;
      description "Number of VRRP IPv6 BFD sessions in UP state";
    }
    leaf ipv6bfd-sessions-down {
      xr:xr-xml-map "vrrp:IPv6BFDSessionsDown";
      type uint32;
      description "Number of VRRP IPv6 BFD sessions in DOWN state";
    }
    leaf ipv6bfd-session-inactive {
      xr:xr-xml-map "vrrp:IPv6BFDSessionInactive";
      type uint32;
      description
        "Number of VRRP IPv6 BFD sessions in INACTIVE
        state";
    }
  }
}
