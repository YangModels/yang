module Cisco-IOS-XR-dwdm-ui-cfg {

  /*** NAMESPACE / PREFIX DEFINITION ***/

  namespace "http://cisco.com/ns/yang/Cisco-IOS-XR-dwdm-ui-cfg";


  prefix "dwdm-ui-cfg";

  /*** LINKAGE (IMPORTS / INCLUDES) ***/

  import Cisco-IOS-XR-types { prefix "xr"; }

  import Cisco-IOS-XR-ifmgr-cfg { prefix "a1"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR dwdm-ui package configuration.

     This YANG module augments the
       Cisco-IOS-XR-ifmgr-cfg
     module with configuration data.

     Copyright (c) 2013-2016 by Cisco Systems, Inc.
     All rights reserved.";

  revision "2015-12-16" {
    description
      "Adding additional In Service Transport Admin State to allow configuration while dwdm controller is in service";
  }

  revision "2015-11-09" {
    description
      "IOS XR 6.0 revision.";
  }

  typedef Prbs-pattern {
    type enumeration {
      enum none {
        value 0;
        description "None Pattern";
      }
      enum null {
        value 1;
        description "Null Pattern";
      }
      enum pn11 {
        value 2;
        description "PN11 Pattern";
      }
      enum pn23 {
        value 3;
        description "PN23 Pattern";
      }
      enum pn31 {
        value 4;
        description "PN31 Pattern";
      }
    }
    description "Prbs pattern";
  }
  typedef Proactive {
    type enumeration {
      enum default {
        value 1;
        description "Proactive Protection Default Mode";
      }
      enum graceful {
        value 2;
        description "Proactive Protection Graceful Mode";
      }
    }
    description "Proactive";
  }
  typedef Expected-tti {
    type enumeration {
      enum expected-tti-ascii {
        value 3;
        description "Expected TTI ascii string";
      }
      enum expected-tti-hex {
        value 4;
        description "Expected TTI hex string";
      }
    }
    description "Expected tti";
  }
  typedef Fec {
    type enumeration {
      enum none {
        value 0;
        description "No FEC";
      }
      enum standard {
        value 1;
        description "Standard FEC";
      }
      enum enhanced {
        value 2;
        description "Enhanced FEC";
      }
      enum high-gain-hd {
        value 3;
        description "High-Gain Hard Decision";
      }
      enum long-haul-hd {
        value 4;
        description "Long-Haul Hard Decision";
      }
      enum high-gain-sd {
        value 5;
        description "High-Gain Soft Decision";
      }
      enum long-haul-sd {
        value 6;
        description "Long-Haul Soft Decision";
      }
      enum ci-bch {
        value 7;
        description "Ci BCH";
      }
      enum high-gain-multivendor-hd {
        value 8;
        description
          "High-Gain Multivendor Interoperable Hard
          Decision";
      }
    }
    description "Fec";
  }
  typedef Framing {
    type enumeration {
      enum opu1e {
        value 1;
        description "opu1e Framing";
      }
      enum opu2e {
        value 2;
        description "opu2e Framing";
      }
    }
    description "Framing";
  }
  typedef Otu-threshold {
    type enumeration {
      enum prefec-sd {
        value 0;
        description "PREFEC SD BER THRESHOLD";
      }
      enum prefec-sf {
        value 1;
        description "PREFEC SF BER THRESHOLD";
      }
      enum otu-sd {
        value 4;
        description "OTU SD BER threshold";
      }
      enum otu-sf {
        value 5;
        description "OTU SF BER threshold";
      }
    }
    description "Otu threshold";
  }
  typedef Dwdm-loopback {
    type enumeration {
      enum none {
        value 0;
        description "No Loopback";
      }
      enum line {
        value 1;
        description "Line Loopback";
      }
      enum internal {
        value 2;
        description "Internal Loopback";
      }
    }
    description "Dwdm loopback";
  }
  typedef Efec {
    type enumeration {
      enum none {
        value 0;
        description
          "default submode to handle backward
          compatibility";
      }
      enum i.4 {
        value 1;
        description "efec i.4";
      }
      enum i.7 {
        value 2;
        description "efec i.7";
      }
    }
    description "Efec";
  }
  typedef Odu-alarm {
    type enumeration {
      enum oci {
        value 14;
        description "ODU OCI";
      }
      enum odu-ais {
        value 15;
        description "ODU AIS";
      }
      enum lck {
        value 16;
        description "ODU LCK";
      }
      enum odu-bdi {
        value 17;
        description "ODU BDI";
      }
      enum odu-sf {
        value 20;
        description "ODU SF BER";
      }
      enum odu-sd {
        value 21;
        description "ODU SD BER";
      }
      enum plm {
        value 22;
        description "ODU PTIM";
      }
      enum odu-tim {
        value 23;
        description "ODU TIM";
      }
    }
    description "Odu alarm";
  }
  typedef Prbs-mode {
    type enumeration {
      enum source {
        value 0;
        description "Source Mode";
      }
      enum sink {
        value 1;
        description "Sink Mode";
      }
      enum source-sink {
        value 2;
        description "Source-Sink Mode";
      }
      enum invalid {
        value 3;
        description "Invalid Mode";
      }
    }
    description "Prbs mode";
  }
  typedef Tx-tti {
    type enumeration {
      enum tx-tti-ascii {
        value 0;
        description "TX TTI ascii string";
      }
      enum tx-tti-hex {
        value 1;
        description "TX TTI hex string";
      }
    }
    description "Tx tti";
  }
  typedef Otu-alarm {
    type enumeration {
      enum los {
        value 0;
        description "LOS";
      }
      enum lof {
        value 1;
        description "LOF";
      }
      enum lom {
        value 2;
        description "LOM";
      }
      enum iae {
        value 6;
        description "OTU IAE";
      }
      enum otu-bdi {
        value 7;
        description "OTU BDI";
      }
      enum otu-tim {
        value 8;
        description "OTU TIM";
      }
      enum otu-sf {
        value 10;
        description "OTU SF BER";
      }
      enum otu-sd {
        value 11;
        description "OTU SD BER";
      }
      enum fec-mismatch {
        value 24;
        description "FEC mismatch";
      }
      enum prefec-sd-ber {
        value 31;
        description "PREFEC SD BER";
      }
      enum prefec-sf-ber {
        value 32;
        description "PREFEC SF BER";
      }
    }
    description "Otu alarm";
  }
  typedef Dwdm-admin-state {
    type enumeration {
      enum out-of-service {
        value 0;
        description "Out of service";
      }
      enum in-service {
        value 1;
        description "In service";
      }
      enum maintenance {
        value 2;
        description "Out of service maintenance";
      }
      enum in-service-config-allowed {
        value 3;
        description "In service Config allowed";
      }
    }
    description "Dwdm admin state";
  }
  typedef Odu-threshold {
    type enumeration {
      enum odu-sd {
        value 8;
        description "ODU SD BER threshold";
      }
      enum odu-sf {
        value 9;
        description "ODU SF BER threshold";
      }
    }
    description "Odu threshold";
  }
  typedef Wave-channel-num {
    type enumeration {
      enum default {
        value 0;
        description "Default Wave Channel Number";
      }
      enum channel-wavelength {
        value 1;
        description "Wavelength Wave Channel Number";
      }
      enum channel-frequency {
        value 2;
        description "Frequency Wave Channel Number";
      }
      enum 100mhz-frequency {
        value 4;
        description "Frequency in Steps of 100MHz";
      }
    }
    description "Wave channel num";
  }

  augment "/a1:interface-configurations/a1:interface-configuration" {
    leaf maintenance-embargo {
      xr:xr-xml-map "dwdm_ui_interface_cfg:MaintenanceEmbargo";
      type boolean;
      description
        "configure maintenance embargo flag on the given
        interface";
    }
    description
      "This augment extends the configuration data of
      'Cisco-IOS-XR-ifmgr-cfg'";
  }

  augment "/a1:interface-configurations/a1:interface-configuration" {

    container dwdm {
      xr:xr-xml-map "dwdm_ui_interface_cfg:DWDM";
      description "DWDM port controller configuration";

      container network-srlgs {
        xr:xr-xml-map "dwdm_ui_interface_cfg:NetworkSrlgTable";
        description "Configure Network srlgs";

        list network-srlg {
          xr:xr-xml-map "dwdm_ui_interface_cfg:NetworkSrlg";
          key "set-id";
          description "Configure network srlg sets";
          leaf set-id {
            xr:xr-xml-map "dwdm_ui_interface_cfg:SetId";
            type uint32 {
              range "1..17";
            }
            description "Set index";
          }
          leaf srlg1 {
            xr:xr-xml-map "dwdm_ui_interface_cfg:Srlg1";
            type uint32 {
              range "0..4294967294";
            }
            description "none";
          }
          leaf srlg2 {
            xr:xr-xml-map "dwdm_ui_interface_cfg:Srlg2";
            type uint32 {
              range "0..4294967294";
            }
            description "none";
          }
          leaf srlg3 {
            xr:xr-xml-map "dwdm_ui_interface_cfg:Srlg3";
            type uint32 {
              range "0..4294967294";
            }
            description "none";
          }
          leaf srlg4 {
            xr:xr-xml-map "dwdm_ui_interface_cfg:Srlg4";
            type uint32 {
              range "0..4294967294";
            }
            description "none";
          }
          leaf srlg5 {
            xr:xr-xml-map "dwdm_ui_interface_cfg:Srlg5";
            type uint32 {
              range "0..4294967294";
            }
            description "none";
          }
          leaf srlg6 {
            xr:xr-xml-map "dwdm_ui_interface_cfg:Srlg6";
            type uint32 {
              range "0..4294967294";
            }
            description "none";
          }
        }
      }

      container g709 {
        xr:xr-xml-map "dwdm_ui_interface_cfg:G709";
        description "Configure G709 parameters";

        container odu {
          xr:xr-xml-map "dwdm_ui_interface_cfg:ODU";
          description "Configure ODU parameters";

          container odu-reports {
            xr:xr-xml-map "dwdm_ui_interface_cfg:ODUReportTable";
            description "Configure ODU alarm reporting";

            list odu-report {
              xr:xr-xml-map "dwdm_ui_interface_cfg:ODUReport";
              key "alarm";
              description "none";
              leaf alarm {
                xr:xr-xml-map "dwdm_ui_interface_cfg:Alarm";
                type Odu-alarm;
                description "ODU alarm type";
              }
            }
          }

          container odu-thresholds {
            xr:xr-xml-map "dwdm_ui_interface_cfg:ODUThresholdTable";
            description "Configure ODU threshold value";

            list odu-threshold {
              xr:xr-xml-map "dwdm_ui_interface_cfg:ODUThreshold";
              key "threshold";
              description "none";
              leaf threshold {
                xr:xr-xml-map "dwdm_ui_interface_cfg:Threshold";
                type Odu-threshold;
                description "ODU Threshold type";
              }
              leaf threshold-value {
                xr:xr-xml-map "dwdm_ui_interface_cfg:ThresholdValue";
                type uint32 {
                  range "1..9";
                }
                mandatory true;
                description "Bit error rate (10 to the minus n)";
              }
            }
          }

          container odu-expected-tti {
            xr:xr-xml-map "dwdm_ui_interface_cfg:ODUExpectedTTI";
            description "Configure ODU Expected TTI value";
            leaf string-type {
              xr:xr-xml-map "dwdm_ui_interface_cfg:StringType";
              type Expected-tti;
              description "TTI string type (ascii or hex format)";
            }
            leaf ascii-string {
              xr:xr-xml-map "dwdm_ui_interface_cfg:AsciiString";
              when "../string-type = 'expected-tti-ascii'" {
                description "../StringType = EXPECTED_TTI_ASCII";
              }
              type string {
                length "0..64";
              }
              description "ASCII text (Max 64 characters)";
            }
            leaf hex-string {
              xr:xr-xml-map "dwdm_ui_interface_cfg:HexString";
              when "../string-type = 'expected-tti-hex'" {
                description "../StringType = EXPECTED_TTI_HEX";
              }
              type string {
                length "0..128";
              }
              description
                "Hex nibbles (Max 128- The string length
                should be an even number)";
            }
          }

          container odu-tx-tti {
            xr:xr-xml-map "dwdm_ui_interface_cfg:ODUTxTTI";
            description "Configure ODU TTI value";
            leaf string-type {
              xr:xr-xml-map "dwdm_ui_interface_cfg:StringType";
              type Tx-tti;
              description "TTI string type (ascii or hex format)";
            }
            leaf ascii-string {
              xr:xr-xml-map "dwdm_ui_interface_cfg:AsciiString";
              when "../string-type = 'tx-tti-ascii'" {
                description "../StringType = TX_TTI_ASCII";
              }
              type string {
                length "0..64";
              }
              description "ASCII text (Max 64 characters)";
            }
            leaf hex-string {
              xr:xr-xml-map "dwdm_ui_interface_cfg:HexString";
              when "../string-type = 'tx-tti-hex'" {
                description "../StringType = TX_TTI_HEX";
              }
              type string {
                length "0..128";
              }
              description
                "Hex nibbles (Max 128- The string length
                should be an even number)";
            }
          }
        }

        container otu {
          xr:xr-xml-map "dwdm_ui_interface_cfg:OTU";
          description "Configure OTU parameters";

          container otu-expected-tti {
            xr:xr-xml-map "dwdm_ui_interface_cfg:OTUExpectedTTI";
            description "Configure OTU Expected TTI value";
            leaf string-type {
              xr:xr-xml-map "dwdm_ui_interface_cfg:StringType";
              type Expected-tti;
              description "TTI string type (ascii or hex format)";
            }
            leaf ascii-string {
              xr:xr-xml-map "dwdm_ui_interface_cfg:AsciiString";
              when "../string-type = 'expected-tti-ascii'" {
                description "../StringType = EXPECTED_TTI_ASCII";
              }
              type string {
                length "0..64";
              }
              description "ASCII text (Max 64 characters)";
            }
            leaf hex-string {
              xr:xr-xml-map "dwdm_ui_interface_cfg:HexString";
              when "../string-type = 'expected-tti-hex'" {
                description "../StringType = EXPECTED_TTI_HEX";
              }
              type string {
                length "0..128";
              }
              description
                "Hex nibbles (Max 128- The string length
                should be an even number)";
            }
          }

          container otu-thresholds {
            xr:xr-xml-map "dwdm_ui_interface_cfg:OTUThresholdTable";
            description "Configure OTU threshold value";

            list otu-threshold {
              xr:xr-xml-map "dwdm_ui_interface_cfg:OTUThreshold";
              key "threshold";
              description "none";
              leaf threshold {
                xr:xr-xml-map "dwdm_ui_interface_cfg:Threshold";
                type Otu-threshold;
                description "OTU Threshold type";
              }
              leaf threshold-value {
                xr:xr-xml-map "dwdm_ui_interface_cfg:ThresholdValue";
                type uint32 {
                  range "1..9";
                }
                mandatory true;
                description "Bit error rate (10 to the minus n)";
              }
            }
          }

          container frr {
            xr:xr-xml-map "dwdm_ui_interface_cfg:FRR";
            description
              "Configure FRR thresholds and Window for
              trigger and revert";

            container trigger-window {
              xr:xr-xml-map "dwdm_ui_interface_cfg:TriggerWindow";
              presence "Indicates a trigger-window node is"+
                " configured.";
              description "Configure FRR trigger window";
              leaf window {
                xr:xr-xml-map "dwdm_ui_interface_cfg:Window";
                type uint32 {
                  range "10..10000";
                }
                mandatory true;
                description
                  "Integration window for FRR trigger in MS";
              }
              leaf dummy {
                xr:xr-xml-map "dwdm_ui_interface_cfg:Dummy";
                type uint32 {
                  range "0..2";
                }
                description
                  "Just a Dummy for window for FRR revert in
                  MS";
              }
            }

            container revert-threshold {
              xr:xr-xml-map "dwdm_ui_interface_cfg:RevertThreshold";
              presence "Indicates a revert-threshold node is"+
                " configured.";
              description
                "Configure proactive protection revert
                threshold";
              leaf ber-base {
                xr:xr-xml-map "dwdm_ui_interface_cfg:BERBase";
                type uint32 {
                  range "1..9";
                }
                mandatory true;
                description "Bit error rate base (x of xE-y)";
              }
              leaf ber-power {
                xr:xr-xml-map "dwdm_ui_interface_cfg:BERPower";
                type uint32 {
                  range "3..10";
                }
                mandatory true;
                description "Bit error rate power (y of xE-y)";
              }
            }

            container trigger-threshold {
              xr:xr-xml-map "dwdm_ui_interface_cfg:TriggerThreshold";
              presence "Indicates a trigger-threshold node is"+
                " configured.";
              description
                "Configure proactive protection trigger
                threshold";
              leaf ber-base {
                xr:xr-xml-map "dwdm_ui_interface_cfg:BERBase";
                type uint32 {
                  range "1..9";
                }
                mandatory true;
                description "Bit error rate base (x of xE-y)";
              }
              leaf ber-power {
                xr:xr-xml-map "dwdm_ui_interface_cfg:BERPower";
                type uint32 {
                  range "2..9";
                }
                mandatory true;
                description "Bit error rate power (y of xE-y)";
              }
            }

            container revert-window {
              xr:xr-xml-map "dwdm_ui_interface_cfg:RevertWindow";
              presence "Indicates a revert-window node is"+
                " configured.";
              description "Configure FRR revert window";
              leaf window {
                xr:xr-xml-map "dwdm_ui_interface_cfg:Window";
                type uint32 {
                  range "500..100000";
                }
                mandatory true;
                description
                  "Integration window for FRR revert in MS";
              }
              leaf dummy {
                xr:xr-xml-map "dwdm_ui_interface_cfg:Dummy";
                type uint32 {
                  range "0..2";
                }
                description
                  "Just a Dummy for window for FRR revert in
                  MS";
              }
            }
          }

          container otu-reports {
            xr:xr-xml-map "dwdm_ui_interface_cfg:OTUReportTable";
            description "Configure OTU alarm reporting";

            list otu-report {
              xr:xr-xml-map "dwdm_ui_interface_cfg:OTUReport";
              key "alarm";
              description "none";
              leaf alarm {
                xr:xr-xml-map "dwdm_ui_interface_cfg:Alarm";
                type Otu-alarm;
                description "OTU alarm type";
              }
            }
          }

          container otu-tx-tti {
            xr:xr-xml-map "dwdm_ui_interface_cfg:OTUTxTTI";
            description "Configure OTU TTI value";
            leaf string-type {
              xr:xr-xml-map "dwdm_ui_interface_cfg:StringType";
              type Tx-tti;
              description "TTI string type (ascii or hex format)";
            }
            leaf ascii-string {
              xr:xr-xml-map "dwdm_ui_interface_cfg:AsciiString";
              when "../string-type = 'tx-tti-ascii'" {
                description "../StringType = TX_TTI_ASCII";
              }
              type string {
                length "0..64";
              }
              description "ASCII text (Max 64 characters)";
            }
            leaf hex-string {
              xr:xr-xml-map "dwdm_ui_interface_cfg:HexString";
              when "../string-type = 'tx-tti-hex'" {
                description "../StringType = TX_TTI_HEX";
              }
              type string {
                length "0..128";
              }
              description
                "Hex nibbles (Max 128- The string length
                should be an even number)";
            }
          }
        }

        container prbs {
          xr:xr-xml-map "dwdm_ui_interface_cfg:PRBS";
          presence "Indicates a prbs node is configured.";
          description "Configure PRBS mode and pattern";
          leaf prbs-mode {
            xr:xr-xml-map "dwdm_ui_interface_cfg:PRBSMode";
            type Prbs-mode;
            mandatory true;
            description "Enable PRBS with mode";
          }
          leaf prbs-pattern {
            xr:xr-xml-map "dwdm_ui_interface_cfg:PRBSPattern";
            type Prbs-pattern;
            mandatory true;
            description "Enable prbs test with pattern";
          }
        }

        container fec {
          xr:xr-xml-map "dwdm_ui_interface_cfg:FEC";
          presence "Indicates a fec node is configured.";
          description "Configure FEC mode";
          leaf fec-mode {
            xr:xr-xml-map "dwdm_ui_interface_cfg:FECMode";
            type Fec;
            mandatory true;
            description
              "None, Standard, Enhanced, High-Gain,
              Long-Haul, Ci-BCH";
          }
          leaf efec-mode {
            xr:xr-xml-map "dwdm_ui_interface_cfg:EFECMode";
            type Efec;
            default "none";
            description
              "Enhanced FECMode to use i.4, i.7, Other
              FECMode to use None";
          }
        }
        leaf proactive {
          xr:xr-xml-map "dwdm_ui_interface_cfg:Proactive";
          type Proactive;
          description
            "Enable proactive protectioni Graceful or
            Default mode";
        }
        leaf bdi-to-gais {
          xr:xr-xml-map "dwdm_ui_interface_cfg:BDIToGAIS";
          type empty;
          description "Enable GAIS insertion";
        }
        leaf tim-to-gais {
          xr:xr-xml-map "dwdm_ui_interface_cfg:TIMToGAIS";
          type empty;
          description
            "Configure Trace Identifier Mismatch alarm
            consequence";
        }
        leaf proactive-logging-file {
          xr:xr-xml-map "dwdm_ui_interface_cfg:ProactiveLoggingFile";
          type xr:Cisco-ios-xr-string {
            length "0..128";
          }
          description "Configure proactive protection log file";
        }
        leaf tti-processing {
          xr:xr-xml-map "dwdm_ui_interface_cfg:TTIProcessing";
          type empty;
          description
            "Configure Trail Trace Identifier  processing";
        }
        leaf enable {
          xr:xr-xml-map "dwdm_ui_interface_cfg:Enable";
          type boolean;
          description "Disable or Enable g709 framing";
        }
        leaf framing {
          xr:xr-xml-map "dwdm_ui_interface_cfg:Framing";
          type Framing;
          description
            "Over clocking mode for client signal bw
            compatibility";
        }
      }

      container wavelength {
        xr:xr-xml-map "dwdm_ui_interface_cfg:Wavelength";
        presence "Indicates a wavelength node is configured.";
        description "Configure transponder wavelength";
        leaf wave-channel {
          xr:xr-xml-map "dwdm_ui_interface_cfg:WaveChannel";
          type uint32 {
            range "1..1568362";
          }
          mandatory true;
          description
            "Select a ITU channel number,channel range for
            C-band: 1~82,L-band:106~185,spacing:50GHZ or
            100MHz";
        }
        leaf wave-channel-number {
          xr:xr-xml-map "dwdm_ui_interface_cfg:WaveChannelNumber";
          type Wave-channel-num;
          mandatory true;
          description "Wave Channel Number";
        }
        leaf prog-frequency {
          xr:xr-xml-map "dwdm_ui_interface_cfg:ProgFrequency";
          type string {
            length "0..128";
          }
          description "Enter Frequency Data in THz";
        }
      }
      leaf enable-vtxp {
        xr:xr-xml-map "dwdm_ui_interface_cfg:EnableVTXP";
        type boolean;
        description "Disable or Enable VTXP configuration";
      }
      leaf network-port-id {
        xr:xr-xml-map "dwdm_ui_interface_cfg:NetworkPortId";
        type string {
          length "0..64";
        }
        description "Configure network port id";
      }
      leaf transport-admin-state {
        xr:xr-xml-map "dwdm_ui_interface_cfg:TransportAdminState";
        type Dwdm-admin-state;
        default "out-of-service";
        description "Configure transport admin state";
      }
      leaf laser {
        xr:xr-xml-map "dwdm_ui_interface_cfg:Laser";
        type empty;
        description "Configure laser off/on";
      }
      leaf transmit-power {
        xr:xr-xml-map "dwdm_ui_interface_cfg:TransmitPower";
        type int32 {
          range "-190..10";
        }
        description "Select power level (in units of 0.1dBm)";
      }
      leaf rx-threshold {
        xr:xr-xml-map "dwdm_ui_interface_cfg:RxThreshold";
        type int32 {
          range "-350..50";
        }
        description "Select power level (in units of 0.1dBm)";
      }
      leaf network-connection-id {
        xr:xr-xml-map "dwdm_ui_interface_cfg:NetworkConnectionId";
        type string {
          length "0..64";
        }
        description "Configure network connection id";
      }
      leaf loopback {
        xr:xr-xml-map "dwdm_ui_interface_cfg:Loopback";
        type Dwdm-loopback;
        default "none";
        description "Configure loopback mode ";
      }
    }
    description
      "This augment extends the configuration data of
      'Cisco-IOS-XR-ifmgr-cfg'";
  }
}
