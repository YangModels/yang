module Cisco-IOS-XR-secure-erase-act-deviations {
  namespace "http://cisco.com/ns/yang/Cisco-IOS-XR-secure-erase-act-deviations";
  prefix secure-erase-act-dev;

  import Cisco-IOS-XR-secure-erase-act {
    prefix secure-erase-act;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a set of deviations for unsupported platforms
     for Cisco-IOS-XR-secure-erase-act
     
     Copyright (c) 2024 by Cisco Systems, Inc.
     All rights reserved.";

  revision 2024-08-19 {
    description
      "IOS XR 25.1.1 revision.";
    semver:module-version "1.0.0";
  }

  deviation "/secure-erase-act:secure-erase" {
    deviate not-supported;
  }
}
