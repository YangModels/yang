submodule Cisco-IOS-XR-controller-ncs1001-ots-oper-sub1 {
  belongs-to Cisco-IOS-XR-controller-ncs1001-ots-oper {
    prefix Cisco-IOS-XR-controller-ncs1001-ots-oper;
  }

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR controller-ncs1001-ots package operational data.
     
     Copyright (c) 2013-2024 by Cisco Systems, Inc.
     All rights reserved.";

  revision 2024-10-15 {
    description
      "Added last link flap field";
    semver:module-version "1.0.0";
  }
  revision 2022-11-24 {
    description
      "leaves receive-power, transmit-power are removed and receive-power-dbm, transmit-power-dbm are modified to receive-power, transmit-power in OTS-EDM-LANE-DATA group";
  }
  revision 2022-11-23 {
    description
      "enum names changed in ots_legacy_ui bag";
  }
  revision 2019-04-05 {
    description
      "Establish semantic version baseline.";
  }
  revision 2015-11-09 {
    description
      "IOS XR 6.0 revision.";
  }

  typedef Amplifier-control-mode {
    type enumeration {
      enum "automatic" {
        value 1;
        description
          "Automatic";
      }
      enum "manual" {
        value 2;
        description
          "Manual";
      }
    }
    description
      "Amplifier control mode";
  }

  typedef Ta-state {
    type enumeration {
      enum "ta-state-ui-oos" {
        value 0;
        description
          "Out Of Service";
      }
      enum "ta-state-ui-main" {
        value 1;
        description
          "Maintenance";
      }
      enum "ta-state-ui-is" {
        value 2;
        description
          "In Service";
      }
      enum "ta-state-ui-ains" {
        value 3;
        description
          "Automatic In Service";
      }
    }
    description
      "Ta state";
  }

  typedef Controller-state {
    type enumeration {
      enum "state-up" {
        value 0;
        description
          "Up";
      }
      enum "state-down" {
        value 1;
        description
          "Down";
      }
      enum "state-admin-down" {
        value 2;
        description
          "Administratively Down";
      }
    }
    description
      "Controller state";
  }

  typedef Ots-laser-state {
    type enumeration {
      enum "on" {
        value 0;
        description
          "On";
      }
      enum "off" {
        value 1;
        description
          "Off";
      }
      enum "unknown" {
        value 2;
        description
          "Unknown";
      }
      enum "apr" {
        value 3;
        description
          "Apr";
      }
      enum "na" {
        value 4;
        description
          "N/A";
      }
    }
    description
      "Ots laser state";
  }

  typedef Ots-amplifier-safety-control-mode {
    type enumeration {
      enum "amplifier-safety-mode-invalid" {
        value 0;
        description
          "Invalid";
      }
      enum "amplifier-safety-mode-auto" {
        value 1;
        description
          "auto";
      }
      enum "amplifier-safety-mode-disabled" {
        value 2;
        description
          "disabled";
      }
    }
    description
      "Ots amplifier safety control mode";
  }

  typedef Ots-amplifier-gain-range {
    type enumeration {
      enum "amplifier-gain-range-invalid" {
        value 0;
        description
          "Invalid";
      }
      enum "amplifier-gain-range-normal" {
        value 1;
        description
          "Normal";
      }
      enum "amplifier-gain-range-ext-end-ed" {
        value 2;
        description
          "Extended";
      }
    }
    description
      "Ots amplifier gain range";
  }

  typedef Ots-port-status {
    type enumeration {
      enum "active" {
        value 0;
        description
          "Active";
      }
      enum "standby" {
        value 1;
        description
          "Standby";
      }
    }
    description
      "Ots port status";
  }

  typedef Ots-port {
    type enumeration {
      enum "com" {
        value 0;
        description
          "Com";
      }
      enum "line" {
        value 1;
        description
          "Line";
      }
      enum "osc" {
        value 2;
        description
          "Osc";
      }
      enum "com-check" {
        value 3;
        description
          "Com Check";
      }
      enum "work" {
        value 4;
        description
          "Working";
      }
      enum "prot" {
        value 5;
        description
          "Protected";
      }
    }
    description
      "Ots port";
  }

  grouping OTS-EDM-SPECTRUM-POWER-INFO {
    description
      "OTS EDM SPECTRUM POWER INFO";
    leaf slice-num {
      type uint32;
      description
        "spectrum slice number";
    }
    leaf lower-frequency {
      type uint64;
      description
        "Lower frequency of the specified PSD (in units
         of GHz)";
    }
    leaf upper-frequency {
      type uint64;
      description
        "Upper frequency of the specified PSD (in units
         of GHz)";
    }
    leaf rx-power {
      type int32;
      description
        "Received Power in multiple of 100, in dBm";
    }
    leaf tx-power {
      type int32;
      description
        "Transmit Power in multiple of 100, in dBm";
    }
    leaf rx-psd {
      type string;
      description
        "Received Power spectral density in microwatts
         per megahertz, uW/MHz";
    }
    leaf tx-psd {
      type string;
      description
        "Transmit Power spectral density in microwatts
         per megahertz, uW/MHz";
    }
  }

  grouping OTS-EDM-SPECTRUM-INFO {
    description
      "power information of slices in optical spectrum";
    leaf total-spectrum-slice-count {
      type uint32;
      description
        "Total number of slices in Spectrum";
    }
    leaf spectrum-slice-spacing {
      type uint32;
      description
        "Spacing between spectrum slices (in units of
         GHz)";
    }
    leaf first-slice-wavelength {
      type string;
      description
        "Wavelength of first slice (in units of nm)";
    }
    list spectrum-slice-power-info {
      description
        "Power information of spectrum slice info";
      uses OTS-EDM-SPECTRUM-POWER-INFO;
    }
  }

  grouping ALARM-DETAIL {
    description
      "Alarm Detail";
    leaf is-detected {
      type boolean;
      description
        "Flag indicating if defect is detected";
    }
    leaf counter {
      type uint32;
      description
        "Alarm counter";
    }
  }

  grouping OTS-EDM-ALARM-INFO {
    description
      "Ots Alarm Information";
    container low-tx-power {
      description
        "Low Tx Power in units of 0.1 dBm";
      uses ALARM-DETAIL;
    }
    container low-rx-power {
      description
        "Low Rx Power in units of 0.1 dBm";
      uses ALARM-DETAIL;
    }
    container rx-los-p {
      description
        "Rx LOS_P";
      uses ALARM-DETAIL;
    }
    container rx-loc {
      description
        "Rx LOC";
      uses ALARM-DETAIL;
    }
    container ampli-gain-deg-low {
      description
        "Ampli Gain Deg Low";
      uses ALARM-DETAIL;
    }
    container ampli-gain-deg-high {
      description
        "Ampli Gain Deg High";
      uses ALARM-DETAIL;
    }
    container auto-laser-shut {
      description
        "Auto Laser Shut";
      uses ALARM-DETAIL;
    }
    container auto-power-red {
      description
        "Auto Power Red";
      uses ALARM-DETAIL;
    }
    container auto-ampli-ctrl-disabled {
      description
        "Auto Ampli Ctrl Disabled";
      uses ALARM-DETAIL;
    }
    container auto-ampli-ctrl-config-mismatch {
      description
        "Auto Ampli Ctrl Config Mismatch";
      uses ALARM-DETAIL;
    }
    container switch-to-protect {
      description
        "Switch To Protect";
      uses ALARM-DETAIL;
    }
    container auto-ampli-ctrl-running {
      description
        "Auto Ampli Ctrl Running";
      uses ALARM-DETAIL;
    }
  }

  grouping OTS-EDM-LANE-DATA {
    description
      "Grey lane data";
    leaf laser-bias-current-milli-amps {
      type uint32;
      description
        "Laser Bias Current in units of 0.01mA";
    }
    leaf laser-bias-current-percent {
      type uint32;
      units "percentage";
      description
        "Laser Bias Current in units of 0.01 percentage";
    }
    leaf receive-power {
      type int32;
      description
        "Transponder receive power in the units of 0
         .01dBm";
    }
    leaf transmit-power {
      type int32;
      description
        "Transmit power in the units of 0.01dBm";
    }
  }

  grouping OTS-EDM-INFO {
    description
      "Ots transponder information";
    container lane-data {
      description
        "Lane information";
      uses OTS-EDM-LANE-DATA;
    }
    container ots-alarm-info {
      description
        "Ots Alarm Information";
      uses OTS-EDM-ALARM-INFO;
    }
    leaf port-type {
      type Ots-port;
      description
        "Port type information";
    }
    leaf total-rx-power {
      type int32;
      description
        "Total Receive Power for Multi-lane optics in
         units of 0.01 dBm";
    }
    leaf total-tx-power {
      type int32;
      description
        "Total Transmit Power for Multi-Lane Optics in
         units of 0.01 dBm";
    }
    leaf rx-voa-attenuation {
      type int32;
      description
        "Rx Voa Attenuation in the units of 0.01dB";
    }
    leaf tx-voa-attenuation {
      type int32;
      description
        "Tx Voa Attenuation in the units of 0.01dB";
    }
    leaf rx-low-threshold-current {
      type int32;
      description
        "Rx Low threshold actual value in units of 0.1dBm";
    }
    leaf wait-to-restore {
      type uint32;
      units "second";
      description
        "elapse time to trigger psm revert in units of
         seconds";
    }
    leaf ampli-tilt {
      type int32;
      description
        "Ampli Tilt in the units of 0.01dBm";
    }
    leaf ampli-gain {
      type int32;
      description
        "Ampli Gain in the units of 0.01dBm";
    }
    leaf port-status {
      type Ots-port-status;
      description
        "Port status information";
    }
    leaf tx-enable {
      type boolean;
      description
        "TX Enable";
    }
    leaf rx-enable {
      type boolean;
      description
        "RX Enable";
    }
    leaf ampli-gain-range {
      type Ots-amplifier-gain-range;
      description
        "Ampli gain range";
    }
    leaf osri {
      type boolean;
      description
        "Optical safety remote interlock";
    }
    leaf safety-control-mode {
      type Ots-amplifier-safety-control-mode;
      description
        "Safety control mode";
    }
    leaf rx-span-loss {
      type int32;
      description
        "RX Span Loss in units of 0.01 dB";
    }
    leaf tx-span-loss {
      type int32;
      description
        "TX Span Loss in units of 0.01 dB";
    }
    leaf laser-state {
      type Ots-laser-state;
      description
        "Showing laser State.";
    }
    leaf back-reflection {
      type int32;
      description
        "Back Reflected Transmit power in units of 0.1dBm";
    }
    leaf controller-state {
      type Controller-state;
      description
        "Ots controller state";
      xr:event-telemetry "Subscribe Telemetry Event";
    }
    leaf transport-admin-state {
      type Ta-state;
      description
        "Transport Admin State";
      xr:event-telemetry "Subscribe Telemetry Event";
    }
    leaf rx-low-threshold {
      type int32;
      description
        "Rx Low threshold value in units of 0.1dBm";
    }
    leaf tx-low-threshold {
      type int32;
      description
        "Tx Low threshold value in units of 0.1dBm";
    }
    leaf rx-power-th-configurable {
      type boolean;
      description
        "Is Rx Low Threshold Configurable";
    }
    leaf tx-power-th-configurable {
      type boolean;
      description
        "Is Tx Low Threshold Configurable";
    }
    leaf rx-voa-attenuation-config-val {
      type int32;
      description
        "RX VOA attenuation configured value in units of
         0.01dB";
    }
    leaf tx-voa-attenuation-config-val {
      type int32;
      description
        "TX VOA attenuation configured value in units of
         0.01dB";
    }
    leaf ampli-gain-config-val {
      type int32;
      description
        "Ampli gain configured value in units of 0.1dB";
    }
    leaf ampli-tilt-config-val {
      type int32;
      description
        "Ampli tilt configured value in units of 0.1dB";
    }
    leaf ampli-channel-power-config-val {
      type int32;
      description
        "Ampli channel power configured value in units of
         0.1dBm";
    }
    leaf channel-power-max-delta-config-val {
      type int32;
      description
        "Channel power max delta configured value in
         units of 0.1 dBm";
    }
    leaf ampli-channel-psd-config-val {
      type int32;
      description
        "Ampli channel psd configured value in units of 0
         .001 nW/MHz";
    }
    leaf rx-low-th-psd-config-val {
      type int32;
      description
        "Rx Low threshold psd value in units of 0.001
         nW/MHz";
    }
    leaf ampli-control-mode-config-val {
      type Amplifier-control-mode;
      description
        "Amplifier Control Mode configured value";
    }
    leaf ampli-gain-range-config-val {
      type Ots-amplifier-gain-range;
      description
        "Amplifier Gain Range configured value";
    }
    leaf safety-control-mode-config-val {
      type Ots-amplifier-safety-control-mode;
      description
        "Amplifier Safety Control Mode configured value";
    }
    leaf osri-config-val {
      type boolean;
      description
        "Is Osri Configured Value";
    }
    leaf tx-config-val {
      type boolean;
      description
        "TX Configured Value is supported";
    }
    leaf rx-config-val {
      type boolean;
      description
        "RX Configured Value is supported";
    }
    leaf rx-thr-fail-low-delta-val {
      type int32;
      description
        "Rx Low Threshold Delta Configured value (in
         units of dBm)";
    }
  }
}
