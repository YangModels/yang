//*************  DO-NOT EDIT  **************
//*********** Auto-generated file ********** 

 module cisco-xr-openconfig-wavelength-router-deviations {

  prefix  "oc-wave-routerdevs";

  namespace "http://cisco.com/ns/yang/cisco-xr-openconfig-wavelength-router-deviations";

  import openconfig-extensions { prefix oc-ext; }
  import openconfig-platform { prefix oc-platform; }
  import openconfig-transport-types { prefix oc-opt-types; }
  import openconfig-wavelength-router { prefix oc-wave-router; }

  organization "Cisco Systems, Inc.";

  contact
    "Cisco Systems, Inc.
     Customer Service

     Postal: 170 West Tasman Drive
     San Jose, CA 95134

     Tel: +1 800 553-NETS

     E-mail: cs-yang@cisco.com";

  description
    "This module contains a set of deviations for 

     openconfig-platform-transceiver.yang@2023-08-30 

     on Cisco IOS-XR devices.

     Copyright (c) 2017 by Cisco Systems, Inc.
     All rights reserved.";

  revision "2024-08-13" {
    description
      "Initial revision applicable to IOS-XR 6.4.1";
  }

  deviation /oc-wave-router:wavelength-router/oc-wave-router:port-spectrum-power-profiles/oc-wave-router:port/oc-wave-router:config/oc-wave-router:name {
    deviate not-supported;
  }

  deviation /oc-wave-router:wavelength-router/oc-wave-router:port-spectrum-power-profiles/oc-wave-router:port/oc-wave-router:spectrum-power-profile/oc-wave-router:distribution/oc-wave-router:config/oc-wave-router:lower-frequency {
    deviate not-supported;
  }

  deviation /oc-wave-router:wavelength-router/oc-wave-router:port-spectrum-power-profiles/oc-wave-router:port/oc-wave-router:spectrum-power-profile/oc-wave-router:distribution/oc-wave-router:config/oc-wave-router:upper-frequency {
    deviate not-supported;
  }

  deviation /oc-wave-router:wavelength-router/oc-wave-router:port-spectrum-power-profiles/oc-wave-router:port/oc-wave-router:spectrum-power-profile/oc-wave-router:distribution/oc-wave-router:config/oc-wave-router:target-power {
    deviate not-supported;
  }

  deviation /oc-wave-router:wavelength-router/oc-wave-router:port-spectrum-power-profiles/oc-wave-router:port/oc-wave-router:spectrum-power-profile/oc-wave-router:distribution/oc-wave-router:state/oc-wave-router:lower-frequency {
    deviate not-supported;
  }

  deviation /oc-wave-router:wavelength-router/oc-wave-router:port-spectrum-power-profiles/oc-wave-router:port/oc-wave-router:spectrum-power-profile/oc-wave-router:distribution/oc-wave-router:state/oc-wave-router:upper-frequency {
    deviate not-supported;
  }

  deviation /oc-wave-router:wavelength-router/oc-wave-router:port-spectrum-power-profiles/oc-wave-router:port/oc-wave-router:spectrum-power-profile/oc-wave-router:distribution/oc-wave-router:state/oc-wave-router:target-power {
    deviate not-supported;
  }

  deviation /oc-wave-router:wavelength-router/oc-wave-router:media-channels/oc-wave-router:channel/oc-wave-router:config/oc-wave-router:attenuation-control-mode {
    deviate not-supported;
  }

  deviation /oc-wave-router:wavelength-router/oc-wave-router:media-channels/oc-wave-router:channel/oc-wave-router:config/oc-wave-router:attenuation-control-range {
    deviate not-supported;
  }

  deviation /oc-wave-router:wavelength-router/oc-wave-router:media-channels/oc-wave-router:channel/oc-wave-router:config/oc-wave-router:max-undershoot-compensation {
    deviate not-supported;
  }

  deviation /oc-wave-router:wavelength-router/oc-wave-router:media-channels/oc-wave-router:channel/oc-wave-router:config/oc-wave-router:max-overshoot-compensation {
    deviate not-supported;
  }

  deviation /oc-wave-router:wavelength-router/oc-wave-router:media-channels/oc-wave-router:channel/oc-wave-router:config/oc-wave-router:name {
    deviate not-supported;
  }

  deviation /oc-wave-router:wavelength-router/oc-wave-router:media-channels/oc-wave-router:channel/oc-wave-router:state/oc-wave-router:name {
    deviate not-supported;
  }

  deviation /oc-wave-router:wavelength-router/oc-wave-router:media-channels/oc-wave-router:channel/oc-wave-router:config/oc-wave-router:super-channel {
    deviate not-supported;
  }

  deviation /oc-wave-router:wavelength-router/oc-wave-router:media-channels/oc-wave-router:channel/oc-wave-router:config/oc-wave-router:super-channel-parent {
    deviate not-supported;
  }

  deviation /oc-wave-router:wavelength-router/oc-wave-router:media-channels/oc-wave-router:channel/oc-wave-router:config/oc-wave-router:ase-control-mode {
    deviate not-supported;
  }

  deviation /oc-wave-router:wavelength-router/oc-wave-router:media-channels/oc-wave-router:channel/oc-wave-router:config/oc-wave-router:ase-injection-mode {
    deviate not-supported;
  }

  deviation /oc-wave-router:wavelength-router/oc-wave-router:media-channels/oc-wave-router:channel/oc-wave-router:config/oc-wave-router:ase-injection-threshold {
    deviate not-supported;
  }

  deviation /oc-wave-router:wavelength-router/oc-wave-router:media-channels/oc-wave-router:channel/oc-wave-router:config/oc-wave-router:ase-injection-delta {
    deviate not-supported;
  }

  deviation /oc-wave-router:wavelength-router/oc-wave-router:media-channels/oc-wave-router:channel/oc-wave-router:config/oc-wave-router:media-channel-injection-offset {
    deviate not-supported;
  }

}
//total deviations:20
