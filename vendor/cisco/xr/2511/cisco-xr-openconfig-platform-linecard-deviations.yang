//*************  DO-NOT EDIT  **************
//*********** Auto-generated file ********** 

 module cisco-xr-openconfig-platform-linecard-deviations {

  namespace "http://cisco.com/ns/yang/cisco-xr-openconfig-platform-linecard-deviations";

  prefix  "oc-linecarddevs";

  import openconfig-platform-linecard { prefix oc-linecard; }
  import openconfig-platform { prefix oc-platform; }

  import cisco-semver { prefix "semver"; }

  organization "Cisco Systems, Inc.";

  contact
    "Cisco Systems, Inc.
     Customer Service

     Postal: 170 West Tasman Drive
     San Jose, CA 95134

     Tel: +1 800 553-NETS

     E-mail: cs-yang@cisco.com";

  description
    "This module contains a set of deviations for 

     openconfig-platform-linecard.yang@2022-04-21 

     on Cisco IOS-XR devices.

     Copyright (c) 2017 by Cisco Systems, Inc.
     All rights reserved.";

  revision "2023-07-11" {
    description
      "Initial revision applicable to IOS-XR 6.4.1";
    semver:module-version "1.0.0";
  }


  deviation /oc-platform:components/oc-platform:component/oc-linecard:linecard/oc-linecard:utilization/oc-linecard:resources/oc-linecard:resource {
    deviate not-supported;
  }

  deviation /oc-platform:components/oc-platform:component/oc-linecard:linecard/oc-linecard:config/oc-linecard:power-admin-state {
    deviate delete {
      default POWER_ENABLED;
    }
  }

  deviation /oc-platform:components/oc-platform:component/oc-linecard:linecard/oc-linecard:state/oc-linecard:power-admin-state {
    deviate delete {
      default POWER_ENABLED;
    }
  }

}
//total deviations:3
