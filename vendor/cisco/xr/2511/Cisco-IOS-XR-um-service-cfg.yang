module Cisco-IOS-XR-um-service-cfg {
  namespace "http://cisco.com/ns/yang/Cisco-IOS-XR-um-service-cfg";
  prefix um-service-cfg;

  import Cisco-IOS-XR-types {
    prefix xr;
  }
  import ietf-inet-types {
    prefix inet;
  }
  import Cisco-IOS-XR-um-interface-cfg {
    prefix a1;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR service package configuration.
     
     This YANG module augments the
     modules with configuration data.
     
     Copyright (c) 2023 by Cisco Systems, Inc.
     All rights reserved.";

  revision 2024-02-21 {
    description
      "Changed service-type to a non-presence container";
    semver:module-version "1.0.0";
  }
  revision 2023-11-22 {
    description
      "Added service-ipv6 node";
  }
  revision 2022-11-30 {
    description
      "Added CGV6 container";
  }
  revision 2022-01-23 {
    description
      "Initial release";
  }

  grouping IF-BODY {
    description
      "grouping cgn";
    leaf cgn {
      type xr:Cisco-ios-xr-string {
        length "1..800" {
          description
            "CGN instance name";
        }
      }
      description
        "Enable inline CGN on this interface";
    }
  }

  augment "/a1:interfaces/a1:interface" {
    description
      "interface";
    uses IF-BODY;
  }
  augment "/a1:interfaces/a1:interface-preconfigure" {
    description
      "interface-preconfigure";
    uses IF-BODY;
  }
  container service {
    description
      "Please enter the service instance";
    container cgv6s {
      description
        "CGv6 Configurations";
      list cgv6 {
        key "cgv6-name";
        description
          "CGv6 Configurations";
        leaf cgv6-name {
          type xr:Cisco-ios-xr-string {
            length "1..24" {
              description
                "Name of the CGv6";
            }
          }
          description
            "CGv6 Configurations";
        }
        container service-inline {
          description
            "Interface on which service to be started";
          container interfaces {
            description
              "Interface name";
            list interface {
              key "interface-name";
              description
                "Interface name";
              leaf interface-name {
                type xr:Interface-name;
                description
                  "Interface name";
              }
            }
          }
        }
        container service-type {
          description
            "Select a service to configure";
          container map-es {
            description
              "MAP-E encapsulation";
            list map-e {
              key "map-e-name";
              description
                "MAP-E encapsulation";
              leaf map-e-name {
                type xr:Cisco-ios-xr-string {
                  length "1..24" {
                    description
                      "Name of map-e instance";
                  }
                }
                description
                  "MAP-E encapsulation";
              }
              leaf br-endpoint-address {
                type inet:ipv6-address-no-zone;
                description
                  "IPv6 address  end at BR";
              }
              leaf contiguous-ports {
                type uint32 {
                  range "1..65536" {
                    description
                      "number of contiguous ports(must be power of 2)";
                  }
                }
                description
                  "contiguous ports(must be power of 2)";
              }
              container cpe-domain {
                description
                  "CPE domain parameters";
                container ipv4 {
                  description
                    "ipv4 parameters";
                  leaf prefix {
                    type inet:ipv4-address-no-zone;
                    must "../mask";
                    description
                      "CPE domain ipv4 prefix";
                  }
                  leaf mask {
                    type inet:ipv4-address-no-zone;
                    must "../prefix";
                    description
                      "address mask";
                  }
                }
                container ipv6 {
                  description
                    "ipv6 parameters";
                  leaf prefix {
                    type inet:ipv6-address-no-zone;
                    description
                      "CPE IPv6 Prefix";
                  }
                }
              }
              leaf sharing-ratio {
                type uint32 {
                  range "1..32768" {
                    description
                      "port sharing ratio(must be power of 2)";
                  }
                }
                description
                  "port sharing ratio(must be power of 2)";
              }
            }
          }
          container map-t-ciscos {
            description
              "map-t translations";
            list map-t-cisco {
              key "map-t-cisco-name";
              description
                "map-t translations";
              leaf map-t-cisco-name {
                type xr:Cisco-ios-xr-string {
                  length "1..24" {
                    description
                      "Name of map-t instance";
                  }
                }
                description
                  "map-t translations";
              }
              leaf sharing-ratio {
                type uint32 {
                  range "1..32768" {
                    description
                      "port sharing ratio (must be power of 2)";
                  }
                }
                description
                  "port sharing ratio(must be power of 2)";
              }
              leaf contiguous-ports {
                type uint32 {
                  range "1..65536" {
                    description
                      "number of contiguous ports (must be power of 2)";
                  }
                }
                description
                  "contiguous ports(must be power of 2)";
              }
              container cpe-domain {
                description
                  "CPE domain parameters";
                container ipv6 {
                  description
                    "ipv6 parameters";
                  leaf vrf {
                    type xr:Cisco-ios-xr-string {
                      length "1..32" {
                        description
                          "VRF name";
                      }
                    }
                    description
                      "ipv6 vrf name";
                  }
                  container prefix {
                    description
                      "prefix";
                    leaf length {
                      type uint32 {
                        range "1..128" {
                          description
                            "prefix length (must be in the range of 1-64 or 128)";
                        }
                      }
                      description
                        "length";
                    }
                  }
                }
                container ipv4 {
                  description
                    "ipv4 parameters";
                  container prefix {
                    description
                      "prefix";
                    leaf length {
                      type uint32 {
                        range "0..32" {
                          description
                            "prefix length";
                        }
                      }
                      description
                        "length";
                    }
                  }
                }
              }
              container cpe-domains {
                description
                  "CPE Domain name";
                list cpe-domain-name {
                  key "cpe-domain-name address";
                  description
                    "CPE Domain name";
                  leaf cpe-domain-name {
                    type xr:Cisco-ios-xr-string {
                      length "1..800" {
                        description
                          "CPE Domain Name";
                      }
                    }
                    description
                      "CPE Domain name";
                  }
                  leaf address {
                    type inet:ipv4-address-no-zone;
                    description
                      "CPE domain ipv4 prefix";
                  }
                  leaf ipv6-prefix {
                    type inet:ipv6-address-no-zone;
                    description
                      "CPE Domain IPv6 Prefix";
                  }
                }
              }
              container ext-domains {
                description
                  "Domain name";
                list ext-domain-name {
                  key "ext-domain-name prefix length";
                  description
                    "Domain name";
                  leaf ext-domain-name {
                    type xr:Cisco-ios-xr-string {
                      length "1..800" {
                        description
                          "Domain Name";
                      }
                    }
                    description
                      "Domain name";
                  }
                  leaf prefix {
                    type inet:ipv6-address-no-zone;
                    description
                      "External domain ipv6 prefix";
                  }
                  leaf length {
                    type uint32 {
                      range "0..128";
                    }
                    description
                      "External domain ipv6 prefix length";
                  }
                  leaf ipv4-vrf {
                    type xr:Cisco-ios-xr-string {
                      length "1..800" {
                        description
                          "IPv4 VRF";
                      }
                    }
                    description
                      "IPv4 VRF";
                  }
                }
              }
              container address-family {
                description
                  "Address family related configuration";
                container ipv4 {
                  description
                    "IPv4 address family";
                  leaf interface {
                    type xr:Interface-name;
                    description
                      "ServiceApp interface to be used";
                  }
                  container tcp {
                    description
                      "Protocol TCP";
                    leaf mss {
                      type uint32 {
                        range "28..1500" {
                          description
                            "Maximum segment size to be used in bytes";
                        }
                      }
                      description
                        "Maximum segment size for TCP in bytes";
                    }
                  }
                  leaf path-mtu {
                    type uint32 {
                      range "65..9216" {
                        description
                          "Path-MTU for IPv4 value in bytes";
                      }
                    }
                    description
                      "Path-MTU for IPv4 to be used for ServiceApp";
                  }
                }
                container ipv6 {
                  description
                    "IPv6 address family";
                  leaf interface {
                    type xr:Interface-name;
                    description
                      "ServiceApp interface to be used";
                  }
                  container tcp {
                    description
                      "Protocol TCP";
                    leaf mss {
                      type uint32 {
                        range "28..1500" {
                          description
                            "Maximum segment size to be used in bytes";
                        }
                      }
                      description
                        "Maximum segment size for TCP in bytes";
                    }
                  }
                  leaf path-mtu {
                    type uint32 {
                      range "1280..9216" {
                        description
                          "Path-MTU for IPv6 value in bytes";
                      }
                    }
                    description
                      "Path-MTU for IPv6 to be used for ServiceApp";
                  }
                }
              }
              leaf service-ipv6-mtu {
                type uint32 {
                  range "1280..65535" {
                    description
                      "Service IPv6 MTU";
                  }
                }
                description
                  "Service IPv6 MTU";
              }
              leaf service-ipv4-mtu {
                type uint32 {
                  range "64..65535" {
                    description
                      "Service IPv4 MTU";
                  }
                }
                description
                  "Service IPv4 MTU";
              }
              container service-ipv4-nexthop {
                description
                  "Service IPv4 Nexthop";
                leaf addr {
                  type inet:ipv4-address-no-zone;
                  description
                    "Service IPv4 Nexthop IP Address";
                }
                leaf vrf {
                  type xr:Cisco-ios-xr-string {
                    length "1..800" {
                      description
                        "VRF name";
                    }
                  }
                  must "../addr";
                  description
                    "Service IPv4 VRF";
                }
              }
              container service-ipv6-nexthop {
                description
                  "Service IPv6 Nexthop";
                leaf addr {
                  type inet:ipv6-address-no-zone;
                  description
                    "Service IPv6 Nexthop IP Address";
                }
                leaf vrf {
                  type xr:Cisco-ios-xr-string {
                    length "1..800" {
                      description
                        "VRF name";
                    }
                  }
                  must "../addr";
                  description
                    "Service IPv6 VRF";
                }
              }
            }
          }
        }
        container service-location {
          description
            "Location on which service to be started";
          leaf preferred-active {
            type xr:Node-id;
            description
              "Active service location";
          }
          leaf preferred-standby {
            type xr:Node-id;
            must "../preferred-active";
            description
              "Standby service location";
          }
        }
      }
    }
    container unsupported-transceiver {
      presence "Indicates a unsupported-transceiver node is configured.";
      description
        "Allow unsupported-transceiver to be used on SPAs";
    }
  }
}
