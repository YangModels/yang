module Cisco-IOS-XR-sysadmin-sdm-diag {
  namespace "http://cisco.com/calvados/diagnostics";
  prefix diagnostics_actions;

  organization
    "Cisco Systems Inc.";
  contact
    "Cisco Systems, Inc.
     Customer Service
     
     Postal: 170 West Tasman Drive
     San Jose, CA 95134
     
     Tel: +1 800 553-NETS
     
     E-mail: cs-yang@cisco.com";
  description
    "This module contains definitions
     for the Calvados model objects.
     
     Copyright (c) 2012-2017 by Cisco Systems, Inc.
     All rights reserved.";

  revision 2017-03-21 {
    description
      "Added completion point to location and testid
       Suppressed the range using cli-suppress-range";
  }

  typedef Location {
    type string;
  }

  typedef Test {
    type string;
    description
      "Enter the test Name";
  }

  typedef Individual_test {
    type string;
    description
      "Enter the test Name";
  }

  typedef Type_int32 {
    type int32;
    description
      "Enter the value ";
  }

  typedef Hour_Minute {
    type string {
      pattern "([01]?[0-9]|2[0-3]):[0-5][0-9]";
    }
  }

  container diagnostic {
    container monitor {
      container rejected {
        list location {
          key "loc";
          leaf loc {
            type Location;
          }
          list test {
            key "test_id run";
            leaf test_id {
              type Individual_test;
            }
            leaf run {
              type enumeration {
                enum "disable" {
                  value 1;
                }
              }
            }
          }
        }
      }
      container interval {
        list location {
          key "loc";
          leaf loc {
            type Location;
          }
          list test {
            key "test_id";
            leaf test_id {
              type Individual_test;
            }
            leaf days {
              type int32 {
                range "0..20";
              }
              mandatory true;
            }
            leaf time {
              type string {
                pattern "([01]?[0-9]|2[0-3]):[0-5][0-9]:[0-5][0-9]";
              }
              mandatory true;
            }
          }
        }
      }
      container threshold {
        list location {
          key "loc";
          leaf loc {
            type Location;
          }
          list test {
            key "test_id";
            leaf test_id {
              type Individual_test;
            }
            leaf failure-count {
              type int32 {
                range "1..99";
              }
              mandatory true;
            }
          }
        }
      }
    }
    container schedule {
      container start {
        list location {
          key "loc";
          leaf loc {
            type Location;
          }
          list test {
            key "test_id";
            leaf test_id {
              type Individual_test;
            }
            list daily {
              key "hour_min";
              leaf hour_min {
                type Hour_Minute;
              }
            }
            list on {
              key "month day_of_month year hour_min";
              leaf month {
                type enumeration {
                  enum "JAN";
                  enum "FEB";
                  enum "MAR";
                  enum "APR";
                  enum "MAY";
                  enum "JUN";
                  enum "JUL";
                  enum "AUG";
                  enum "SEP";
                  enum "OCT";
                  enum "NOV";
                  enum "DEC";
                }
              }
              leaf day_of_month {
                type int32 {
                  range "1..31";
                }
              }
              leaf year {
                type int32 {
                  range "2013..2099";
                }
              }
              leaf hour_min {
                type Hour_Minute;
              }
            }
            list weekly {
              key "daysofweek hour_min";
              leaf daysofweek {
                type enumeration {
                  enum "SUN";
                  enum "MON";
                  enum "TUE";
                  enum "WED";
                  enum "THR";
                  enum "FRI";
                  enum "SAT";
                }
              }
              leaf hour_min {
                type Hour_Minute;
              }
            }
          }
        }
      }
    }
    container status {
      config false;
      list location_index {
        key "data_idx";
        leaf data_idx {
          type int32;
        }
        leaf description {
          type string;
        }
        leaf curr_running_tst_runby {
          type string;
        }
      }
    }
    container diag_start {
      config false;
      list location {
        key "loc";
        leaf loc {
          type Location;
        }
        leaf description {
          type string;
          default "port.";
        }
        list test {
          key "test_type";
          leaf test_type {
            type Test;
          }
          leaf description {
            type string;
            default "Test.";
          }
        }
      }
    }
    container diag_stop {
      config false;
      list location {
        key "loc";
        leaf loc {
          type Location;
        }
        leaf description {
          type string;
          default "port.";
        }
        list test {
          key "test_type";
          leaf test_type {
            type Test;
          }
          leaf description {
            type string;
            default "Test.";
          }
        }
      }
    }
    container content {
      config false;
      list location {
        key "loc";
        leaf loc {
          type Location;
        }
        leaf description {
          type string;
          default "port.";
        }
        list data_list {
          key "data_idx";
          leaf data_idx {
            type int32;
          }
          leaf id {
            type int32;
            description
              "To display the test information";
          }
          leaf test_name {
            type string;
          }
          leaf attribute {
            type string;
          }
          leaf timeinfo {
            type string;
          }
          leaf threshold {
            type int32;
          }
        }
      }
    }
    container result {
      config false;
      list location {
        key "loc";
        leaf loc {
          type Location;
        }
        leaf description {
          type string;
          default "port.";
        }
        list test {
          key "test_type";
          leaf test_type {
            type Test;
            description
              "test name|all";
          }
          leaf description {
            type string;
            default "port.";
          }
          list detail {
            key "det";
            leaf det {
              type string;
            }
            list data_list {
              key "data_idx";
              leaf data_idx {
                type int32;
              }
              leaf detail_flag {
                type int32;
              }
              leaf sl_no {
                type int32;
              }
              leaf test_name {
                type string;
              }
              leaf test_result {
                type string;
              }
              leaf err_code {
                type int32;
              }
              leaf err_description {
                type string;
              }
              leaf test_type {
                type string;
              }
              leaf hm_test_count {
                type int32;
              }
              leaf od_test_count {
                type int32;
              }
              leaf sched_test_count {
                type int32;
              }
              leaf run_cnt {
                type int32;
              }
              leaf lt_exe_time {
                type string;
              }
              leaf ft_fail_time {
                type string;
              }
              leaf lt_fail_time {
                type string;
              }
              leaf lt_pass_time {
                type string;
              }
              leaf total_fail_cnt {
                type int32;
              }
              leaf cons_fail_cnt {
                type int32;
              }
              leaf more_info {
                type string;
              }
            }
          }
        }
      }
    }
  }
}
