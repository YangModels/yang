module Cisco-IOS-XR-sysadmin-clear-asr9k {
  namespace "http://www.cisco.com/ns/yang/Cisco-IOS-XR-sysadmin-clear-ASR9K";
  prefix calvados_clear;

  import Cisco-IOS-XR-sysadmin-ethsw-esdma-cli-asr9k {
    prefix esdma;
  }
  import canb_cli_clear {
    prefix canb_clear;
  }

  organization
    "Cisco Systems Inc.";
  contact
    "Cisco Systems, Inc.
     Customer Service
     \t
     Postal: 170 West Tasman Drive
     San Jose, CA 95134
     
     Tel: +1 800 553-NETS
     
     E-mail: cs-yang@cisco.com";
  description
    "This module contains definitions
     for the Calvados model objects.
     
     This module contains a collection of YANG
     definitions for Cisco IOS-XR SysAdmin configuration.
     
     This module defines the top level container for
     all 'clear' commands for Sysadmin.
     
     Copyright(c) 2012-2016 by Cisco Systems, Inc.
     All rights reserved.
     
     Copyright (c) 2012-2017 by Cisco Systems, Inc.
     All rights reserved.";

  revision 2017-11-10 {
    description
      "Changed the namespace for ASR9K platform";
  }

  container clear {
    container controller {
      container switch {
        uses esdma:switch_clear;
      }
    }
    uses canb_clear:canb-clear-grp;
  }
}
