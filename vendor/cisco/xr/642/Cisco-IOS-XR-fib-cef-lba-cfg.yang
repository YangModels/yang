module Cisco-IOS-XR-fib-cef-lba-cfg {
  namespace "http://cisco.com/ns/yang/Cisco-IOS-XR-fib-cef-lba-cfg";
  prefix fib-cef-lba-cfg;

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR fib-cef-lba package configuration.
     
     This module contains definitions
     for the following management objects:
       fiblb: FIB load-balancing
     
     Copyright (c) 2013-2017 by Cisco Systems, Inc.
     All rights reserved.";

  revision 2015-11-09 {
    description
      "IOS XR 6.0 revision.";
  }

  container fiblb {
    presence "Indicates a fiblb node is configured.";
    description
      "FIB load-balancing";
    leaf fields {
      type uint32 {
        range "0..1";
      }
      mandatory true;
      description
        "Specify number of fields used for the load
         balancing";
    }
    leaf payload {
      type boolean;
      mandatory true;
      description
        "Payload Load-Balancing";
    }
  }
}
