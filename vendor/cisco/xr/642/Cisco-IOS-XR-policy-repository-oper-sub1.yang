submodule Cisco-IOS-XR-policy-repository-oper-sub1 {
  belongs-to Cisco-IOS-XR-policy-repository-oper {
    prefix Cisco-IOS-XR-policy-repository-oper;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR policy-repository package operational data.
     
     Copyright (c) 2013-2017 by Cisco Systems, Inc.
     All rights reserved.";

  revision 2017-09-22 {
    description
      "Introduced shadow process container.";
  }
  revision 2017-05-01 {
    description
      "Fixing backward compatibility error in module.";
  }
  revision 2015-11-09 {
    description
      "IOS XR 6.0 revision.";
  }

  typedef Group {
    type enumeration {
      enum "address-family-group" {
        value 0;
        description
          "Address Family Group";
      }
      enum "session-group" {
        value 1;
        description
          "Session Group";
      }
      enum "neighbor-group" {
        value 2;
        description
          "Neighbor Group";
      }
      enum "neighbor" {
        value 3;
        description
          "Neighbor";
      }
      enum "error-group" {
        value 4;
        description
          "Error Group";
      }
    }
    description
      "BGP Neighbor Group Type";
  }

  typedef Attach-point-direction {
    type enumeration {
      enum "in" {
        value 0;
        description
          "Attach Point Direction IN";
      }
      enum "out" {
        value 1;
        description
          "Attach Point Direction OUT";
      }
    }
    description
      "Attach Point Direction";
  }

  typedef Sub-address-family {
    type enumeration {
      enum "unicast" {
        value 0;
        description
          "Unicast";
      }
      enum "multicast" {
        value 1;
        description
          "Multicast";
      }
      enum "label" {
        value 2;
        description
          "Label";
      }
      enum "tunnel" {
        value 3;
        description
          "Tunnel";
      }
      enum "vpn" {
        value 4;
        description
          "VPN";
      }
      enum "mdt" {
        value 5;
        description
          "MDT";
      }
      enum "vpls" {
        value 6;
        description
          "VPLS";
      }
      enum "rt-constraint" {
        value 7;
        description
          "RTConstraint";
      }
      enum "mvpn" {
        value 8;
        description
          "MVPN";
      }
      enum "flow" {
        value 9;
        description
          "FLOW";
      }
      enum "vpn-mcast" {
        value 10;
        description
          "VPN Multicast";
      }
      enum "evpn" {
        value 11;
        description
          "EVPN";
      }
      enum "saf-none" {
        value 12;
        description
          "No SAFI";
      }
      enum "saf-unknown" {
        value 13;
        description
          "Unknown";
      }
    }
    description
      "Sub Address Family";
  }

  typedef Address-family {
    type enumeration {
      enum "ipv4" {
        value 0;
        description
          "IPv4 Address Family";
      }
      enum "ipv6" {
        value 1;
        description
          "IPv6 Address Family";
      }
      enum "l2vpn" {
        value 2;
        description
          "L2VPN Address Family";
      }
      enum "ls" {
        value 3;
        description
          "LINKSTATE Address Family";
      }
      enum "af-none" {
        value 4;
        description
          "No Address Family";
      }
      enum "af-unknown" {
        value 5;
        description
          "Unknown Address Family";
      }
    }
    description
      "Address Family";
  }

  typedef Object-status {
    type enumeration {
      enum "active" {
        value 0;
        description
          "The object is in use";
      }
      enum "inactive" {
        value 1;
        description
          "The object is referenced by another object, but
           not used";
      }
      enum "unused" {
        value 2;
        description
          "The object is not used or referenced";
      }
    }
    description
      "Whether an RPL object is used/referenced";
  }

  typedef String {
    type string;
    description
      "String";
  }

  grouping SET-INFO {
    description
      "List of sets";
    leaf set-domain {
      type string;
      description
        "Domain of sets";
    }
    leaf-list set-name {
      type String;
      description
        "Names of sets in this domain";
    }
  }

  grouping SET-LIST {
    description
      "List of sets in one domain";
    uses SET-INFO;
  }

  grouping RPL-SETS-INFO {
    description
      "Names of set objects";
    list sets {
      description
        "List of sets in several domains";
      uses SET-LIST;
    }
  }

  grouping CLIENT-INFO {
    description
      "Policy attachment information";
    leaf protocol {
      type string;
      description
        "Protocol to which policy attached";
    }
    leaf vrf-name {
      type string;
      description
        "VRF name";
    }
    leaf proto-instance {
      type string;
      description
        "Protocol instance";
    }
    leaf af-name {
      type Address-family;
      description
        "Address Family Identifier";
    }
    leaf saf-name {
      type Sub-address-family;
      description
        "Subsequent Address Family Identifier";
    }
    leaf neighbor-address {
      type string;
      description
        "Neighbor IP Address";
    }
    leaf neighbor-af-name {
      type Address-family;
      description
        "Neighbor IP Address Family";
    }
    leaf group-name {
      type string;
      description
        "Neighbor Group Name";
    }
    leaf direction {
      type Attach-point-direction;
      description
        "Direction In or Out";
    }
    leaf group {
      type Group;
      description
        "Neighbor Group ";
    }
    leaf source-protocol {
      type string;
      description
        "Source Protocol to redistribute, Source Protocol
         can be one of the following values{all,
         connected, local, static, bgp, rip, isis, ospf
         ,ospfv3, eigrp, unknown }";
    }
    leaf aggregate-network-address {
      type string;
      description
        "Aggregate IP address or Network IP Address in
         IPv4 or IPv6 Format";
    }
    leaf interface-name {
      type string;
      description
        "Interface Name";
    }
    leaf instance {
      type string;
      description
        "Instance";
    }
    leaf area-id {
      type string;
      description
        "OSPF Area ID in Decimal Integer Format";
    }
    leaf propogate-from {
      type int32;
      description
        "ISIS Propogate From Level";
    }
    leaf propogate-to {
      type int32;
      description
        "ISIS Propogate To Level";
    }
    leaf route-policy-name {
      type string;
      description
        "Policy that uses object in question";
    }
    leaf attached-policy {
      type string;
      description
        "The attached policy that (maybe indirectly) uses
         the object in question";
    }
    leaf attach-point {
      type string;
      description
        "Name of attach point where policy is attached";
    }
  }

  grouping RPL-ATTACHMENT-INFO {
    description
      "Places where a policy is attached";
    list binding {
      description
        "bindings list";
      uses CLIENT-INFO;
    }
  }

  grouping REF-INFO {
    description
      "Set reference information";
    leaf route-policy-name {
      type string;
      description
        "Name of policy";
    }
    leaf used-directly {
      type boolean;
      description
        "Whether the policy uses this object directly or
         indirectly";
    }
    leaf status {
      type Object-status;
      description
        "Active, Inactive, or Unused";
    }
  }

  grouping RPL-REFERENCES-INFO {
    description
      "Set references list";
    list reference {
      description
        "Information about policies referring to this
         object";
      uses REF-INFO;
    }
  }

  grouping RPL-OBJECTS-INFO {
    description
      "Names of policy objects";
    leaf-list object {
      type String;
      description
        "Policy objects";
    }
  }

  grouping RPL-MAX-LIMITS-INFO {
    description
      "Policy maximum limits info";
    leaf maximum-lines-of-policy {
      type uint32;
      description
        "Maximum lines of configuration allowable for all
         policies and sets";
    }
    leaf current-lines-of-policy-limit {
      type uint32;
      description
        "Number of lines of configuration for
         policies/sets currently allowed";
    }
    leaf current-lines-of-policy-used {
      type uint32;
      description
        "Current number of lines configured for all
         policies and sets";
    }
    leaf maximum-number-of-policies {
      type uint32;
      description
        "Maximum number of policies allowable";
    }
    leaf current-number-of-policies-limit {
      type uint32;
      description
        "Number of policies currently allowed";
    }
    leaf current-number-of-policies-used {
      type uint32;
      description
        "Current number of policies configured";
    }
    leaf compiled-policies-length {
      type uint32;
      description
        "The total compiled length of all policies";
    }
  }
}
