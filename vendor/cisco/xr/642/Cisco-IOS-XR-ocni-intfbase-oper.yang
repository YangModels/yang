module Cisco-IOS-XR-ocni-intfbase-oper {
  namespace "http://cisco.com/ns/yang/Cisco-IOS-XR-ocni-intfbase-oper";
  prefix ocni-intfbase-oper;

  include Cisco-IOS-XR-ocni-intfbase-oper-sub1 {
    revision-date 2017-11-23;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ocni-intfbase package operational data.
     
     This module contains definitions
     for the following management objects:
       ocni-ni-intfbase: An OpenConfig description of a
         network-instance. This may be a Layer 3 forwarding construct
         such as a virtual routing and forwarding (VRF) instance, or
         a Layer 2 instance such as a virtual switch instance (VSI).
         Mixed Layer 2 and Layer 3 instances are also supported.
     
     Copyright (c) 2013-2017 by Cisco Systems, Inc.
     All rights reserved.";

  revision 2017-11-23 {
    description
      "Support for telemetry backend code.";
  }
  revision 2015-11-09 {
    description
      "IOS XR 6.0 revision.";
  }

  container ocni-ni-intfbase {
    config false;
    description
      "An OpenConfig description of a network-instance.
       This may be a Layer 3 forwarding construct such
       as a virtual routing and forwarding (VRF)
       instance, or a Layer 2 instance such as a virtual
       switch instance (VSI). Mixed Layer 2 and Layer 3
       instances are also supported.";
    container network-instances {
      description
        "Network instances configured on the local system";
      list network-instance {
        key "name";
        description
          "Network instances configured on the local
           system";
        container interfaces {
          description
            "An interface associated with the network
             instance";
          list interface {
            key "id";
            description
              "An interface associated with the network
               instance";
            leaf id {
              type string;
              description
                "A reference to an identifier for this
                 interface which acts as a key for this list";
            }
            uses OVERLAY-OCNI-NI-INTFBASE-INTERFACE;
          }
        }
        leaf name {
          type string;
          description
            "A unique name identifying the network instance";
        }
      }
    }
  }
}
