submodule Cisco-IOS-XR-pppoe-ea-oper-sub1 {
  belongs-to Cisco-IOS-XR-pppoe-ea-oper {
    prefix Cisco-IOS-XR-pppoe-ea-oper;
  }

  import ietf-yang-types {
    prefix yang;
  }
  import Cisco-IOS-XR-types {
    prefix xr;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR pppoe-ea package operational data.
     
     Copyright (c) 2013-2017 by Cisco Systems, Inc.
     All rights reserved.";

  revision 2015-11-09 {
    description
      "IOS XR 6.0 revision.";
  }

  grouping PPPOE-EA-INTERFACE-INFO {
    description
      "PPPoE EA interface information";
    container peer-mac {
      description
        "Peer Mac-address";
      uses ETHER-MACADDR-TYPE;
    }
    container local-mac {
      description
        "Local Mac-address";
      uses ETHER-MACADDR-TYPE;
    }
    container srgv-mac {
      description
        "SRG VMac-address";
      uses ETHER-MACADDR-TYPE;
    }
    leaf interface {
      type xr:Interface-name;
      description
        "Interface";
    }
    leaf session-id {
      type uint16;
      description
        "Session ID";
    }
    leaf parent-interface {
      type xr:Interface-name;
      description
        "Parent Interface";
    }
    leaf is-priority-set {
      type boolean;
      description
        "Is Priority Set";
    }
    leaf priority {
      type uint8;
      description
        "Priority";
    }
    leaf is-in-sync {
      type boolean;
      description
        "Is in sync";
    }
    leaf is-platform-created {
      type boolean;
      description
        "Is Platform created";
    }
    leaf-list vlanid {
      type uint16;
      max-elements "2";
      description
        "VLAN Ids";
    }
  }

  grouping ETHER-MACADDR-TYPE {
    description
      "ETHER MACADDR TYPE";
    leaf macaddr {
      type yang:hex-string;
      description
        "macaddr";
    }
  }

  grouping PPPOE-EA-PARENT-INTERFACE-INFO {
    description
      "PPPoE EA parent interface information";
    container srgv-mac {
      description
        "SRG VMac-address";
      uses ETHER-MACADDR-TYPE;
    }
    leaf interface {
      type xr:Interface-name;
      description
        "Interface";
    }
    leaf is-in-sync {
      type boolean;
      description
        "Is in sync";
    }
  }
}
