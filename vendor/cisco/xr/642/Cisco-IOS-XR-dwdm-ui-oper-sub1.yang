submodule Cisco-IOS-XR-dwdm-ui-oper-sub1 {
  belongs-to Cisco-IOS-XR-dwdm-ui-oper {
    prefix Cisco-IOS-XR-dwdm-ui-oper;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR dwdm-ui package operational data.
     
     Copyright (c) 2013-2017 by Cisco Systems, Inc.
     All rights reserved.";

  revision 2015-11-09 {
    description
      "IOS XR 6.0 revision.";
  }

  typedef G709aps-byte {
    type enumeration {
      enum "pp-no-protect" {
        value 0;
        description
          "No Protection";
      }
      enum "pp-no-request" {
        value 15;
        description
          "No Request";
      }
      enum "pp-regen-degrade" {
        value 63;
        description
          "Regenerator Degrade";
      }
      enum "pp-sig-degrade" {
        value 175;
        description
          "Signal Degrade";
      }
      enum "pp-remote-main" {
        value 239;
        description
          "Maintenance Request";
      }
      enum "pp-aps-unknown" {
        value 255;
        description
          "Unknown";
      }
    }
    description
      "G709aps byte";
  }

  typedef G709ppintf-state {
    type enumeration {
      enum "pp-intf-up" {
        value 0;
        description
          "Interface is Up";
      }
      enum "pp-intf-failing" {
        value 1;
        description
          "Interface is Going Down";
      }
      enum "pp-intf-down" {
        value 2;
        description
          "Interface Down";
      }
    }
    description
      "G709ppintf state";
  }

  typedef G709ppfsm-state {
    type enumeration {
      enum "in-active" {
        value 0;
        description
          "In Active";
      }
      enum "disabled" {
        value 1;
        description
          "Disabled";
      }
      enum "normal-state" {
        value 2;
        description
          "Normal";
      }
      enum "local-failing" {
        value 3;
        description
          "Local Failing";
      }
      enum "remote-failing" {
        value 4;
        description
          "Remote Failing";
      }
      enum "main-t-failing" {
        value 5;
        description
          "Maintance Failing";
      }
      enum "regen-failing" {
        value 6;
        description
          "Regenerator Failing";
      }
      enum "local-failed" {
        value 7;
        description
          "Local Failed";
      }
      enum "remote-failed" {
        value 8;
        description
          "Remote Failed";
      }
      enum "main-t-failed" {
        value 9;
        description
          "Maintance Failed";
      }
      enum "regen-failed" {
        value 10;
        description
          "Regenerator Failed";
      }
    }
    description
      "G709ppfsm state";
  }

  typedef G709ppfsm-mode {
    type enumeration {
      enum "pp-disable" {
        value 0;
        description
          "OFF";
      }
      enum "pp-default-mode" {
        value 1;
        description
          "ON (Default Mode)";
      }
      enum "pp-graceful-mode" {
        value 2;
        description
          "ON (Graceful Mode)";
      }
    }
    description
      "G709ppfsm mode";
  }

  typedef Dwdm-wave-channel-owner {
    type enumeration {
      enum "default" {
        value 0;
        description
          "Hardware Default";
      }
      enum "configuration" {
        value 1;
        description
          "Configuration";
      }
      enum "gmpls" {
        value 2;
        description
          "GMPLS Signaled";
      }
    }
    description
      "Dwdm wave channel owner";
  }

  typedef G709efec-mode {
    type enumeration {
      enum "g975-none" {
        value 0;
        description
          "";
      }
      enum "g975-1-i4" {
        value 1;
        description
          "G975.1 I.4";
      }
      enum "g975-1-i7" {
        value 2;
        description
          "G975.1 I.7";
      }
    }
    description
      "G709efec mode";
  }

  typedef Dwdmtas-state {
    type enumeration {
      enum "tas-oos" {
        value 0;
        description
          "Out of Service";
      }
      enum "tas-is" {
        value 1;
        description
          "In Service";
      }
      enum "tas-oos-mt" {
        value 2;
        description
          "Out of Service Maintenance";
      }
      enum "tas-is-cfg" {
        value 3;
        description
          "In Service Config allowed";
      }
    }
    description
      "Dwdmtas state";
  }

  typedef Dwdm-controller-state {
    type enumeration {
      enum "dwdm-ui-state-up" {
        value 0;
        description
          "Up";
      }
      enum "dwdm-ui-state-down" {
        value 1;
        description
          "Down";
      }
      enum "dwdm-ui-state-admin-down" {
        value 2;
        description
          "Administratively Down";
      }
    }
    description
      "Dwdm controller state";
  }

  typedef G709prbs-mode {
    type enumeration {
      enum "mode-source" {
        value 0;
        description
          "mode source";
      }
      enum "mode-sink" {
        value 1;
        description
          "mode sink";
      }
      enum "mode-source-sink" {
        value 2;
        description
          "mode source sink";
      }
      enum "mode-invalid" {
        value 3;
        description
          "mode invalid";
      }
    }
    description
      "G709prbs mode";
  }

  typedef G709prbs-pattern {
    type enumeration {
      enum "pattern-none" {
        value 0;
        description
          "pattern none";
      }
      enum "pattern-null" {
        value 1;
        description
          "pattern null";
      }
      enum "pattern-pn11" {
        value 2;
        description
          "pattern pn11";
      }
      enum "pattern-pn23" {
        value 3;
        description
          "pattern pn23";
      }
      enum "pattern-pn31" {
        value 4;
        description
          "pattern pn31";
      }
    }
    description
      "G709prbs pattern";
  }

  typedef G709prbs-interval {
    type enumeration {
      enum "current-interval" {
        value 0;
        description
          "Current interval";
      }
      enum "previous-interval" {
        value 1;
        description
          "Previous interval";
      }
      enum "previous-interval2" {
        value 2;
        description
          "Previous interval 2";
      }
      enum "previous-interval3" {
        value 3;
        description
          "Previous interval 3";
      }
      enum "previous-interval4" {
        value 4;
        description
          "Previous interval 4";
      }
      enum "previous-interval5" {
        value 5;
        description
          "Previous interval 5";
      }
      enum "previous-interval6" {
        value 6;
        description
          "Previous interval 6";
      }
      enum "previous-interval7" {
        value 7;
        description
          "Previous interval 7";
      }
      enum "previous-interval8" {
        value 8;
        description
          "Previous interval 8";
      }
      enum "previous-interval9" {
        value 9;
        description
          "Previous interval 9";
      }
      enum "previous-interval10" {
        value 10;
        description
          "Previous interval 10";
      }
      enum "previous-interval11" {
        value 11;
        description
          "Previous interval 11";
      }
      enum "previous-interval12" {
        value 12;
        description
          "Previous interval 12";
      }
      enum "previous-interval13" {
        value 13;
        description
          "Previous interval 13";
      }
      enum "previous-interval14" {
        value 14;
        description
          "Previous interval 14";
      }
      enum "previous-interval15" {
        value 15;
        description
          "Previous interval 15";
      }
      enum "previous-interval16" {
        value 16;
        description
          "Previous interval 16";
      }
      enum "previous-interval17" {
        value 17;
        description
          "Previous interval 17";
      }
      enum "previous-interval18" {
        value 18;
        description
          "Previous interval 18";
      }
      enum "previous-interval19" {
        value 19;
        description
          "Previous interval 19";
      }
      enum "previous-interval20" {
        value 20;
        description
          "Previous interval 20";
      }
      enum "previous-interval21" {
        value 21;
        description
          "Previous interval 21";
      }
      enum "previous-interval22" {
        value 22;
        description
          "Previous interval 22";
      }
      enum "previous-interval23" {
        value 23;
        description
          "Previous interval 23";
      }
      enum "previous-interval24" {
        value 24;
        description
          "Previous interval 24";
      }
      enum "previous-interval25" {
        value 25;
        description
          "Previous interval 25";
      }
      enum "previous-interval26" {
        value 26;
        description
          "Previous interval 26";
      }
      enum "previous-interval27" {
        value 27;
        description
          "Previous interval 27";
      }
      enum "previous-interval28" {
        value 28;
        description
          "Previous interval 28";
      }
      enum "previous-interval29" {
        value 29;
        description
          "Previous interval 29";
      }
      enum "previous-interval30" {
        value 30;
        description
          "Previous interval 30";
      }
      enum "previous-interval31" {
        value 31;
        description
          "Previous interval 31";
      }
      enum "previous-interval32" {
        value 32;
        description
          "Previous interval 32";
      }
    }
    description
      "PRBS test interval information";
  }

  grouping DWDM-EDM-VTXP-INFO {
    description
      "VTXP Information";
    leaf vtxp-enable {
      type boolean;
      description
        "Is VTXP attribute enabled";
    }
  }

  grouping DWDM-EDM-SIGNAL-LOG-INFO {
    description
      "Signal log information";
    leaf is-log-enabled {
      type boolean;
      description
        "'true' if signal log is enabled 'false'
         otherwise";
    }
    leaf log-filename {
      type string {
        length "0..64";
      }
      description
        "Log file name ";
    }
  }

  grouping DWDM-EDM-PROACTIVE-INFO {
    description
      "Proactive Information";
    leaf proactive-feature {
      type boolean;
      description
        "Feature Support";
    }
    leaf proactive-mode {
      type G709ppfsm-mode;
      description
        "Proactive Mode";
    }
    leaf proactive-fsm-state {
      type G709ppfsm-state;
      description
        "Proactive FSM State";
    }
    leaf proactive-fsm-if-state {
      type G709ppintf-state;
      description
        "Proactive FSM IF State";
    }
    leaf tas-state {
      type Dwdmtas-state;
      description
        "TAS State";
    }
    leaf trig-thresh-coeff {
      type uint8;
      description
        "Trigger threshold coefficient";
    }
    leaf trig-thresh-power {
      type uint8;
      description
        "Trigger threshold power";
    }
    leaf rvrt-thresh-coeff {
      type uint8;
      description
        "Revert threshold coefficient";
    }
    leaf rvrt-thresh-power {
      type uint8;
      description
        "Revert threshold power";
    }
    leaf default-trig-thresh-coeff {
      type uint8;
      description
        "Default Trigger threshold coefficient";
    }
    leaf default-trig-thresh-power {
      type uint8;
      description
        "Default Trigger threshold power";
    }
    leaf default-rvrt-thresh-coeff {
      type uint8;
      description
        "Default Revert threshold coefficient";
    }
    leaf default-rvrt-thresh-power {
      type uint8;
      description
        "Default Revert threshold power";
    }
    leaf trig-samples {
      type uint8;
      description
        "Required Trigger Samples";
    }
    leaf rvrt-samples {
      type uint8;
      description
        "Required Revert Samples";
    }
    leaf trigger-window {
      type uint32;
      description
        "Trigger Integration window";
    }
    leaf revert-window {
      type uint32;
      description
        "Revert Integration Window";
    }
    leaf protection-trigger {
      type boolean;
      description
        "Protection Trigger State";
    }
    leaf interface-trigger {
      type boolean;
      description
        "Proactive Interface Triffer";
    }
    leaf tx-aps {
      type uint8;
      description
        "Transmitted APS Byte";
    }
    leaf tx-aps-descr {
      type G709aps-byte;
      description
        "Tx APS Description";
    }
    leaf rx-aps {
      type uint8;
      description
        "Received APS byte";
    }
    leaf rx-aps-descr {
      type G709aps-byte;
      description
        "Rx APS Description";
    }
    leaf alarm-state {
      type boolean;
      description
        "AlarmState";
    }
    leaf trig-ec-cnt {
      type uint32;
      description
        "Trigger EC Cnt";
    }
    leaf rvrt-ec-cnt {
      type uint32;
      description
        "Revert EC Cnt";
    }
    leaf prefec-thresh-crossed {
      type boolean;
      description
        "Prefec Trigger Thresh Crossed";
    }
  }

  grouping DWDM-EDM-NETWORK-SRLG-INFO {
    description
      "Network SRLG Information";
    leaf-list network-srlg {
      type uint32;
      max-elements "102";
      description
        "Network Srlg";
    }
  }

  grouping DWDM-EDM-TDC-INFO {
    description
      "TDC information";
    leaf tdc-valid {
      type boolean;
      description
        "TRUE for Valid else Invalid";
    }
    leaf major-alarm {
      type boolean;
      description
        "TRUE for Alarm condition else FALSE";
    }
    leaf operation-mode {
      type boolean;
      description
        "TRUE for MANUAL else AUTO";
    }
    leaf tdc-status {
      type boolean;
      description
        "TRUE if TDC Aquiring else Locked";
    }
    leaf dispersion-offset {
      type int32;
      description
        "TDC Dispersion Offset";
    }
    leaf reroute-ber {
      type int32;
      description
        "Reroute BER";
    }
    leaf is-reroute-control-enabled {
      type boolean;
      description
        "TRUE for ENABLED else DISABLED";
    }
  }

  grouping DWDM-EDM-OPTICS-INFO {
    description
      "optics transponder information";
    leaf optics-type {
      type string {
        length "0..64";
      }
      description
        "Optics type name";
    }
    leaf clock-source {
      type uint8;
      description
        "Actual transmit clock source";
    }
    leaf wave-frequency-progressive-string {
      type string {
        length "0..64";
      }
      description
        "Wave Frequency Information for Progressive
         Frequencies";
    }
    leaf wavelength-progressive-string {
      type string {
        length "0..64";
      }
      description
        "Wavelength Information for Progressive
         Frequencies";
    }
    leaf is-wave-frequency-progressive-valid {
      type boolean;
      description
        "True if Progressive Frequency is supported by hw";
    }
    leaf wavelength-progressive {
      type uint32;
      description
        "Wavelength Information for Progressive
         Frequencies";
    }
    leaf wave-band {
      type uint32;
      description
        "Wavelength band information";
    }
    leaf wave-channel {
      type uint32;
      description
        "Current ITU wavelength channel number";
    }
    leaf wave-frequency {
      type uint32;
      description
        " wavelenght frequency read from hw in the uint 0
         .01nm";
    }
    leaf is-wave-frequency-valid {
      type boolean;
      description
        "True if hw supported wavelength frequency
         readback";
    }
    leaf wave-channel-owner {
      type Dwdm-wave-channel-owner;
      description
        "Owner of current wavelength";
    }
    leaf gmpls-set-wave-channel {
      type uint16;
      description
        "Wavelength channel set by GMPLS";
    }
    leaf configured-wave-channel {
      type uint16;
      description
        "Wavelength channel set from configuration";
    }
    leaf default-wave-channel {
      type uint16;
      description
        "Wavelength channel default from hardware";
    }
    leaf transmit-power {
      type int32;
      description
        "Transmit power in the unit of 0.01dbm";
    }
    leaf transmit-power-threshold {
      type int32;
      description
        "Transmit power threshold value";
    }
    leaf laser-current-bias {
      type int32;
      description
        "Laser current bias value";
    }
    leaf laser-current-bias-threshold {
      type int32;
      description
        " Laser Current Bias threshold value";
    }
    leaf receive-power {
      type int32;
      description
        "Transponder receive power";
    }
    leaf is-rx-los-threshold-supported {
      type boolean;
      description
        "TRUE if  Rx LOS thresold configurable";
    }
    leaf rx-los-threshold {
      type int32;
      description
        "Rx LOS threshold value";
    }
    leaf transmit-power-min {
      type int32;
      description
        "Transmit  power mininum value in the interval
         time";
    }
    leaf transmit-power-max {
      type int32;
      description
        "Transmit power maximum value in the interval
         time";
    }
    leaf transmit-power-avg {
      type int32;
      description
        "Transmit optical average value in the interval
         time";
    }
    leaf receive-power-min {
      type int32;
      description
        "Recieve power mininum value in the interval time";
    }
    leaf receive-power-max {
      type int32;
      description
        "Receive power maximum value in the interval time";
    }
    leaf receive-power-avg {
      type int32;
      description
        "Recieve power average value in the interval time";
    }
    leaf laser-bias-current-min {
      type int32;
      description
        "Laser bias current minimum value in the interval
         time";
    }
    leaf laser-bias-current-max {
      type int32;
      description
        "Laser bias current maxinum value in the interval
         time";
    }
    leaf laser-bias-current-avg {
      type int32;
      description
        "Laser bias current average value in the interval
         time";
    }
    leaf chromatic-dispersion {
      type int32;
      description
        "Current chromatic dispersion";
    }
    leaf differential-group-delay {
      type int32;
      description
        "Current differential group Delay";
    }
    leaf polarization-mode-dispersion {
      type int32;
      description
        "Current polarization mode dispersion";
    }
    leaf signal-to-noise-ratio {
      type int32;
      description
        "Current optical signal to noise ratio";
    }
    leaf polarization-dependent-loss {
      type int32;
      description
        "Current Polarization Dependent loss";
    }
    leaf polarization-change-rate {
      type uint32;
      description
        "Current Polarization change rate";
    }
    leaf phase-noise {
      type uint32;
      description
        "Current Phase Noise";
    }
    leaf output-power-fail {
      type uint32;
      description
        "Transmit power failure(above/belowe a threshold)
         count";
    }
    leaf input-power-fail {
      type uint32;
      description
        "Receive power failure(above/belowe a threshold)
         count";
    }
  }

  grouping DWDM-EDM-G709-ODU {
    description
      "dwdm odu information";
    container oci {
      description
        "Open Connection Indiction information";
      uses DWDM-EDM-G709-ALARM;
    }
    container ais {
      description
        "Alarm Indication Signal information";
      uses DWDM-EDM-G709-ALARM;
    }
    container lck {
      description
        "Upstream Connection Locked information";
      uses DWDM-EDM-G709-ALARM;
    }
    container bdi {
      description
        "Backward Defect Indication information";
      uses DWDM-EDM-G709-ALARM;
    }
    container eoc {
      description
        "GCC End of Channel information";
      uses DWDM-EDM-G709-ALARM;
    }
    container ptim {
      description
        "Payload Type Identifier Mismatch information";
      uses DWDM-EDM-G709-ALARM;
    }
    container tim {
      description
        "Trace Identifier Mismatch information";
      uses DWDM-EDM-G709-ALARM;
    }
    container sf-ber {
      description
        "Signal Fail  BER information";
      uses DWDM-EDM-G709-ALERT;
    }
    container sd-ber {
      description
        "Signal Degrade BER information";
      uses DWDM-EDM-G709-ALERT;
    }
    container bbe-tca {
      description
        "Background Block Error TCA information";
      uses DWDM-EDM-G709-ALERT;
    }
    container es-tca {
      description
        "Errored Seconds TCA information";
      uses DWDM-EDM-G709-ALERT;
    }
    container bbe {
      description
        "Background Block Error information";
      uses DWDM-EDM-G709-PM;
    }
    container es {
      description
        "Errored Seconds information";
      uses DWDM-EDM-G709-PM;
    }
    container ses {
      description
        "Severly Errored Seconds information";
      uses DWDM-EDM-G709-PM;
    }
    container uas {
      description
        "Unavailability Seconds information";
      uses DWDM-EDM-G709-PM;
    }
    container fc {
      description
        "Failure count information";
      uses DWDM-EDM-G709-PM;
    }
    container bber {
      description
        "Background Block Error Rate count information";
      uses DWDM-EDM-G709-PM;
    }
    container esr {
      description
        "Errored Seconds Rate information";
      uses DWDM-EDM-G709-PM;
    }
    container sesr {
      description
        "Severly Errored Seconds Rate information";
      uses DWDM-EDM-G709-PM;
    }
    container tti {
      description
        "Trail Trace Identifier information";
      uses DWDM-EDM-G709-TTI;
    }
    leaf bip {
      type uint64;
      description
        "Bit Interleave Parity(BIP) counter";
    }
    leaf bei {
      type uint64;
      description
        "Backward Error Indication counter";
    }
  }

  grouping DWDM-EDM-G709-TTI {
    description
      "G709 TTI information";
    leaf tx-string-type {
      type uint32;
      description
        "Type of String";
    }
    leaf expected-string-type {
      type uint32;
      description
        "Type of String";
    }
    leaf rx-string-type {
      type uint32;
      description
        "Type of String";
    }
    leaf tx-tti {
      type string {
        length "0..129";
      }
      description
        "Tx TTI String ";
    }
    leaf tx-sapi0 {
      type string {
        length "0..5";
      }
      description
        "Tx SAPI[0] Field";
    }
    leaf tx-sapi {
      type string {
        length "0..16";
      }
      description
        "Tx SAPI[1-15] Field";
    }
    leaf tx-sapi-range {
      type string {
        length "0..6";
      }
      description
        " Tx SAPI Range String";
    }
    leaf tx-dapi0 {
      type string {
        length "0..5";
      }
      description
        "Tx DAPI[0] Field";
    }
    leaf tx-dapi {
      type string {
        length "0..16";
      }
      description
        "Tx DAPI[1-15] Field";
    }
    leaf tx-dapi-range {
      type string {
        length "0..6";
      }
      description
        " Tx DAPI Range String";
    }
    leaf tx-oper-spec {
      type string {
        length "0..33";
      }
      description
        "Tx Operator Specific Field";
    }
    leaf tx-oper-spec-range {
      type string {
        length "0..6";
      }
      description
        " Tx Operator Specific Field Range String";
    }
    leaf rx-tti {
      type string {
        length "0..129";
      }
      description
        "Rx TTI String ";
    }
    leaf rx-sapi0 {
      type string {
        length "0..5";
      }
      description
        "Rx SAPI[0] Field";
    }
    leaf rx-sapi {
      type string {
        length "0..16";
      }
      description
        "Rx SAPI[1-15] Field";
    }
    leaf rx-sapi-range {
      type string {
        length "0..6";
      }
      description
        " Rx SAPI Range String";
    }
    leaf rx-dapi0 {
      type string {
        length "0..5";
      }
      description
        "Rx DAPI[0] Field";
    }
    leaf rx-dapi {
      type string {
        length "0..16";
      }
      description
        "Rx DAPI[1-15] Field";
    }
    leaf rx-dapi-range {
      type string {
        length "0..6";
      }
      description
        " Rx DAPI Range String";
    }
    leaf rx-oper-spec-range {
      type string {
        length "0..6";
      }
      description
        " Rx Operator Specific Field Range String";
    }
    leaf rx-oper-spec {
      type string {
        length "0..33";
      }
      description
        "Rx Operator Specific Field";
    }
    leaf expected-tti {
      type string {
        length "0..129";
      }
      description
        "Expected TTI String";
    }
    leaf expected-sapi0 {
      type string {
        length "0..5";
      }
      description
        "Expected SAPI[0] Field";
    }
    leaf expected-sapi {
      type string {
        length "0..16";
      }
      description
        "Expected SAPI[1-15] Field";
    }
    leaf exp-sapi-range {
      type string {
        length "0..6";
      }
      description
        " Expected SAPI Range String";
    }
    leaf expected-dapi0 {
      type string {
        length "0..5";
      }
      description
        "Expected DAPI[0] Field";
    }
    leaf expected-dapi {
      type string {
        length "0..16";
      }
      description
        "Expected DAPI[1-15] Field";
    }
    leaf exp-dapi-range {
      type string {
        length "0..6";
      }
      description
        " Expected DAPI Range String";
    }
    leaf expected-oper-spec {
      type string {
        length "0..33";
      }
      description
        "Expected Operator Specific Field";
    }
    leaf exp-oper-spec-range {
      type string {
        length "0..6";
      }
      description
        " Expected Operator Specific Field Range String";
    }
  }

  grouping DWDM-EDM-G709-PM {
    description
      "G709 PM information";
    leaf counter {
      type uint64;
      description
        "Performance Monitoring counter";
    }
  }

  grouping DWDM-EDM-G709-OTU {
    description
      "DWDM OTU information";
    container los {
      description
        "Loss of Signal information";
      uses DWDM-EDM-G709-ALARM;
    }
    container lof {
      description
        "Loss of Frame information";
      uses DWDM-EDM-G709-ALARM;
    }
    container lom {
      description
        "Loss of MultiFrame information";
      uses DWDM-EDM-G709-ALARM;
    }
    container oof {
      description
        "Out of Frame information";
      uses DWDM-EDM-G709-ALARM;
    }
    container oom {
      description
        "Out of MultiFrame information";
      uses DWDM-EDM-G709-ALARM;
    }
    container ais {
      description
        "Alarm Indication Signal information";
      uses DWDM-EDM-G709-ALARM;
    }
    container iae {
      description
        "Incoming Alignment Error information";
      uses DWDM-EDM-G709-ALARM;
    }
    container bdi {
      description
        "Backward Defect Indication information";
      uses DWDM-EDM-G709-ALARM;
    }
    container tim {
      description
        "Trace Identifier Mismatch information";
      uses DWDM-EDM-G709-ALARM;
    }
    container eoc {
      description
        "GCC End of Channel information";
      uses DWDM-EDM-G709-ALARM;
    }
    container sf-ber {
      description
        "Signal Fail  BER information";
      uses DWDM-EDM-G709-ALERT;
    }
    container sd-ber {
      description
        "Signal Degrade BER information";
      uses DWDM-EDM-G709-ALERT;
    }
    container prefec-sf-ber {
      description
        "Prefec Signal Fail BER information";
      uses DWDM-EDM-G709-ALERT;
    }
    container prefec-sd-ber {
      description
        "Prefec Signal Degrade BER information";
      uses DWDM-EDM-G709-ALERT;
    }
    container bbe-tca {
      description
        " Backgound Block Error TCA information";
      uses DWDM-EDM-G709-ALERT;
    }
    container es-tca {
      description
        "Errored Seconds TCA information";
      uses DWDM-EDM-G709-ALERT;
    }
    container bbe {
      description
        "Backgound Block Error information";
      uses DWDM-EDM-G709-PM;
    }
    container es {
      description
        "Errored Seconds information ";
      uses DWDM-EDM-G709-PM;
    }
    container ses {
      description
        "Severly Errored Seconds information";
      uses DWDM-EDM-G709-PM;
    }
    container uas {
      description
        "Unavailability Seconds information";
      uses DWDM-EDM-G709-PM;
    }
    container fc {
      description
        "Failure Count information";
      uses DWDM-EDM-G709-PM;
    }
    container bber {
      description
        "Backgound Block Error Rate information";
      uses DWDM-EDM-G709-PM;
    }
    container esr {
      description
        "Errored Seconds Rate information";
      uses DWDM-EDM-G709-PM;
    }
    container sesr {
      description
        "Severly Errored Seconds Rate information";
      uses DWDM-EDM-G709-PM;
    }
    container tti {
      description
        "Trail Trace Identifier information";
      uses DWDM-EDM-G709-TTI;
    }
    leaf bei {
      type uint64;
      description
        "Backward Error Indication counter";
    }
    leaf bip {
      type uint64;
      description
        "Bit Interleave Parity(BIP) counter";
    }
  }

  grouping DWDM-EDM-G709-ALERT {
    description
      "G709 Alert Information";
    leaf reporting-enabled {
      type boolean;
      description
        "Is reporting enabled?";
    }
    leaf is-detected {
      type boolean;
      description
        "Is defect detected?";
    }
    leaf is-asserted {
      type boolean;
      description
        "Is defect delared?";
    }
    leaf threshold {
      type int32;
      description
        "Error threshold power";
    }
    leaf counter {
      type uint64;
      description
        "Error counter";
    }
  }

  grouping DWDM-EDM-G709-ALARM {
    description
      " G709 Alarm information";
    leaf reporting-enabled {
      type boolean;
      description
        "Is reporting enabled?";
    }
    leaf is-detected {
      type boolean;
      description
        "Is defect detected?";
    }
    leaf is-asserted {
      type boolean;
      description
        "Is defect delared?";
    }
    leaf counter {
      type uint64;
      description
        "Alarm counter";
    }
  }

  grouping DWDM-EDM-G709-INFO {
    description
      "g709 information";
    container fec-mismatch {
      description
        "FEC mismatch alarm";
      uses DWDM-EDM-G709-ALARM;
    }
    container ec-tca {
      description
        "FEC Corrected bits TCA information";
      uses DWDM-EDM-G709-ALERT;
    }
    container uc-tca {
      description
        "FEC uncorrected words TCA information";
      uses DWDM-EDM-G709-ALERT;
    }
    container otu-info {
      description
        "OTU layer information";
      uses DWDM-EDM-G709-OTU;
    }
    container odu-info {
      description
        "ODU layer Information";
      uses DWDM-EDM-G709-ODU;
    }
    leaf is-g709-enabled {
      type boolean;
      description
        " Is G709 framing enabled";
    }
    leaf is-fec-mode-default {
      type boolean;
      description
        " Is Operating FEC Mode Default";
    }
    leaf fec-mode {
      type int32;
      description
        "FEC information";
    }
    leaf remote-fec-mode {
      type int32;
      description
        "Remote FEC information";
    }
    leaf efec-mode {
      type G709efec-mode;
      description
        "EFEC information";
    }
    leaf loopback-mode {
      type int32;
      description
        "Loopback information";
    }
    leaf ec {
      type uint64;
      description
        "Corrected bit error counter ";
    }
    leaf ec-accum {
      type uint64;
      description
        "FEC Corrected bit error accumulated counter";
    }
    leaf uc {
      type uint64;
      description
        "FEC Uncorrected words counter";
    }
    leaf fec-ber {
      type uint64;
      description
        "pre fec ber calculated";
    }
    leaf fec-ber-man {
      type int32;
      description
        "pre fec ber calculated";
    }
    leaf q {
      type uint64;
      description
        "q value calculated";
    }
    leaf q-margin {
      type uint64;
      description
        "q margin calculated";
    }
    leaf fe-cstr {
      type string {
        length "0..64";
      }
      description
        "FEC BER String ";
    }
    leaf qstr {
      type string {
        length "0..64";
      }
      description
        "Q String ";
    }
    leaf qmargin-str {
      type string {
        length "0..64";
      }
      description
        "QMargin String";
    }
    leaf network-port-id {
      type string {
        length "0..65";
      }
      description
        "Network port ID";
    }
    leaf network-conn-id {
      type string {
        length "0..65";
      }
      description
        "Network connection ID";
    }
    leaf is-prbs-enabled {
      type boolean;
      description
        "'true' if Prbs is enabled 'false' otherwise";
    }
    leaf g709-prbs-mode {
      type G709prbs-mode;
      description
        "Configured mode of PRBS Test";
    }
    leaf g709-prbs-pattern {
      type G709prbs-pattern;
      description
        "Pattern of PRBS Test";
    }
    leaf prbs-time-stamp {
      type uint64;
      description
        "Time stamp for prbs configuration";
    }
  }

  grouping DWDM-EDM-PORT-INFO {
    description
      "dwdm port operational information";
    container g709-info {
      description
        "G709 operational information";
      uses DWDM-EDM-G709-INFO;
    }
    container optics-info {
      description
        "Optics operational information";
      uses DWDM-EDM-OPTICS-INFO;
    }
    container tdc-info {
      description
        "TDC operational information";
      uses DWDM-EDM-TDC-INFO;
    }
    container network-srlg-info {
      description
        "Network SRLG information";
      uses DWDM-EDM-NETWORK-SRLG-INFO;
    }
    container proactive {
      description
        "Proactive protection information";
      uses DWDM-EDM-PROACTIVE-INFO;
    }
    container signal-log {
      description
        "Signal log information";
      uses DWDM-EDM-SIGNAL-LOG-INFO;
    }
    leaf controller-state {
      type Dwdm-controller-state;
      description
        "DWDM controller state: Up, Down or
         Administratively Down";
    }
    leaf transport-admin-state {
      type Dwdmtas-state;
      description
        "DWDM controller TAS state: IS, OOS, OOS-MT or
         IS-CFG";
    }
    leaf slice-state {
      type boolean;
      description
        "DWDM port slice state Up/Down";
    }
  }

  grouping DWDM-EDM-WAVE-INFO {
    description
      "wavelength information";
    leaf wave-band {
      type uint32;
      description
        "Wavelength band";
    }
    leaf wave-channel-min {
      type uint32;
      description
        "Lowest ITU wavelength channel number supported";
    }
    leaf wave-channel-max {
      type uint32;
      description
        "Highest ITU wavelength channel number supported";
    }
  }

  grouping PRBS-INTERVAL {
    description
      "PRBS Interval Information";
    leaf interval-index {
      type G709prbs-interval;
      description
        "Index of bucket, current and previous";
    }
    leaf configured-pattern {
      type G709prbs-pattern;
      description
        "Configured pattern of PRBS test";
    }
    leaf start-at {
      type string {
        length "0..64";
      }
      description
        "Interval start timestamp";
    }
    leaf stop-at {
      type string {
        length "0..64";
      }
      description
        "Interval stop timestamp";
    }
    leaf received-pattern {
      type G709prbs-pattern;
      description
        "Received Pattern of PRBS Test";
    }
    leaf bit-error-count {
      type uint64;
      description
        "Bit Error Count";
    }
    leaf found-count {
      type uint64;
      description
        "Count of pattern found in interval";
    }
    leaf lost-count {
      type uint64;
      description
        "Count of pattern lost in interval";
    }
    leaf found-at {
      type string {
        length "0..64";
      }
      description
        "Pattern first found at timestamp";
    }
    leaf lost-at {
      type string {
        length "0..64";
      }
      description
        "Pattern first lost at timestamp";
    }
  }

  grouping DWDM-EDM-PRBS-INFO {
    description
      "PRBS information";
    leaf is-prbs-enabled {
      type boolean;
      description
        "'True' if PRBS is enabled 'False' otherwise";
    }
    leaf prbs-config-mode {
      type G709prbs-mode;
      description
        "Configured mode of PRBS test";
    }
    list prbs-entry {
      description
        "History consists of 15-minute/24-hour intervals";
      uses PRBS-INTERVAL;
    }
  }
}
