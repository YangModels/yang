module Cisco-IOS-XR-snmp-entitymib-cfg {
  namespace "http://cisco.com/ns/yang/Cisco-IOS-XR-snmp-entitymib-cfg";
  prefix snmp-entitymib-cfg;

  import Cisco-IOS-XR-snmp-agent-cfg {
    prefix a1;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR snmp-entitymib package configuration.
     
     This YANG module augments the
       Cisco-IOS-XR-snmp-agent-cfg
     module with configuration data.
     
     Copyright (c) 2013-2017 by Cisco Systems, Inc.
     All rights reserved.";

  revision 2017-05-01 {
    description
      "Fixing backward compatibility error in module.";
  }
  revision 2015-01-07 {
    description
      "IOS XR 5.3.1 revision.";
  }

  augment "/a1:mib" {
    description
      "This augment extends the configuration data of
       'Cisco-IOS-XR-snmp-agent-cfg'";
    container entity-mib {
      description
        "Entity MIB";
      leaf entity-index-persistence {
        type empty;
        description
          "Enable entPhysicalIndex persistence";
      }
    }
  }
  augment "/a1:snmp/a1:notification" {
    description
      "This augment extends the configuration data of
       'Cisco-IOS-XR-snmp-agent-cfg'";
    container entity {
      description
        "Enable ENTITY-MIB notifications";
      leaf enable {
        type empty;
        description
          "Enable entityMIB notifications";
      }
    }
  }
}
