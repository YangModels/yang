module Cisco-IOS-XR-infra-alarm-logger-oper {
  namespace "http://cisco.com/ns/yang/Cisco-IOS-XR-infra-alarm-logger-oper";
  prefix infra-alarm-logger-oper;

  include Cisco-IOS-XR-infra-alarm-logger-oper-sub1 {
    revision-date 2017-09-07;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR infra-alarm-logger package operational data.
     
     This module contains definitions
     for the following management objects:
       alarm-logger: Alarm Logger operational data
     
     Copyright (c) 2013-2017 by Cisco Systems, Inc.
     All rights reserved.";

  revision 2017-09-07 {
    description
      "Fixed type translation error.";
  }
  revision 2015-01-07 {
    description
      "IOS XR 5.3.1 revision.";
  }

  container alarm-logger {
    config false;
    description
      "Alarm Logger operational data";
    container buffer-status {
      description
        "Describes buffer utilization and parameters
         configured";
      uses AL-LOGGING-INFO-BAG;
    }
    container alarms {
      description
        "Table that contains the database of logged
         alarms";
      list alarm {
        key "event-id";
        description
          "One of the logged alarms";
        leaf event-id {
          type uint32;
          description
            "Event ID";
        }
        uses AL-ALDEMS-ALARM-BAG;
      }
    }
  }
}
