submodule Cisco-IOS-XR-ocni-intfbase-oper-sub1 {
  belongs-to Cisco-IOS-XR-ocni-intfbase-oper {
    prefix Cisco-IOS-XR-ocni-intfbase-oper;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR ocni-intfbase package operational data.
     
     Copyright (c) 2013-2017 by Cisco Systems, Inc.
     All rights reserved.";

  revision 2017-11-23 {
    description
      "Support for telemetry backend code.";
  }
  revision 2015-11-09 {
    description
      "IOS XR 6.0 revision.";
  }

  typedef Yang2bag-string {
    type string;
    description
      "Yang2bag string";
  }

  grouping STATE {
    description
      "STATE";
    leaf id {
      type Yang2bag-string;
      description
        "A unique identifier for this interface - this is
         expressed as a free-text string";
    }
    leaf interface {
      type Yang2bag-string;
      description
        "Reference to a base interface.  If a reference
         to a subinterface is required, this leaf must be
         specified to indicate the base interface.";
    }
    leaf subinterface {
      type uint32;
      description
        "Reference to a subinterface -- this requires the
         base interface to be specified using the
         interface leaf in this container.  If only a
         reference to a base interface is requuired, this
         leaf should not be set.";
    }
    leaf-list associated-address-family {
      type Yang2bag-string;
      description
        "The address families on the subinterface which
         are to be associated with this network instance.
         When this leaf-list is empty and the network
         instance requires Layer 3 information the
         address families for which the network instance
         is enabled should be imported. If the value of
         this leaf-list is specified then the association
         MUST only be made for those address families
         that are included in the list.";
    }
  }

  grouping OVERLAY-OCNI-NI-INTFBASE-INTERFACE {
    description
      "An interface associated with the network instance";
    container state {
      description
        "Operational state parameters relating to the
         associated interface";
      uses STATE;
    }
  }
}
