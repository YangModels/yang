module Cisco-IOS-XR-sysadmin-fabric-mgr-fsdb-aggregator {
  namespace "http://www.cisco.com/ns/yang/Cisco-IOS-XR-sysadmin-fabric-mgr-fsdb-aggregator";
  prefix fabric_fsdb_aggr;

  import tailf-common {
    prefix tailf;
  }
  import Cisco-IOS-XR-sysadmin-fabric-types {
    prefix fabric-types;
  }
  import Cisco-IOS-XR-sysadmin-show-trace {
    prefix show-trace;
  }

  revision 2017-06-07 {
    description
      "Updated the relative path for instance_folded config";
  }
  revision 2017-05-22 {
    description
      "Support added to place fabric link ports in maintenance.";
  }
  revision 2017-05-01 {
    description
      "Namespace change to comply with Cisco guidelines on namespace";
  }
  revision 2016-10-12 {
    description
      "Unhide commands and configs. Moved to advanced-grp";
  }

  grouping plane_show {
    list plane {
      key "planeid";
      max-elements "1024";
      tailf:hidden "internal-command";
      tailf:cli-no-key-completion;
      tailf:cli-no-match-completion;
      tailf:display-groups "fabric-brief fabric-detail";
      tailf:cli-show-template
        "$(.legend_shown != true ?$(.path ~= statistics ?$(.display_groups ~= fabric-brief ? 
         $( |rjust:4)Flags\\\\: E-D  - Exceeded display width.
         $( |rjust:18)Check detail option.
         
                              In                   Out        CE         UCE        PE   
         Plane               Cells                Cells      Cells      Cells      Cells
         --------------------------------------------------------------------------------
         :
         * If uncorrectable errored cells have a very high value check link flap history
         ):$(.display_groups ~= fabric-brief ?
         Plane Admin Plane  Plane  up->dn  up->mcast
         Id    State State  Mode   counter   counter
         --------------------------------------
         :
         Plane Admin Plane  Plane  up->dn  up->mcast Total   Down    PPU
         Id    State State  Mode   counter   counter Bundles Bundles State
         ---------------------------------------------------------------
         )))$(.path ~= statistics ?$(.display_groups ~= fabric-brief ?$(planeid|rjust:2)   $(rx_data_cells|rjust:20) $(tx_data_cells|rjust:20) $(rx_ce_cells_is_overflow == true ?$(E-D|rjust:10):$(rx_ce_cells|rjust:10)) $(rx_uce_cells_is_overflow == true ?$(E-D|rjust:10):$(rx_uce_cells|rjust:10)) $(rx_pe_cells_is_overflow == true ?$(E-D|rjust:10):$(rx_pe_cells|rjust:10))
         :
         The fabric plane number is $(planeid)
           Total received data cells\\\\: $(rx_data_cells)
           Total transmitted data cells\\\\: $(tx_data_cells)
           Total received correctable errored cells\\\\: $(rx_ce_cells)
           Total received uncorrectable errored cells\\\\: $(rx_uce_cells)
           Total received parity error cells\\\\: $(rx_pe_cells)
           Total unicast lost cells\\\\: $(ucast_lost_cells)
           Total multicast lost cells\\\\: $(mcast_lost_cells)
           Asic internal drops\\\\: $(asic_internal_drops)
           Asic internal error\\\\: $(is_asic_internal_error == false ? None:
           +----------------------------------------------------------------------------+
           |Asic      |CRC |Size|Mis |Code|No  |No  |Tokn|Err |                         |
           |(R/S/A\\\\)   |Err |Err |Alig|Grp |Sig |Sign|Err |Tokn| Last Error Found        |
           |          |    |    |Err |Err |Lock|Acpt|    |Cnt |                         |
           +----------+----+----+----+----+----+----+----+----+-------------------------+
         $(asic_internal_error|show)  +----------------------------------------------------------------------------+)
           Last clearing of statistics\\\\: $(last_clear_ts)
           Last clearing reason of statistics\\\\: $(last_clear_reason)
           Last clearing request of statistics\\\\: $(last_clear_req_ts)
           Last clearing request status of statistics\\\\: $(last_clear_status)
         ):$(.display_groups ~= fabric-brief ?$(planeid|ljust:5) $(admin-state|ljust:5) $(ucast_oper_state|ljust:8) $(plane_mode|ljust:5) $(ucast_cnt_dn|rjust:7) $(ucast_cnt_some_up|rjust:9)
         :$(planeid|ljust:5) $(admin-state|ljust:5) $(ucast_oper_state|ljust:8) $(plane_mode|rjust:5) $(ucast_cnt_dn|rjust:7) $(ucast_cnt_some_up|rjust:9) $(.path ~= fsdbagg_active ?$(total_bundles|rjust:6)  $(down_bundles|rjust:6)  :$(NA|rjust:6)  $(NA|rjust:6)  )$(ppu_state|ljust:10)
         ))";
      tailf:cli-show-template-enter "";
      tailf:cli-suppress-table;
      tailf:cli-show-template-legend
        "$(.path ~= statistics ?$(.display_groups ~= fabric-brief ? 
         $( |rjust:4)Flags\\\\: E-D  - Exceeded display width.
         $( |rjust:18)Check detail option.
         
                              In                   Out        CE         UCE        PE   
         Plane               Cells                Cells      Cells      Cells      Cells
         --------------------------------------------------------------------------------
         :
         * If uncorrectable errored cells have a very high value check link flap history
         ):$(.display_groups ~= fabric-detail ?
         Plane Admin Plane  Plane  up->dn  up->mcast Total   Down    PPU
         Id    State State  Mode   counter   counter Bundles Bundles State
         ------------------------------------------------------------
         :
         Plane Admin Plane  Plane  up->dn  up->mcast
         Id    State State  Mode   counter   counter
         --------------------------------------
         ))";
      leaf planeid {
        type fabric-types:plane_type;
        tailf:cli-disallow-value "(fabric-brief)|(fabric-detail)";
        tailf:display-groups "fabric-brief fabric-detail";
      }
      leaf admin-state {
        type string;
        tailf:hidden "internal";
      }
      leaf ucast_oper_state {
        type string;
        tailf:hidden "internal";
      }
      leaf mcast_oper_state {
        type string;
        tailf:hidden "internal";
      }
      leaf plane_mode {
        type string;
        tailf:hidden "internal";
      }
      leaf ucast_cnt_up {
        type int32;
        tailf:hidden "internal";
      }
      leaf ucast_cnt_some_up {
        type int32;
        tailf:hidden "internal";
      }
      leaf ucast_cnt_dn {
        type int32;
        tailf:hidden "internal";
      }
      leaf mcast_cnt_up {
        type int32;
        tailf:hidden "internal";
      }
      leaf mcast_cnt_some_up {
        type int32;
        tailf:hidden "internal";
      }
      leaf mcast_cnt_dn {
        type int32;
        tailf:hidden "internal";
      }
      leaf total_bundles {
        type int32;
        tailf:hidden "internal";
      }
      leaf down_bundles {
        type int32;
        tailf:hidden "internal";
      }
      leaf rx_data_cells {
        type uint64;
        tailf:hidden "internal";
      }
      leaf tx_data_cells {
        type uint64;
        tailf:hidden "internal";
      }
      leaf rx_ce_cells_is_overflow {
        type boolean;
        tailf:hidden "internal";
      }
      leaf rx_ce_cells {
        type uint64;
        tailf:hidden "internal";
      }
      leaf rx_uce_cells_is_overflow {
        type boolean;
        tailf:hidden "internal";
      }
      leaf rx_uce_cells {
        type uint64;
        tailf:hidden "internal";
      }
      leaf rx_pe_cells_is_overflow {
        type boolean;
        tailf:hidden "internal";
      }
      leaf rx_pe_cells {
        type uint64;
        tailf:hidden "internal";
      }
      leaf ucast_lost_cells {
        type uint32;
        tailf:hidden "internal";
      }
      leaf mcast_lost_cells {
        type uint32;
        tailf:hidden "internal";
      }
      leaf last_clear_ts {
        type string;
        tailf:hidden "internal";
      }
      leaf last_clear_reason {
        type string;
        tailf:hidden "internal";
      }
      leaf last_clear_req_ts {
        type string;
        tailf:hidden "internal";
      }
      leaf last_clear_status {
        type string;
        tailf:hidden "internal";
      }
      leaf is_asic_internal_error {
        type boolean;
        tailf:hidden "internal";
      }
      leaf asic_internal_drops {
        type uint64;
        tailf:hidden "internal";
      }
      leaf asic_location_drops {
        type string;
        tailf:hidden "internal";
      }
      leaf ppu_state {
        type string;
        tailf:hidden "internal";
      }
      list asic_internal_error {
        key "asic_number";
        tailf:cli-suppress-table;
        tailf:cli-show-template-enter "";
        tailf:cli-show-template "  |$(asic_location|ljust:10)| $($(link_crc_error == true ? Y : N)|ljust:3)| $($(link_size_error == true ? Y : N)|ljust:3)| $($(link_mis_align_error == true ? Y : N)|ljust:3)| $($(link_code_group_error == true ? Y : N)|ljust:3)| $($(link_no_sig_lock_error == true ? Y : N)|ljust:3)| $($(link_no_sign_accept_error == true ? Y : N)|ljust:3)| $($(link_token_error == true ? Y : N)|ljust:3)| $($(error_token_count == true ? Y : N)|ljust:3)| $(last_asic_internal_error_ts|ljust:24)|\n";
        leaf asic_number {
          type int64;
          tailf:display-groups "fabric-detail";
        }
        leaf asic_location {
          type string;
          tailf:hidden "internal";
        }
        leaf link_crc_error {
          type boolean;
          tailf:hidden "internal";
        }
        leaf link_size_error {
          type boolean;
          tailf:hidden "internal";
        }
        leaf link_mis_align_error {
          type boolean;
          tailf:hidden "internal";
        }
        leaf link_code_group_error {
          type boolean;
          tailf:hidden "internal";
        }
        leaf link_no_sig_lock_error {
          type boolean;
          tailf:hidden "internal";
        }
        leaf link_no_sign_accept_error {
          type boolean;
          tailf:hidden "internal";
        }
        leaf link_token_error {
          type boolean;
          tailf:hidden "internal";
        }
        leaf error_token_count {
          type boolean;
          tailf:hidden "internal";
        }
        leaf last_asic_internal_error_ts {
          type string;
          tailf:hidden "internal";
        }
      }
    }
  }

  grouping fsdb_agg_conf_plane {
    list plane {
      key "plane_id";
      description
        "Set state of fabric plane";
      tailf:info "Set state of fabric plane";
      leaf plane_id {
        type fabric-types:conf_plane_type;
      }
      leaf shutdown {
        type empty;
        description
          "Shut down state.";
        tailf:cli-full-command;
        tailf:info "Shut down state.";
      }
      leaf b2b {
        type empty;
        must "not((/controller/fabric/fabric/fsdbagg/plane/instance) or (/controller/fabric/fabric/fsdbagg/plane/instance_folded))" {
          error-message "instance S2 card already configured";
          tailf:dependency ".";
        }
        description
          "Back to Back plane mode.";
        tailf:cli-full-command;
        tailf:info "Back to Back plane mode.";
      }
      list instance {
        must "count(/controller/fabric/fabric/fsdbagg/plane/instance[location=current()/location])=1" {
          error-message "instance S2 card already configured";
          tailf:dependency ".";
        }
        key "instance-id";
        description
          "Multi-Chassis S2 configuration";
        leaf instance-id {
          type fabric-types:conf_instance_type;
          tailf:validate "fsdbagg_plane_instance_vp" {
            tailf:dependency "../location";
          }
        }
        leaf location {
          type fabric-types:conf_location_type;
          tailf:cli-expose-key-name;
        }
      }
      list instance_folded {
        must "not((/controller/fabric/fabric/fsdbagg/plane/plane_id = 1) or (/controller/fabric/fabric/fsdbagg/plane/plane_id = 3) or (/controller/fabric/fabric/fsdbagg/plane/plane_id = 5))" {
          error-message "Invalid folded plane id. Valid plane ids 0, 2 and 4";
          tailf:dependency ".";
        }
        must "count(/controller/fabric/fabric/fsdbagg/plane/instance_folded[location=current()/location])=1" {
          error-message "instance S2 card already configured";
          tailf:dependency ".";
        }
        key "instance-id";
        description
          "Multi-Chassis S2 Folded chassis configuration";
        tailf:hidden "advanced-grp";
        leaf instance-id {
          type fabric-types:conf_folded_instance_type;
        }
        leaf location {
          type fabric-types:conf_location_type;
          tailf:cli-expose-key-name;
        }
      }
    }
    container link {
      description
        "Link configuration commands";
      tailf:info "Link configuration commands";
      container port {
        description
          "Set admin state of a fabric link port";
        tailf:info "Set admin state of a fabric link port";
        list location {
          key "loc_str";
          tailf:cli-drop-node-name;
          tailf:cli-no-key-completion;
          leaf loc_str {
            type fabric-types:link_port_location_type;
          }
          leaf shutdown {
            type empty;
            description
              "Shut down state.";
            tailf:info "Shut down state.";
            tailf:cli-delete-container-on-delete;
          }
          leaf maintenance {
            type empty;
            description
              "maintenance state.";
            tailf:info "maintenance state.";
            tailf:cli-delete-container-on-delete;
          }
        }
      }
    }
  }

  grouping fabric_sys_plane_health {
    list sys_plane_info_list {
      key "plane_id";
      tailf:cli-suppress-table;
      tailf:cli-show-template-enter "";
      tailf:cli-show-template-legend
        "    $(Plane|ljust:5) $(Admin|ljust:5) $(Plane|ljust:8) $(Racks|ljust:8) $(Data|ljust:10)
             $(id|ljust:5) $(state|ljust:5) $(state|ljust:8) $(in issue|ljust:8) $(drop/error|ljust:10)
             -----------------------------------------------------------
        ";
      tailf:cli-show-template "    $(plane_id|ljust:5) $(admin-state|ljust:5) $(plane_state|ljust:8) $(plane_mode|ljust:5) $(racks_w_plane_fault|ljust:8) $($(is_data_drop == true ?Yes:No)|ljust:10)\n";
      tailf:cli-show-template-footer "\\r    -----------------------------------------------------------\n";
      leaf plane_id {
        type int32;
      }
      leaf admin-state {
        type string;
        tailf:hidden "internal";
      }
      leaf plane_state {
        type string;
        tailf:hidden "internal";
      }
      leaf plane_mode {
        type string;
        tailf:hidden "internal";
      }
      leaf racks_w_plane_fault {
        type int32;
        tailf:hidden "internal";
      }
      leaf is_data_drop {
        type boolean;
        tailf:hidden "internal";
      }
    }
  }

  grouping fsdb_process_status {
    list fsdb_status {
      key "rack_id";
      tailf:callpoint "fsdb_health";
      tailf:cli-suppress-table;
      tailf:cli-show-template-enter "";
      tailf:cli-show-template "$($(status == true ?Ok:N)|rjust:2)|";
      leaf rack_id {
        type int32;
      }
      leaf status {
        type boolean;
        tailf:hidden "internal";
      }
    }
  }

  grouping sfe_process_status {
    list sfe_status {
      key "rack_id";
      tailf:callpoint "sfe_health";
      tailf:cli-suppress-table;
      tailf:cli-show-template-enter "";
      tailf:cli-show-template "$($(status == true ?Ok:N)|rjust:2)|";
      leaf rack_id {
        type int32;
      }
      leaf status {
        type boolean;
        tailf:hidden "internal";
      }
    }
    list sfe_drvr_loc {
      key "loc_str";
      tailf:callpoint "sfe_health_drvr_loc";
      tailf:cli-suppress-table;
      tailf:cli-show-template-enter "";
      tailf:cli-show-template "$($(loc_str)|rjust:5)|";
      leaf loc_str {
        type string;
      }
    }
    list sfe_fm_sep {
      key "loc_str";
      tailf:callpoint "sfe_health_fm_sep";
      tailf:cli-suppress-table;
      tailf:cli-show-template-enter "";
      tailf:cli-show-template "-----+";
      leaf loc_str {
        type string;
      }
    }
  }

  grouping rack_plane_num_amba_reachable {
    list reachable_amba {
      key "idx";
      tailf:callpoint "fabric_health_fsdb";
      tailf:cli-suppress-table;
      tailf:cli-show-template-enter "";
      tailf:cli-show-template "$(num_reachable|ljust:6)";
      leaf idx {
        type int32;
      }
      leaf num_reachable {
        type int32;
        tailf:hidden "internal";
      }
    }
  }

  grouping fabric_rack_plane_health {
    list rack_plane_info_list {
      key "plane_id";
      tailf:cli-suppress-table;
      tailf:cli-show-template-enter "";
      tailf:cli-show-template-legend
        "    $(Plane|ljust:5) $(Plane|ljust:8) $(SFE Asics|ljust:12) $(Fab ids|ljust:9)
             $(id|ljust:5) $(state|ljust:8) $(T/U/D|ljust:12) $(Reachable|ljust:9)
             --------------------------------------
        ";
      tailf:cli-show-template "    $(plane_id|ljust:5) $(plane_state|ljust:8) $(plane_mode|ljust:5) $($(asics_total)/$(asics_up)/$(asics_dn)|ljust:12) $(reachable_amba|show)\n";
      tailf:cli-show-template-footer "\\r    --------------------------------------\n";
      leaf plane_id {
        type int32;
      }
      leaf plane_state {
        type string;
        tailf:hidden "internal";
      }
      leaf plane_mode {
        type string;
        tailf:hidden "internal";
      }
      leaf asics_total {
        type int32;
        tailf:hidden "internal";
      }
      leaf asics_up {
        type int32;
        tailf:hidden "internal";
      }
      leaf asics_dn {
        type int32;
        tailf:hidden "internal";
      }
      uses rack_plane_num_amba_reachable;
    }
  }

  grouping fabric_rack_health {
    list rack_info_list {
      key "rack_id";
      tailf:cli-suppress-table;
      tailf:cli-show-template-enter "";
      tailf:cli-show-template-legend
        "Rack Health\\\\:
         -------------
        ";
      tailf:cli-show-template
        "    Rack\\\\: $(rack_name), Type\\\\: $(rack_type)
         
         $(rack_type ~= LCC ?    $(SFE Asics|ljust:10) $(FIA Asics|ljust:15) $(Planes|ljust:6) 
             $(T/U/D|ljust:10) $(T/U/D/V|ljust:15) $(U/M/D|ljust:6) 
             ------------------------------------------
             $($(sfe_asics_total)/$(sfe_asics_up)/$(sfe_asics_dn)|ljust:10) $($(fia_asics_total)/$(fia_asics_up)/$(fia_asics_dn)/$(amba_valid)|ljust:15) $($(plane_up)/$(plane_mcast_dn)/$(plane_dn)|ljust:6) 
         
         $(show_rack_plane_detail == true ?$(rack_plane_info_list|show)
         ):    $(SFE Asics|ljust:10) 
             $(T/U/D|ljust:10) 
             -----------------
             $($(sfe_asics_total)/$(sfe_asics_up)/$(sfe_asics_dn)|ljust:10)
         )
        ";
      leaf rack_id {
        type int32;
      }
      leaf rack_name {
        type string;
        tailf:hidden "internal";
      }
      leaf rack_type {
        type string;
        tailf:hidden "internal";
      }
      leaf sfe_asics_total {
        type int32;
        tailf:hidden "internal";
      }
      leaf sfe_asics_up {
        type int32;
        tailf:hidden "internal";
      }
      leaf sfe_asics_dn {
        type int32;
        tailf:hidden "internal";
      }
      leaf fia_asics_total {
        type int32;
        tailf:hidden "internal";
      }
      leaf fia_asics_up {
        type int32;
        tailf:hidden "internal";
      }
      leaf fia_asics_dn {
        type int32;
        tailf:hidden "internal";
      }
      leaf plane_up {
        type uint32;
        tailf:hidden "internal";
      }
      leaf plane_dn {
        type uint32;
        tailf:hidden "internal";
      }
      leaf plane_mcast_dn {
        type uint32;
        tailf:hidden "internal";
      }
      leaf plane_admin_dn {
        type uint32;
        tailf:hidden "internal";
      }
      leaf show_rack_plane_detail {
        type boolean;
        default "false";
        tailf:hidden "internal";
      }
      leaf amba_valid {
        type int32;
        tailf:hidden "internal";
      }
      uses fabric_rack_plane_health;
    }
  }

  grouping fabric_health {
    container fab_health {
      tailf:callpoint "fabric_health";
      tailf:cli-full-show-path;
      tailf:hidden "internal-command";
      list sys_info_list {
        key "index_key";
        tailf:cli-suppress-table;
        tailf:cli-show-template-enter "";
        tailf:cli-show-template-legend
          "
           Fabric System Health
           ---------------------
           $(Flags:|ljust:6) $(T - Total,|ljust:15) $(U - Up,|ljust:15) $(A - Admin Down|ljust:15)
           $( |ljust:6) $(L - LCC,|ljust:15) $(M - Mcast Down,|ljust:15) $(Y - Yes|ljust:15)
           $( |ljust:6) $(F - FCC,|ljust:15) $(D - Down,|ljust:15) $(N - No or Not Ok|ljust:15)
           $( |ljust:6) $(V - Valid,|ljust:15)
           
          ";
        tailf:cli-show-template
          "Collaborator Process State\\\\:
           ------------------------------
               FSDB Aggregator\\\\:$(aggr_status == true ? OK: Not OK)
               +-----------+$(rack_id_separator)
               |Rack id    |$(available_rack_ids)
               +-----------+$(rack_id_separator)
               |FSDB status|$(fsdb_status|show)
               +-----------+$(rack_id_separator)
               |SFE status |$(sfe_status|show)
               +-----------+$(rack_id_separator)
           
           Router Health\\\\:
           -----------------
           
               $(Rack|ljust:7) $(Planes|ljust:7) $(SFE Asics|ljust:14) $(Fia Asics|ljust:14)
               $(T/L/F|ljust:7) $(U/M/D/A|ljust:7) $(T/U/D|ljust:14) $(T/U/D|ljust:14)
               ------------------------------------------------------
               $($(rack_total)/$(rack_lcc)/$(rack_fcc)|ljust:7) $($(plane_up)/$(plane_mcast_dn)/$(plane_dn)/$(plane_admin_dn)|ljust:7) $($(sfe_asics_total)/$(sfe_asics_up)/$(sfe_asics_dn)|ljust:14) $($(fia_asics_total)/$(fia_asics_up)/$(fia_asics_dn)|ljust:14) 
           
           $(show_sys_plane_detail == true ?$(sys_plane_info_list|show)
           )$(rack_info_list|show)
          ";
        leaf index_key {
          type int32;
        }
        leaf aggr_status {
          type boolean;
          tailf:hidden "internal";
        }
        leaf available_rack_ids {
          type string;
          tailf:hidden "internal";
        }
        leaf rack_id_separator {
          type string;
          tailf:hidden "internal";
        }
        leaf available_fm_loc {
          type string;
          tailf:hidden "internal";
        }
        leaf fm_loc_separator {
          type string;
          tailf:hidden "internal";
        }
        leaf rack_total {
          type uint32;
          tailf:hidden "internal";
        }
        leaf rack_lcc {
          type uint32;
          tailf:hidden "internal";
        }
        leaf rack_fcc {
          type uint32;
          tailf:hidden "internal";
        }
        leaf plane_up {
          type uint32;
          tailf:hidden "internal";
        }
        leaf plane_dn {
          type uint32;
          tailf:hidden "internal";
        }
        leaf plane_mcast_dn {
          type uint32;
          tailf:hidden "internal";
        }
        leaf plane_admin_dn {
          type uint32;
          tailf:hidden "internal";
        }
        leaf show_sys_plane_detail {
          type boolean;
          default "false";
          tailf:hidden "internal";
        }
        leaf sfe_asics_total {
          type uint32;
          tailf:hidden "internal";
        }
        leaf sfe_asics_up {
          type uint32;
          tailf:hidden "internal";
        }
        leaf sfe_asics_dn {
          type uint32;
          tailf:hidden "internal";
        }
        leaf fia_asics_total {
          type uint32;
          tailf:hidden "internal";
        }
        leaf fia_asics_up {
          type uint32;
          tailf:hidden "internal";
        }
        leaf fia_asics_dn {
          type uint32;
          tailf:hidden "internal";
        }
        uses fabric_sys_plane_health;
        uses fabric_rack_health;
        uses fsdb_process_status;
        uses sfe_process_status;
      }
    }
  }

  grouping fsdb_agg_plane_clear {
    list plane {
      key "planeid";
      tailf:cli-no-key-completion;
      tailf:cli-no-match-completion;
      leaf planeid {
        type fabric-types:plane_type;
      }
      tailf:action "clear_counter" {
        tailf:actionpoint "fabric_fsdb_aggr_clear";
        input;
        output;
      }
      tailf:action "clear_stats" {
        tailf:actionpoint "fabric_fsdb_aggr_clear";
        input;
        output;
      }
    }
  }

  grouping fsdb_aggr_trace {
    container fsdb-aggregator {
      description
        "FSDB Aggregator information";
      tailf:hidden "internal-command";
      tailf:cli-incomplete-show-path;
      tailf:cli-incomplete-command;
      tailf:info "FSDB Aggregator informaiton";
      container fsdbagg {
        tailf:cli-incomplete-show-path;
        tailf:cli-incomplete-command;
        tailf:cli-drop-node-name;
        uses show-trace:traceable;
      }
    }
  }

  grouping fsdb_aggr_ppu {
    container ppu {
      description
        "Plane by plane upgrade.";
      tailf:info "Plane by plane upgrade.";
      tailf:action "start" {
        tailf:info "Start PPU.";
        description
          "Start PPU.";
        tailf:confirm-text "Start Plane by Plane Upgrade ?" {
          tailf:confirm-default "false";
        }
        tailf:actionpoint "fabric_ap";
        input;
        output {
          leaf PPU {
            type string;
          }
        }
      }
      tailf:action "force" {
        tailf:info "Force PPU.";
        description
          "Force PPU.";
        tailf:confirm-text "Force Plane by Plane Upgrade ?" {
          tailf:confirm-default "false";
        }
        tailf:actionpoint "fabric_ap";
        input;
        output {
          leaf PPU {
            type string;
          }
        }
      }
    }
  }

  grouping bundle_summary_show {
    list bundle_summary_list {
      key "idx";
      tailf:cli-suppress-table;
      tailf:cli-show-template-legend
        "Total    Down     Bundle not  Total   Down    Bport not
         Bundles  Bundles  connected   Bports  Bports  connected
         -------------------------------------------------------
        ";
      tailf:cli-show-template-enter "";
      tailf:cli-show-template "$(total_bundles|ljust:8) $(down_bundles|ljust:8) $(bundles_not_connected|ljust:11) $(total_bports|ljust:7) $(down_bports|ljust:7) $(bports_not_connected|ljust:10)\n";
      leaf idx {
        type int32;
      }
      leaf total_bundles {
        type uint32;
        tailf:hidden "internal";
      }
      leaf down_bundles {
        type uint32;
        tailf:hidden "internal";
      }
      leaf bundles_not_connected {
        type uint32;
        tailf:hidden "internal";
      }
      leaf total_bports {
        type uint32;
        tailf:hidden "internal";
      }
      leaf down_bports {
        type uint32;
        tailf:hidden "internal";
      }
      leaf bports_not_connected {
        type uint32;
        tailf:hidden "internal";
      }
    }
  }

  grouping bundle_all_show {
    list bundle_all_list {
      key "idx";
      tailf:display-groups "fabric-brief fabric-detail";
      tailf:cli-suppress-table;
      tailf:cli-show-template-legend
        "$(.display_groups ~= fabric-brief ?Bundle       Oper 
         R/S/P        State
         ------------------
         :Bundle       Oper  Plane Total Down  Bundle       Bundle
         R/S/P        State Id    Links Links Port1        Port2 
         --------------------------------------------------------
         )";
      tailf:cli-show-template-enter "";
      tailf:cli-show-template "$(.display_groups ~= fabric-brief ?$(bundle_id|ljust:12) $(oper_state|ljust:5):$(bundle_id|ljust:12) $(oper_state|ljust:5) $(plane_id|ljust:5) $(total_links|rjust:5) $(down_links|ljust:5) $(bport1|ljust:12) $(bport2|ljust:12))\n";
      leaf idx {
        type int64;
        tailf:cli-disallow-value "(fabric-brief)|(fabric-detail)";
        tailf:display-groups "fabric-brief fabric-detail";
      }
      leaf bundle_id {
        type string;
        tailf:hidden "internal";
      }
      leaf oper_state {
        type string;
        tailf:hidden "internal";
      }
      leaf plane_id {
        type uint32;
        tailf:hidden "internal";
      }
      leaf total_links {
        type uint32;
        tailf:hidden "internal";
      }
      leaf down_links {
        type uint32;
        tailf:hidden "internal";
      }
      leaf bport1 {
        type string;
        tailf:hidden "internal";
      }
      leaf bport2 {
        type string;
        tailf:hidden "internal";
      }
    }
  }

  grouping bport_all_show {
    list bport_all_list {
      key "idx";
      tailf:display-groups "fabric-brief fabric-detail";
      tailf:cli-suppress-table;
      tailf:cli-show-template-legend
        "$(.display_groups ~= fabric-brief ?Bundle Port  Admin  Oper  
         R/S/P        State  State 
         --------------------------
         :Bundle Port  Admin  Oper          Down
         R/S/P        State  State         Flags
         ---------------------------------------
         )";
      tailf:cli-show-template-enter "";
      tailf:cli-show-template "$(bport_id|ljust:12) $(admin-state|ljust:6) $(oper_state|ljust:6)$(.display_groups ~= fabric-detail ? $(down_flags|rjust:12))\n";
      leaf idx {
        type int64;
        tailf:cli-disallow-value "(fabric-brief)|(fabric-detail)";
        tailf:display-groups "fabric-brief fabric-detail";
      }
      leaf bport_id {
        type string;
        tailf:hidden "internal";
      }
      leaf admin-state {
        type string;
        tailf:hidden "internal";
      }
      leaf oper_state {
        type string;
        tailf:hidden "internal";
      }
      leaf down_flags {
        type string;
        tailf:hidden "internal";
      }
    }
  }

  grouping bport_all_stats_show {
    list bport_stats_all_racks {
      key "idx";
      tailf:display-groups "fabric-brief fabric-detail";
      tailf:cli-suppress-table;
      tailf:cli-show-template
        "Total racks\\\\: $(total_racks)
         
         $(bport_stats_rack|show)";
      tailf:cli-show-template-enter "";
      leaf idx {
        type int32;
        tailf:cli-disallow-value "(fabric-brief)|(fabric-detail)";
        tailf:display-groups "fabric-brief fabric-detail";
      }
      leaf total_racks {
        type uint32;
        tailf:hidden "internal";
      }
      list bport_stats_rack {
        key "idx";
        tailf:cli-suppress-table;
        tailf:cli-show-template
          "Rack $(rack_num_str)\\\\:
           
           $(bport_stats|show)
          ";
        tailf:cli-show-template-enter "";
        leaf idx {
          type int32;
          tailf:display-groups "fabric-brief fabric-detail";
        }
        leaf rack_num_str {
          type string;
          tailf:hidden "internal";
        }
        list bport_stats {
          key "idx";
          tailf:cli-suppress-table;
          tailf:cli-show-template-legend
            "$(.display_groups ~= fabric-brief ? 
             $( |rjust:4)Flags\\\\: E-D  - Exceeded display width.
             $( |rjust:18)Check detail option.
             
             Bundle Port            In              Out        CE         UCE        PE   
             R/S/P                  Cells           Cells      Cells      Cells      Cells
             -----------------------------------------------------------------------------
             )";
          tailf:cli-show-template-enter "";
          tailf:cli-show-template
            "$(.display_groups ~= fabric-brief ?$(bport_id|ljust:12) $(rx_data_cells|rjust:15) $(tx_data_cells|rjust:15) $(rx_ce_cells_is_overflow == true ?$(E-D|rjust:10):$(rx_ce_cells|rjust:10)) $(rx_uce_cells_is_overflow == true ?$(E-D|rjust:10):$(rx_uce_cells|rjust:10)) $(rx_pe_cells_is_overflow == true ?$(E-D|rjust:10):$(rx_pe_cells|rjust:10)):
             The fabric bundle port is $(bport_id)
               Total received data cells\\\\: $(rx_data_cells)
               Total transmitted data cells\\\\: $(tx_data_cells)
               Total received correctable errored cells\\\\: $(rx_ce_cells)
               Total received uncorrectable errored cells\\\\: $(rx_uce_cells)
               Total received parity error cells\\\\: $(rx_pe_cells)
               Last clearing of statistics\\\\: $(last_clear_ts))
            ";
          leaf idx {
            type int64;
            tailf:display-groups "fabric-brief fabric-detail";
          }
          leaf bport_id {
            type string;
            tailf:hidden "internal";
          }
          leaf rx_data_cells {
            type uint64;
            tailf:hidden "internal";
          }
          leaf tx_data_cells {
            type uint64;
            tailf:hidden "internal";
          }
          leaf rx_ce_cells_is_overflow {
            type boolean;
            tailf:hidden "internal";
          }
          leaf rx_ce_cells {
            type uint64;
            tailf:hidden "internal";
          }
          leaf rx_uce_cells_is_overflow {
            type boolean;
            tailf:hidden "internal";
          }
          leaf rx_uce_cells {
            type uint64;
            tailf:hidden "internal";
          }
          leaf rx_pe_cells_is_overflow {
            type boolean;
            tailf:hidden "internal";
          }
          leaf rx_pe_cells {
            type uint64;
            tailf:hidden "internal";
          }
          leaf last_clear_ts {
            type string;
            tailf:hidden "internal";
          }
        }
      }
    }
  }

  grouping fsdb_aggr_bundle {
    container bundle {
      tailf:callpoint "fabric_fsdb_aggr_bundle_cp";
      tailf:hidden "internal-command";
      container summary {
        tailf:info "Show summary of bundle data.";
        uses bundle_summary_show;
      }
      container all {
        tailf:info "Show all fabric bundles.";
        uses bundle_all_show;
      }
      container port {
        tailf:info "Fabric bundle port option.";
        container all {
          tailf:info "Show all fabric bundle ports.";
          uses bport_all_show;
          container statistics {
            tailf:info "Statistics option.";
            uses bport_all_stats_show;
          }
        }
        list location {
          key "loc_str";
          tailf:info "Bundle port location R/S/P.";
          tailf:cli-no-key-completion;
          tailf:cli-no-match-completion;
          tailf:cli-suppress-table;
          tailf:cli-show-template-enter "";
          leaf loc_str {
            type fabric-types:bundle_location_type;
          }
          uses bport_all_show;
          container statistics {
            tailf:info "Statistics option.";
            uses bport_all_stats_show;
          }
        }
      }
      list location {
        key "loc_str";
        tailf:info "Bundle location R/S/P.";
        tailf:cli-no-key-completion;
        tailf:cli-no-match-completion;
        tailf:cli-suppress-table;
        tailf:cli-show-template-enter "";
        leaf loc_str {
          type fabric-types:bundle_location_type;
        }
        uses bundle_all_show;
      }
    }
  }

  grouping fsdb_aggr_clear {
    container counter {
      config false;
      tailf:hidden "internal-command";
      tailf:callpoint "fabric_fsdb_aggr_clear";
      uses fsdb_agg_plane_clear;
    }
    container clear_statistics {
      config false;
      tailf:hidden "internal-command";
      tailf:callpoint "fabric_fsdb_aggr_clear";
      uses fsdb_agg_plane_clear;
    }
  }

  grouping fsdb_aggr {
    container fsdbagg_active {
      tailf:hidden "internal-command";
      tailf:callpoint "fabric_fsdb_aggr_plane";
      uses plane_show;
      uses fsdb_aggr_bundle;
      container statistics {
        tailf:hidden "internal-command";
        uses plane_show;
      }
    }
    container fsdbagg_link {
      tailf:hidden "internal-command";
      tailf:callpoint "fabric_fsdb_aggr_system_info";
      list port {
        key "portname";
        leaf portname {
          type fabric-types:link_port_type;
        }
        leaf description {
          type string;
          default "port.";
        }
      }
    }
    container fsdbagg_sfe_asic_type {
      tailf:hidden "internal-command";
      tailf:callpoint "fabric_fsdb_aggr_system_info";
      list asic_types {
        key "asicname";
        leaf asicname {
          type string;
        }
        leaf description {
          type string;
          default "asic.";
        }
        list block {
          key "blockname";
          leaf blockname {
            type string;
          }
        }
      }
    }
    container fsdbagg_standby {
      tailf:hidden "internal-command";
      tailf:callpoint "fabric_fsdb_aggr_plane_standby";
      uses plane_show;
      container statistics {
        tailf:hidden "internal-command";
        uses plane_show;
      }
    }
    uses fabric_health;
    uses fsdb_aggr_trace;
  }
  tailf:id "http://www.cisco.com/panini/calvados/fabric/fsdb_aggr";
}
