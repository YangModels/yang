module Cisco-IOS-XR-nto-misc-oper {
  namespace "http://cisco.com/ns/yang/Cisco-IOS-XR-nto-misc-oper";
  prefix nto-misc-oper;

  import Cisco-IOS-XR-types {
    prefix xr;
  }
  include Cisco-IOS-XR-nto-misc-oper-sub1 {
    revision-date 2015-11-09;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR nto-misc package operational data.
     
     This module contains definitions
     for the following management objects:
       memory-summary: Memory summary information
     
     Copyright (c) 2013-2017 by Cisco Systems, Inc.
     All rights reserved.";

  revision 2015-11-09 {
    description
      "IOS XR 6.0 revision.";
  }

  container memory-summary {
    config false;
    description
      "Memory summary information";
    container nodes {
      description
        "List of nodes";
      list node {
        key "node-name";
        description
          "Name of nodes";
        container summary {
          description
            "Memory summary information for a specific node";
          uses NODE-MEM-INFO;
        }
        container detail {
          description
            "Detail Memory summary information for a
             specific node";
          uses NODE-MEM-INFO-DETAIL;
        }
        leaf node-name {
          type xr:Node-id;
          description
            "Node name";
        }
      }
    }
  }
}
