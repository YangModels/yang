module Cisco-IOS-XR-sysadmin-obfl-clear {
  namespace "http://cisco.com/ns/yang/Cisco-IOS-XR-sysadmin-obfl-clear";
  prefix obflclear;

  import tailf-common {
    prefix tailf;
  }

  organization
    "Cisco Systems Inc.";
  description
    "This module is for clearing OBFL data.";

  revision 2017-07-31 {
    description
      "Changed namespace to follow Cisco guidelines on naming conventions";
  }
  revision 2016-10-12 {
    description
      "Unhide commands and configs. Moved to advanced-grp";
  }
  revision 2011-12-03 {
    description
      "Initial revision.";
  }

  grouping obflclear-grp {
    container logging {
      config false;
      tailf:info "OBFL Clear onboard logging";
      tailf:hidden "advanced-grp";
      container onboard {
        config false;
        tailf:info "OBFL Clear onboard logging";
        tailf:callpoint "obfl_clear_cp";
        list location {
          key "location";
          config false;
          tailf:info "Select node location";
          tailf:cli-no-match-completion;
          leaf location {
            type string;
          }
          tailf:action "clear" {
            tailf:actionpoint "action_obflclear";
            input {
              leaf all {
                type empty;
                mandatory true;
              }
            }
          }
        }
      }
    }
  }
  tailf:id "http://cisco.com/calvados/obflclear";
}
