module Cisco-IOS-XR-qos-mibs-cfg {
  namespace "http://cisco.com/ns/yang/Cisco-IOS-XR-qos-mibs-cfg";
  prefix qos-mibs-cfg;

  import Cisco-IOS-XR-snmp-agent-cfg {
    prefix a1;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR qos-mibs package configuration.
     
     This YANG module augments the
       Cisco-IOS-XR-snmp-agent-cfg
     module with configuration data.
     
     Copyright (c) 2013-2017 by Cisco Systems, Inc.
     All rights reserved.";

  revision 2017-05-01 {
    description
      "Fixing backward compatibility error in module.";
  }
  revision 2015-11-09 {
    description
      "IOS XR 6.0 revision.";
  }

  augment "/a1:mib" {
    description
      "This augment extends the configuration data of
       'Cisco-IOS-XR-snmp-agent-cfg'";
    container cb-qosmib {
      description
        "CBQoSMIB configuration";
      container cache {
        description
          "CBQoSMIB statistics data caching";
        leaf enable {
          type empty;
          description
            "Enable CBQoSMIB statistics data caching";
        }
        leaf refresh-time {
          type uint32 {
            range "5..60";
          }
          units "second";
          description
            "Cache refresh time in seconds";
        }
        leaf service-policy-count {
          type uint32 {
            range "1..5000";
          }
          description
            "Maximum number of service policies to cache
             the statistics for";
        }
      }
      leaf member-interface-stats {
        type empty;
        description
          "Enable bundle member interface statistics
           retrieval.";
      }
      leaf persist {
        type empty;
        description
          "Persist CBQoSMIB config, service-policy and
           object indices";
      }
    }
  }
}
