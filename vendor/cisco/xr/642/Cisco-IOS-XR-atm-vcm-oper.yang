module Cisco-IOS-XR-atm-vcm-oper {
  namespace "http://cisco.com/ns/yang/Cisco-IOS-XR-atm-vcm-oper";
  prefix atm-vcm-oper;

  import Cisco-IOS-XR-types {
    prefix xr;
  }
  import Cisco-IOS-XR-atm-common-datatypes {
    prefix dt1;
  }
  include Cisco-IOS-XR-atm-vcm-oper-sub4 {
    revision-date 2017-09-07;
  }
  include Cisco-IOS-XR-atm-vcm-oper-sub3 {
    revision-date 2017-09-07;
  }
  include Cisco-IOS-XR-atm-vcm-oper-sub2 {
    revision-date 2017-09-07;
  }
  include Cisco-IOS-XR-atm-vcm-oper-sub1 {
    revision-date 2017-09-07;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR atm-vcm package operational data.
     
     This module contains definitions
     for the following management objects:
       atm-vcm: ATM VCM operational data
     
     Copyright (c) 2013-2017 by Cisco Systems, Inc.
     All rights reserved.";

  revision 2017-09-07 {
    description
      "Fixed type translation error.";
  }
  revision 2015-11-09 {
    description
      "IOS XR 6.0 revision.";
  }

  typedef Atm-pvc-vpi-range {
    type uint32 {
      range "0..4095";
    }
    description
      "Atm pvc vpi range";
  }

  typedef Atm-pvc-vci-range {
    type uint32 {
      range "1..65535";
    }
    description
      "Atm pvc vci range";
  }

  container atm-vcm {
    config false;
    description
      "ATM VCM operational data";
    container nodes {
      description
        "Contains all the nodes";
      list node {
        key "node-name";
        description
          "The node on which ATM Interfaces/VCs/VPs are
           located";
        container vcs {
          description
            "Contains all VC information for node";
          list vc {
            key "interface-name";
            description
              "All VC information on a node";
            leaf interface-name {
              type xr:Interface-name;
              description
                "Interface name";
            }
            leaf vpi {
              type Atm-pvc-vpi-range;
              description
                "VPI";
            }
            leaf vci {
              type Atm-pvc-vci-range;
              description
                "VCI";
            }
            uses ATM-VCM-VC;
          }
        }
        container cell-packs {
          description
            "Contains all cell packing information for node";
          list cell-pack {
            description
              "All cell packing information on a node";
            leaf interface-name {
              type xr:Interface-name;
              description
                "Interface name";
            }
            leaf pci {
              type uint32;
              description
                "PCI";
            }
            uses ATM-CELL-PACKING-DATA;
          }
        }
        container pvps {
          description
            "Contains all L2 PVP information for node";
          list pvp {
            key "interface-name";
            description
              "All L2 PVP information on a node";
            leaf interface-name {
              type xr:Interface-name;
              description
                "Interface name";
            }
            leaf vpi {
              type uint32;
              description
                "VPI";
            }
            uses ATM-VCM-VC;
          }
        }
        container class-links {
          description
            "Contains all class link information for node";
          list class-link {
            key "vpi";
            description
              "All ATM VC information on a node";
            leaf vpi {
              type uint32;
              description
                "VPI";
            }
            leaf vci {
              type uint32;
              description
                "VCI";
            }
            uses ATM-CLASS-LINK-VPI-VCI;
          }
        }
        container interfaces {
          description
            "Contains all Interface information for node";
          list interface {
            key "interface-name";
            description
              "ATM Interface data";
            leaf interface-name {
              type xr:Interface-name;
              description
                "Interface name";
            }
            uses ATM-VCM-IF;
          }
        }
        container vp-tunnels {
          description
            "Contains all VP-tunnel information for node";
          list vp-tunnel {
            key "interface-name";
            description
              "All VP-tunnel information on a node";
            leaf interface-name {
              type xr:Interface-name;
              description
                "Interface name";
            }
            leaf vpi {
              type uint32;
              description
                "VPI";
            }
            uses ATM-VCM-VP;
          }
        }
        leaf node-name {
          type xr:Node-id;
          description
            "The node name";
        }
      }
    }
  }
}
