submodule Cisco-IOS-XR-ipv6-ping-act {

    belongs-to Cisco-IOS-XR-ping-act {
        prefix "ping-act";
    }

    include "Cisco-IOS-XR-ipv4-ping-act";
    
    organization "Cisco Systems, Inc.";
    
    contact
    "Cisco Systems, Inc.
     Customer Service

     Postal: 170 West Tasman Drive
     San Jose, CA 95134

     Tel: +1 800 553-NETS

     E-mail: cs-yang@cisco.com";

    description 
    "This module contains a collection of YANG definitions
     for Cisco IOS-XR IPv6 ping action package configuration.

     Copyright (c) 2016 by Cisco Systems, Inc.
     All rights reserved.";
    
    revision "2016-09-13" {
        description
            "IOS XR 6.2.1 revision.";
    }

    grouping IPV6-SPECIFIC-OPTIONS {
 
       leaf priority {
           description "Priority of the packet";
           type uint8 {
               range "0..15";
           }
       }

       leaf outgoing-interface {
           description "Outgoing interface, needed in case of ping to link local address";
           type string;
       }
   }

   grouping IPV6-PING-INPUT {

       uses PING-OPTIONS;

       uses IPV6-SPECIFIC-OPTIONS; 
   }

   grouping IPV6-PING-OUTPUT {

       uses PING-COMMON-INPUT-OUTPUT-OPTIONS;

       leaf sweep-min {
           description "Minimum value of sweep size";
           type uint32;
       }

       leaf sweep-max {
           description "Maximum value of sweep size";
           type uint64;
       }

       leaf rotate-pattern {
           description "Rotate Pattern is enabled";
           type boolean;
       }

       container replies {

           list reply {

               key reply-index;

               leaf reply-index {
                   description "Index of the reply list";
                   type uint64 {
                       range "1..2147483647";
                   }
               }

               leaf result {
                   description "Response for each packet";
                   type string;
               }
           }
       } 

       leaf hits {
           description "Number of packets reach to destination and get reply back";
           type uint64;
       }

       leaf total {
           description "Total number of packets sent out";
           type uint64;
       }

       leaf success-rate {
           description "Successful rate of ping";
           type uint64;
       }

       leaf rtt-min {
           description "Minimum value of Round Trip Time";
           type uint64;
       }

       leaf rtt-avg {
           description "Average value of Round Trip Time";
           type uint64;
       }

       leaf rtt-max {
           description "Maximum value of Round Trip Time";
           type uint64;
       }
    }
}
