module Cisco-IOS-XR-sysadmin-sdr-connect {
  namespace "http://www.cisco.com/ns/yang/Cisco-IOS-XR-sysadmin-sdr-connect";
  prefix inter_sdr_connect;

  organization
    "Cisco Systems Inc.";
  contact
    "Cisco Systems, Inc.
     Customer Service
     
     Postal: 170 West Tasman Drive
     San Jose, CA 95134
     
     Tel: +1 800 553-NETS
     
     E-mail: cs-yang@cisco.com";
  description
    "This module contains definitions
     for the Calvados model objects.
     
     This module implements entities for inter sdr connect
     feature
     
     Copyright (c) 2012-2017 by Cisco Systems, Inc.
     All rights reserved.";

  revision 2017-10-09 {
    description
      "Initial version";
  }

  container sdr-connect {
    container connect {
      description
        "Connect two Secure Domain Routers";
      list sdr {
        key "sdr-name remote-sdr-name csi-id";
        description
          "Secure Domain Router connect config";
        leaf sdr-name {
          type string {
            pattern "[a-zA-Z0-9_-]{1,30}";
          }
          mandatory true;
          description
            "Name of the Secure Domain Router , 30 max characters";
        }
        leaf remote-sdr-name {
          type string {
            pattern "[a-zA-Z0-9_-]{1,30}";
          }
          mandatory true;
          description
            "Name of the Remote Secure Domain Router , 30 max characters";
        }
        leaf csi-id {
          type uint32 {
            range "1 .. 15";
          }
          mandatory true;
          description
            "Index unique for each SDR connection pair";
        }
      }
    }
  }
}
