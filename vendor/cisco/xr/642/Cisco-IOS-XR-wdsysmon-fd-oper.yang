module Cisco-IOS-XR-wdsysmon-fd-oper {
  namespace "http://cisco.com/ns/yang/Cisco-IOS-XR-wdsysmon-fd-oper";
  prefix wdsysmon-fd-oper;

  import Cisco-IOS-XR-types {
    prefix xr;
  }
  include Cisco-IOS-XR-wdsysmon-fd-oper-sub1 {
    revision-date 2015-11-09;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR wdsysmon-fd package operational data.
     
     This module contains definitions
     for the following management objects:
       system-monitoring: Processes operational data
     
     Copyright (c) 2013-2017 by Cisco Systems, Inc.
     All rights reserved.";

  revision 2015-11-09 {
    description
      "IOS XR 6.0 revision.";
  }
  revision 2015-08-15 {
    description
      "IOS XR 5.3.2 revision.";
  }

  container system-monitoring {
    config false;
    description
      "Processes operational data";
    list cpu-utilization {
      key "node-name";
      description
        "Processes CPU utilization information";
      leaf node-name {
        type xr:Node-id;
        description
          "Node name";
      }
      uses NODE-CPU-UTIL;
    }
  }
}
