module Cisco-IOS-XR-sysadmin-sdr-mgr {
  namespace "http://www.cisco.com/ns/yang/Cisco-IOS-XR-sysadmin-sdr-mgr";
  prefix calvados_sdr;

  import tailf-common {
    prefix tailf;
  }
  import ietf-inet-types {
    prefix inet;
  }
  import Cisco-IOS-XR-sysadmin-show-trace {
    prefix show_trace;
  }

  organization
    "Cisco Systems Inc.";
  contact
    "Cisco Systems, Inc.
     Customer Service
     
     Postal: 170 West Tasman Drive
     San Jose, CA 95134
     
     Tel: +1 800 553-NETS
     
     E-mail: cs-yang@cisco.com";
  description
    "This module contains a collection of YANG
     definitions for Cisco IOS-XR SysAdmin configuration.
     
     This module defines the SDR-SM support config for SDR
     
     Copyright(c) 2011-2017 by Cisco Systems, Inc.
     All rights reserved.";

  revision 2017-07-22 {
    description
      "Updated location pattern to include Compute Cards";
  }
  revision 2017-06-20 {
    description
      "Changed the type of rp leaves in container pairing2 to string";
  }
  revision 2017-06-16 {
    description
      "Added leaf issu to provide an option to disable SDR ISSU";
  }
  revision 2017-06-09 {
    description
      "SDR config will now take a list of initial images";
  }
  revision 2017-04-12 {
    description
      "Changed the namespace and module name";
  }
  revision 2016-10-12 {
    description
      "Unhide commands and configs. Moved to advanced-grp";
  }
  revision 2016-05-12 {
    description
      "Initial Version";
  }

  typedef Location {
    type string {
      pattern "((0?[0-9]|1[1-5]|[bB]\\d)/(([rR][pP]|[lL][cC]|[cC][bB])?\\d{1,2}))(/[cC][pP][uU]0)?|all";
    }
    description
      "A system location in Rack/Slot/Instance";
  }

  typedef RPLocation {
    type string {
      pattern "((0?[0-9]|1[1-5]|[bB]\\d)/(([rR][pP]|[cC][bB])\\d{1,2}))(/[cC][pP][uU]0)?";
    }
    description
      "A system location in Rack/Slot/Instance";
  }

  typedef VMLocation {
    type string {
      pattern "((0?[0-9]|1[1-5]|[bB]\\d)/((([rR]([sS]){0,1}[pP])|[cC][bB])?\\d{1,2})/[V][M](0?[0-9]|1[1-5]))?";
    }
    description
      "A system location in Rack/Slot/Instance";
  }

  typedef VMLocationall {
    type string {
      pattern "((0?[0-9]|1[1-5]|[bB]\\d)/((([rR]([sS]){0,1}[pP])|[cC][bB])?\\d{1,2})/[V][M](0?[0-9]|1[1-5]))?|all";
    }
    description
      "A system location in Rack/Slot/Instance";
  }

  typedef CardType {
    type enumeration {
      enum "RP";
      enum "LC";
      enum "CC";
    }
    description
      "The List of supported Card Types";
  }

  typedef vm_reload_reason {
    type enumeration {
      enum "CARD_OFFLINE";
      enum "CARD_SHUTDOWN";
      enum "ALL_VM_RELOAD";
      enum "VM_REQUESTED_GRACEFUL_RELOAD";
      enum "VM_REQUESTED_UNGRACEFUL_RELOAD";
      enum "SDR_CLI_REQUESTED";
      enum "SDR_VCPU_VMEM_CHANGED";
      enum "SDR_HEARTBEAT_FAILURE";
      enum "FIRST_BOOT";
      enum "SMU";
      enum "REASON_UNKNOWN";
    }
    description
      "The List of vm reload reasons";
  }
  tailf:id "http://www.cisco.com/panini/calvados/sdr_mgr/sdr_sm";

  container sdr-config {
    tailf:cli-drop-node-name;
    tailf:validate "sdr_validate" {
      tailf:dependency ".";
    }
    list sdr {
      key "name";
      description
        "Add/Edit a Secure Domain Router by name";
      tailf:info "Secure Domain Router config/exec commands";
      tailf:cli-suppress-table;
      tailf:cli-show-template-enter
        "
         SDR: $(name)
        ";
      tailf:cli-show-template "$(nodes|show)";
      leaf name {
        type string {
          pattern "[a-zA-Z0-9_-]{1,30}";
        }
        description
          "Name of the Secure Domain Router , 30 max characters";
        tailf:info "sdr name (1 to 30 characters(0-9,a-z,A-Z,-,_))";
      }
      leaf initial-image {
        type string;
        description
          "List of the initial image and packages for the Secure Domain Router.";
        tailf:cli-multi-value;
        tailf:cli-completion-actionpoint "package-complete";
        tailf:info "List of initial Image and packages for a Secure Domain Router";
      }
      leaf lead_down_delta {
        type uint32;
        description
          "Amount of time between lead down to declare SDR down";
        tailf:hidden "advanced-grp";
        tailf:info "Amount of time between lead down to declare SDR down";
      }
      leaf pairing-mode {
        type enumeration {
          enum "intra-rack";
          enum "inter-rack";
        }
        description
          "Setting for pairing mode";
        tailf:info "Specify pairing mode intra-rack/inter-rack";
      }
      leaf issu {
        type enumeration {
          enum "disable";
        }
        description
          "ISSU flag. Once disabled, ISSU won't be performed for this SDR.";
        tailf:info "ISSU flag";
      }
      container resources {
        description
          "Edit resources for a Secure Domain Router";
        tailf:info "Resources for a Secure Domain Router";
        leaf fgid {
          type uint32 {
            range "25000..524288";
          }
          description
            "Fgids for a Secure Domain Router";
          tailf:info "fgids for a Secure Domain Router";
        }
        leaf mgmt_ext_vlan {
          type uint32 {
            range "2..4094";
          }
          description
            "Management External VLAN for Secure Domain Router";
          tailf:info "Management External VLAN for Secure Domain Router";
        }
        list card-type {
          key "type";
          tailf:info "Specify card-type";
          leaf type {
            type CardType;
            description
              "Card Type";
          }
          leaf vm-memory {
            type uint32 {
              range "1..128";
            }
            description
              "VM Memory Size in units of [GB]";
            tailf:info "VM Memory Size in units of [GB]";
          }
          leaf vm-cpu {
            type uint32 {
              range "1..128";
            }
            description
              "VM Number of CPUs";
            tailf:info "VM Number of CPUs";
          }
        }
        leaf disk-space-size {
          type uint32;
          description
            "Edit disk space size for a Secure Domain Router, unit in [MB]";
          tailf:info "Disk space for sdr";
        }
      }
      list location {
        key "node-location";
        min-elements 1;
        max-elements "64";
        description
          "Enter list of nodes' location to add to this LR";
        tailf:info "Enter list of nodes locations for the SDR";
        leaf node-location {
          type Location;
          description
            "Enter location or all";
        }
      }
      container Action {
        config false;
        tailf:callpoint "loc";
        tailf:cli-drop-node-name;
        tailf:cli-suppress-show-path;
        tailf:cli-suppress-show-match;
        tailf:action "re_pair" {
          tailf:actionpoint "re_pair_sdr";
          input {
            choice what_act {
              mandatory true;
            }
          }
          output {
            leaf result {
              type string;
              mandatory true;
            }
          }
        }
        list location {
          key "node-location";
          min-elements 1;
          max-elements "64";
          tailf:cli-suppress-show-path;
          tailf:cli-suppress-show-match;
          leaf node-location {
            type VMLocationall;
            description
              "Enter location or all";
            tailf:cli-suppress-show-path;
            tailf:cli-suppress-show-match;
          }
          tailf:action "reload" {
            tailf:actionpoint "reload-sdr";
            tailf:confirm-text "Reload ?" {
              tailf:confirm-default "false";
            }
            input {
              choice what_act {
                mandatory true;
                case act_force {
                  leaf force {
                    type empty;
                    mandatory false;
                  }
                }
                case act_coredump {
                  leaf coredump {
                    type empty;
                    mandatory false;
                  }
                }
              }
            }
            output {
              leaf result {
                type string;
                mandatory true;
              }
            }
          }
          tailf:action "shut" {
            tailf:actionpoint "reload-sdr";
            tailf:confirm-text "Shut ?" {
              tailf:confirm-default "false";
            }
            input;
            output {
              leaf result {
                type string;
                mandatory true;
              }
            }
          }
          tailf:action "start" {
            tailf:actionpoint "reload-sdr";
            tailf:confirm-text "Start ?" {
              tailf:confirm-default "false";
            }
            input;
            output {
              leaf result {
                type string;
                mandatory true;
              }
            }
          }
        }
      }
      container detail {
        config false;
        tailf:callpoint "show";
        tailf:cli-suppress-show-match;
        list location {
          key "node-location";
          min-elements 1;
          max-elements "64";
          tailf:cli-incomplete-command;
          tailf:cli-show-template-enter "------SDR Detail at location $(node-location)------\n";
          leaf node-location {
            type VMLocation;
            tailf:cli-suppress-show-path;
            tailf:cli-suppress-show-match;
          }
          leaf sdr-id {
            type uint32;
            tailf:alt-name "SDR Id";
            tailf:cli-suppress-show-path;
            tailf:cli-suppress-show-match;
          }
          leaf ip-addr {
            type inet:ip-address;
            description
              "IP address of VM";
            tailf:alt-name "IP Address of VM";
            tailf:cli-suppress-show-path;
            tailf:cli-suppress-show-match;
          }
          leaf mac-address {
            type string;
            description
              "MAC address of VM";
            tailf:alt-name "MAC address of VM";
            tailf:cli-suppress-show-path;
            tailf:cli-suppress-show-match;
          }
          leaf boot_part {
            type string;
            tailf:alt-name "Boot Partition";
            tailf:cli-suppress-show-path;
            tailf:cli-suppress-show-match;
          }
          leaf data_part {
            type string;
            tailf:alt-name "Data Partition";
            tailf:cli-suppress-show-path;
            tailf:cli-suppress-show-match;
          }
          leaf big_disk {
            type string;
            tailf:alt-name "Big Disk Partition";
            tailf:cli-suppress-show-path;
            tailf:cli-suppress-show-match;
          }
          leaf vm_id {
            type uint32;
            tailf:alt-name "VM Id";
            tailf:cli-suppress-show-path;
            tailf:cli-suppress-show-match;
          }
          leaf vmcpu {
            type uint32;
            tailf:alt-name "VM CPUs";
            tailf:cli-suppress-show-path;
            tailf:cli-suppress-show-match;
          }
          leaf vmmemory {
            type uint32;
            tailf:alt-name "VM Memory[in MB]";
            tailf:cli-suppress-show-path;
            tailf:cli-suppress-show-match;
          }
          leaf card-type {
            type string;
            tailf:alt-name "Card Type";
            tailf:cli-suppress-show-path;
            tailf:cli-suppress-show-match;
          }
          leaf card_serial {
            type string;
            tailf:alt-name "Card Serial";
            tailf:cli-suppress-show-path;
            tailf:cli-suppress-show-match;
          }
          leaf rack-type {
            type string;
            tailf:alt-name "Rack Type";
            tailf:cli-suppress-show-path;
            tailf:cli-suppress-show-match;
          }
          leaf chassis_serial {
            type string;
            tailf:alt-name "Chassis Serial";
            tailf:cli-suppress-show-path;
            tailf:cli-suppress-show-match;
          }
          leaf hw_version {
            type string;
            tailf:alt-name "Hardware Version";
            tailf:cli-suppress-show-path;
            tailf:cli-suppress-show-match;
          }
          leaf mgmt_ext_vlan {
            type string;
            tailf:alt-name "Management External VLAN";
            tailf:cli-suppress-show-path;
            tailf:cli-suppress-show-match;
          }
          leaf state {
            type string;
            description
              "State of VM";
            tailf:alt-name "VM State";
            tailf:cli-suppress-show-path;
            tailf:cli-suppress-show-match;
          }
          leaf start-time {
            type string;
            tailf:alt-name "Start Time";
            tailf:cli-suppress-show-path;
            tailf:cli-suppress-show-match;
          }
          leaf reboot_count {
            type uint32;
            description
              "Number of times rebooted since first boot";
            tailf:alt-name "Reboot Count(Since VM Carving)";
            tailf:cli-suppress-show-path;
            tailf:cli-suppress-show-match;
          }
          leaf rh_count {
            type uint32;
            description
              "Number of times rebooted since lasr card reload";
            tailf:alt-name "Reboot Count(Since Card Reload)";
            tailf:cli-suppress-show-path;
            tailf:cli-suppress-show-match;
          }
          list reboot_hist1 {
            key "count";
            tailf:alt-name "";
            tailf:callpoint "sdr_rh";
            tailf:cli-suppress-table;
            tailf:cli-suppress-show-path;
            tailf:cli-suppress-show-match;
            tailf:cli-show-template-enter "";
            tailf:cli-show-template "               $(Time) $(Reason)\n";
            leaf count {
              type uint32;
              tailf:cli-suppress-show-path;
              tailf:cli-suppress-show-match;
            }
            leaf Time {
              type string;
              tailf:cli-suppress-show-path;
              tailf:cli-suppress-show-match;
            }
            leaf Reason {
              type string;
              description
                "Reason for reload";
              tailf:cli-incomplete-show-path;
              tailf:alt-name "Reload Reason";
              tailf:cli-suppress-show-path;
              tailf:cli-suppress-show-match;
            }
          }
        }
      }
      container reboot-history {
        config false;

        grouping rebhist {
          list location {
            key "node-location";
            min-elements 1;
            max-elements "64";
            tailf:cli-incomplete-command;
            tailf:cli-suppress-table;
            tailf:cli-show-template-legend
              "
                            Reboots
                            Since
               \t\tLocation     Created   Reason
               ---------------------------------------------------------------------
              ";
            tailf:cli-show-template-enter "";
            tailf:cli-show-template
              "$(.legend_shown!=true?
                            Reboots
                            Since
               Location     Created   Reason
               ---------------------------------------------------------------------
               )$(node-location|ljust:12) $(reboot_count|ljust:9)
               $(reboot_hist2|show)";
            leaf node-location {
              type VMLocation;
            }
            leaf reboot_count {
              type uint32;
              description
                "Number of times rebooted since first boot";
              tailf:alt-name "Reboot Count(Since VM Carving)";
              tailf:cli-suppress-show-path;
              tailf:cli-suppress-show-match;
            }
            leaf rh_count {
              type uint32;
              description
                "Number of times rebooted since last card reload";
              tailf:alt-name "Reboot Count(Since Card Reload)";
              tailf:cli-suppress-show-path;
              tailf:cli-suppress-show-match;
            }
            list reboot_hist2 {
              key "count";
              tailf:alt-name "";
              tailf:callpoint "sdr_rh";
              tailf:cli-suppress-show-path;
              tailf:cli-suppress-show-match;
              tailf:cli-suppress-table;
              tailf:cli-show-template-enter "";
              tailf:cli-show-template "                       $(Time|ljust:19) $(Reason)\n";
              leaf count {
                type uint32;
                tailf:cli-suppress-show-path;
                tailf:cli-suppress-show-match;
              }
              leaf Time {
                type string;
                tailf:cli-suppress-show-path;
                tailf:cli-suppress-show-match;
              }
              leaf Reason {
                type string;
                description
                  "Reason for reload";
                tailf:cli-incomplete-show-path;
                tailf:alt-name "Reload Reason";
                tailf:cli-suppress-show-path;
                tailf:cli-suppress-show-match;
              }
            }
          }
        }
        tailf:callpoint "show";
        tailf:cli-suppress-show-match;
        tailf:cli-show-template "$(default-disp|show)";
        container reverse {
          uses rebhist;
        }
        container default-disp {
          tailf:cli-drop-node-name;
          uses rebhist;
        }
      }
      container nodes {
        config false;
        tailf:callpoint "show";
        tailf:cli-drop-node-name;
        list location {
          key "node-location";
          min-elements 1;
          max-elements "64";
          tailf:cli-suppress-table;
          tailf:cli-show-template-enter "";
          tailf:cli-show-template-legend
            "Location     IP Address      Status           Boot Count  Time Started
             -----------------------------------------------------------------------------
            ";
          tailf:cli-show-template
            "$(.legend_shown!=true?Location     IP Address      Status           Boot Count  Time Started
             -----------------------------------------------------------------------------
             )$(node-location|ljust:12) $(ip-addr|ljust:15) $(state|ljust:16) $(rh_count|ljust:11) $(start-time|ljust:19)
            ";
          tailf:cli-incomplete-command;
          leaf node-location {
            type VMLocation;
          }
          leaf sdr-id {
            type uint32;
            tailf:cli-suppress-show-path;
            tailf:cli-suppress-show-match;
          }
          leaf ip-addr {
            type inet:ip-address;
            description
              "IP address of VM";
            tailf:alt-name "IP Address of VM";
            tailf:cli-suppress-show-path;
            tailf:cli-suppress-show-match;
          }
          leaf mac-address {
            type string;
            description
              "MAC address of VM";
            tailf:alt-name "MAC address of VM";
            tailf:cli-suppress-show-path;
            tailf:cli-suppress-show-match;
          }
          leaf state {
            type string;
            description
              "State of VM";
            tailf:alt-name "VM State";
            tailf:cli-suppress-show-path;
            tailf:cli-suppress-show-match;
          }
          leaf start-time {
            type string;
            tailf:cli-suppress-show-path;
            tailf:cli-suppress-show-match;
          }
          leaf reload_reason {
            type string;
            description
              "Reason for last reload";
            tailf:alt-name "Last Reload Reason";
            tailf:cli-suppress-show-path;
            tailf:cli-suppress-show-match;
          }
          leaf reboot_count {
            type uint32;
            description
              "Number of times rebooted since first boot";
            tailf:alt-name "Reboot Count(Since VM Carving)";
            tailf:cli-suppress-show-path;
            tailf:cli-suppress-show-match;
          }
          leaf rh_count {
            type uint32;
            description
              "Number of times rebooted since first boot";
            tailf:alt-name "Reboot Count";
            tailf:cli-suppress-show-path;
            tailf:cli-suppress-show-match;
          }
        }
      }
      container pairing2 {
        config false;
        tailf:callpoint "pair";
        tailf:alt-name "pairing";
        tailf:cli-suppress-show-match;
        tailf:cli-show-template
          " Pairing Mode  $(pairing-mode)
            SDR Lead
              Node 0 $(sdrlead/rp1)
              Node 1 $(sdrlead/rp2)
           $(pairing|show)";
        leaf pairing-mode {
          type string;
          description
            "Mode of Pairing";
          tailf:cli-suppress-show-path;
          tailf:cli-suppress-show-match;
        }
        container sdrlead {
          tailf:cli-suppress-show-match;
          tailf:cli-suppress-show-path;
          leaf rp1 {
            type string;
            tailf:cli-suppress-show-path;
            tailf:cli-suppress-show-match;
          }
          leaf rp2 {
            type string;
            tailf:cli-suppress-show-path;
            tailf:cli-suppress-show-match;
          }
        }
        list pairing {
          key "name";
          min-elements 1;
          max-elements "64";
          tailf:cli-suppress-show-path;
          tailf:cli-suppress-show-match;
          tailf:cli-suppress-table;
          tailf:cli-show-template-enter " Pairs\n";
          tailf:cli-show-template
            "   Pair Name $(name)
                 Node 0   $(rp1)
                 Node 1   $(rp2)
            ";
          leaf name {
            type string;
            tailf:cli-suppress-show-path;
            tailf:cli-suppress-show-match;
          }
          leaf rp1 {
            type string;
            tailf:cli-suppress-show-path;
            tailf:cli-suppress-show-match;
          }
          leaf rp2 {
            type string;
            tailf:cli-suppress-show-path;
            tailf:cli-suppress-show-match;
          }
        }
      }
      list pairing {
        key "name";
        description
          "Add/Edit a RP Pairing by name";
        tailf:info "Specify static pairing for sdr";
        leaf name {
          type string {
            pattern "[a-zA-Z0-9_-]{1,64}";
          }
          tailf:info "pairing name (1 to 64 characters(0-9,a-z,A-Z,-,_))";
        }
        leaf rp1 {
          type RPLocation;
          mandatory true;
          description
            "Enter RP Node location";
          tailf:info "RP Node Location";
        }
        leaf rp2 {
          type RPLocation;
          mandatory true;
          description
            "Enter RP Node location";
          tailf:info "RP Node Location";
        }
      }
    }
  }
  container sdr-manager {
    config false;
    tailf:cli-incomplete-show-path;
    tailf:info "SDR Manager traces";
    container sdr_mgr {
      tailf:cli-drop-node-name;
      uses show_trace:traceable;
    }
  }
  container private-sdr {
    tailf:hidden "advanced-grp";
    list sdr-name {
      key "name";
      min-elements 0;
      max-elements "64";
      leaf name {
        type string;
      }
      leaf id {
        type uint32;
      }
      leaf lead_rack0 {
        type uint32;
      }
      leaf lead_rack1 {
        type uint32;
      }
      list pairing {
        key "num";
        min-elements 0;
        max-elements "64";
        leaf num {
          type uint32;
        }
        leaf second_exist {
          type boolean;
        }
        leaf rp1_rack {
          type uint32;
        }
        leaf rp1_slot {
          type uint32;
        }
        leaf rp2_rack {
          type uint32;
        }
        leaf rp2_slot {
          type uint32;
        }
      }
    }
  }
}
