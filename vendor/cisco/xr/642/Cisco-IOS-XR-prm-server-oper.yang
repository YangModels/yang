module Cisco-IOS-XR-prm-server-oper {
  namespace "http://cisco.com/ns/yang/Cisco-IOS-XR-prm-server-oper";
  prefix prm-server-oper;

  import Cisco-IOS-XR-types {
    prefix xr;
  }
  include Cisco-IOS-XR-prm-server-oper-sub1 {
    revision-date 2016-02-22;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR prm-server package operational data.
     
     This module contains definitions
     for the following management objects:
       hardware-module: PRM data
       prm: prm
     
     Copyright (c) 2013-2017 by Cisco Systems, Inc.
     All rights reserved.";

  revision 2016-02-22 {
    description
      "Initial revision.";
  }
  revision 2015-11-09 {
    description
      "IOS XR 6.0 revision.";
  }

  container hardware-module {
    config false;
    description
      "PRM data";
    container nodes {
      description
        "List of PRM Nodes";
      list node {
        key "node-name";
        description
          "Node Information";
        container np {
          description
            "Server specific";
          container cpu {
            description
              "Resource specific";
            container indexes {
              description
                "Data for software resource";
              list index {
                key "index";
                description
                  "Queue Stats";
                leaf index {
                  type uint32;
                  description
                    "Index value";
                }
                uses BCM-EDM-COSQ-INFO;
              }
            }
          }
          container platform-drop {
            description
              "Platform drops";
            container indxes {
              description
                "Captured Packets";
              list indx {
                key "index";
                description
                  "Captured packets";
                leaf index {
                  type uint32;
                  description
                    "Index value";
                }
                uses PLAT-DROP-CAPTURED-PAK;
              }
            }
            container idxes {
              description
                "Stats for Drop packets";
              list idx {
                key "index";
                description
                  "Drop Stats";
                leaf index {
                  type uint32;
                  description
                    "Index value";
                }
                uses PLAT-DROP-STATS-INFO;
              }
            }
          }
        }
        leaf node-name {
          type xr:Node-id;
          description
            "The node name";
        }
      }
    }
  }
  container prm {
    config false;
    description
      "prm";
    container nodes {
      description
        "List of PRM Nodes";
      list node {
        key "node-name";
        description
          "Node Information";
        container server {
          description
            "Server specific";
          container resource {
            description
              "Resource specific";
            container indexes {
              description
                "Data for software resource";
              list index {
                key "index";
                description
                  "Data for software resource";
                leaf index {
                  type uint32;
                  description
                    "Index value";
                }
                uses RESOURCE-EDM-DATA;
              }
            }
          }
        }
        leaf node-name {
          type xr:Node-id;
          description
            "The node name";
        }
      }
    }
  }
}
