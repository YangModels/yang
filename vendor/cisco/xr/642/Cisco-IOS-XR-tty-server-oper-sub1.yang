submodule Cisco-IOS-XR-tty-server-oper-sub1 {
  belongs-to Cisco-IOS-XR-tty-server-oper {
    prefix Cisco-IOS-XR-tty-server-oper;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR tty-server package operational data.
     
     Copyright (c) 2013-2017 by Cisco Systems, Inc.
     All rights reserved.";

  revision 2017-09-07 {
    description
      "Fixed type translation error.";
  }
  revision 2015-07-30 {
    description
      "Descriptions updated.";
  }
  revision 2015-01-07 {
    description
      "IOS XR 5.3.1 revision.";
  }

  grouping TTY-CONNECTION-STATS {
    description
      "TTY connection statistics";
    leaf incoming-host-address {
      type string {
        length "0..46";
      }
      description
        "Incoming host address(max)";
    }
    leaf host-address-family {
      type uint32;
      description
        "Incoming host address family";
    }
    leaf service {
      type uint32;
      description
        "Input transport";
    }
  }
}
