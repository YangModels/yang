submodule Cisco-IOS-XR-l2-eth-infra-oper-sub1 {
  belongs-to Cisco-IOS-XR-l2-eth-infra-oper {
    prefix Cisco-IOS-XR-l2-eth-infra-oper;
  }

  import ietf-yang-types {
    prefix yang;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR l2-eth-infra package operational data.
     
     Copyright (c) 2013-2017 by Cisco Systems, Inc.
     All rights reserved.";

  revision 2015-11-09 {
    description
      "IOS XR 6.0 revision.";
  }

  typedef Eth-caps-ucast-mac-mode {
    type enumeration {
      enum "reserved" {
        value 0;
        description
          "Reserved";
      }
      enum "permit" {
        value 1;
        description
          "Permit";
      }
    }
    description
      "Eth caps ucast mac mode";
  }

  grouping ETH-CAPS-UCAST-MAC-ENTRY-TYPE {
    description
      "ETH CAPS UCAST MAC ENTRY TYPE";
    leaf mac-address {
      type yang:mac-address;
      description
        "MAC address";
    }
    leaf mode {
      type Eth-caps-ucast-mac-mode;
      description
        "Unicast MAC mode";
    }
  }

  grouping ETHER-CAPS-UCAST-FILTER {
    description
      "Per interface unicast MAC filter information";
    list unicast-filter {
      description
        "Unicast MAC filter information";
      uses ETH-CAPS-UCAST-MAC-ENTRY-TYPE;
    }
  }
}
