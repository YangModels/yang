module Cisco-IOS-XR-reset-optics-act {
  namespace "http://cisco.com/ns/yang/Cisco-IOS-XR-reset-optics-act";
  prefix controller-optics-reload-act;

  import Cisco-IOS-XR-types {
    prefix csc;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR to reload optics module.
     
     Copyright (c) 2024-2025 by Cisco Systems, Inc., and/or its affiliates.
     All rights reserved.";

  revision 2025-02-04 {
    description
      "Reload transceivers/optics";
    semver:module-version "1.0.0";
  }

  typedef reload-method {
    type enumeration {
      enum "cold" {
        description
          "Cold reload the Optics";
      }
      enum "warm" {
        description
          "Warm reload the Optics";
      }
    }
    description
      "Reload action type";
  }

  rpc reload-controller-optics {
    description
      "Reload controller Optics";
    input {
      leaf controller-name {
        type csc:Interface-name;
        mandatory true;
        description
          "Controller name in R/S/I/P format";
      }
      leaf reload {
        type reload-method;
        default "cold";
        description
          "Reload operation type";
      }
      leaf delay {
        type uint64;
        description
          "Delay in nanoseconds before issuing command";
      }
      leaf message {
        type string;
        description
          "Informational reason for the operation";
      }
      leaf force {
        type boolean;
        description
          "Do not wait for software to shutdown gracefully";
      }
    }
    csc:xr-task "dwdm | interface";
  }
}
