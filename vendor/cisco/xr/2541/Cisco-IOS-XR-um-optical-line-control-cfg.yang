module Cisco-IOS-XR-um-optical-line-control-cfg {
  namespace "http://cisco.com/ns/yang/Cisco-IOS-XR-um-optical-line-control-cfg";
  prefix um-optical-line-control-cfg;

  import Cisco-IOS-XR-types {
    prefix xr;
  }
  import ietf-inet-types {
    prefix inet;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR optical-line-control package configuration.
     
     This YANG module augments the
     modules with configuration data.
     
     Copyright (c) 2025 by Cisco Systems, Inc.
     All rights reserved.";

  revision 2025-07-22 {
    description
      "Initial release";
  }

  container optical-line-control {
    description
      "Optical Line Control ";
    container controller {
      description
        "Controller Selection";
      container interfaces {
        description
          "configure this node";
        list interface {
          key "interface-name";
          description
            "configure this node";
          leaf interface-name {
            type xr:Interface-name;
            description
              "configure this node";
          }
          container otdr {
            description
              "OTDR Configuration";
            leaf auto-scan {
              type enumeration {
                enum "disable" {
                  value 1;
                  description
                    "Disable OTDR Auto Scan";
                }
                enum "enable" {
                  value 2;
                  description
                    "Enable OTDR Auto Scan";
                }
              }
              description
                "OTDR Auto Scan Feature";
            }
            container raman-turn-up {
              description
                "Configuration of Raman Turn Up on successful OTDR Scan";
              leaf otdr-scan-for-raman-turn-up {
                type enumeration {
                  enum "disable" {
                    value 1;
                    description
                      "Disable OTDR Scan for Raman Turn Up";
                  }
                  enum "enable" {
                    value 2;
                    description
                      "Enable OTDR Scan for Raman Turn Up";
                  }
                }
                description
                  "configure this node";
              }
              leaf relaxation-factor {
                type uint32 {
                  range "0..100" {
                    description
                      "Enter the relaxation factor in range 0 to 100.";
                  }
                }
                description
                  "Relaxation factor";
              }
            }
          }
          leaf fiber-type {
            type enumeration {
              enum "SMF" {
                value 1;
                description
                  "Type SMF";
              }
              enum "SMF-28E" {
                value 2;
                description
                  "Type SMF-28E";
              }
              enum "TW-RS" {
                value 3;
                description
                  "Type TW-RS";
              }
              enum "TW-Reach" {
                value 4;
                description
                  "Type TW-Reach";
              }
              enum "E-LEAF" {
                value 5;
                description
                  "Type E-LEAF";
              }
              enum "FREE-LIGHT" {
                value 6;
                description
                  "Type FREE-LIGHT";
              }
              enum "METRO-CORE" {
                value 7;
                description
                  "Type METRO-CORE";
              }
              enum "TERA-LIGHT" {
                value 8;
                description
                  "Type TERA-LIGHT";
              }
              enum "TW-minus" {
                value 9;
                description
                  "Type TW-minus";
              }
              enum "TW-plus" {
                value 10;
                description
                  "Type TW-plus";
              }
              enum "ULL-SMF28" {
                value 11;
                description
                  "Type ULL-SMF28";
              }
              enum "TW-Classic" {
                value 12;
                description
                  "Type TW-Classic";
              }
            }
            description
              "Fiber type";
          }
          container apc-local {
            description
              "Automatic Power Control Application for Agents";
            container tx {
              description
                "Disable APC agent in TX direction";
              container disable {
                presence "Indicates a disable node is configured.";
                description
                  "Disable APC on APC agent.";
              }
            }
            container rx {
              description
                "Disable APC agent in RX direction";
              container disable {
                presence "Indicates a disable node is configured.";
                description
                  "Disable APC on APC agent.";
              }
            }
          }
          container dual-band-psds {
            description
              "Dual Band Power Spectral Density Configuration";
            list dual-band-psd {
              key "psd-index";
              description
                "Dual Band Power Spectral Density Configuration";
              leaf psd-index {
                type uint32 {
                  range "1..33" {
                    description
                      "Enter the Dual Band PSD index.";
                  }
                }
                description
                  "PSD Index";
              }
              leaf psd-value {
                type int32 {
                  range "-300..230" {
                    description
                      "Enter the psd in range -30.0 dBm per 12.5 GHz to 23.0 dBm per 12.5 GHz in increments of 0.1 dBm per 12.5 GHz.";
                  }
                }
                mandatory true;
                description
                  "PSD Value";
              }
            }
          }
          container raman-tuning {
            description
              "Automatic Raman Tuning Application";
            leaf raman-tune {
              type enumeration {
                enum "disable" {
                  value 1;
                  description
                    "Disable Automatic Raman Tune";
                }
                enum "enable" {
                  value 2;
                  description
                    "Enable Automatic Raman Tune";
                }
                enum "manual" {
                  value 3;
                  description
                    "Enable Manual Raman Tune";
                }
              }
              description
                "configure this node";
            }
            leaf raman-gain-target {
              type uint32 {
                range "80..250" {
                  description
                    "Enter Target Raman Gain 8.0 dB to 25.0 dB in increments of 0.1 dB.";
                }
              }
              description
                "Configure Tuning Raman Gain Target";
            }
            leaf tuning-mode {
              type enumeration {
                enum "C-L-band" {
                  value 1;
                  description
                    "Raman Tuning Mode C-Band and L-Band";
                }
                enum "C-band-only" {
                  value 2;
                  description
                    "Raman Tuning Mode C-Band Only";
                }
              }
              description
                "Configure Raman Tuning Mode";
            }
            container tune-with-payload {
              presence "Indicates a tune-with-payload node is configured.";
              description
                "Configure Raman Tuning to perform tuning using Payload";
            }
          }
          container link-tuner {
            description
              "Link Tuner Application";
            leaf link-tuner {
              type enumeration {
                enum "disable" {
                  value 1;
                  description
                    "Disable Link-Tuner";
                }
                enum "enable" {
                  value 2;
                  description
                    "Enable Link-Tuner";
                }
                enum "manual" {
                  value 3;
                  description
                    "Enable Manual Link-Tuner";
                }
              }
              description
                "configure this node";
            }
            leaf spectrum-density {
              type uint32 {
                range "1..100" {
                  description
                    "Enter spectrum density in range 1 to 100 in increments of 1";
                }
              }
              description
                "spectrum density";
            }
          }
          container connector-loss {
            description
              "Connector loss";
            leaf tx {
              type xr:Cisco-ios-xr-string {
                length "1..6" {
                  description
                    "Enter tx connector loss in range 0 dB to 20 dB. Precision: 0.01 dB.";
                }
              }
              description
                "Connector loss at transmit point";
            }
            leaf rx {
              type xr:Cisco-ios-xr-string {
                length "1..6" {
                  description
                    "Enter rx connector loss in range 0 dB to 20 dB. Precision: 0.01 dB.";
                }
              }
              description
                "Connector loss at receive point";
            }
          }
          leaf span-length {
            type uint32 {
              range "1..2000" {
                description
                  "Enter Span length in 0.1 km";
              }
            }
            description
              "Span Length";
          }
          leaf gain-estimator {
            type enumeration {
              enum "disable" {
                value 1;
                description
                  "Disable Gain Estimator";
              }
              enum "enable" {
                value 2;
                description
                  "Enable Gain Estimator";
              }
              enum "manual" {
                value 3;
                description
                  "Enable Manual Gain Estimator";
              }
            }
            description
              "Gain estimator application";
          }
          container partner-band-port {
            description
              "Partner band port information configuration";
            container ipv4 {
              description
                "IPv4 address of the interlink port modeled as management port";
              leaf address {
                type inet:ipv4-address-no-zone;
                must "../controller/interface";
                description
                  "IP address of the interlink port modeled as management port";
              }
              container controller {
                description
                  "Controller Selection";
                leaf interface {
                  type xr:Interface-name;
                  must "../../address";
                  description
                    "configure this node";
                }
              }
            }
            container local {
              description
                "Configuring partner band as a local entity";
              container controller {
                description
                  "Controller Selection";
                leaf interface {
                  type xr:Interface-name;
                  description
                    "configure this node";
                }
              }
            }
          }
          container bfr-pause {
            presence "Indicates a bfr-pause node is configured.";
            description
              "Pause BFR on whole domain.";
          }
          leaf patchcord-loss-threshold {
            type uint32 {
              range "0..200" {
                description
                  "Enter maximum loss threshold in range 0.0 dB to 20.0 dB (in units of 0.1dB).";
              }
            }
            description
              "Configure patchcord loss threshold";
          }
          leaf apc-alarm-hold-off-timer {
            type uint32 {
              range "1..1800" {
                description
                  "Enter alarm duration in seconds";
              }
            }
            description
              "Configure APC hold-off timer duration in seconds";
          }
          container apc-span-mode {
            description
              "Configure APC in span-mode";
            container tx {
              presence "Indicates a tx node is configured.";
              description
                "Configure APC in span-mode in TX direction";
            }
            container rx {
              presence "Indicates a rx node is configured.";
              description
                "Configure APC in span-mode in RX direction";
            }
          }
          container apc-span-loss-correction-threshold {
            description
              "Configure span-loss threshold for APC correction";
            leaf tx {
              type uint32 {
                range "2..200" {
                  description
                    "Enter the span-loss threshold in increments of 0.1 dB";
                }
              }
              description
                "Configure span-loss threshold for APC correction in TX direction";
            }
            leaf rx {
              type uint32 {
                range "2..200" {
                  description
                    "Enter the span-loss threshold in increments of 0.1 dB";
                }
              }
              description
                "Configure span-loss threshold for APC correction in RX direction";
            }
          }
          container apc-span-mode-pause {
            description
              "Configure APC to pause in span-mode";
            container tx {
              presence "Indicates a tx node is configured.";
              description
                "Configure APC to pause in span-mode in TX direction";
            }
            container rx {
              presence "Indicates a rx node is configured.";
              description
                "Configure APC to pause in span-mode in RX direction";
            }
          }
          leaf apc-alarm-discrepancy-threshold {
            type uint32 {
              range "5..200" {
                description
                  "Enter discrepancy threshold in increments of 0.1 dB";
              }
            }
            description
              "Configure discrepancy threshold for APC for alarm notification";
          }
          container gain-range-margin {
            description
              "Gain Range Margin ";
            leaf rx {
              type uint32 {
                range "0..30" {
                  description
                    "Enter RX Gain Range Margin in range 0.0 dBm to 3.0 dBm in increments of 0.1 dB.";
                }
              }
              description
                "RX Gain Range Margin";
            }
          }
          container span-loss {
            description
              "Span Loss Application ";
            leaf min {
              type uint32 {
                range "0..420" {
                  description
                    "Enter minimum threshold in range 0.0 dB to 42.0 dB in increments of 0.1 dB.";
                }
              }
              description
                "Minimum threshold";
            }
            leaf max {
              type uint32 {
                range "0..420" {
                  description
                    "Enter maximum threshold in range 0.0 dB to 42.0 dB in increments of 0.1 dB.";
                }
              }
              description
                "Maximum threshold";
            }
            leaf payload-osc-min-deviation {
              type uint32 {
                range "0..420" {
                  description
                    "Enter minimum threshold in range 0.0 dB to 42.0 dB in increments of 0.1 dB.";
                }
              }
              description
                "Minimum allowed difference between measured OSC and payload span loss";
            }
            leaf payload-osc-max-deviation {
              type uint32 {
                range "0..420" {
                  description
                    "Enter maximum threshold in range 0.0 dB to 42.0 dB in increments of 0.1 dB.";
                }
              }
              description
                "Maximum allowed difference between measured OSC and payload span loss";
            }
            leaf max-baseline-deviation {
              type uint32 {
                range "0..420" {
                  description
                    "Enter maximum threshold in range 0.0 dB to 42.0 dB in increments of 0.1 dB.";
                }
              }
              description
                "Maximum allowed difference between measured Rx and baselined Rx span loss";
            }
            leaf min-baseline-deviation {
              type uint32 {
                range "0..420" {
                  description
                    "Enter minimum threshold in range 0.0 dB to 42.0 dB in increments of 0.1 dB.";
                }
              }
              description
                "Minimum allowed difference between measured Rx and baselined Rx span loss";
            }
          }
          leaf apc {
            type enumeration {
              enum "disable" {
                value 1;
                description
                  "Disable APC. This configuration is application only on terminal nodes";
              }
              enum "enable" {
                value 2;
                description
                  "Enable APC. This configuration is application only on terminal nodes";
              }
              enum "manual" {
                value 3;
                description
                  "Enable Manual triggered based APC. This configuration is application only on terminal nodes";
              }
            }
            description
              "Automatic Power Control Application";
          }
          container apc-pause {
            presence "Indicates a apc-pause node is configured.";
            description
              "Pause APC regulation on whole domain.";
          }
          container psds {
            description
              "Power Spectral Density Configuration";
            list psd {
              key "psd-index";
              description
                "Power Spectral Density Configuration";
              leaf psd-index {
                type uint32 {
                  range "1..33" {
                    description
                      "Enter the PSD index.";
                  }
                }
                description
                  "PSD Index";
              }
              leaf psd-value {
                type int32 {
                  range "-300..230" {
                    description
                      "Enter the psd in range -30.0 dBm per 12.5 GHz to 23.0 dBm per 12.5 GHz in increments of 0.1 dBm per 12.5 GHz.";
                  }
                }
                mandatory true;
                description
                  "PSD Value";
              }
            }
          }
          leaf drop-psd {
            type int32 {
              range "-300..230" {
                description
                  "Enter the psd in range -30.0 dBm per 12.5 GHz to 23.0 dBm per 12.5 GHz in increments of 0.1 dBm per 12.5 GHz.";
              }
            }
            description
              "Drop side PSD Configuration";
          }
          leaf psd-min {
            type int32 {
              range "-400..230" {
                description
                  "Enter the psd in range -40.0 dBm per 12.5 GHz to 23.0 dBm per 12.5 GHz in increments of 0.1 dBm per 12.5 GHz.";
              }
            }
            description
              "PSD minimum Configuration";
          }
          leaf psd-target {
            type int32 {
              range "-400..230" {
                description
                  "Enter the psd target in range -40.0 dBm per 12.5 GHz to 23.0 dBm per 12.5 GHz in increments of 0.1 dBm per 12.5 GHz.";
              }
            }
            description
              "PSD Target Configuration";
          }
          leaf expected-total-input-power {
            type int32 {
              range "-400..230" {
                description
                  "Enter the expected total input power in range -40.0 dBm to 23.0 dBm in increments of 0.1 dBm.";
              }
            }
            description
              "Expected Total Input Power Configuration";
          }
          leaf channel-minimum-input-psd {
            type int32 {
              range "-400..230" {
                description
                  "Enter the channel minimum input PSD in range -40.0 dBm per 12.5 GHz to 23.0 dBm per 12.5 GHz in increments of 0.1 dBm per 12.5 GHz.";
              }
            }
            description
              "Channel Minimum Input PSD Configuration";
          }
          leaf channel-rx-power-low-rel-thr {
            type int32 {
              range "-200..-10" {
                description
                  "Enter the channel rx power low relative threshold in range -20.0 dB to -1.0 dB in increments of 0.1 dB.";
              }
            }
            description
              "Channel Rx Power Low Relative Threshold Configuration";
          }
          leaf channel-rx-power-high-rel-thr {
            type int32 {
              range "10..200" {
                description
                  "Enter the channel rx power high relative threshold in range 1.0 dB to 20.0 dB in increments of 0.1 dB.";
              }
            }
            description
              "Channel Rx Power High Relative Threshold Configuration";
          }
          leaf ampli-apc {
            type enumeration {
              enum "span-mode" {
                value 1;
                description
                  "Span loss based APC mode";
              }
            }
            description
              "Automatic Power Control Application for Amplifier";
          }
          leaf channel-apc {
            type enumeration {
              enum "flat-psd-eq-mode" {
                value 1;
                description
                  "Flat PSD channel equalization APC mode";
              }
            }
            description
              "Enable Automatic Power Control of Wavelength Blocker";
          }
          container ampli-apc-pause {
            presence "Indicates a ampli-apc-pause node is configured.";
            description
              "Pause APC regulation for Amplifier";
          }
          container channel-apc-pause {
            presence "Indicates a channel-apc-pause node is configured.";
            description
              "Pause APC regulation for Wavelength Blocker";
          }
        }
      }
    }
    container automatic-link-bringup {
      presence "Indicates a automatic-link-bringup node is configured.";
      description
        "Automatic link bringup";
    }
  }
}
