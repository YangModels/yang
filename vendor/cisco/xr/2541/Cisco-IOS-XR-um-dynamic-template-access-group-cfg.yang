module Cisco-IOS-XR-um-dynamic-template-access-group-cfg {
  namespace "http://cisco.com/ns/yang/Cisco-IOS-XR-um-dynamic-template-access-group-cfg";
  prefix um-dynamic-template-access-group-cfg;

  import Cisco-IOS-XR-types {
    prefix xr;
  }
  import Cisco-IOS-XR-um-dynamic-template-cfg {
    prefix a1;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR dynamic-template-access-group package configuration.
     
     This YANG module augments the
     modules with configuration data.
     
     Copyright (c) 2021-2025 by Cisco Systems, Inc., and/or its affiliates.
     All rights reserved.";

  revision 2022-07-11 {
    description
      "Added missing description statement to nodes";
    semver:module-version "1.0.0";
  }
  revision 2021-12-12 {
    description
      "Initial release";
  }

  grouping TEMPLATE-BODY {
    description
      "Grouping for template";
    container ipv4 {
      description
        "ipv4 subcommands";
      container access-group {
        description
          "Specify access control for packets";
        container filter-packets {
          description
            "configure this node";
          container ingress {
            description
              "Filter incoming packets";
            leaf access-group-name {
              type xr:Cisco-ios-xr-string {
                length "1..64" {
                  description
                    "access-list name";
                }
                pattern "[a-z0-9A-Z][-_.:a-z0-9A-Z]*";
              }
              description
                "Specify access control for packets";
            }
          }
          container egress {
            description
              "Filter outgoing packets";
            leaf access-group-name {
              type xr:Cisco-ios-xr-string {
                length "1..64" {
                  description
                    "access-list name";
                }
                pattern "[a-z0-9A-Z][-_.:a-z0-9A-Z]*";
              }
              description
                "Specify access control for packets";
            }
          }
        }
      }
    }
    container ipv6 {
      description
        "ipv6 subcommands";
      container access-group {
        description
          "Specify access control for packets";
        container filter-packets {
          description
            "configure this node";
          container ingress {
            description
              "Filter incoming packets";
            leaf access-group-name {
              type xr:Cisco-ios-xr-string {
                length "1..64" {
                  description
                    "access-list name";
                }
                pattern "[a-z0-9A-Z][-_.:a-z0-9A-Z]*";
              }
              description
                "Specify access control for packets";
            }
          }
          container egress {
            description
              "Filter outgoing packets";
            leaf access-group-name {
              type xr:Cisco-ios-xr-string {
                length "1..64" {
                  description
                    "access-list name";
                }
                pattern "[a-z0-9A-Z][-_.:a-z0-9A-Z]*";
              }
              description
                "Specify access control for packets";
            }
          }
        }
      }
    }
  }

  augment "/a1:dynamic-template/a1:type/a1:ppp/a1:template" {
    description
      "This augment extends dynamic-template ppp nodes
       configuration";
    uses TEMPLATE-BODY;
  }
  augment "/a1:dynamic-template/a1:type/a1:ipsubscriber/a1:template" {
    description
      "This augment extends dynamic-template ipsubscriber nodes
       configuration";
    uses TEMPLATE-BODY;
  }
  augment "/a1:dynamic-template/a1:type/a1:service/a1:template" {
    description
      "This augment extends dynamic-template service nodes
       configuration";
    uses TEMPLATE-BODY;
  }
}
