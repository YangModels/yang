/* ----------------------------------------------------------------------------
 * openconfig-yiny-it-sanitize.yang - YANG OC Schema definitions for YinY
 *                                    sanitization IT
 *
 * October 2023, Benjamin Horspool
 *
 * Copyright (c) 2023 by Cisco Systems, Inc.
 * All rights reserved.
 * ----------------------------------------------------------------------------
 */

module openconfig-yiny-it-sanitize {
  namespace "http://openconfig.net/yang/yiny-it-sanitize";
  prefix "oc-yiny-it-sanitize";

  import ietf-inet-types { prefix "inet"; }
  import ietf-yang-types { prefix "yang"; }
  import openconfig-types { prefix "oc-types"; }
  import openconfig-inet-types { prefix "oc-inet"; }
  import openconfig-yang-types { prefix "oc-yang"; }
  import openconfig-isis-types { prefix "oc-isis-types"; }
  import openconfig-packet-match-types { prefix "oc-pkt-match-types"; }

  revision "2023-10-19" {
    description "Initial release";
  }

  container sanitize-cont {
    // IP-address types.
    leaf ietf-ipv4-address { type inet:ipv4-address; }
    leaf ietf-ipv4-prefix { type inet:ipv4-prefix; }
    leaf ietf-ipv6-address { type inet:ipv6-address; }
    leaf ietf-ipv6-prefix { type inet:ipv6-prefix; }
    leaf oc-ipv4-address { type oc-inet:ipv4-address; }
    leaf oc-ipv4-prefix { type oc-inet:ipv4-prefix; }
    leaf oc-ipv6-address { type oc-inet:ipv6-address; }
    leaf oc-ipv6-prefix { type oc-inet:ipv6-prefix; }

    // IP-address union type.
    leaf oc-ip-prefix { type oc-inet:ip-prefix; }

    // Lowercase types.
    leaf ietf-hex { type yang:hex-string; }
    leaf oc-hex { type oc-yang:hex-string; }
    leaf oc-domain-name { type oc-inet:domain-name; }
    leaf oc-area-address { type oc-isis-types:area-address; }
    leaf oc-lsp-id { type oc-isis-types:lsp-id; }
    leaf oc-net { type oc-isis-types:net; }
    leaf oc-system-id { type oc-isis-types:system-id; }
    leaf oc-phys-address { type oc-yang:phys-address; }
    leaf oc-mac-address { type oc-yang:mac-address; }

    // Date types.
    leaf ietf-date { type yang:date-and-time; }
    leaf oc-date { type oc-yang:date-and-time; }

    // Special types.
    leaf oc-port-num-range { type oc-pkt-match-types:port-num-range; }

    // Types that need encoding and decoding.
    leaf oc-routing-password { type oc-types:routing-password; }

    // OC style list with key needing sanitizing.
    list oc-style-list {
      key "ip";
      leaf ip {
        type leafref {
          path "../config/ip";
        }
      }

      container config {
        leaf ip { type oc-inet:ip-address; }
        leaf mac-address { type oc-yang:mac-address; }
        leaf lsp-id { type oc-isis-types:lsp-id; }
      }
    }

    // Leaf list needing sanitizing.
    leaf-list leaf_list { type oc-yang:hex-string; }
  }
}
