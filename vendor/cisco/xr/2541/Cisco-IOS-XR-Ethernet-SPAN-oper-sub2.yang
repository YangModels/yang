submodule Cisco-IOS-XR-Ethernet-SPAN-oper-sub2 {
  belongs-to Cisco-IOS-XR-Ethernet-SPAN-oper {
    prefix Cisco-IOS-XR-Ethernet-SPAN-oper;
  }

  import Cisco-IOS-XR-types {
    prefix xr;
  }
  import cisco-semver {
    prefix semver;
  }
  include Cisco-IOS-XR-Ethernet-SPAN-oper-sub1 {
    revision-date 2025-04-04;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR Ethernet-SPAN package operational data.
     
     Copyright (c) 2013-2025 by Cisco Systems, Inc.
     All rights reserved.";

  revision 2025-04-04 {
    description
      "Add application destination class
       2025-03-17
         Add combined stats fields to SPAN stats
       2024-10-03
         Update sflow data to binary format
       2024-06-26
         Simpilfy drops filter to single item, replacing deprecated (and unused) tm-drop and forward-drop filters
       2024-01-26
         Add option to mirror all dropped packets
       2024-01-23
         Add support for sFlow destinations
       2023-09-12
         Support a single MPLS ACL under SPAN attachments
       2023-07-24
         Remove support for sflow destination
       2022-09-08
         Add rate-limiting support
       2022-09-05
         Operational data for GRE tunnel interfaces
       2022-08-19
         Add sflow destination
       2022-08-01
         Add per-session mirror interval
       2022-07-13
         Add MPLS IPv4 and MPLS IPv6 ACLs under SPAN attachments
       2022-06-29
         Change Buffer Drop references to Traffic Management
       2022-06-17
         Added support for ACL merge groups
       2022-05-27
         Added support for per-session statistics.
       2022-04-13
         Added support for mirroring dropped packets
       2021-09-15
         Added support for mirror first configured on sessions
       2021-08-20
         Added support for ERSPAN session ID under GRE destinations";
    semver:module-version "6.0.0";
  }
  revision 2021-07-19 {
    description
      "Added extended range of values to mirror interval sampling
       2021-06-02
          Added support for non-default VRFs and router-id";
    semver:module-version "5.0.0";
  }
  revision 2020-12-03 {
    description
      "Added support for multiple attachments per class on an interface
       2020-09-14
           Added support for mirror rx and tx traffic to separate destinations
       2020-04-03
           Added support for bundle destinations.";
    semver:module-version "4.0.0";
  }
  revision 2020-01-30 {
    description
      "Added support for L3 IPv4 and IPv6 ACLs on a L2 ethernet SPAN session
       2019-12-12
         Added support for file format and PCAP filter expressions under file
       2019-10-02
         Added support for UDP destinations and CloudSPAN.";
    semver:module-version "3.0.0";
  }
  revision 2019-05-12 {
    description
      "Added support for file destinations.";
    semver:module-version "2.0.0";
  }
  revision 2019-04-05 {
    description
      "Establish semantic version baseline.";
    semver:module-version "1.0.0";
  }
  revision 2015-11-09 {
    description
      "IOS XR 6.0 revision.";
  }

  grouping SPAN-MA-ATT-BAG-DEST-INFO {
    description
      "Attachment Destination Info";
    container destination-id {
      description
        "Destination ID";
      uses DESTINATION-ID;
    }
    leaf dest-pw-type-not-supported {
      type boolean;
      description
        "The destination PW type is not supported";
    }
  }

  grouping SPAN-MA-ATTACHMENT-BAG {
    description
      "SPAN MA Attachment Information";
    container traffic-parameters {
      description
        "Traffic mirroring parameters";
      uses TRAFFIC-MIRRORING-PARAMETERS;
    }
    container destination-id {
      description
        "Destination ID";
      uses DESTINATION-ID;
    }
    container rx-destination-info {
      description
        "Rx Destination Info";
      uses SPAN-MA-ATT-BAG-DEST-INFO;
    }
    container tx-destination-info {
      description
        "Tx Destination Info";
      uses SPAN-MA-ATT-BAG-DEST-INFO;
    }
    leaf name {
      type string;
      description
        "Session Name";
    }
    leaf local-class {
      type Session-class;
      description
        "Local attachment class";
    }
    leaf id {
      type uint32;
      description
        "Numerical ID assigned to session";
    }
    leaf separate-destinations {
      type boolean;
      description
        "Separate Destinations";
    }
    leaf global-class {
      type Session-class;
      description
        "Global session class";
    }
    leaf session-is-configured {
      type boolean;
      description
        "The Session is configured globally";
    }
    leaf source-interface {
      type xr:Interface-name;
      description
        "Source interface";
    }
    leaf source-interface-state {
      type Im-state-enum;
      description
        "Source interface state";
    }
    leaf pfi-error {
      type uint32;
      description
        "Last error returned from PFI for this interface";
    }
    leaf config-error {
      type uint32;
      description
        "Error returned when configuring global session
         config";
    }
    leaf dest-pw-type-not-supported {
      type boolean;
      description
        "The destination PW type is not supported";
    }
    leaf source-interface-is-a-destination {
      type boolean;
      description
        "This source interface is a destination for
         another monitor-session";
    }
    leaf destination-interface {
      type xr:Interface-name;
      description
        "Destination interface (deprecated by
         DestinationID, invalid for pseudowires)";
    }
    leaf traffic-direction {
      type Traffic-direction;
      description
        "Traffic mirroring direction (deprecated by
         TrafficParameters)";
    }
  }

  grouping SPAN-MA-STATISTICS-BAG {
    description
      "SPAN MA Statistics Information";
    leaf rx-packets-mirrored {
      type uint64;
      description
        "RX Packets Mirrored";
    }
    leaf rx-octets-mirrored {
      type uint64;
      description
        "RX Octets Mirrored";
    }
    leaf tx-packets-mirrored {
      type uint64;
      description
        "TX Packets Mirrored";
    }
    leaf tx-octets-mirrored {
      type uint64;
      description
        "TX Octets Mirrored";
    }
    leaf packets-not-mirrored {
      type uint64;
      description
        "Packets Not Mirrored";
    }
    leaf octets-not-mirrored {
      type uint64;
      description
        "Octets Not Mirrored";
    }
    leaf total-packets-mirrored {
      type uint64;
      description
        "Total Packets Mirrored";
    }
    leaf total-octets-mirrored {
      type uint64;
      description
        "Total Octets Mirrored";
    }
  }
}
