module Cisco-IOS-XR-um-grpc-cfg {
  namespace "http://cisco.com/ns/yang/Cisco-IOS-XR-um-grpc-cfg";
  prefix um-grpc-cfg;

  import Cisco-IOS-XR-types {
    prefix xr;
  }
  import ietf-inet-types {
    prefix inet;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco grpc package configuration.
     
     Copyright (c) 2025 by Cisco Systems, Inc., and/or its affiliates.
     All rights reserved.";

  revision 2025-10-13 {
    description
      "Changed container notls to leaf node; Added gnpsi container
       2025-09-04
         Updated gRPC server's min and max TLS versions
       2025-08-18
         Added support for max concurrent streams per server
       2025-08-08
         Added support for ANY in listen addresses
       2025-07-08
         Added support for get-limit-multiple
       2025-06-13
         Updated listening-address-argument to listen-address
       2025-05-13
         Added support for gRPC multi-servers
       2025-03-19
         Added Support for remote-connection and SR-TE service instance
       2024-06-18
         Added support for tls-max-version and tls-min-version
       2024-04-04
         Updated port range for gribi, grpc, gnmi
       2024-03-04
         Added support for aaa accounting
       2023-12-14
         Added support for max concurrent streams per connection
       2023-11-28
         Added support for service layer and updated gnsi
       2023-09-15
         Updating model for um2 changes
       2023-06-28
         Added certificate common name
       2023-06-15
         Added support for IANA defined gRPC ports.
       2023-04-16
         Added container memory
       2023-03-22
         Added container keepalive
       2023-01-23
         Added support for virtual IP as gRPC tunnel source address and domain name as gRPC tunnel destination.
       2023-01-05
         Added p4rt container.
       2022-11-07
         Added gRPC SRTE service
       2022-09-26
         Added TTL leaf.
       2022-08-24
         Added tls-v1-disable container.";
    semver:module-version "3.0.0";
  }
  revision 2021-09-29 {
    description
      "Added certificate-authentication & local-connection containers
       2021-07-28
          Added tunnel container.";
    semver:module-version "2.1.0";
  }
  revision 2021-05-20 {
    description
      "Added leaf min-keepalive-interval.
       2020-08-01
           Added aaa container.";
    semver:module-version "2.0.0";
  }
  revision 2019-06-10 {
    description
      "Establish semantic version baseline.";
    semver:module-version "1.1.0";
  }
  revision 2019-03-30 {
    description
      "Initial version";
  }

  container grpc {
    presence "grpc configuration commands";
    description
      "grpc configuration commands";
    leaf certificate-authentication {
      type empty;
      description
        "DEPRECATED. Removing in 26.3.1: Enables Certificate based Authentication";
    }
    leaf tls-max-version {
      type enumeration {
        enum "1.0" {
          value 0;
          description
            "DEPRECATED. Removing in 26.3.1: Configure TLS 1.0 as maximum TLS version";
        }
        enum "1.1" {
          value 1;
          description
            "DEPRECATED. Removing in 26.3.1: Configure TLS 1.1 as maximum TLS version";
        }
        enum "1.2" {
          value 2;
          description
            "DEPRECATED. Removing in 26.3.1: Configure TLS 1.2 as maximum TLS version";
        }
        enum "1.3" {
          value 3;
          description
            "DEPRECATED. Removing in 26.3.1: Configure TLS 1.3 as maximum TLS version";
        }
      }
      description
        "DEPRECATED. Removing in 26.3.1: gRPC maximum TLS version";
    }
    leaf tls-min-version {
      type enumeration {
        enum "1.0" {
          value 0;
          description
            "DEPRECATED. Removing in 26.3.1: Configure TLS 1.0 as minimum TLS version";
        }
        enum "1.1" {
          value 1;
          description
            "DEPRECATED. Removing in 26.3.1: Configure TLS 1.1 as minimum TLS version";
        }
        enum "1.2" {
          value 2;
          description
            "DEPRECATED. Removing in 26.3.1: Configure TLS 1.2 as minimum TLS version";
        }
        enum "1.3" {
          value 3;
          description
            "DEPRECATED. Removing in 26.3.1: Configure TLS 1.3 as minimum TLS version";
        }
      }
      description
        "DEPRECATED. Removing in 26.3.1: gRPC minimum TLS version";
    }
    leaf tls-mutual {
      type empty;
      description
        "DEPRECATED. Removing in 26.3.1: Mutual Authentication";
    }
    leaf tlsv1-disable {
      type empty;
      description
        "Disable support for TLS version 1.0ntlsv1-disable CLI is deprecated.nUse tls-min-version CLI to set minimum TLS version.";
    }
    leaf max-request-total {
      type uint32 {
        range "1..256" {
          description
            "Maximum concurrent requests in total";
        }
      }
      description
        "Maximum concurrent requests in total";
    }
    leaf max-request-per-user {
      type uint32 {
        range "1..32" {
          description
            "Maximum concurrent requests per user";
        }
      }
      description
        "Maximum concurrent requests per user";
    }
    leaf max-streams {
      type uint32 {
        range "1..128" {
          description
            "Maximum number of streaming gRPCs (Default: 32)";
        }
      }
      description
        "Maximum number of streaming gRPCs (Default: 32)";
    }
    leaf max-streams-per-user {
      type uint32 {
        range "1..128" {
          description
            "Maximum number of streaming gRPCs per user (Default: 32)";
        }
      }
      description
        "Maximum number of streaming gRPCs per user (Default: 32)";
    }
    leaf port {
      type uint32 {
        range "1024..65535" {
          description
            "DEPRECATED. Removing in 26.3.1: Server listening port, default: 57400";
        }
      }
      description
        "DEPRECATED. Removing in 26.3.1: Server listening port";
    }
    leaf vrf {
      type xr:Cisco-ios-xr-string {
        length "1..1024" {
          description
            "DEPRECATED. Removing in 26.3.1: vrf name";
        }
      }
      description
        "DEPRECATED. Removing in 26.3.1: Server vrf";
    }
    leaf certificate-id {
      type xr:Cisco-ios-xr-string {
        length "1..1024" {
          description
            "DEPRECATED. Removing in 26.3.1: Certificate ID";
        }
      }
      description
        "DEPRECATED. Removing in 26.3.1: Active Certificate";
    }
    leaf name {
      type xr:Cisco-ios-xr-string {
        length "1..64" {
          description
            "gRPC server name";
        }
      }
      description
        "gRPC server name";
    }
    container aaa {
      description
        "AAA authorization and authentication for gRPC";
      container authorization {
        description
          "AAA authorization methodlist for gRPC";
        leaf exec {
          type xr:Cisco-ios-xr-string {
            length "1..1024" {
              description
                "AAA methodlist name";
            }
          }
          description
            "AAA authorization exec method list";
        }
      }
      container accounting {
        description
          "Accounting configurations for gRPC";
        leaf queue-size {
          type uint32 {
            range "1..512" {
              description
                "Queue size, values: 1-512. (default 100)";
            }
          }
          description
            "Maximum configurable size of the accounting queue";
        }
        leaf history-memory {
          type uint32 {
            range "1..400" {
              description
                "History max memory, values: 1-400 MB (default 40 MB)";
            }
          }
          description
            "Maximum configurable memory of the accounting history in MB";
        }
      }
      container authentication {
        description
          "AAA authentication methodlist for gRPC";
        leaf login {
          type xr:Cisco-ios-xr-string {
            length "1..1024" {
              description
                "AAA methodlist name";
            }
          }
          description
            "AAA authentication login method list";
        }
      }
    }
    container address-family {
      description
        "DEPRECATED. Removing in 26.3.1: Address family identifier type";
      choice ADDRESS-FAMILY {
        description
          "DEPRECATED. Removing in 26.3.1: Address family identifier type";
        case IPV4 {
          leaf ipv4 {
            type empty;
            description
              "DEPRECATED. Removing in 26.3.1: IPv4 address-family";
          }
        }
        case IPV6 {
          leaf ipv6 {
            type empty;
            description
              "DEPRECATED. Removing in 26.3.1: IPv6 address-family";
          }
        }
        case DUAL {
          leaf dual {
            type empty;
            description
              "DEPRECATED. Removing in 26.3.1: dual stackaddress-family";
          }
        }
      }
    }
    leaf min-keepalive-interval {
      type uint32 {
        range "1..10000" {
          description
            "Keepalive interval in seconds";
        }
      }
      description
        "DEPRECATED. Removing in 26.3.1: Minimum client keepalive interval";
    }
    leaf max-concurrent-streams {
      type uint32 {
        range "1..128" {
          description
            "gRPC concurrent stream limit, default 32";
        }
      }
      description
        "gRPC server maximum concurrent streams per connection";
    }
    container keepalive {
      description
        "DEPRECATED. Removing in 26.3.1: Server keepalive time and timeout";
      leaf time {
        type uint32 {
          range "1..10000" {
            description
              "Server keepalive time in seconds (default 30)";
          }
        }
        description
          "Server keepalive time";
      }
      leaf timeout {
        type uint32 {
          range "1..10000" {
            description
              "DEPRECATED. Removing in 26.3.1: Server keepalive timeout in seconds (default 20)";
          }
        }
        description
          "DEPRECATED. Removing in 26.3.1: Server keepalive timeout";
      }
    }
    container memory {
      description
        "EMSd-Go soft memory limit in MB";
      leaf limit {
        type uint32 {
          range "600..1400" {
            description
              "Soft memory limit in MB, default 1024MB";
          }
        }
        description
          "Soft memory limit in MB";
      }
    }
    leaf local-connection {
      type empty;
      description
        "DEPRECATED. Removing in 26.3.1: Enable gRPC server over Unix socket";
    }
    container remote-connection {
      description
        "DEPRECATED. Removing in 26.3.1: Configuration to toggle TCP support on the gRPC server";
      leaf disable {
        type empty;
        description
          "Disable TCP on the gRPC server";
      }
    }
    leaf default-server-disable {
      type empty;
      description
        "Configuration to disable the default gRPC server";
    }
    leaf ttl {
      type uint32 {
        range "0..255" {
          description
            "DEPRECATED. Removing in 26.3.1: gRPC packets TTL value";
        }
      }
      description
        "DEPRECATED. Removing in 26.3.1: gRPC packets TTL value";
    }
    container service-layer {
      presence "grpc service layer configuration";
      description
        "grpc service layer configuration";
      leaf auto-register {
        type empty;
        description
          "Enable service-layer auto-register";
      }
    }
    container servers {
      description
        "gRPC server configuration";
      list server {
        key "server-name";
        description
          "gRPC server configuration";
        leaf server-name {
          type xr:Cisco-ios-xr-string {
            length "1..64" {
              description
                "Unique name for the gRPC server";
            }
          }
          description
            "Unique name for the gRPC server";
        }
        container tunnel {
          description
            "grpc tunnel service of the gRPC server";
          container destinations {
            description
              "gRPC tunnel destination";
            list destination {
              key "grpc-tunnel-destination port-number";
              description
                "gRPC tunnel destination";
              leaf grpc-tunnel-destination {
                type xr:Cisco-ios-xr-string {
                  length "1..1024" {
                    description
                      "IPv4/IPv6 address or domain name";
                  }
                }
                description
                  "gRPC tunnel destination";
              }
              leaf port-number {
                type uint32 {
                  range "1..65535" {
                    description
                      "Port number";
                  }
                }
                description
                  "Destination port";
              }
              leaf vrf {
                type xr:Cisco-ios-xr-string {
                  length "1..1024" {
                    description
                      "VRF name";
                  }
                }
                description
                  "VRF for the dial-out";
              }
              leaf source-interface {
                type xr:Interface-name;
                description
                  "Source interface";
              }
              leaf target {
                type xr:Cisco-ios-xr-string {
                  length "1..1024" {
                    description
                      "Target name";
                  }
                }
                description
                  "Target name to register tunnel service";
              }
              leaf address-family {
                type enumeration {
                  enum "ipv4" {
                    value 1;
                    description
                      "IPv4";
                  }
                  enum "ipv6" {
                    value 2;
                    description
                      "IPv6";
                  }
                }
                description
                  "Specify the AF for the returned addresses from DNS. Only applicable to domain name.";
              }
              container source {
                description
                  "Virtual IP address family";
                container ipv6 {
                  description
                    "IPv6 address family";
                  container virtual {
                    description
                      "Virtual address";
                    leaf address {
                      type empty;
                      description
                        "Virtual address";
                    }
                  }
                }
                container ipv4 {
                  description
                    "IPv4 address family";
                  container virtual {
                    description
                      "Virtual address";
                    leaf address {
                      type empty;
                      description
                        "Virtual address";
                    }
                  }
                }
              }
            }
          }
        }
        container services {
          description
            "List of gRPC services to be registered with the server";
          leaf gnmi {
            type empty;
            description
              "gNMI";
          }
          leaf gnoi {
            type empty;
            description
              "gNOI";
          }
          leaf gnsi {
            type empty;
            description
              "gNSI";
          }
          leaf cnmi {
            type empty;
            description
              "cNMI";
          }
          leaf p4rt {
            type empty;
            description
              "P4 runtime";
          }
          leaf gnpsi {
            type empty;
            description
              "gNPSI";
          }
          leaf srte {
            type empty;
            description
              "SR-TE";
          }
          leaf slapi {
            type empty;
            description
              "SL-API";
          }
          leaf gribi {
            type empty;
            description
              "gRIBI";
          }
          leaf attestz {
            type empty;
            description
              "ATTESTZ";
          }
          leaf enrollz {
            type empty;
            description
              "ENROLLZ";
          }
        }
        leaf disable {
          type empty;
          description
            "Disable gRPC server";
        }
        leaf port {
          type uint32 {
            range "1024..65535" {
              description
                "gRPC service port, valid range: 1024-65535";
            }
          }
          description
            "gRPC server listening port";
        }
        leaf vrf {
          type xr:Cisco-ios-xr-string {
            length "1..1024" {
              description
                "Server network instance";
            }
          }
          description
            "Server network instance";
        }
        leaf address-family {
          type enumeration {
            enum "ipv4" {
              value 1;
              description
                "IPv4 address-family";
            }
            enum "ipv6" {
              value 2;
              description
                "IPv6 address-family";
            }
            enum "dual" {
              value 3;
              description
                "dual stackaddress-family";
            }
          }
          description
            "Address family identifier type";
        }
        container keepalive {
          description
            "Server keepalive time and timeout";
          leaf time {
            type uint32 {
              range "1..10000" {
                description
                  "Server keepalive time in seconds (default 30s)";
              }
            }
            description
              "Server keepalive time";
          }
          leaf min-keepalive-interval {
            type uint32 {
              range "1..10000" {
                description
                  "Enforcement time for the keepalive ping in seconds";
              }
            }
            description
              "Minimum time a clinet shoult wait before sending a keepalive ping";
          }
          leaf timeout {
            type uint32 {
              range "1..10000" {
                description
                  "Server keepalive timeout in seconds (default 20s)";
              }
            }
            description
              "Server keepalive parameters";
          }
        }
        leaf ttl {
          type uint32 {
            range "0..255" {
              description
                "gRPC packets TTL value";
            }
          }
          description
            "gRPC packets TTL value";
        }
        leaf local-connection {
          type empty;
          description
            "Enable gRPC server over Unix socket";
        }
        container remote-connection {
          description
            "Configuration to toggle TCP support on the gRPC server";
          leaf disable {
            type empty;
            description
              "Disable TCP on the gRPC server";
          }
        }
        container metadata-authentication {
          description
            "Enable metadata authentication";
          leaf disable {
            type empty;
            description
              "Disable metadata authentication on the gRPC server";
          }
        }
        leaf max-concurrent-streams {
          type uint32 {
            range "1..128" {
              description
                "gRPC concurrent stream limit, default 32";
            }
          }
          description
            "gRPC server maximum concurrent streams per connection";
        }
        leaf dscp {
          type union {
            type uint32 {
              range "0..63" {
                description
                  "Differentiated services code point";
              }
            }
            type enumeration {
              enum "af11" {
                value 10;
                description
                  "AF11 (DSCP 001010)";
              }
              enum "af12" {
                value 12;
                description
                  "AF12 (DSCP 001100)";
              }
              enum "af13" {
                value 14;
                description
                  "AF13 (DSCP 001110)";
              }
              enum "af21" {
                value 18;
                description
                  "AF21 (DSCP 010010)";
              }
              enum "af22" {
                value 20;
                description
                  "AF22 (DSCP 010100)";
              }
              enum "af23" {
                value 22;
                description
                  "AF23 (DSCP 010110)";
              }
              enum "af31" {
                value 26;
                description
                  "AF31 (DSCP 011010)";
              }
              enum "af32" {
                value 28;
                description
                  "AF32 (DSCP 011100)";
              }
              enum "af33" {
                value 30;
                description
                  "AF33 (DSCP 011110)";
              }
              enum "af41" {
                value 34;
                description
                  "AF41 (DSCP 100010)";
              }
              enum "af42" {
                value 36;
                description
                  "AF42 (DSCP 100100)";
              }
              enum "af43" {
                value 38;
                description
                  "AF43 (DSCP 100110)";
              }
              enum "cs1" {
                value 8;
                description
                  "CS1 (Precedence 1) (DSCP 001000)";
              }
              enum "cs2" {
                value 16;
                description
                  "CS2 (Precedence 2) (DSCP 010000)";
              }
              enum "cs3" {
                value 24;
                description
                  "CS3 (Precedence 3) (DSCP 011000)";
              }
              enum "cs4" {
                value 32;
                description
                  "CS4 (Precedence 4) (DSCP 100000)";
              }
              enum "cs5" {
                value 40;
                description
                  "CS5 (Precedence 5) (DSCP 101000)";
              }
              enum "cs6" {
                value 48;
                description
                  "CS6 (Precedence 6) (DSCP 110000)";
              }
              enum "cs7" {
                value 56;
                description
                  "CS7 (Precedence 7) (DSCP 111000)";
              }
              enum "default" {
                value 0;
                description
                  "Default (DSCP 000000)";
              }
              enum "ef" {
                value 46;
                description
                  "EF (DSCP 101110)";
              }
            }
          }
          description
            "QoS marking DSCP to be set on transmitted gRPC";
        }
        container listen-addresses {
          description
            "gRPC server listening addresses";
          choice LISTEN-ADDRESSES {
            description
              "gRPC server listening addresses";
            case LISTEN-ADDRESS {
              container listen-address {
                presence "Listen address";
                description
                  "Listen address";
                leaf-list address {
                  type inet:ip-address-no-zone;
                  max-elements "31";
                  description
                    "Listen address";
                }
              }
            }
            case ANY {
              leaf any {
                type empty;
                description
                  "Listen on all addresses";
              }
            }
          }
        }
        container tls {
          description
            "TLS configuration options for gRPC server";
          container version {
            description
              "gRPC TLS version";
            leaf min-version {
              type enumeration {
                enum "1.2" {
                  value 2;
                  description
                    "Configure TLS 1.2 as minimum TLS version";
                }
                enum "1.3" {
                  value 3;
                  description
                    "Configure TLS 1.3 as minimum TLS version";
                }
              }
              description
                "TLS min version";
            }
            leaf max-version {
              type enumeration {
                enum "1.2" {
                  value 2;
                  description
                    "Configure TLS 1.2 as maximum TLS version";
                }
                enum "1.3" {
                  value 3;
                  description
                    "Configure TLS 1.3 as maximum TLS version";
                }
              }
              description
                "TLS max version";
            }
          }
          container cipher {
            description
              "gRPC TLS 1.2 cipher suites";
            leaf enable {
              type string {
                length "1..1024" {
                  description
                    "List of comma separated ciphers";
                }
              }
              description
                "Enable ciphers if 'default disable'";
            }
            leaf default {
              type enumeration {
                enum "enable" {
                  value 2;
                  description
                    "Enable all ciphers";
                }
                enum "disable" {
                  value 1;
                  description
                    "Disable all ciphers";
                }
              }
              description
                "Default of all ciphers";
            }
            leaf disable {
              type string {
                length "1..1024" {
                  description
                    "List of comma separated ciphers";
                }
              }
              description
                "Disable ciphers if 'default enable'";
            }
          }
          leaf mutual {
            type empty;
            description
              "TLS mutual authentication";
          }
          leaf trustpoint {
            type xr:Cisco-ios-xr-string {
              length "1..1024" {
                description
                  "TLS trustpoint name";
              }
            }
            description
              "TLS trustpoint";
          }
          leaf disable {
            type empty;
            description
              "Disable TLS for gRPC server";
          }
        }
        leaf ssl-profile-id {
          type xr:Cisco-ios-xr-string {
            length "1..1024" {
              description
                "SSL profile Id";
            }
          }
          description
            "gRPC server SSL profile Id";
        }
      }
    }
    container certificate {
      description
        "gRPC server certificate";
      leaf common-name {
        type xr:Cisco-ios-xr-string {
          length "1..64" {
            description
              "Common name when generate certificates, default: ems.cisco.com";
          }
        }
        description
          "Common name when generate certificates";
      }
    }
    container segment-routing {
      presence "segment-routing";
      description
        "gRPC segment-routing configuration";
      container traffic-eng {
        presence "traffic-eng";
        description
          "gRPC segment-routing traffic-eng configuration";
        leaf policy-service {
          type empty;
          description
            "Enable SRTE policy services";
        }
        container service-instances {
          description
            "Configure a named service";
          list service-instance {
            key "service-instance-name";
            description
              "Configure a named service";
            leaf service-instance-name {
              type xr:Cisco-ios-xr-string {
                length "1..128" {
                  description
                    "service instance name";
                }
              }
              description
                "service instance name";
            }
            container addresses {
              description
                "Destination address";

              grouping OPTIONS {
                description
                  "Options for service instance address";
                leaf notls {
                  type empty;
                  description
                    "turn off TLS";
                }
                leaf source-interface {
                  type xr:Interface-name;
                  description
                    "Source interface to be used for dialout";
                }
                leaf vrf {
                  type xr:Cisco-ios-xr-string {
                    length "1..32" {
                      description
                        "Enter VRF Name";
                    }
                  }
                  description
                    "Enter specific VRF Name for this nexthop";
                }
                leaf tls-hostname-override {
                  type xr:Cisco-ios-xr-string {
                    length "1..32" {
                      description
                        "server hostname override";
                    }
                  }
                  description
                    "host name to use for TLS cert verification";
                }
              }
              list ipv4-address {
                key "ipv4-address port";
                description
                  "Destination address";
                leaf ipv4-address {
                  type inet:ip-address-no-zone;
                  description
                    "Enter Destination IPv4 address";
                }
                leaf port {
                  type uint32 {
                    range "1..65535" {
                      description
                        "Enter port number";
                    }
                  }
                  description
                    "Enter port number";
                }
                uses OPTIONS;
              }
              list ipv6-address {
                key "ipv6-address port";
                description
                  "Destination address";
                leaf ipv6-address {
                  type inet:ip-address-no-zone;
                  description
                    "Enter Destination IPv6 address";
                }
                leaf port {
                  type uint32 {
                    range "1..65535" {
                      description
                        "Enter port number";
                    }
                  }
                  description
                    "Enter port number";
                }
                uses OPTIONS;
              }
            }
          }
        }
      }
    }
    leaf tls-trustpoint {
      type xr:Cisco-ios-xr-string {
        length "1..1024" {
          description
            "trustpoint name";
        }
      }
      description
        "DEPRECATED. Removing in 26.3.1: Configure trustpoint";
    }
    leaf dscp {
      type union {
        type uint32 {
          range "0..63" {
            description
              "DEPRECATED. Removing in 26.3.1: Differentiated services code point";
          }
        }
        type enumeration {
          enum "af11" {
            value 10;
            description
              "DEPRECATED. Removing in 26.3.1: AF11 (DSCP 001010)";
          }
          enum "af12" {
            value 12;
            description
              "DEPRECATED. Removing in 26.3.1: AF12 (DSCP 001100)";
          }
          enum "af13" {
            value 14;
            description
              "DEPRECATED. Removing in 26.3.1: AF13 (DSCP 001110)";
          }
          enum "af21" {
            value 18;
            description
              "DEPRECATED. Removing in 26.3.1: AF21 (DSCP 010010)";
          }
          enum "af22" {
            value 20;
            description
              "DEPRECATED. Removing in 26.3.1: AF22 (DSCP 010100)";
          }
          enum "af23" {
            value 22;
            description
              "DEPRECATED. Removing in 26.3.1: AF23 (DSCP 010110)";
          }
          enum "af31" {
            value 26;
            description
              "DEPRECATED. Removing in 26.3.1: AF31 (DSCP 011010)";
          }
          enum "af32" {
            value 28;
            description
              "DEPRECATED. Removing in 26.3.1: AF32 (DSCP 011100)";
          }
          enum "af33" {
            value 30;
            description
              "DEPRECATED. Removing in 26.3.1: AF33 (DSCP 011110)";
          }
          enum "af41" {
            value 34;
            description
              "DEPRECATED. Removing in 26.3.1: AF41 (DSCP 100010)";
          }
          enum "af42" {
            value 36;
            description
              "DEPRECATED. Removing in 26.3.1: AF42 (DSCP 100100)";
          }
          enum "af43" {
            value 38;
            description
              "DEPRECATED. Removing in 26.3.1: AF43 (DSCP 100110)";
          }
          enum "cs1" {
            value 8;
            description
              "DEPRECATED. Removing in 26.3.1: CS1 (Precedence 1) (DSCP 001000)";
          }
          enum "cs2" {
            value 16;
            description
              "DEPRECATED. Removing in 26.3.1: CS2 (Precedence 2) (DSCP 010000)";
          }
          enum "cs3" {
            value 24;
            description
              "DEPRECATED. Removing in 26.3.1: CS3 (Precedence 3) (DSCP 011000)";
          }
          enum "cs4" {
            value 32;
            description
              "DEPRECATED. Removing in 26.3.1: CS4 (Precedence 4) (DSCP 100000)";
          }
          enum "cs5" {
            value 40;
            description
              "DEPRECATED. Removing in 26.3.1: CS5 (Precedence 5) (DSCP 101000)";
          }
          enum "cs6" {
            value 48;
            description
              "DEPRECATED. Removing in 26.3.1: CS6 (Precedence 6) (DSCP 110000)";
          }
          enum "cs7" {
            value 56;
            description
              "DEPRECATED. Removing in 26.3.1: CS7 (Precedence 7) (DSCP 111000)";
          }
          enum "default" {
            value 0;
            description
              "DEPRECATED. Removing in 26.3.1: Default (DSCP 000000)";
          }
          enum "ef" {
            value 46;
            description
              "DEPRECATED. Removing in 26.3.1: EF (DSCP 101110)";
          }
        }
      }
      description
        "DEPRECATED. Removing in 26.3.1: QoS marking DSCP to be set on transmitted gRPC";
    }
    container listen-addresses {
      description
        "DEPRECATED. Removing in 26.3.1: gRPC server listening addresses";
      choice LISTEN-ADDRESSES {
        description
          "DEPRECATED. Removing in 26.3.1: gRPC server listening addresses";
        case LISTEN-ADDRESS {
          container listen-address {
            presence "DEPRECATED. Removing in 26.3.1: Listen address";
            description
              "DEPRECATED. Removing in 26.3.1: Listen address";
            leaf-list address {
              type inet:ip-address-no-zone;
              max-elements "31";
              description
                "DEPRECATED. Removing in 26.3.1: Listen address";
            }
          }
        }
        case ANY {
          leaf any {
            type empty;
            description
              "DEPRECATED. Removing in 26.3.1: Listen on all addresses";
          }
        }
      }
    }
    container tunnel {
      description
        "grpc tunnel service";
      container destinations {
        description
          "gRPC tunnel destination";
        list destination {
          key "grpc-tunnel-destination port-number";
          description
            "DEPRECATED. Removing in 26.3.1: gRPC tunnel destination";
          leaf grpc-tunnel-destination {
            type xr:Cisco-ios-xr-string {
              length "1..1024" {
                description
                  "IPv4/IPv6 address or domain name";
              }
            }
            description
              "gRPC tunnel destination";
          }
          leaf port-number {
            type uint32 {
              range "1..65535" {
                description
                  "Port number";
              }
            }
            description
              "DEPRECATED. Removing in 26.3.1: Destination port";
          }
          leaf vrf {
            type xr:Cisco-ios-xr-string {
              length "1..1024" {
                description
                  "VRF name";
              }
            }
            description
              "VRF for the dial-out";
          }
          leaf source-interface {
            type xr:Interface-name;
            description
              "Source interface";
          }
          leaf target {
            type xr:Cisco-ios-xr-string {
              length "1..1024" {
                description
                  "Target name";
              }
            }
            description
              "Target name to register tunnel service";
          }
          leaf address-family {
            type enumeration {
              enum "ipv4" {
                value 1;
                description
                  "IPv4";
              }
              enum "ipv6" {
                value 2;
                description
                  "IPv6";
              }
            }
            description
              "Specify the AF for the returned addresses from DNS. Only applicable to domain name.";
          }
          container source {
            description
              "Virtual IP address family";
            container ipv6 {
              description
                "IPv6 address family";
              container virtual {
                description
                  "Virtual address";
                leaf address {
                  type empty;
                  description
                    "Virtual address";
                }
              }
            }
            container ipv4 {
              description
                "IPv4 address family";
              container virtual {
                description
                  "Virtual address";
                leaf address {
                  type empty;
                  description
                    "Virtual address";
                }
              }
            }
          }
        }
      }
    }
    container tls-cipher {
      description
        "DEPRECATED. Removing in 26.3.1: gRPC TLS 1.0-1.2 cipher suites";
      leaf enable {
        type string {
          length "1..1024" {
            description
              "DEPRECATED. Removing in 26.3.1: List of comma separated ciphers";
          }
        }
        description
          "DEPRECATED. Removing in 26.3.1: Enable ciphers if 'default disable'";
      }
      leaf default {
        type enumeration {
          enum "enable" {
            value 2;
            description
              "DEPRECATED. Removing in 26.3.1: Enable all ciphers";
          }
          enum "disable" {
            value 1;
            description
              "DEPRECATED. Removing in 26.3.1: Disable all ciphers";
          }
        }
        description
          "DEPRECATED. Removing in 26.3.1: Default of all ciphers";
      }
      leaf disable {
        type string {
          length "1..1024" {
            description
              "DEPRECATED. Removing in 26.3.1: List of comma separated ciphers";
          }
        }
        description
          "DEPRECATED. Removing in 26.3.1: Disable ciphers if 'default enable'";
      }
    }
    leaf no-tls {
      type empty;
      description
        "DEPRECATED. Removing in 26.3.1: No TLS";
    }
    container gribi {
      presence "gRIBI service configuration";
      description
        "gRIBI service configuration";
      leaf port {
        type uint32 {
          range "1024..65535" {
            description
              "gRIBI service port, values: 9340,1024-65535; default: 9340";
          }
        }
        description
          "gRIBI service listening port";
      }
    }
    container p4rt {
      presence "gRPC p4 runtime configuration";
      description
        "gRPC p4 runtime configuration";
      leaf port {
        type uint32 {
          range "1024..65535" {
            description
              "p4 runtime service port, values: 9559,1024-65535; default: 9559";
          }
        }
        description
          "p4 runtime service listening port";
      }
      container interfaces {
        description
          "Configure p4rt interface attributes";
        list interface {
          key "interface-name";
          description
            "Interface to configure";
          leaf interface-name {
            type xr:Interface-name;
            description
              "Interface to configure";
          }
          leaf port-id {
            type uint32 {
              range "1..4294967039" {
                description
                  "Port identifier as a decimal value";
              }
            }
            description
              "Configure p4rt port identifier";
          }
        }
      }
      container locations {
        description
          "NPU location";
        list location {
          key "npu-location npu-id";
          description
            "NPU location";
          leaf npu-location {
            type xr:Node-id;
            description
              "NPU location";
          }
          leaf npu-id {
            type uint32 {
              range "0..7" {
                description
                  "NPU id";
              }
            }
            description
              "NPU id";
          }
          leaf device-id {
            type uint64 {
              range "1..18446744073709551615" {
                description
                  "Device identifier as a decimal value";
              }
            }
            mandatory true;
            description
              "Configure p4rt device identifier";
          }
        }
      }
    }
    container gnsi {
      description
        "gNSI";
      container service {
        description
          "gNSI service-level configuration";
        container certz {
          description
            "gNSI certificate management";
          leaf ssl-profile-id {
            type xr:Cisco-ios-xr-string {
              length "1..256" {
                description
                  "SSL profile name";
              }
            }
            description
              "DEPRECATED. Removing in 26.3.1: SSL profile to be consumed by gRPC server";
          }
        }
      }
    }
    container gnpsi {
      presence "gNPSI service configuration";
      description
        "gNPSI service configuration";
      container stream {
        description
          "gNPSI stream configuration";
        container queue {
          description
            "gNPSI stream queue configuration";
          leaf size {
            type uint32 {
              range "1..8000" {
                description
                  "gNPSI stream queue size (default 4000)";
              }
            }
            description
              "Configure gNPSI stream queue size";
          }
        }
      }
    }
    container gnmi {
      presence "gNMI service configuration";
      description
        "gNMI service configuration";
      leaf port {
        type uint32 {
          range "1024..65535" {
            description
              "gNMI service port, values: 9339,1024-65535; default: 9339";
          }
        }
        description
          "gNMI service listening port";
      }
      leaf get-limit-multiple {
        type uint32 {
          range "1..20" {
            description
              "gNMI service get-limit-multiple; default: 1";
          }
        }
        description
          "gNMI get request max size-limit multiplier, to support larger get results";
      }
    }
  }
}
