module Cisco-IOS-XR-controller-ncs1001-ots-och-oper {
  namespace "http://cisco.com/ns/yang/Cisco-IOS-XR-controller-ncs1001-ots-och-oper";
  prefix controller-ncs1001-ots-och-oper;

  import Cisco-IOS-XR-types {
    prefix xr;
  }
  import cisco-semver {
    prefix semver;
  }
  include Cisco-IOS-XR-controller-ncs1001-ots-och-oper-sub1 {
    revision-date 2024-10-15;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR controller-ncs1001-ots-och package operational data.
     
     This module contains definitions
     for the following management objects:
       ots-och-oper: OTS-OCH operational data
     
     Copyright (c) 2013-2024 by Cisco Systems, Inc.
     All rights reserved.";

  revision 2024-10-15 {
    description
      "Added last link flap field";
    semver:module-version "1.0.0";
  }
  revision 2022-11-24 {
    description
      "leaves receive-power, transmit-power are removed and receive-power-dbm, transmit-power-dbm are modified to receive-power, transmit-power in OTS-EDM-LANE-DATA group";
  }
  revision 2019-04-05 {
    description
      "Establish semantic version baseline.";
  }
  revision 2015-11-09 {
    description
      "IOS XR 6.0 revision.";
  }

  container ots-och-oper {
    config false;
    description
      "OTS-OCH operational data";
    container ots-och-ports {
      description
        "Port operational data for all OTS-OCH
         controllers";
      list ots-och-port {
        key "name";
        description
          "OTS-OCH controller operational data";
        container ots-och-info {
          description
            "OTS-OCH operational data";
          uses OTS-OCH-EDM-INFO;
        }
        leaf name {
          type xr:Interface-name;
          description
            "Port name";
        }
      }
    }
  }
}
