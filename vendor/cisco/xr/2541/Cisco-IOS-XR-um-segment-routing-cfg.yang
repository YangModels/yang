module Cisco-IOS-XR-um-segment-routing-cfg {
  namespace "http://cisco.com/ns/yang/Cisco-IOS-XR-um-segment-routing-cfg";
  prefix um-segment-routing-cfg;

  import ietf-inet-types {
    prefix inet;
  }
  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco segment-routing package configuration.
     Copyright (c) 2025 by Cisco Systems, Inc., and/or its affiliates.
     All rights reserved.";

  revision 2025-07-22 {
    description
      "Fixed canonical ordering.
       2025-03-06
         Initial UM2 release
       2022-05-31
         Model Deprecated";
    semver:module-version "2.0.0";
  }
  revision 2021-05-10 {
    description
      "Initial release";
    semver:module-version "1.0.0";
  }

  container segment-routing {
    presence "Segment Routing";
    status deprecated;
    description
      "Segment Routing";
    container mapping-server {
      description
        "Segment Routing Mapping Server (SRMS)";
      container prefix-sid-map {
        description
          "Prefix SID Map";
        container address-families {
          description
            "Address Family";
          list address-family {
            key "af-name";
            description
              "Address Family";
            leaf af-name {
              type enumeration {
                enum "ipv4" {
                  value 1;
                  description
                    "IP version 4";
                }
                enum "ipv6" {
                  value 2;
                  description
                    "IP version 6";
                }
              }
              description
                "Address Family";
            }
            container addresses {
              description
                "IPaddress";
              list address {
                key "ip-address prefix";
                description
                  "IPaddress";
                leaf ip-address {
                  type inet:ip-address-no-zone;
                  description
                    "IPaddress";
                }
                leaf prefix {
                  type uint32 {
                    range "0..128";
                  }
                  description
                    "IP address prefix";
                }
                leaf start-sid-index-range {
                  type uint32 {
                    range "0..1048575" {
                      description
                        "Start of SID index range";
                    }
                  }
                  mandatory true;
                  description
                    "Start of SID index range";
                }
                leaf range {
                  type uint32 {
                    range "0..65535" {
                      description
                        "Number of allocated SIDs";
                    }
                  }
                  description
                    "Number of allocated SIDs";
                }
                leaf attached {
                  type empty;
                  description
                    "Attached entry advertised via the A-flag";
                }
              }
            }
          }
        }
      }
    }
    container adjacency-sid {
      description
        "Segment Routing (MPLS) Adjacency SID";
      container interfaces {
        description
          "Interface Instance";
        list interface {
          key "interface-name";
          description
            "Interface Instance";
          leaf interface-name {
            type xr:Interface-name;
            description
              "Interface";
          }
          container address-families {
            description
              "Address Family";
            list address-family {
              must "unicast";
              key "af-name";
              description
                "Address Family";
              leaf af-name {
                type enumeration {
                  enum "ipv4" {
                    value 1;
                    description
                      "IP version 4";
                  }
                  enum "ipv6" {
                    value 2;
                    description
                      "IP version 6 link-local address";
                  }
                }
                description
                  "Address Family";
              }
              container unicast {
                description
                  "Unicast Address Family";
                container l2-adjacency-sid-ipv6 {
                  when "../../af-name = 'ipv6'";
                  must "index or absolute";
                  presence "L2 Adjacency SID";
                  description
                    "L2 Adjacency SID";
                  choice L2-ADJACENCY-SID {
                    description
                      "L2 Adjacency SID";
                    case INDEX {
                      leaf index {
                        type uint32 {
                          range "0..1048575" {
                            description
                              "L2 Adjacency SID value";
                          }
                        }
                        description
                          "L2 Adjacency SID value";
                      }
                    }
                    case ABSOLUTE {
                      leaf absolute {
                        type uint32 {
                          range "15000..1048575" {
                            description
                              "L2 Adjacency SID value";
                          }
                        }
                        description
                          "L2 Adjacency SID value";
                      }
                    }
                  }
                }
                container l2-adjacency-sid-ipv4 {
                  when "../../af-name = 'ipv4'";
                  must "index or absolute";
                  presence "L2 Adjacency SID";
                  description
                    "L2 Adjacency SID";
                  choice L2-ADJACENCY-SID {
                    description
                      "L2 Adjacency SID";
                    case INDEX {
                      leaf index {
                        type uint32 {
                          range "0..1048575" {
                            description
                              "L2 Adjacency SID value";
                          }
                        }
                        description
                          "L2 Adjacency SID value";
                      }
                    }
                    case ABSOLUTE {
                      leaf absolute {
                        type uint32 {
                          range "15000..1048575" {
                            description
                              "L2 Adjacency SID value";
                          }
                        }
                        description
                          "L2 Adjacency SID value";
                      }
                    }
                  }
                }
                container l2-adjacency-sid-next-hop {
                  description
                    "L2 Adjacency SID";
                  container next-hops {
                    description
                      "Neighbor Address";
                    list next-hop {
                      must "index or absolute";
                      key "ip-address";
                      description
                        "Neighbor Address";
                      leaf ip-address {
                        type inet:ip-address-no-zone;
                        description
                          "IPaddress";
                      }
                      choice NEXT-HOP {
                        description
                          "L2 Adjacency SID";
                        case INDEX {
                          leaf index {
                            type uint32 {
                              range "0..1048575" {
                                description
                                  "L2 Adjacency SID value";
                              }
                            }
                            description
                              "L2 Adjacency SID value";
                          }
                        }
                        case ABSOLUTE {
                          leaf absolute {
                            type uint32 {
                              range "15000..1048575" {
                                description
                                  "L2 Adjacency SID value";
                              }
                            }
                            description
                              "L2 Adjacency SID value";
                          }
                        }
                      }
                    }
                  }
                }
              }
            }
          }
        }
      }
    }
    container local-block {
      description
        "Local Block (SRLB) of labels";
      leaf local-block-lower-bound {
        type uint32 {
          range "15000..1048575" {
            description
              "The lower bound of SRLB";
          }
        }
        must "../local-block-upper-bound";
        description
          "The lower bound of SRLB";
      }
      leaf local-block-upper-bound {
        type uint32 {
          range "7..1048575" {
            description
              "The upper bound of SRLB (block size may not exceed 262143)";
          }
        }
        must "../local-block-lower-bound";
        description
          "The upper bound of SRLB (block size may not exceed 262143)";
      }
    }
    container global-block {
      description
        "Prefix-SID Global label Block (SRGB)";
      container indices {
        description
          "Index that represents the order in which global blocks are used";
        list index {
          key "index-value";
          description
            "Index that represents the order in which global blocks are used";
          leaf index-value {
            type uint32 {
              range "1..7" {
                description
                  "Index value";
              }
            }
            description
              "Index value";
          }
          leaf index-lower-bound {
            type uint32 {
              range "16000..1048575" {
                description
                  "The lower bound of SRGB";
              }
            }
            mandatory true;
            description
              "The lower bound of SRGB";
          }
          leaf index-upper-bound {
            type uint32 {
              range "7..1048575" {
                description
                  "The upper bound of SRGB";
              }
            }
            mandatory true;
            description
              "The upper bound of SRGB";
          }
        }
      }
      container global-block-range {
        description
          "Prefix-SID Global label Block (SRGB)";
        leaf global-block-lower-bound {
          type uint32 {
            range "16000..1048575" {
              description
                "The lower bound of SRGB";
            }
          }
          must "../global-block-upper-bound";
          description
            "The lower bound of SRGB";
        }
        leaf global-block-upper-bound {
          type uint32 {
            range "7..1048575" {
              description
                "The upper bound of SRGB";
            }
          }
          must "../global-block-lower-bound";
          description
            "The upper bound of SRGB";
        }
      }
    }
  }
}
