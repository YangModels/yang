module Cisco-IOS-XR-openconfig-transport-line-common-ext {
  namespace "http://cisco.com/ns/yang/Cisco-IOS-XR-openconfig-transport-line-common-ext";
  prefix oc-line-com-ext;

  import openconfig-platform {
    prefix oc-platform;
  }
  import openconfig-transport-line-common {
    prefix oc-line-com;
  }
  import openconfig-yang-types {
    prefix oc-yang;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module is an extension of optical transport line common model
     and contains the definition of extended parameters for transport line
     common to configure the rx and tx thresholds of optics
     
     This module contains definitions for the following management objects:
     General Parameters
     Submarine Parameters
     
     Copyright (c) 2025 by Cisco Systems, Inc.
     All rights reserved.";

  revision 2025-09-22 {
    description
      "Added support for OSC regulation configuration and operational";
    reference "26.1.1";
  }
  revision 2025-06-25 {
    description
      "Added support for channel control and management.";
    reference "25.4.1";
  }
  revision 2025-03-25 {
    description
      "IOS XR 6.0 revision";
    reference "7.3.1";
  }

  grouping thresholds-config {
    description
      "Configuration data for a thresholds";
    leaf input-signal-power-lower {
      type decimal64 {
        fraction-digits 2;
      }
      units "0.01dBm";
      description
        "Lower power threshold for laser input power
         in unit of 0.01dBm";
    }
    leaf input-signal-power-upper {
      type decimal64 {
        fraction-digits 2;
      }
      units "0.01dBm";
      description
        "Upper power threshold for laser input power
         in unit of 0.01dBm";
    }
    leaf output-signal-power-lower {
      type decimal64 {
        fraction-digits 2;
      }
      units "0.01dBm";
      description
        "Lower power threshold for laser output power
         in unit of 0.01dBm";
    }
    leaf output-signal-power-upper {
      type decimal64 {
        fraction-digits 2;
      }
      units "0.01dBm";
      description
        "Upper power threshold for laser output power
         in unit of 0.01dBm";
    }
    leaf input-channel-power-delta-lower {
      type decimal64 {
        fraction-digits 2;
      }
      units "dB";
      description
        "Channel recieve power low threshold
         in unit of dB";
    }
    leaf input-channel-power-delta-upper {
      type decimal64 {
        fraction-digits 2;
      }
      units "dB";
      description
        "Channel recieve power high threshold
         in unit of dB";
    }
    leaf rx-expected-span-loss {
      type decimal64 {
        fraction-digits 2;
      }
      units "dB";
      description
        "Expected Span loss in unit of dB";
    }
    leaf rx-span-loss-deg-rel-thr {
      type decimal64 {
        fraction-digits 2;
      }
      units "dB";
      description
        "Signal Rx span loss Degrade Rel threshold
         in unit of dB";
    }
    leaf rx-span-loss-fail-rel-thr {
      type decimal64 {
        fraction-digits 2;
      }
      units "dB";
      description
        "Signal Rx span loss Fail Rel threshold
         in unit of dB";
    }
  }

  grouping thresholds-state {
    description
      "State data for a thresholds";
  }

  grouping channel-control-config {
    description
      "Configuration data for Channel Startup Management";
    leaf channel-minimum-input-psd {
      type decimal64 {
        fraction-digits 2;
      }
      units "dBm";
      description
        "Channel minimum input PSD in
         in unit of dBm per 12.5 GHz";
    }
    leaf input-power-total-expected {
      type decimal64 {
        fraction-digits 2;
      }
      units "dBm";
      description
        "Channel expected total input power in
         unit of dBm";
    }
  }

  grouping channel-control-state {
    description
      "State data for Channel Startup Management";
  }

  grouping osc-regulation-config {
    description
      "Configuration data for OSC Regulation Management";
    leaf span-mode {
      type boolean;
      description
        "OSC regulation span mode configuration";
    }
    leaf span-pause {
      type boolean;
      description
        "OSC regulation span pause configuration";
    }
  }

  grouping osc-regulation-state {
    description
      "Operational data for OSC Regulation Management";
    leaf status {
      type enumeration {
        enum "BLOCKED" {
          description
            "OSC regulation is blocked";
        }
        enum "IDLE" {
          description
            "OSC regulation is idle";
        }
        enum "REGULATING" {
          description
            "OSC regulation is regulating";
        }
        enum "PAUSED" {
          description
            "OSC regulation is paused";
        }
        enum "DISABLED" {
          description
            "OSC regulation is disabled";
        }
      }
      description
        "Current operational mode that triggered OSC regulation.";
    }
    leaf blocking-reason {
      type string;
      description
        "Free-form reason string explaining why regulation is currently blocked or paused (empty if not blocked).";
    }
    leaf last-span-loss-input {
      type decimal64 {
        fraction-digits 2;
      }
      units "dB";
      description
        "Most recent measured span loss at the input (dB).";
    }
    leaf last-span-loss-input-time {
      type oc-yang:date-and-time;
      description
        "Timestamp of last span loss input measurement.";
    }
    leaf last-correction-time {
      type oc-yang:date-and-time;
      description
        "Timestamp of the last applied OSC regulation correction.";
    }
  }

  grouping span-loss-state {
    description
      "Operational data for Spanloss Management";
    leaf rx-signal-span-loss {
      type decimal64 {
        fraction-digits 2;
      }
      units "dB";
      description
        "Signal Span loss in unit of dB";
    }
    leaf rx-calibration-baseline-span-loss {
      type decimal64 {
        fraction-digits 2;
      }
      units "dB";
      description
        "Calibration Span loss in unit of dB";
    }
  }

  grouping oc-line-extended-threshold {
    description
      "Extended transport line common parameters";
    container cisco {
      description
        "Extended transport line common parameters";
      container thresholds {
        description
          "Enclosing container for alarm thresholds.";
        container config {
          description
            "Extended Thresholds Configuration parameters";
          uses thresholds-config;
        }
        container state {
          config false;
          description
            "Extended Thresholds Operational parameters";
          uses thresholds-config;
          uses thresholds-state;
        }
      }
      container channel-control {
        description
          "Enclosing container for Channel Startup Management parameters.";
        container config {
          description
            "Extended Channel Startup Management Configuration parameters";
          uses channel-control-config;
        }
        container state {
          config false;
          description
            "Extended Channel Startup Management Operational parameters";
          uses channel-control-config;
          uses channel-control-state;
        }
      }
      container osc-regulation {
        description
          "Enclosing container for OSC Regulation Management parameters.";
        container config {
          description
            "Extended OSC Regulation Configuration parameters";
          uses osc-regulation-config;
        }
        container state {
          config false;
          description
            "Extended OSC Regulation Operational parameters";
          uses osc-regulation-config;
          uses osc-regulation-state;
        }
      }
      container span-loss {
        description
          "Enclosing container for Spanloss Management parameters.";
        container state {
          config false;
          description
            "Extended Spanloss Operational parameters";
          uses span-loss-state;
        }
      }
    }
  }

  augment "/oc-platform:components/oc-platform:component/oc-platform:port/oc-line-com:optical-port" {
    description
      "This augment extends the configuration data of oc-line-com";
    uses oc-line-extended-threshold;
  }
}
