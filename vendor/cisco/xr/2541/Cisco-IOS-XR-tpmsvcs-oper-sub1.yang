submodule Cisco-IOS-XR-tpmsvcs-oper-sub1 {
  belongs-to Cisco-IOS-XR-tpmsvcs-oper {
    prefix Cisco-IOS-XR-tpmsvcs-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR tpmsvcs package operational data.
     
     Copyright (c) 2013-2025 by Cisco Systems, Inc.
     All rights reserved.";

  revision 2025-02-20 {
    description
      "Show device info for tpm";
    semver:module-version "1.0.0";
  }
  revision 2019-04-05 {
    description
      "Establish semantic version baseline.";
  }
  revision 2015-11-09 {
    description
      "IOS XR 6.0 revision.";
  }

  grouping TAMSVCS-HA-SUDI-CERTS {
    description
      "Tam/Tpm Ha Sudi certs bag";
    leaf ha-sudi-root-cert {
      type string;
      description
        "HA Sudi Root Certificate";
    }
    leaf ha-sudi-subca-cert {
      type string;
      description
        "HA Sudi SubCA Certificate";
    }
    leaf ha-sudi-cert {
      type string;
      description
        "HA Sudi Certificate of Tam/Tpm Device";
    }
  }

  grouping TAMSVCS-DEVICE-INFO {
    description
      "Tam/Tpm device info bag";
    container firmware-status {
      description
        "Tam firmware status";
      uses TAMSVCS-FIRMWARE-STATUS;
    }
    leaf device-type {
      type string;
      description
        "Type of Tam/Tpm Device";
    }
    leaf device-pid {
      type string;
      description
        "Pid of Tam/Tpm Device";
    }
    leaf device-serial {
      type string;
      description
        "Serial Number of Tam/Tpm Device";
    }
    leaf device-firware-version {
      type string;
      description
        "Firmware version of the device";
    }
    leaf server-version {
      type string;
      description
        "Tam/Tpm Server Version";
    }
    leaf server-package-version {
      type string;
      description
        "Tam/Tpm Services Server Package Version";
    }
    leaf client-package-version {
      type string;
      description
        "Tam/Tpm Services Client Package Version";
    }
  }

  grouping TAMSVCS-FIRMWARE-STATUS {
    description
      "Tam firmware status";
    leaf crc-supported {
      type boolean;
      description
        "Firmware CRC supported";
    }
    leaf crc {
      type uint32;
      description
        "Firmware CRC";
    }
    leaf restore-status-supported {
      type boolean;
      description
        "Firmware restore status supported";
    }
    leaf restore-status {
      type uint32;
      description
        "Firmware restore status";
    }
  }

  grouping TAMSVCS-INFO-ALL {
    description
      "Tam All info bag";
    container firmware-status {
      description
        "Tam firmware status";
      uses TAMSVCS-FIRMWARE-STATUS;
    }
    leaf device-type {
      type string;
      description
        "Type of Tam/Tpm Device";
    }
    leaf device-pid {
      type string;
      description
        "Pid of Tam/Tpm Device";
    }
    leaf device-serial {
      type string;
      description
        "Serial Number of Tam/Tpm Device";
    }
    leaf device-firware-version {
      type string;
      description
        "Firmware version of the device";
    }
    leaf server-version {
      type string;
      description
        "Tam/Tpm Server Version";
    }
    leaf server-package-version {
      type string;
      description
        "Tam/Tpm Services Server Package Version";
    }
    leaf client-package-version {
      type string;
      description
        "Tam/Tpm Services Client Package Version";
    }
    leaf sudi-root-cert {
      type string;
      description
        "Sudi Root Certificate";
    }
    leaf sudi-subca-cert {
      type string;
      description
        "Sudi SubCA Certificate";
    }
    leaf sudi-cert {
      type string;
      description
        "Sudi Leaf Certificate";
    }
    leaf ha-sudi-root-cert {
      type string;
      description
        "HA Sudi Root Certificate";
    }
    leaf ha-sudi-subca-cert {
      type string;
      description
        "HA Sudi SubCA Certificate";
    }
    leaf ha-sudi-cert {
      type string;
      description
        "HA Sudi Leaf Certificate";
    }
  }
}
