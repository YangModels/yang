module Cisco-IOS-XR-mpls-te-act {
  namespace "http://cisco.com/ns/yang/Cisco-IOS-XR-mpls-te-act";
  prefix mpls-te-act;

  import cisco-semver {
    prefix semver;
  }
  import Cisco-IOS-XR-types {
    prefix csc;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR mpls traffic-eng action commands.
     
     Copyright (c) 2023-2025 by Cisco Systems, Inc., and/or its affiliates.
     All rights reserved.";

  revision 2025-09-05 {
    description
      "Added an RPC to clear event history of all MPLS traffic-eng headend tunnels.";
    semver:module-version "1.0.0";
  }
  revision 2023-07-06 {
    description
      "IOS XR 7.11.1 revision.";
  }
  revision 2022-02-23 {
    description
      "IOS XR 7.5.4 revision.";
  }

  rpc clear-lsp-counters-all {
    description
      "clear mpls traffic-eng signaling counters for all tunnels";
    csc:xr-task "mpls-te";
    csc:cli-command "clear mpls traffic-eng counters signaling all";
  }
  rpc clear-lsp-counters-name {
    description
      "clear mpls traffic-eng signaling counters for a tunnel with given name";
    input {
      leaf name {
        type string;
        mandatory true;
        description
          "Tunnel name";
      }
    }
    csc:xr-task "mpls-te";
    csc:cli-command "clear mpls traffic-eng counters signaling name <name>";
  }
  rpc reoptimize-lsp-all {
    description
      "Force an immediate reoptimization of all mpls traffic-eng tunnels";
    csc:xr-task "mpls-te";
    csc:cli-command "mpls traffic-eng reoptimize all";
  }
  rpc reoptimize-lsp-name {
    description
      "Force an immediate reoptimization of a tunnel with given name";
    input {
      leaf name {
        type string;
        mandatory true;
        description
          "Tunnel name";
      }
    }
    csc:xr-task "mpls-te";
    csc:cli-command "mpls traffic-eng reoptimize name <name>";
  }
  rpc resetup-lsp-all {
    description
      "Force an immediate tear down and setup of all mpls traffic-eng tunnels";
    csc:xr-task "mpls-te";
    csc:cli-command "mpls traffic-eng resetup all";
  }
  rpc resetup-lsp-name {
    description
      "Force an immediate tear down and setup a tunnel with given name";
    input {
      leaf name {
        type string;
        mandatory true;
        description
          "Tunnel name";
      }
    }
    csc:xr-task "mpls-te";
    csc:cli-command "mpls traffic-eng resetup name <name>";
  }
  rpc auto-bw-apply-all {
    description
      "Apply auto-bandwidth adjustment instantly on all mpls traffic-eng tunnels";
    csc:xr-task "mpls-te";
    csc:cli-command "mpls traffic-eng auto-bw apply all";
  }
  rpc auto-bw-apply-name {
    description
      "Apply auto-bandwidth adjustment instantly on a tunnel with given name";
    input {
      leaf name {
        type string;
        mandatory true;
        description
          "Tunnel name";
      }
    }
    csc:xr-task "mpls-te";
    csc:cli-command "mpls traffic-eng auto-bw apply name <name>";
  }
  rpc tunnel-teardown-all {
    description
      "Force an immediate tear down and setup of all mpls traffic-eng tunnels";
    csc:xr-task "mpls-te";
    csc:cli-command "mpls traffic-eng teardown all";
  }
  rpc tunnel-teardown-head {
    description
      "Force an immediate tear down and setup of mpls traffic-eng head tunnels";
    csc:xr-task "mpls-te";
    csc:cli-command "mpls traffic-eng teardown head";
  }
  rpc tunnel-teardown-mid {
    description
      "Force an immediate tear down and setup of mpls traffic-eng mid tunnels";
    csc:xr-task "mpls-te";
    csc:cli-command "mpls traffic-eng teardown mid";
  }
  rpc tunnel-teardown-tail {
    description
      "Force an immediate tear down and setup of mpls traffic-eng tail tunnels";
    csc:xr-task "mpls-te";
    csc:cli-command "mpls traffic-eng teardown tail";
  }
  rpc clear-event-history-tunnels-all {
    description
      "Clear event history of all MPLS traffic-eng headend tunnels";
    csc:xr-task "mpls-te";
    csc:cli-command "clear mpls traffic-eng event-history tunnels all";
  }
}
