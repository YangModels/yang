module Cisco-IOS-XR-um-config-mode-cfg {
  namespace "http://cisco.com/ns/yang/Cisco-IOS-XR-um-config-mode-cfg";
  prefix um-config-mode-cfg;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR config-mode package configuration.
     
     This YANG module augments the
     modules with configuration data.
     
     Copyright (c) 2021-2025 by Cisco Systems, Inc., and/or its affiliates.
     All rights reserved.";

  revision 2021-02-02 {
    description
      "Initial release";
    semver:module-version "1.0.0";
  }

  container configuration {
    description
      "Configuration mode";
    container mode {
      description
        "Mode of config sessions";
      container exclusive {
        presence "Indicates a exclusive node is configured.";
        description
          "Automatically enable exclusive config sessions";
      }
    }
  }
}
