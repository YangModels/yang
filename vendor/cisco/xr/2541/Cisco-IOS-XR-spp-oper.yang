module Cisco-IOS-XR-spp-oper {
  namespace "http://cisco.com/ns/yang/Cisco-IOS-XR-spp-oper";
  prefix spp-oper;

  import Cisco-IOS-XR-types {
    prefix xr;
  }
  import cisco-semver {
    prefix semver;
  }
  include Cisco-IOS-XR-spp-oper-sub1 {
    revision-date 2025-05-10;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR spp package operational data.
     
     This module contains definitions
     for the following management objects:
       spp: SPP operational data
     
     Copyright (c) 2013-2025 by Cisco Systems, Inc.
     All rights reserved.";

  revision 2025-05-10 {
    description
      "Introduced yang support for spp";
    semver:module-version "1.0.0";
  }
  revision 2019-04-05 {
    description
      "Establish semantic version baseline.";
  }
  revision 2015-11-09 {
    description
      "IOS XR 6.0 revision.";
  }

  container spp {
    config false;
    description
      "SPP operational data";
    container nodes {
      description
        "List of nodes for SPP operational data";
      list node {
        key "node-name";
        description
          "SPP operational data for a particular RP/LC
           node";
        container spp-node-drop-counters {
          description
            "This container provides drop counters across
             SPP nodes";
          list spp-node-drop-counter {
            key "spp-node-name";
            description
              "SPP node level drop counters";
            leaf spp-node-name {
              type string;
              description
                "Name of the spp node";
            }
            uses SPP-NODE-DROP-COUNTERS-INFO;
          }
        }
        leaf node-name {
          type xr:Node-id;
          description
            "The identifier for the node";
        }
      }
    }
  }
}
