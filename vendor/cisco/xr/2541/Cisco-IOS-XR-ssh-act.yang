module Cisco-IOS-XR-ssh-act {
  namespace "http://cisco.com/ns/yang/Cisco-IOS-XR-ssh-act";
  prefix ssh-act;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR action package configuration.
     
     Copyright (c) 2021-2025 by Cisco Systems, Inc., and/or its affiliates.
     All rights reserved.";

  revision 2025-04-24 {
    description
      "Adding action model for ssh server authorized keys";
    semver:module-version "1.1.0";
  }
  revision 2021-09-02 {
    description
      "Action model for SSH";
    semver:module-version "1.0.0";
  }

  rpc clear-ssh-session {
    description
      "clears specific incoming session based on the session id";
    input {
      leaf incoming-session-id {
        type uint32 {
          range "1..4294967295";
        }
        description
          "incoming session id";
      }
    }
  }
  rpc clear-ssh-all {
    description
      "clears all incoming SSH session";
  }
  rpc clear-ssh-outgoing-session {
    description
      "Disconnect client connection";
    input {
      leaf outgoing-session-id {
        type uint32 {
          range "1..4294967295";
        }
        description
          "outgoing session id";
      }
    }
  }
  rpc clear-ssh-stale-session {
    description
      "clear stale incoming SSH sessions";
  }
  rpc ssh-server-authorized-keys-import {
    description
      "Rotate the authorized keys for the user instead of appending new ones.";
    input {
      container key-input {
        description
          "SSH authorized keys";
        choice key-source {
          mandatory true;
          description
            "Source of SSH authorized keys";
          case key-file {
            description
              "Input SSH authorized keys through file";
            leaf filepath {
              type string;
              description
                "Path to RSA/ED25519/ECDSA pubkey file harddisk:/ or disk0:/ or tftp";
            }
          }
          case key-direct {
            description
              "Input SSH authorized keys directly";
            leaf-list authorized-keys {
              type string {
                length "1..1024";
              }
              min-elements 1;
              max-elements "3000";
              description
                "List of SSH authorized keys";
            }
          }
        }
      }
      leaf username {
        type string;
        description
          "Import SSH authorized keys for user";
      }
    }
  }
  rpc ssh-server-authorized-keys-zeroize {
    description
      "Remove authorized keys";
    input {
      leaf username {
        type string;
        description
          "Remove SSH authorized keys for user";
      }
    }
  }
  rpc ssh-server-authorized-keys-export {
    description
      "Export current pubkey file of user to /disk0:/authorized_keys_user folder";
    input {
      leaf username {
        type string;
        description
          "Export SSH authorized keys for user";
      }
    }
  }
}
