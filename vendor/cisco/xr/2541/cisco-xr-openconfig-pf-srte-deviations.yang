//*************  DO-NOT EDIT  **************
//*********** Auto-generated file ********** 

 module cisco-xr-openconfig-pf-srte-deviations {

  prefix  "oc-pf-srtedevs";

  namespace "http://cisco.com/ns/yang/cisco-xr-openconfig-pf-srte-deviations";

  import openconfig-pf-srte { prefix oc-pf-srte; }
  import openconfig-network-instance { prefix oc-ni; }

  organization "Cisco Systems, Inc.";

  contact
    "Cisco Systems, Inc.
     Customer Service

     Postal: 170 West Tasman Drive
     San Jose, CA 95134

     Tel: +1 800 553-NETS

     E-mail: cs-yang@cisco.com";

  description
    "This module contains a set of deviations for 

     openconfig-pf-srte.yang@2019-10-15 

     on Cisco IOS-XR devices.

     Copyright (c) 2017 by Cisco Systems, Inc.
     All rights reserved.";

  revision "2023-02-17" {
    description
      "Initial revision applicable to IOS-XR 6.4.1";
  }


  deviation /oc-ni:network-instances/oc-ni:network-instance/oc-ni:policy-forwarding/oc-ni:policies/oc-ni:policy/oc-ni:rules/oc-ni:rule/oc-pf-srte:srte/oc-pf-srte:config/oc-pf-srte:mpls-bsid {
    deviate not-supported;
  }

  deviation /oc-ni:network-instances/oc-ni:network-instance/oc-ni:policy-forwarding/oc-ni:policies/oc-ni:policy/oc-ni:rules/oc-ni:rule/oc-pf-srte:srte/oc-pf-srte:config/oc-pf-srte:srte-endpoint {
    deviate not-supported;
  }

  deviation /oc-ni:network-instances/oc-ni:network-instance/oc-ni:policy-forwarding/oc-ni:policies/oc-ni:policy/oc-ni:rules/oc-ni:rule/oc-pf-srte:srte/oc-pf-srte:config/oc-pf-srte:srte-color {
    deviate not-supported;
  }

  deviation /oc-ni:network-instances/oc-ni:network-instance/oc-ni:policy-forwarding/oc-ni:policies/oc-ni:policy/oc-ni:rules/oc-ni:rule/oc-pf-srte:srte/oc-pf-srte:config/oc-pf-srte:srte-preference {
    deviate not-supported;
  }

  deviation /oc-ni:network-instances/oc-ni:network-instance/oc-ni:policy-forwarding/oc-ni:policies/oc-ni:policy/oc-ni:rules/oc-ni:rule/oc-pf-srte:srte/oc-pf-srte:state/oc-pf-srte:mpls-bsid {
    deviate not-supported;
  }

  deviation /oc-ni:network-instances/oc-ni:network-instance/oc-ni:policy-forwarding/oc-ni:policies/oc-ni:policy/oc-ni:rules/oc-ni:rule/oc-pf-srte:srte/oc-pf-srte:state/oc-pf-srte:srte-endpoint {
    deviate not-supported;
  }

  deviation /oc-ni:network-instances/oc-ni:network-instance/oc-ni:policy-forwarding/oc-ni:policies/oc-ni:policy/oc-ni:rules/oc-ni:rule/oc-pf-srte:srte/oc-pf-srte:state/oc-pf-srte:srte-color {
    deviate not-supported;
  }

  deviation /oc-ni:network-instances/oc-ni:network-instance/oc-ni:policy-forwarding/oc-ni:policies/oc-ni:policy/oc-ni:rules/oc-ni:rule/oc-pf-srte:srte/oc-pf-srte:state/oc-pf-srte:srte-preference {
    deviate not-supported;
  }

  deviation /oc-ni:network-instances/oc-ni:network-instance/oc-ni:policy-forwarding/oc-ni:policies/oc-ni:policy/oc-ni:rules/oc-ni:rule/oc-ni:action/oc-pf-srte:segment-lists/oc-pf-srte:segment-list {
    deviate not-supported;
  }


}
//total deviations:9
