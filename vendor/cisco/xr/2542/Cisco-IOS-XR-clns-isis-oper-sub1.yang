submodule Cisco-IOS-XR-clns-isis-oper-sub1 {
  belongs-to Cisco-IOS-XR-clns-isis-oper {
    prefix Cisco-IOS-XR-clns-isis-oper;
  }

  import ietf-inet-types {
    prefix inet;
  }
  import ietf-yang-types {
    prefix yang;
  }
  import Cisco-IOS-XR-types {
    prefix xr;
  }
  import cisco-semver {
    prefix semver;
  }
  include Cisco-IOS-XR-clns-isis-oper-sub2 {
    revision-date 2025-09-19;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR clns-isis package operational data.
     
     Copyright (c) 2013-2025 by Cisco Systems, Inc.
     All rights reserved.";

  revision 2025-09-19 {
    description
      "Add interface-status and interface-name-xr to neibhor-summary
       2025-06-13
         Add LSP purge log
       2024-06-07
         Add list search suport for process queues
       2024-05-23
         Add list search support for instance summary
       2024-02-01
         Add ip-only support
       2023-06-23
         Add 'autoroute announce exclude segment-routing all' support
       2023-03-31
         Add uloop filtering
       2023-02-26
         Restructure isis global statistics
       2022-12-15
         Add a warning when the interface mtu is smaller than the lsp-mtu
       2022-08-12
         Add show isis database unauthenticated
       2022-07-30
         Add Flex-algo Reverse Affinity support
       2022-07-28
         Add ISIS UHP support
       2022-04-23
         add ISIS UPA support
       2022-03-04
         add ISIS process and job IDs
       2022-01-30
         add per-area, per topology statistic indexed list.
       2022-01-11
         add show isis neighbor summary statistic info.
       2021-09-03
         Show output added for IP Flex-algo.";
    semver:module-version "5.0.0";
  }
  revision 2021-07-07 {
    description
      "Add timestamp and age to isis local rib routes.";
    semver:module-version "4.1.0";
  }
  revision 2021-03-13 {
    description
      "Interface bandwidth changed from uint32_t to uint64_t
       2021-01-04
           Add private adjacency bag
       2020-11-05
           Flex-algo extension for show isis topology.
       2020-10-27
           Add a new type Isis-flex-algo-metric for flex-algo metrics and change the metric-type leaf in ISIS-SH-FLEX-ALGO-AREA to use it.
       2020-10-20
           Change in Yang tool corrected strings repair-s-rv6* to repair-srv6*, end-xsid* to end-x-sid*, and is-s-rv6 to is-srv6. Changed avg-dela-rawy to avg-delay-raw to fix misspelling via CSCvu63930. Changed SRv6 function-type to sid-behavior, uint32_t to mgmt_srv6_sid_fmt, and num-sid to num-sids for consistency and to comply with current IETF ISIS SRv6 draft via CSCvu06764.";
    semver:module-version "4.0.0";
  }
  revision 2020-05-12 {
    description
      "Added SRLG and SRLG Static
       2020-03-25
         Added operational data for new features.";
    semver:module-version "3.0.0";
  }
  revision 2019-09-25 {
    description
      "Added operational data for new features
       2019-05-14
         Conditional Advertise-prefix support
       2019-05-03
         move ocni-isis opencfg model from native model to private oper model";
    semver:module-version "2.0.0";
  }
  revision 2019-04-05 {
    description
      "Establish semantic version baseline.";
    semver:module-version "1.0.0";
  }
  revision 2019-03-28 {
    description
      "Upgrade ocni-isis to opencfg model version 0.4.2";
  }
  revision 2019-02-23 {
    description
      "Added is_srv6 flag to ISIS IPv6 route";
  }
  revision 2019-02-16 {
    description
      "Added interface link-group name";
  }
  revision 2018-10-15 {
    description
      "Add SRv6 configured locators";
  }
  revision 2018-10-04 {
    description
      "Update SRv6 locator table";
  }
  revision 2018-05-17 {
    description
      "Update opencfg isis model";
  }
  revision 2018-04-07 {
    description
      "Update SRv6 definitions to draft-filsfils-spring-srv6-network-programming-04";
  }
  revision 2018-01-24 {
    description
      "Added SRLG TILFA operation CLI.";
  }
  revision 2017-12-06 {
    description
      "Add segment-routing srv6";
  }
  revision 2017-08-08 {
    description
      "Add openconfig network instance model isis telemetry EDM function support.";
  }
  revision 2017-06-26 {
    description
      "Change identifiers to be more readable.";
  }
  revision 2017-05-01 {
    description
      "Fixing backward compatibility error in module.";
  }
  revision 2015-11-09 {
    description
      "IOS XR 6.0 revision.";
  }

  typedef Qos-pak-prio {
    type enumeration {
      enum "qos-pak-prio-unspec" {
        value 0;
        description
          "qos pak prio unspec";
      }
      enum "qos-pak-prio-normal" {
        value 1;
        description
          "qos pak prio normal";
      }
      enum "qos-pak-prio-medium" {
        value 2;
        description
          "qos pak prio medium";
      }
      enum "qos-pak-prio-high" {
        value 3;
        description
          "qos pak prio high";
      }
      enum "qos-pak-prio-crucial" {
        value 4;
        description
          "qos pak prio crucial";
      }
    }
    description
      "Qos pak prio";
  }

  typedef Isis-overload-bit-mode {
    type enumeration {
      enum "isis-overload-bit-unset" {
        value 0;
        description
          "Overload bit not set";
      }
      enum "isis-overload-bit-set" {
        value 1;
        description
          "Overload bit permanently set";
      }
      enum "isis-overload-bit-on-startup-period" {
        value 2;
        description
          "overload bit is set for a timed period when an
           area starts";
      }
      enum "isis-overload-bit-on-startup-bgp" {
        value 3;
        description
          "overload bit set until BGP has converged";
      }
    }
    description
      "Isis overload bit mode";
  }

  typedef Isis-max-metric-mode {
    type enumeration {
      enum "isis-max-metric-unset" {
        value 0;
        description
          "max metric not set";
      }
      enum "isis-max-metric-set" {
        value 1;
        description
          "max metric always set";
      }
      enum "isis-max-metric-on-startup-period" {
        value 2;
        description
          "max metric is set for a timed period when an
           area starts";
      }
      enum "isis-max-metric-on-startup-bgp" {
        value 3;
        description
          "max metric set until BGP has converged";
      }
    }
    description
      "Isis max metric mode";
  }

  typedef Isis-startup-status {
    type enumeration {
      enum "isis-startup-ssm-active" {
        description
          "Startup-state-machine controlled restart in
           progress";
      }
      enum "isis-startup-ssm-complete" {
        description
          "Startup-state-machine controlled restart
           complete";
      }
      enum "isis-startup-ssm-aborted" {
        description
          "Startup-state-machine controlled restart
           aborted";
      }
      enum "isis-startup-ssm-not-run" {
        description
          "Startup-state-machine controlled not attempted";
      }
    }
    description
      "Isis startup status";
  }

  typedef Isis-nsf-flavor {
    type enumeration {
      enum "isis-nsf-protocol-none" {
        value 0;
        description
          "NSF not configured";
      }
      enum "isis-nsf-protocol-cisco" {
        value 1;
        description
          "Internal checkpoint NSF";
      }
      enum "isis-nsf-protocol-ietf" {
        value 2;
        description
          "IETF-standard NSF";
      }
      enum "isis-nsf-protocol-nsr" {
        value 3;
        description
          "Cisco-proprietary NSR";
      }
    }
    description
      "Isis nsf flavor";
  }

  typedef Isis-sh-err-facility {
    type enumeration {
      enum "isis-facility-none" {
        description
          "Unknown facility";
      }
      enum "isis-facility-config" {
        description
          "Configuration facility";
      }
      enum "isis-facility-conman" {
        description
          "Conman non-config facility";
      }
      enum "isis-facility-spf" {
        description
          "SPF facility";
      }
      enum "isis-facility-rib" {
        description
          "RIB facility";
      }
      enum "isis-facility-sr" {
        description
          "Segment-Routing facility";
      }
      enum "isis-facility-flood-ing" {
        description
          "Flooding facility";
      }
      enum "isis-facility-adj" {
        description
          "Adjacency facility";
      }
      enum "isis-facility-lock-ing" {
        description
          "Locking facility";
      }
      enum "isis-facility-ti-min-g" {
        description
          "Timing facility";
      }
      enum "isis-facility-testing" {
        description
          "Testing facility";
      }
      enum "isis-facility-misc" {
        description
          "Miscellaneous facility";
      }
      enum "isis-num-err-facilities" {
        description
          "Number of error facilties";
      }
    }
    description
      "IS-IS Error Facilities";
  }

  typedef Isis-prot-supp {
    type uint8;
    description
      "Isis prot supp";
  }

  typedef Isis-uloop-event {
    type enumeration {
      enum "isis-u-loop-event-none" {
        description
          "Undefined microloop-avoidance event";
      }
      enum "isis-u-loop-event-link-down" {
        description
          "A link went down";
      }
      enum "isis-u-loop-event-link-up" {
        description
          "A link went up";
      }
      enum "isis-u-loop-event-ol-bit-set" {
        description
          "A router has set its overload-bit";
      }
      enum "isis-u-loop-event-ol-bit-unset" {
        description
          "A router has unset its overload-bit";
      }
      enum "isis-nr-of-u-loop-event-s" {
        description
          "Wrong microloop-avoidance event id";
      }
    }
    description
      "Isis uloop event";
  }

  typedef Isis-uloop-avoidance {
    type enumeration {
      enum "isis-u-loop-avoidance-type-none" {
        value 0;
        description
          "No MicroLoop avoidance";
      }
      enum "isis-u-loop-avoidance-type-all" {
        value 1;
        description
          "Apply MicroLoop avoidance for all prefixes";
      }
      enum "isis-u-loop-avoidance-type-protected" {
        value 2;
        description
          "Apply MicroLoop avoidance only for protected
           prefixes";
      }
      enum "isis-u-loop-avoidance-type-sr" {
        value 3;
        description
          "Segment Routing MicroLoop avoidance for All
           single-link changes";
      }
    }
    description
      "Isis uloop avoidance";
  }

  typedef Isis-metric-style {
    type enumeration {
      enum "isis-metric-style-narrow" {
        value 0;
        description
          "old-style (ISO 10589) metrics";
      }
      enum "isis-metric-style-wide" {
        value 1;
        description
          "new-style 32-bit metrics";
      }
      enum "isis-metric-style-transition" {
        value 2;
        description
          "send/accept both forms of metric";
      }
      enum "isis-metric-style-narrow-transition" {
        value 3;
        description
          "send old-style (ISO 10589) metrics but accept
           both";
      }
      enum "isis-metric-style-wide-transition" {
        value 4;
        description
          "send new-style 32-bit metrics but accept both";
      }
    }
    description
      "Isis metric style";
  }

  typedef Isis-flex-algo-metric {
    type enumeration {
      enum "isis-flex-metric-igp" {
        value 0;
        description
          "IGP metric";
      }
      enum "isis-flex-metric-min-delay" {
        value 1;
        description
          "Minimum link delay";
      }
      enum "isis-flex-metric-te" {
        value 2;
        description
          "Traffic Engineering metric";
      }
      enum "isis-flex-metric-bw" {
        value 3;
        description
          "Traffic Engineering metric";
      }
    }
    description
      "Isis flex algo metric";
  }

  typedef Isis-if-af-prefix-unknown-reason {
    type enumeration {
      enum "isis-intf-af-prefix-unknown-adv-suppressed" {
        description
          "isis intf af prefix unknown adv suppressed";
      }
      enum "isis-intf-af-prefix-unknown-global-addr-reg-error" {
        description
          "isis intf af prefix unknown global addr reg
           error";
      }
      enum "isis-intf-af-prefix-unknown-internal-error" {
        description
          "isis intf af prefix unknown internal error";
      }
    }
    description
      "Isis if af prefix unknown reason";
  }

  typedef Isis-if-af-fwd-addr-unknown-reason {
    type enumeration {
      enum "isis-intf-af-fwd-addr-unknown-cfg-passive" {
        description
          "isis intf af fwd addr unknown cfg passive";
      }
      enum "isis-intf-af-fwd-addr-unknown-static-nbr" {
        description
          "isis intf af fwd addr unknown static nbr";
      }
      enum "isis-intf-af-fwd-addr-unknown-proto-doesnt-exist" {
        description
          "isis intf af fwd addr unknown proto doesnt
           exist";
      }
      enum "isis-intf-af-fwd-addr-unknown-next-hop-reg-error" {
        description
          "isis intf af fwd addr unknown next hop reg
           error";
      }
      enum "isis-intf-af-fwd-addr-unknown-no-link-local-add" {
        description
          "isis intf af fwd addr unknown no link local add";
      }
      enum "isis-intf-af-fwd-addr-unknown-af-not-up" {
        description
          "isis intf af fwd addr unknown af not up";
      }
      enum "isis-intf-af-fwd-addr-unknown-vrf-enabled" {
        description
          "isis intf af fwd addr unknown vrf enabled";
      }
      enum "isis-intf-af-fwd-addr-unknown-internal-error" {
        description
          "isis intf af fwd addr unknown internal error";
      }
    }
    description
      "Isis if af fwd addr unknown reason";
  }

  typedef Isis-if-af-proto-down-reason {
    type enumeration {
      enum "isis-intf-af-proto-down-imd-conn-fail" {
        description
          "isis intf af proto down imd conn fail";
      }
      enum "isis-intf-af-proto-down-imd-node-doesnt-exist" {
        description
          "isis intf af proto down imd node doesnt exist";
      }
      enum "isis-intf-af-proto-down-imd-exist-reg-error" {
        description
          "isis intf af proto down imd exist reg error";
      }
      enum "isis-intf-af-proto-down-imd-state-reg-error" {
        description
          "isis intf af proto down imd state reg error";
      }
      enum "isis-intf-af-proto-down-af-not-up" {
        description
          "isis intf af proto down af not up";
      }
      enum "isis-intf-af-proto-down-internal-error" {
        description
          "isis intf af proto down internal error";
      }
    }
    description
      "Isis if af proto down reason";
  }

  typedef Isis-if-af-disabled-reason {
    type enumeration {
      enum "isis-intf-af-disabled-no-topo-enabled" {
        description
          "isis intf af disabled no topo enabled";
      }
      enum "isis-intf-af-disabled-internal-error" {
        description
          "isis intf af disabled internal error";
      }
    }
    description
      "Isis if af disabled reason";
  }

  typedef Isis-frr-tiebreaker {
    type enumeration {
      enum "isis-frr-tiebreaker-down-stream" {
        value 0;
        description
          "Backup path is via downstream node";
      }
      enum "isis-frr-tiebreaker-lc-disjoint" {
        value 1;
        description
          "Backup path is line card disjoint";
      }
      enum "isis-frr-tiebreaker-low-est-backup-metric" {
        value 2;
        description
          "Backup path has lowest metric";
      }
      enum "isis-frr-tiebreaker-node-protecting" {
        value 3;
        description
          "Backup path is node protecting";
      }
      enum "isis-frr-tiebreaker-primary-path" {
        value 4;
        description
          "Backup path is ECMP";
      }
      enum "isis-frr-tiebreaker-secondary-path" {
        value 5;
        description
          "Backup path is not an ECMP";
      }
      enum "isis-frr-tiebreaker-srlg-disjoint" {
        value 6;
        description
          "Backup path is SRLG disjoint";
      }
      enum "isis-frr-tiebreaker-default" {
        value 7;
        description
          "Backup path is link protecting";
      }
    }
    description
      "Isis frr tiebreaker";
  }

  typedef Isis-frr {
    type enumeration {
      enum "isis-frr-type-none" {
        value 0;
        description
          "Computation disabled";
      }
      enum "isis-frr-type-per-link" {
        value 1;
        description
          "Prefix independent per-link computation";
      }
      enum "isis-frr-type-per-prefix" {
        value 2;
        description
          "Prefix dependent computation";
      }
      enum "isis-frr-type-sr-u-loop" {
        value 3;
        description
          "Segment Routing Microloop Avoidance computation";
      }
    }
    description
      "Isis frr";
  }

  typedef Isis-if-topo-adv-prefix-disabled-reason {
    type enumeration {
      enum "isis-intf-topo-adv-prefix-disabled-intf-suppressed" {
        description
          "isis intf topo adv prefix disabled intf
           suppressed";
      }
      enum "isis-intf-topo-adv-prefix-disabled-af-not-up" {
        description
          "isis intf topo adv prefix disabled af not up";
      }
      enum "isis-intf-topo-adv-prefix-disabled-af-prefixes-unknown" {
        description
          "isis intf topo adv prefix disabled af prefixes
           unknown";
      }
      enum "isis-intf-topo-adv-prefix-disabled-internal-error" {
        description
          "isis intf topo adv prefix disabled internal
           error";
      }
    }
    description
      "Isis if topo adv prefix disabled reason";
  }

  typedef Isis-if-topo-adj-form-disabled-reason {
    type enumeration {
      enum "isis-intf-topo-adj-form-disabled-intf-passive" {
        description
          "isis intf topo adj form disabled intf passive";
      }
      enum "isis-intf-topo-adj-form-disabled-static-nbr" {
        description
          "isis intf topo adj form disabled static nbr";
      }
      enum "isis-intf-topo-adj-form-disabled-af-not-up" {
        description
          "isis intf topo adj form disabled af not up";
      }
      enum "isis-intf-topo-adj-form-disabled-af-fwd-addr-unknown" {
        description
          "isis intf topo adj form disabled af fwd addr
           unknown";
      }
      enum "isis-intf-topo-adj-form-disabled-topo-not-cfg" {
        description
          "isis intf topo adj form disabled topo not cfg";
      }
      enum "isis-intf-topo-adj-form-disabled-topo-can-not-participate" {
        description
          "isis intf topo adj form disabled topo can not
           participate";
      }
      enum "isis-intf-topo-adj-form-disabled-idle" {
        description
          "isis intf topo adj form disabled idle";
      }
      enum "isis-intf-topo-adj-form-disabled-internal-error" {
        description
          "isis intf topo adj form disabled internal error";
      }
      enum "isis-intf-topo-adj-form-disabled-mtu" {
        description
          "isis intf topo adj form disabled mtu";
      }
      enum "isis-intf-topo-adj-form-disabled-snpa" {
        description
          "isis intf topo adj form disabled snpa";
      }
      enum "isis-intf-topo-adj-form-disabled-mcast" {
        description
          "isis intf topo adj form disabled mcast";
      }
    }
    description
      "Isis if topo adj form disabled reason";
  }

  typedef Isis-if-topo-disabled-reason {
    type enumeration {
      enum "isis-intf-topo-disabled-not-cfg" {
        description
          "isis intf topo disabled not cfg";
      }
      enum "isis-intf-topo-disabled-internal-error" {
        description
          "isis intf topo disabled internal error";
      }
    }
    description
      "Isis if topo disabled reason";
  }

  typedef Isis-circuit-id {
    type yang:hex-string;
    description
      "Isis circuit id";
  }

  typedef Isis-sh-pdu-rejection-reason {
    type enumeration {
      enum "isis-pdu-not-rejected" {
        description
          "Not Rejected";
      }
      enum "isis-pdu-rejected-oom" {
        description
          "Out of Memory";
      }
      enum "isis-pdu-rejected-internal-error" {
        description
          "Internal error";
      }
      enum "isis-pdu-rejected-cant-get-buffer" {
        description
          "Can't get buffer for incoming PDU";
      }
      enum "isis-pdu-rejected-cant-find-mac-head-er" {
        description
          "Can't find layer-2 header in frame";
      }
      enum "isis-pdu-rejected-cant-read-mac-head-er" {
        description
          "Can't read layer-2 header in frame";
      }
      enum "isis-pdu-rejected-nsf-prohibits" {
        description
          "PDU rejected during NSF switch-over";
      }
      enum "isis-pdu-rejected-adj-held-down" {
        description
          "Interface in Adjacency Holddown state";
      }
      enum "isis-pdu-rejected-intf-not-running" {
        description
          "IS-IS not running and active on interface";
      }
      enum "isis-pdu-rejected-interface-is-passive" {
        description
          "Received a PDU on a passive interface";
      }
      enum "isis-pdu-rejected-unknown-pdu-type" {
        description
          "Unrecognized PDU type";
      }
      enum "isis-pdu-rejected-parse-error" {
        description
          "PDU has unparsable TLVs";
      }
      enum "isis-pdu-rejected-invalid-dest-mac-addr" {
        description
          "No valid layer-2 destination address";
      }
      enum "isis-pdu-rejected-invalid-version" {
        description
          "Invalid protocol version";
      }
      enum "isis-pdu-rejected-invalid-sysid-length" {
        description
          "Invalid System ID length";
      }
      enum "isis-pdu-rejected-bad-hdr-length" {
        description
          "Bad header length";
      }
      enum "isis-pdu-rejected-pdu-too-small" {
        description
          "PDU size too small to contain header";
      }
      enum "isis-pdu-rejected-bad-pdu-length" {
        description
          "Packet is larger than header indicates";
      }
      enum "isis-pdu-rejected-pdu-larger-than-buffer" {
        description
          "Large PDU does not fit in our buffers";
      }
      enum "isis-pdu-rejected-pdu-larger-than-mtu" {
        description
          "Large PDU larger than our MTU";
      }
      enum "isis-pdu-rejected-auth-failed" {
        description
          "Authentication failed";
      }
      enum "isis-pdu-rejected-bad-ext-end-ed-seqnr" {
        description
          "Extended Sequence Number check failed";
      }
      enum "isis-pdu-rejected-circuit-type-mismatch" {
        description
          "PDU type didn't match with interface
           Circuit-type";
      }
      enum "isis-lsp-rejected-too-m-any-purge-s" {
        description
          "Too many LSP purges received";
      }
      enum "isis-iih-rejected-lan-iih-on-p2p-intf" {
        description
          "Received multipoint hello on P2P interface";
      }
      enum "isis-iih-rejected-p2p-iih-on-lan-intf" {
        description
          "Received P2P hello on multipoint interface";
      }
      enum "isis-iih-rejected-our-own-hello" {
        description
          "Received our own Hello";
      }
      enum "isis-iih-rejected-bad-circuit-type" {
        description
          "Invalid Circuit-type in hello";
      }
      enum "isis-iih-rejected-nr-of-area-addresses" {
        description
          "Unsupported number of area-addresses";
      }
      enum "isis-iih-rejected-area-mismatch" {
        description
          "Received hello with Mismatching AreaAddresses";
      }
      enum "isis-iih-rejected-level-or-area-mismatch" {
        description
          "Received hello with Mismatching Level or
           AreaAddresses";
      }
      enum "isis-iih-rejected-area-s-changed" {
        description
          "Neighbors advertised Areas changed";
      }
      enum "isis-iih-rejected-missing-area-address" {
        description
          "Received hello without required Area Address";
      }
      enum "isis-iih-rejected-instance-id-mismatch" {
        description
          "Received hello with wrong Instance ID";
      }
      enum "isis-iih-rejected-bad-instance-topo-id" {
        description
          "Received hello with bad Instance ID";
      }
      enum "isis-iih-rejected-instance-topo-id-mismatch" {
        description
          "Received hello with Topology ID Mismatch";
      }
      enum "isis-iih-rejected-no-common-topologies" {
        description
          "Received hello with no common Topologies";
      }
      enum "isis-iih-rejected-src-snpa-mismatch" {
        description
          "Received hello with wrong source MAC address";
      }
      enum "isis-iih-rejected-se-cond-adj-on-p2p" {
        description
          "Received hello from a 2nd system on p2p
           interface";
      }
      enum "isis-iih-rejected-circuit-nr-changed" {
        description
          "Neighbor's Circuit ID changed";
      }
      enum "isis-iih-rejected-3way-hand-shake-failed" {
        description
          "3Way Handshake failed for hello";
      }
      enum "isis-pdu-rejected-socket-error" {
        description
          "Socket error";
      }
      enum "isis-pdu-rejected-intf-not-configured" {
        description
          "IS-IS not configured on interface";
      }
      enum "isis-lsp-rejected-throttle-d-on-arrival" {
        description
          "LSP throttled because minimum arrival time";
      }
      enum "isis-lsp-rejected-invalid-purge" {
        description
          "LSP Purge contained non-allowed TLVs";
      }
      enum "isis-pdu-rejected-no-adj-with-sender" {
        description
          "No Adjacency with Sender";
      }
      enum "isis-pdu-rejected-wrong-adj-state" {
        description
          "Adjacency with Sender in Wrong State";
      }
      enum "isis-pdu-rejected-invalid-head-er" {
        description
          "Invalid protocol header";
      }
      enum "isis-pdu-rejected-invalid-reason" {
        description
          "Invalid PDU Rejection enumeration value";
      }
      enum "isis-nr-of-pdu-rejection-reasons" {
        description
          "Number of PDU Rejection Reasons";
      }
    }
    description
      "PDU Rejection reason";
  }

  typedef Isis-if-mcast-invalid-reason {
    type enumeration {
      enum "isis-intf-mcast-invalid-join-error" {
        description
          "Error when attempting to join this multicast
           group";
      }
      enum "isis-intf-mcast-invalid-internal-error" {
        description
          "Internal error";
      }
      enum "isis-intf-mcast-invalid-not-yet-needed" {
        description
          "Multicast group membership not yet requested";
      }
    }
    description
      "Isis if mcast invalid reason";
  }

  typedef Isis-if-clns-snpa-unknown-reason {
    type enumeration {
      enum "isis-intf-clns-snpa-unknown-access-error" {
        description
          "isis intf clns snpa unknown access error";
      }
      enum "isis-intf-clns-snpa-unknown-not-lan" {
        description
          "isis intf clns snpa unknown not lan";
      }
      enum "isis-intf-clns-snpa-unknown-internal-error" {
        description
          "isis intf clns snpa unknown internal error";
      }
    }
    description
      "Isis if clns snpa unknown reason";
  }

  typedef Isis-known {
    type enumeration {
      enum "isis-unknown" {
        value 0;
        description
          "Unknown";
      }
      enum "isis-known" {
        value 1;
        description
          "Known";
      }
    }
    description
      "Isis known";
  }

  typedef Isis-if-clns-mtu-invalid-reason {
    type enumeration {
      enum "isis-intf-clns-mtu-invalid-too-small" {
        description
          "isis intf clns mtu invalid too small";
      }
      enum "isis-intf-clns-mtu-invalid-internal-error" {
        description
          "isis intf clns mtu invalid internal error";
      }
    }
    description
      "Isis if clns mtu invalid reason";
  }

  typedef Isis-if-clns-proto-down-reason {
    type enumeration {
      enum "isis-intf-clns-proto-down-add-to-intf-stack-fail" {
        description
          "isis intf clns proto down add to intf stack
           fail";
      }
      enum "isis-intf-clns-proto-down-no-imd-conn" {
        description
          "isis intf clns proto down no imd conn";
      }
      enum "isis-intf-clns-proto-down-imd-node-doesnt-exist" {
        description
          "isis intf clns proto down imd node doesnt exist";
      }
      enum "isis-intf-clns-proto-down-imd-exist-reg-error" {
        description
          "isis intf clns proto down imd exist reg error";
      }
      enum "isis-intf-clns-proto-down-imd-state-reg-error" {
        description
          "isis intf clns proto down imd state reg error";
      }
      enum "isis-intf-clns-proto-down-clns-not-up" {
        description
          "isis intf clns proto down clns not up";
      }
    }
    description
      "Isis if clns proto down reason";
  }

  typedef Isis-sh-if-fsopt-psnp-delay-src {
    type enumeration {
      enum "isis-fls-psnp-delay-from-rtr-cfg" {
        description
          "From router configuration";
      }
      enum "isis-fls-psnp-delay-from-snp-psnp-sub-tlv" {
        description
          "From SNP PSNP subtlv configuration";
      }
      enum "isis-fls-psnp-delay-from-iih-psnp-sub-tlv" {
        description
          "From IIH PSNP subtlv configuration";
      }
      enum "isis-fls-psnp-delay-from-intf-cfg" {
        description
          "From interface configuration";
      }
    }
    description
      "Source of flood speed optimization PSNP delay";
  }

  typedef Isis-extended-circuit-number {
    type uint32;
    description
      "Isis extended circuit number";
  }

  typedef Isis-circuit-number {
    type uint8;
    description
      "Isis circuit number";
  }

  typedef Isis-if-adv-prefix-disabled-reason {
    type enumeration {
      enum "isis-intf-adv-prefix-disabled-if-cfg-suppressed" {
        description
          "isis intf adv prefix disabled if cfg suppressed";
      }
      enum "isis-intf-adv-prefix-disabled-no-topo-participate" {
        description
          "isis intf adv prefix disabled no topo
           participate";
      }
      enum "isis-intf-adv-prefix-disabled-internal-error" {
        description
          "isis intf adv prefix disabled internal error";
      }
    }
    description
      "Isis if adv prefix disabled reason";
  }

  typedef Isis-if-adj-form-disabled-reason {
    type enumeration {
      enum "isis-intf-adj-form-disabled-cfg-passive" {
        description
          "isis intf adj form disabled cfg passive";
      }
      enum "isis-intf-adj-form-disabled-static-nbr" {
        description
          "isis intf adj form disabled static nbr";
      }
      enum "isis-intf-adj-form-disabled-no-topo-participate" {
        description
          "isis intf adj form disabled no topo participate";
      }
      enum "isis-intf-adj-form-disabled-add-to-intf-stack-fail" {
        description
          "isis intf adj form disabled add to intf stack
           fail";
      }
      enum "isis-intf-adj-form-disabled-clns-io" {
        description
          "isis intf adj form disabled clns io";
      }
      enum "isis-intf-adj-form-disabled-internal-error" {
        description
          "isis intf adj form disabled internal error";
      }
    }
    description
      "Isis if adj form disabled reason";
  }

  typedef Isis-if-disabled-reason {
    type enumeration {
      enum "isis-intf-disabled-no-net-cfg" {
        description
          "isis intf disabled no net cfg";
      }
      enum "isis-intf-disabled-area-missing" {
        description
          "isis intf disabled area missing";
      }
      enum "isis-intf-disabled-no-area-running" {
        description
          "isis intf disabled no area running";
      }
      enum "isis-intf-disabled-no-topos-cfg" {
        description
          "isis intf disabled no topos cfg";
      }
      enum "isis-intf-disabled-no-imd-conn" {
        description
          "isis intf disabled no imd conn";
      }
      enum "isis-intf-disabled-imd-reg-error" {
        description
          "isis intf disabled imd reg error";
      }
      enum "isis-intf-disabled-level-mismatch" {
        description
          "isis intf disabled level mismatch";
      }
      enum "isis-intf-disabled-base-caps-error" {
        description
          "isis intf disabled base caps error";
      }
      enum "isis-intf-disabled-intf-doesnt-exist" {
        description
          "isis intf disabled intf doesnt exist";
      }
      enum "isis-intf-disabled-intf-shutdown" {
        description
          "isis intf disabled intf shutdown";
      }
      enum "isis-intf-disabled-internal-error" {
        description
          "isis intf disabled internal error";
      }
      enum "isis-intf-disabled-proto-shut" {
        description
          "isis intf disabled proto shut";
      }
    }
    description
      "Isis if disabled reason";
  }

  typedef Isis-enabled {
    type enumeration {
      enum "isis-disabled" {
        value 0;
        description
          "Disabled";
      }
      enum "isis-enabled" {
        value 1;
        description
          "Enabled";
      }
    }
    description
      "Isis enabled";
  }

  typedef Isis-mesh-group-number {
    type uint32;
    description
      "Isis mesh group number";
  }

  typedef Isis-edm-label-type-enum {
    type enumeration {
      enum "isis-edm-label-alloc-prefix-sid" {
        value 0;
        description
          "isis edm label alloc prefix sid";
      }
      enum "isis-edm-label-alloc-local-sid" {
        value 1;
        description
          "isis edm label alloc local sid";
      }
      enum "isis-edm-label-alloc-max" {
        value 2;
        description
          "isis edm label alloc max";
      }
    }
    description
      "isislabeltype";
  }

  typedef Isis-metric-mode {
    type enumeration {
      enum "isis-metric-mode-fixed" {
        value 0;
        description
          "Fixed";
      }
      enum "isis-metric-mode-relative" {
        value 1;
        description
          "Relative";
      }
      enum "isis-metric-mode-absolute" {
        value 2;
        description
          "Absolute";
      }
    }
    description
      "Isis metric mode";
  }

  typedef Isis-spf-trigger {
    type enumeration {
      enum "isis-spf-trig-config" {
        description
          "Configuration change";
      }
      enum "isis-spf-trig-nsr-fo" {
        description
          "NSR FO is done";
      }
      enum "isis-spf-trig-periodic" {
        description
          "Periodic SPF";
      }
      enum "isis-spf-trig-clear" {
        description
          "Cleared route table";
      }
      enum "isis-spf-trig-null0-intf" {
        description
          "Null0 intf up";
      }
      enum "isis-spf-trig-test" {
        description
          "Periodic test trigger";
      }
      enum "isis-spf-trig-newadj" {
        description
          "New adjacency";
      }
      enum "isis-spf-trig-deladj" {
        description
          "Deleted adjacency";
      }
      enum "isis-spf-trig-next-hop" {
        description
          "IP nexthop address change";
      }
      enum "isis-spf-trig-metric" {
        description
          "Changed interface metric";
      }
      enum "isis-spf-trig-dis" {
        description
          "Change to elected DIS";
      }
      enum "isis-spf-trig-frr-per-link" {
        description
          "Change to per-link FRR config";
      }
      enum "isis-spf-trig-frr-per-prefix" {
        description
          "Change to per-prefix FRR config";
      }
      enum "isis-spf-trig-ucmp" {
        description
          "Change to UCMP config/calculation";
      }
      enum "isis-spf-trig-bfd-up" {
        description
          "BFD up for link topology";
      }
      enum "isis-spf-trig-bfd-down" {
        description
          "BFD down for link topology";
      }
      enum "isis-spf-trig-new-tunnel" {
        description
          "New TE Autoroute Tunnel";
      }
      enum "isis-spf-trig-del-tunnel" {
        description
          "Deleted TE Autoroute Tunnel";
      }
      enum "isis-spf-trig-chg-tunnel" {
        description
          "Changed TE Autoroute Tunnel";
      }
      enum "isis-spf-trig-new-node" {
        description
          "New LSP zero which participates in topology";
      }
      enum "isis-spf-trig-del-node" {
        description
          "New LSP zero which no longer participates in
           topology";
      }
      enum "isis-spf-trig-newlsp" {
        description
          "Previously unseen LSP fragment";
      }
      enum "isis-spf-trig-lsp-expiry" {
        description
          "LSP expired";
      }
      enum "isis-spf-trig-attach-set" {
        description
          "Attached bit set";
      }
      enum "isis-spf-trig-attach-clr" {
        description
          "Attached bit cleared";
      }
      enum "isis-spf-trig-overload-set" {
        description
          "Overload bit set";
      }
      enum "isis-spf-trig-overload-clr" {
        description
          "Overload bit cleared";
      }
      enum "isis-spf-trig-link-good" {
        description
          "Good news link TLV content change";
      }
      enum "isis-spf-trig-link-bad" {
        description
          "Bad news link TLV content change";
      }
      enum "isis-spf-trig-prefix-good" {
        description
          "Good news prefix TLV content change";
      }
      enum "isis-spf-trig-prefix-bad" {
        description
          "Bad news prefix TLV content change";
      }
      enum "isis-spf-trig-prefix" {
        description
          "Neutral (neither good nor bad news) prefix TLV
           content change";
      }
      enum "isis-spf-trig-area-addr" {
        description
          "Area address TLV content change";
      }
      enum "isis-spf-trig-ip-addr" {
        description
          "IP address TLV content change";
      }
      enum "isis-spf-trig-rtrid" {
        description
          "Router id TLV content change";
      }
      enum "isis-spf-trig-flex-algo" {
        description
          "Flex-Algo support change";
      }
      enum "isis-spf-trig-srv6-cap" {
        description
          "SRv6 router capability change";
      }
      enum "isis-spf-trig-srv6-locator" {
        description
          "SRv6 locator TLV change";
      }
      enum "isis-spf-trig-prefix-policy" {
        description
          "Prefix policy change";
      }
    }
    description
      "Isis spf trigger";
  }

  typedef Isis-spf-class {
    type enumeration {
      enum "isis-spf-frr-sr-u-loop" {
        value 0;
        description
          "Remote microloop avoidance SPF";
      }
      enum "isis-spf-frr-per-link" {
        value 1;
        description
          "FRR per-link SPF";
      }
      enum "isis-spf-partial" {
        value 2;
        description
          "PRC";
      }
      enum "isis-spf-frr-per-prefix" {
        value 3;
        description
          "FRR per-prefix SPF";
      }
      enum "isis-spf-ucmp-calc" {
        value 4;
        description
          "UCMP SPF";
      }
      enum "isis-spf-flex" {
        value 5;
        description
          "Flex-Algo SPF";
      }
      enum "isis-spf-next-hop" {
        value 6;
        description
          "Next Hop";
      }
      enum "isis-spf-incremental" {
        value 7;
        description
          "Incremental SPF";
      }
      enum "isis-spf-full" {
        value 8;
        description
          "Full SPF";
      }
    }
    description
      "Types of route calculation";
  }

  typedef Isis-sh-te-pce-flooding-scope {
    type enumeration {
      enum "none" {
        description
          "Flooding is disabled";
      }
      enum "area" {
        description
          "Area wide flooding";
      }
      enum "domain" {
        description
          "Domain wide flooding";
      }
    }
    description
      "Isis sh te pce flooding scope";
  }

  typedef Isis-sh-te-link {
    type enumeration {
      enum "isis-sh-te-link-p2p" {
        description
          "Tunnel is absolute";
      }
      enum "isis-sh-te-link-broadcast" {
        description
          "Broadcast link";
      }
    }
    description
      "Isis sh te link";
  }

  typedef Isis-reachable {
    type enumeration {
      enum "isis-unreachable" {
        value 0;
        description
          "Unreachable";
      }
      enum "isis-reachable" {
        value 1;
        description
          "Reachable";
      }
    }
    description
      "Isis reachable";
  }

  typedef Isis-admin-tag {
    type uint32;
    description
      "Isis admin tag";
  }

  typedef Mgmt-srv6-endpoint {
    type enumeration {
      enum "unknown" {
        value 0;
        description
          "Unknown Endpoint type";
      }
      enum "end" {
        value 1;
        description
          "End (no PSP/USP)";
      }
      enum "end-with-psp" {
        value 2;
        description
          "End with PSP";
      }
      enum "end-with-usp" {
        value 3;
        description
          "End with USP";
      }
      enum "end-with-psp-usp" {
        value 4;
        description
          "End with PSP/USP";
      }
      enum "end-x" {
        value 5;
        description
          "End.X (no PSP/USP)";
      }
      enum "end-x-with-psp" {
        value 6;
        description
          "End.X with PSP";
      }
      enum "end-x-with-usp" {
        value 7;
        description
          "End.X with USP";
      }
      enum "end-x-with-psp-usp" {
        value 8;
        description
          "End.X with PSP/USP";
      }
      enum "end-tbl" {
        value 9;
        description
          "End.T (no PSP/USP)";
      }
      enum "end-tbl-with-psp" {
        value 10;
        description
          "End.T with PSP";
      }
      enum "end-tbl-with-usp" {
        value 11;
        description
          "End.T with USP";
      }
      enum "end-tbl-with-psp-usp" {
        value 12;
        description
          "End.T with PSP/USP";
      }
      enum "end-b6-insert" {
        value 13;
        description
          "End.B6.Insert";
      }
      enum "end-b6-encaps" {
        value 14;
        description
          "End.B6.Encaps";
      }
      enum "end-bm" {
        value 15;
        description
          "End.BM";
      }
      enum "end-dx6" {
        value 16;
        description
          "End.DX6";
      }
      enum "end-dx4" {
        value 17;
        description
          "End.DX4";
      }
      enum "end-dt6" {
        value 18;
        description
          "End.DT6";
      }
      enum "end-dt4" {
        value 19;
        description
          "End.DT4";
      }
      enum "end-dt46" {
        value 20;
        description
          "End.DT46";
      }
      enum "end-dx2" {
        value 21;
        description
          "End.DX2";
      }
      enum "end-dx2v" {
        value 22;
        description
          "End.DX2V";
      }
      enum "end-dt2u" {
        value 23;
        description
          "End.DT2U";
      }
      enum "end-dt2m" {
        value 24;
        description
          "End.DT2M";
      }
      enum "end-s" {
        value 25;
        description
          "End.S";
      }
      enum "end-b6-insert-red" {
        value 26;
        description
          "End.B6.Insert.Reduced";
      }
      enum "end-b6-encaps-red" {
        value 27;
        description
          "End.B6.Encaps.Reduced";
      }
      enum "end-with-usd" {
        value 28;
        description
          "End with USD";
      }
      enum "end-with-psp-usd" {
        value 29;
        description
          "End with PSP/USD";
      }
      enum "end-with-usp-usd" {
        value 30;
        description
          "End with USP/USD";
      }
      enum "end-with-psp-usp-usd" {
        value 31;
        description
          "End with PSP/USP/USD";
      }
      enum "end-x-with-usd" {
        value 32;
        description
          "End.X with USD";
      }
      enum "end-x-with-psp-usd" {
        value 33;
        description
          "End.X with PSP/USD";
      }
      enum "end-x-with-usp-usd" {
        value 34;
        description
          "End.X with USP/USD";
      }
      enum "end-x-with-psp-usp-usd" {
        value 35;
        description
          "End.X with PSP/USP/USD";
      }
      enum "end-tbl-with-usd" {
        value 36;
        description
          "End.T with USD";
      }
      enum "end-tbl-with-psp-usd" {
        value 37;
        description
          "End.T with PSP/USD";
      }
      enum "end-tbl-with-usp-usd" {
        value 38;
        description
          "End.T with USP/USD";
      }
      enum "end-tbl-with-psp-usp-usd" {
        value 39;
        description
          "End.T with PSP/USP/USD";
      }
      enum "end-op" {
        value 40;
        description
          "End.OP";
      }
      enum "end-otp" {
        value 41;
        description
          "End.OTP";
      }
      enum "un-shift-only" {
        value 42;
        description
          "uN Shift-only";
      }
      enum "un" {
        value 43;
        description
          "uN";
      }
      enum "un-psp" {
        value 44;
        description
          "uN with PSP";
      }
      enum "un-usp" {
        value 45;
        description
          "uN with USP";
      }
      enum "un-psp-usp" {
        value 46;
        description
          "uN with PSP-USP";
      }
      enum "un-usd" {
        value 47;
        description
          "uN with USD";
      }
      enum "un-psp-usd" {
        value 48;
        description
          "uN with PSP-USD";
      }
      enum "un-usp-usd" {
        value 49;
        description
          "uN with USP-USD";
      }
      enum "un-psp-usp-usd" {
        value 50;
        description
          "uN with PSP_USP-USD";
      }
      enum "ua-shift-only" {
        value 51;
        description
          "uA Shift-only";
      }
      enum "ua" {
        value 52;
        description
          "uA";
      }
      enum "ua-psp" {
        value 53;
        description
          "uA with PSP";
      }
      enum "ua-usp" {
        value 54;
        description
          "uA with USP";
      }
      enum "ua-psp-usp" {
        value 55;
        description
          "uA with PSP-USP";
      }
      enum "ua-usd" {
        value 56;
        description
          "uA with USD";
      }
      enum "ua-psp-usd" {
        value 57;
        description
          "uA with PSP-USD";
      }
      enum "ua-usp-usd" {
        value 58;
        description
          "uA with USP-USD";
      }
      enum "ua-psp-usp-usd" {
        value 59;
        description
          "uA with PSP_USP-USD";
      }
      enum "udx6" {
        value 60;
        description
          "uDX6";
      }
      enum "udx4" {
        value 61;
        description
          "uDX4";
      }
      enum "udt6" {
        value 62;
        description
          "uDT6";
      }
      enum "udt4" {
        value 63;
        description
          "uDT4";
      }
      enum "udt46" {
        value 64;
        description
          "uDT46";
      }
      enum "udx2" {
        value 65;
        description
          "uDX2";
      }
      enum "udx2v" {
        value 66;
        description
          "uDX2V";
      }
      enum "udt2u" {
        value 67;
        description
          "uDT2U";
      }
      enum "udt2m" {
        value 68;
        description
          "uDT2M";
      }
      enum "ub6-insert" {
        value 69;
        description
          "uB6 Insert";
      }
      enum "ub6-encaps" {
        value 70;
        description
          "uB6 Encaps";
      }
      enum "ub6-insert-red" {
        value 71;
        description
          "uB6 Insert.Red";
      }
      enum "ub6-encaps-red" {
        value 72;
        description
          "uB6 Encaps.Red";
      }
      enum "ubm" {
        value 73;
        description
          "uBM";
      }
      enum "ub6-psp-usd-insert-red" {
        value 79;
        description
          "uB6 with PSP-USD Insert.Red";
      }
      enum "ub6-psp-usd-encaps-red" {
        value 80;
        description
          "uB6 with PSP-USD Encaps.Red";
      }
      enum "utef" {
        value 81;
        description
          "PT uTEF";
      }
      enum "ub6-insert-red-shift-only" {
        value 82;
        description
          "uB6 Insert.Red Shift-only";
      }
    }
    description
      "SRv6 Endpoint Behavior Type";
  }

  typedef Mgmt-srv6-sid-fmt {
    type enumeration {
      enum "none" {
        value 0;
        description
          "No format";
      }
      enum "base" {
        value 1;
        description
          "Base Format";
      }
      enum "f3216" {
        value 2;
        description
          "Micro-segment F3216 Format";
      }
    }
    description
      "SRv6 SID Format Type";
  }

  typedef Isis-sh-route-adv-origin {
    type enumeration {
      enum "isis-sh-route-adv-origin-interface" {
        description
          "IS-IS interface prefix";
      }
      enum "isis-sh-route-adv-origin-redistributed" {
        description
          "Redistributed prefix";
      }
      enum "isis-sh-route-adv-origin-native" {
        description
          "Native prefix";
      }
      enum "isis-sh-route-adv-origin-summary" {
        description
          "Summary prefix";
      }
      enum "isis-sh-route-adv-origin-default" {
        description
          "Explicit origination of default prefix";
      }
    }
    description
      "Origin of a prefix advertisement";
  }

  typedef Isis-local-label-state {
    type enumeration {
      enum "isis-srmpls-label-none" {
        description
          "No label requested from LSD";
      }
      enum "isis-srmpls-label-unavailable" {
        description
          "Label assignment failed";
      }
      enum "isis-srmpls-label-request-ed" {
        description
          "Request to LSD pending";
      }
      enum "isis-srmpls-label-assigned" {
        description
          "Label assigned by LSD";
      }
    }
    description
      "Isis local label state";
  }

  typedef Isis-prefix-priority {
    type enumeration {
      enum "isis-prefix-priority-critical" {
        value 0;
        description
          "Critical priority prefixes";
      }
      enum "isis-prefix-priority-high" {
        value 1;
        description
          "High priority prefixes";
      }
      enum "isis-prefix-priority-med" {
        value 2;
        description
          "Medium priority prefixes";
      }
      enum "isis-prefix-priority-low" {
        value 3;
        description
          "Low priority prefixes";
      }
    }
    description
      "Isis prefix priority";
  }

  typedef Isis-sr-exclude {
    type enumeration {
      enum "isis-tunnel-sr-exclude-none" {
        value 0;
        description
          "None";
      }
      enum "isis-tunnel-sr-exclude-label" {
        value 1;
        description
          "Labeled";
      }
      enum "isis-tunnel-sr-exclude-all" {
        value 2;
        description
          "Both labeled and unlabeled";
      }
    }
    description
      "Isis sr exclude";
  }

  typedef Isis-tilfa-computation {
    type enumeration {
      enum "isis-tilfa-comp-none" {
        description
          "isis tilfa comp none";
      }
      enum "isis-tilfa-comp-link" {
        description
          "isis tilfa comp link";
      }
      enum "isis-tilfa-comp-node" {
        description
          "isis tilfa comp node";
      }
      enum "isis-tilfa-comp-srlg" {
        description
          "isis tilfa comp srlg";
      }
      enum "isis-tilfa-comp-node-srlg" {
        description
          "isis tilfa comp node srlg";
      }
      enum "isis-tilfa-comp-lc" {
        description
          "isis tilfa comp lc";
      }
      enum "isis-tilfa-comp-node-lc" {
        description
          "isis tilfa comp node lc";
      }
      enum "isis-tilfa-comp-srlg-lc" {
        description
          "isis tilfa comp srlg lc";
      }
      enum "isis-tilfa-comp-node-srlg-lc" {
        description
          "isis tilfa comp node srlg lc";
      }
    }
    description
      "Isis tilfa computation";
  }

  typedef Isis-prefix-tag {
    type uint32;
    description
      "Isis prefix tag";
  }

  typedef Isis-metric {
    type uint32;
    description
      "Isis metric";
  }

  typedef Isis-prefix-origin {
    type enumeration {
      enum "isis-prefix-origin-l1-summary-null" {
        value 0;
        description
          "Level 1 Summary Null Route";
      }
      enum "isis-prefix-origin-l1" {
        value 1;
        description
          "Level 1 Route";
      }
      enum "isis-prefix-origin-l2-summary-null" {
        value 2;
        description
          "Level 2 Summary Null Route";
      }
      enum "isis-prefix-origin-l2" {
        value 3;
        description
          "Level 2 Route";
      }
      enum "isis-prefix-origin-inter-area-summary-null" {
        value 4;
        description
          "Level 1 Interarea Summary Null Route";
      }
      enum "isis-prefix-origin-inter-area" {
        value 5;
        description
          "Level 1 Interarea Route";
      }
      enum "isis-prefix-origin-default-nearest-attached" {
        value 6;
        description
          "Nearest Attached Default Route";
      }
      enum "isis-prefix-origin-invalid" {
        value 7;
        description
          "Invalid Origin";
      }
    }
    description
      "Isis prefix origin";
  }

  typedef Isis-string {
    type string;
    description
      "Isis string";
  }

  typedef Isis-redist-proto {
    type enumeration {
      enum "isis-redist-connected" {
        value 0;
        description
          "Redistributed protocol is Connected";
      }
      enum "isis-redist-static" {
        value 1;
        description
          "Redistributed protocol is Static";
      }
      enum "isis-redist-ospf" {
        value 2;
        description
          "Redistributed protocol is OSPF";
      }
      enum "isis-redist-bgp" {
        value 3;
        description
          "Redistributed protocol is BGP";
      }
      enum "isis-redist-isis" {
        value 4;
        description
          "Redistributed protocol is IS-IS";
      }
      enum "isis-redist-ospfv3" {
        value 5;
        description
          "Redistributed protocol is OSPFv3";
      }
      enum "isis-redist-rip" {
        value 6;
        description
          "Redistributed protocol is RIP";
      }
      enum "isis-redist-eigrp" {
        value 7;
        description
          "Redistributed protocol is EIGRP";
      }
      enum "isis-redist-subscriber" {
        value 8;
        description
          "Redistributed protocol is Subscriber";
      }
      enum "isis-redist-application" {
        value 9;
        description
          "Redistributed protocol is Application";
      }
      enum "isis-redist-mobile" {
        value 10;
        description
          "Redistributed protocol is Mobile";
      }
    }
    description
      "Isis redist proto";
  }

  typedef Isis-valid {
    type enumeration {
      enum "isis-invalid" {
        value 0;
        description
          "Invalid";
      }
      enum "isis-valid" {
        value 1;
        description
          "Valid";
      }
    }
    description
      "Isis valid";
  }

  typedef Isis-pseudo-node-number {
    type uint8;
    description
      "Isis pseudo node number";
  }

  typedef Isis-lsp-trigger {
    type enumeration {
      enum "isis-lsp-trig-config" {
        description
          "Any configuration change";
      }
      enum "isis-lsp-trig-config-fast" {
        description
          "Confguration trigger using LSP exp. backoff";
      }
      enum "isis-lsp-trig-newadj" {
        description
          "New adjacency came up";
      }
      enum "isis-lsp-trig-deladj" {
        description
          "Adjacency went down";
      }
      enum "isis-lsp-trig-bestadj" {
        description
          "Best parallel adjacency changed";
      }
      enum "isis-lsp-trig-dr-change" {
        description
          "DIS changed, or pseudonode changed";
      }
      enum "isis-lsp-trig-area-set" {
        description
          "Active area set changed";
      }
      enum "isis-lsp-trig-attach" {
        description
          "Attached bit changed state";
      }
      enum "isis-lsp-trig-hippity" {
        description
          "LSPDB overload bit changed state";
      }
      enum "isis-lsp-trig-regen" {
        description
          "LSP regeneration";
      }
      enum "isis-lsp-trig-ip-if-up" {
        description
          "Directly connected IP prefix up";
      }
      enum "isis-lsp-trig-ip-if-down" {
        description
          "Directly connected IP prefix down";
      }
      enum "isis-lsp-trig-ip-inter-area" {
        description
          "Interarea IP route appeared or gone";
      }
      enum "isis-lsp-trig-ip-external" {
        description
          "Redistributed IP route appeared or gone";
      }
      enum "isis-lsp-trig-ip-external-full" {
        description
          "Full IP redistribution";
      }
      enum "isis-lsp-trig-ip-def-orig" {
        description
          "Default information originate changed";
      }
      enum "isis-lsp-trig-ip-addr-chg" {
        description
          "Local IP interface address changed";
      }
      enum "isis-lsp-trig-af-if-change" {
        description
          "Address-family interface state change";
      }
      enum "isis-lsp-trig-te-info" {
        description
          "TE bandwidth resource information";
      }
      enum "isis-lsp-trig-te-pce-info" {
        description
          "TE PCE information";
      }
      enum "isis-lsp-trig-te-fa-info" {
        description
          "TE forwarding adjacency information";
      }
      enum "isis-lsp-trig-nsr-fo" {
        description
          "NSR FO is done";
      }
      enum "isis-lsp-trig-pn-cancel" {
        description
          "Pseudo-node generation canceled";
      }
      enum "isis-lsp-trig-lkgp" {
        description
          "Link-group offset metric change";
      }
      enum "isis-lsp-trig-pp" {
        description
          "Proactive Protection metric change";
      }
      enum "isis-lsp-trig-config-force-send" {
        description
          "Any configuration change that requires all LSPs
           to be updated";
      }
      enum "isis-lsp-trig-config-force-init" {
        description
          "Any configuration change that requires the LBD
           database re-init.";
      }
      enum "isis-lsp-trig-adj-sid-add" {
        description
          "Adjacency SID added";
      }
      enum "isis-lsp-trig-adj-sid-delete" {
        description
          "Adjacency SID deleted";
      }
      enum "isis-lsp-trig-adj-sid-change" {
        description
          "Adjacency SIDs added and/or deleted";
      }
      enum "isis-lsp-trig-msd" {
        description
          "Maximum SID depth change";
      }
      enum "isis-lsp-trig-adj-sid-wait-timer" {
        description
          "Adjacency SID wait timer expired";
      }
      enum "isis-lsp-trig-direct-gen" {
        description
          "Direct LSP generation";
      }
      enum "isis-lsp-trig-flex-algo-enable-disable" {
        description
          "Flex-Algo Enable/Disable";
      }
      enum "isis-lsp-trig-reverse-metric" {
        description
          "Reverse metric";
      }
      enum "isis-lsp-trig-metric-fallback" {
        description
          "Metric Fallback";
      }
      enum "isis-lsp-trig-pm-link-anomaly" {
        description
          "Link Anomaly";
      }
      enum "isis-lsp-trig-pm-delay-loss" {
        description
          "Link delay/loss changed";
      }
      enum "isis-lsp-trig-pm-bw-util" {
        description
          "Link bandwidth utilization changed";
      }
      enum "isis-lsp-trig-cs-update" {
        description
          "Canary Stamp data changed";
      }
      enum "isis-lsp-trig-bfd-chg" {
        description
          "BFD useability change";
      }
      enum "isis-lsp-trig-bfd-up" {
        description
          "BFD session up event";
      }
      enum "isis-lsp-trig-bfd-down" {
        description
          "BFD session down event";
      }
      enum "isis-lsp-trig-up-a-expiry" {
        description
          "UPA lifetime expired";
      }
      enum "isis-lsp-trig-remote-ip-addr-chg" {
        description
          "Remote IP interface-address changed";
      }
      enum "isis-lsp-trig-remote-link-id-chg" {
        description
          "Remote link-id attribute changed";
      }
      enum "isis-lsp-trig-sa-bit-change" {
        description
          "Neighbor SA bit changed";
      }
    }
    description
      "Isis lsp trigger";
  }

  typedef Isis-adj-topo-status {
    type enumeration {
      enum "isis-adj-topo-status-ok" {
        description
          "Topology is included in adjacency";
      }
      enum "isis-adj-topo-status-intf-not-configured" {
        description
          "Topology is not configured on the interface";
      }
      enum "isis-adj-topo-status-intf-not-running" {
        description
          "Topology is not running on the interface";
      }
      enum "isis-adj-topo-status-init-state" {
        description
          "Adjacency is in INIT state";
      }
      enum "isis-adj-topo-status-neighbor-doesnt-participate" {
        description
          "Neighbor doesn't participate in topology";
      }
      enum "isis-adj-topo-status-ipv4-address-tlv-missing" {
        description
          "Neighbor IIH doesn't contain IPv4 address TLV";
      }
      enum "isis-adj-topo-status-ipv4-address-tlv-empty" {
        description
          "Neighbor's IPv4 address TLV is empty";
      }
      enum "isis-adj-topo-status-ipv6-address-tlv-missing" {
        description
          "Neighbor IIH doesn't contain IPv6 address TLV";
      }
      enum "isis-adj-topo-status-ipv6-address-tlv-empty" {
        description
          "Neighbor's IPv6 address TLV is empty";
      }
      enum "isis-adj-topo-status-ipv4-address-matches-ours" {
        description
          "Neighbor's IPv4 address matches ours";
      }
      enum "isis-adj-topo-status-ipv6-address-matches-ours" {
        description
          "Neighbor's IPv6 address matches ours";
      }
      enum "isis-adj-topo-status-ipv4-address-subnet-mismatch" {
        description
          "Neighbor's IPv4 address is in a different
           subnet to ours";
      }
      enum "isis-adj-topo-status-ipv6-address-not-link-local" {
        description
          "Neighbor's IPv6 address is not link local";
      }
      enum "isis-adj-topo-status-bfd-down" {
        description
          "BFD is down";
      }
    }
    description
      "Status of a topology in an adjacency";
  }

  typedef Isis-dr-priority {
    type uint8;
    description
      "Isis dr priority";
  }

  typedef Isis-adj-bfd-state {
    type enumeration {
      enum "isis-adj-bfd-no-state" {
        value 0;
        description
          "No BFD session created";
      }
      enum "isis-adj-bfd-down-state" {
        value 1;
        description
          "BFD session is DOWN";
      }
      enum "isis-adj-bfd-init-state" {
        value 2;
        description
          "Waiting for BFD session to come UP";
      }
      enum "isis-adj-bfd-up-state" {
        value 3;
        description
          "BFD session is UP";
      }
    }
    description
      "Current BFD state of an adjacency";
  }

  typedef Isis-sh-lsp-db-install-reason {
    type enumeration {
      enum "isis-sh-lsp-install-reason-unknown" {
        description
          "Unknown reason why LSP was installed";
      }
      enum "isis-sh-lsp-install-reason-lsp-recvd-from-neighbor" {
        description
          "A neighbor sent us a new LSP";
      }
      enum "isis-sh-lsp-install-reason-purge-recvd-from-neighbor" {
        description
          "A neighbor sent us a purged LSP";
      }
      enum "isis-sh-lsp-install-reason-own-lsp-content-changed" {
        description
          "Our LSP's content changed";
      }
      enum "isis-sh-lsp-install-reason-own-lsp-refresh" {
        description
          "Time to refresh our own LSP";
      }
      enum "isis-sh-lsp-install-reason-over-write-stale-lsp" {
        description
          "Received stale LSP from neighbor";
      }
      enum "isis-sh-lsp-install-reason-own-lsp-purge" {
        description
          "Purging our own LSP";
      }
      enum "isis-sh-lsp-install-reason-other-lsp-purge" {
        description
          "Purging another router's LSP";
      }
      enum "isis-sh-lsp-install-reason-own-p-node-purge" {
        description
          "Purging our own pseudonode LSP";
      }
      enum "isis-sh-lsp-install-reason-other-p-node-purge" {
        description
          "Purging another router's pseudonode LSP";
      }
      enum "isis-sh-lsp-install-reason-dummy-from-csnp" {
        description
          "Dummy LSP because we received a CSNP";
      }
      enum "isis-sh-lsp-install-reason-dummy-from-psnp" {
        description
          "Dummy LSP because we received a PSNP";
      }
      enum "isis-sh-lsp-install-reason-dummy-from-nsf" {
        description
          "Dummy LSP learned from NSF";
      }
      enum "isis-sh-lsp-install-reason-nsr-synchronize" {
        description
          "LSP received from Active RP";
      }
      enum "isis-sh-lsp-install-reason-nsr-purge-synchronize" {
        description
          "Purged LSP received from Active RP";
      }
      enum "isis-sh-lsp-install-reason-test" {
        description
          "Created a test LSP";
      }
      enum "isis-sh-lsp-install-reason-delete" {
        description
          "Deleted LSP from own LSPDB";
      }
      enum "isis-sh-lsp-install-num-reasons" {
        description
          "Number of reasons to install an LSP";
      }
    }
    description
      "Origin of an installed LSP";
  }

  typedef Isis-lsp-db-op {
    type enumeration {
      enum "isis-lsp-db-clear" {
        description
          "Clear the LSP database";
      }
      enum "isis-lsp-db-insert-new-lsp" {
        description
          "Insertion of new LSP";
      }
      enum "isis-lsp-db-replace-lsp-with-lsp" {
        description
          "LSP replacing LSP";
      }
      enum "isis-lsp-db-purge-lsp" {
        description
          "LSP purged by the local system";
      }
      enum "isis-lsp-db-delete-lsp" {
        description
          "Removal of the LSP from the database";
      }
    }
    description
      "Isis lsp db op";
  }

  typedef Isis-adj-topo-change {
    type enumeration {
      enum "isis-adj-topo-up-change" {
        value 0;
        description
          "Topology up";
      }
      enum "isis-adj-topo-next-hop-change" {
        value 1;
        description
          "Topology next-hop changed";
      }
      enum "isis-adj-topo-down-change" {
        value 2;
        description
          "Topology down";
      }
    }
    description
      "Per-topology change type for an adjacency";
  }

  typedef Isis-adj-state-reason {
    type enumeration {
      enum "isis-adj-up-nsf-restart" {
        value 0;
        description
          "NSF Restart";
      }
      enum "isis-adj-up-new-adj" {
        value 1;
        description
          "New adjacency";
      }
      enum "isis-adj-up-restarted" {
        value 2;
        description
          "Restarted";
      }
      enum "isis-adj-up-nsf-restored" {
        value 3;
        description
          "Restored during NSF";
      }
      enum "isis-adj-up-chkpt-restored" {
        value 4;
        description
          "Restored from checkpoint";
      }
      enum "isis-adj-init-reason" {
        value 5;
        description
          "Into INIT";
      }
      enum "isis-adj-init-neighbor-forgot" {
        value 6;
        description
          "Neighbor forgot us";
      }
      enum "isis-adj-down-hold-time" {
        value 7;
        description
          "Holdtime expired";
      }
      enum "isis-adj-down-if-down" {
        value 8;
        description
          "Interface state going down";
      }
      enum "isis-adj-down-cfg-mismatch" {
        value 9;
        description
          "Area address/level mismatch";
      }
      enum "isis-adj-down-circ-id" {
        value 10;
        description
          "Circuit ID changed";
      }
      enum "isis-adj-down-nsf-ack-fail" {
        value 11;
        description
          "NSF could not CSNP Ack P2P adjacency";
      }
      enum "isis-adj-down-db-clear" {
        value 12;
        description
          "Clear of the Adjacency DB";
      }
      enum "isis-adj-down-no-common-topology" {
        value 13;
        description
          "Neighbors have no common link topology";
      }
      enum "isis-adj-down-restart-tlv-missing" {
        value 14;
        description
          "Restart TLV missing during IETF NSF restart";
      }
      enum "isis-adj-down-bfd-down" {
        value 15;
        description
          "BFD session has gone DOWN";
      }
      enum "isis-adj-down-3way-down" {
        value 16;
        description
          "3-way state down";
      }
      enum "isis-adj-down-mac-address" {
        value 17;
        description
          "MAC address change";
      }
    }
    description
      "Isis adj state reason";
  }

  typedef Isis-level {
    type enumeration {
      enum "isis-level0" {
        value 0;
        description
          "isis level0";
      }
      enum "isis-level1" {
        value 1;
        description
          "isis level1";
      }
      enum "isis-level2" {
        value 2;
        description
          "isis level2";
      }
    }
    description
      "Isis level";
  }

  typedef Isis-static-nbr-down-reason {
    type enumeration {
      enum "static-nbr-down-reason-none" {
        description
          "static nbr down reason none";
      }
      enum "static-nbr-down-reason-system-id-not-set" {
        description
          "static nbr down reason system id not set";
      }
      enum "static-nbr-down-reason-if-media-unknown" {
        description
          "static nbr down reason if media unknown";
      }
      enum "static-nbr-down-reason-if-not-p2p" {
        description
          "static nbr down reason if not p2p";
      }
      enum "static-nbr-down-reason-idb-topo-down" {
        description
          "static nbr down reason idb topo down";
      }
      enum "static-nbr-down-reason-rpl-drop" {
        description
          "static nbr down reason rpl drop";
      }
      enum "static-nbr-down-reason-max" {
        description
          "static nbr down reason max";
      }
    }
    description
      "Isis static nbr down reason";
  }

  typedef Isis-up {
    type enumeration {
      enum "isis-down" {
        value 0;
        description
          "Down";
      }
      enum "isis-up" {
        value 1;
        description
          "Up";
      }
    }
    description
      "Isis up";
  }

  typedef Isis-srv6-endpoint-func {
    type uint16;
    description
      "Isis srv6 endpoint func";
  }

  typedef Isis-ip-prefix-length {
    type uint8;
    description
      "Isis ip prefix length";
  }

  typedef Isis-ipv6-address {
    type inet:ipv6-address;
    description
      "Isis ipv6 address";
  }

  typedef Isis-sh-interface-name {
    type string;
    description
      "Isis sh interface name";
  }

  typedef Isis-nodal-sid-value {
    type uint32;
    description
      "Isis nodal sid value";
  }

  typedef Isis-ipv4-address {
    type inet:ipv4-address;
    description
      "Isis ipv4 address";
  }

  typedef Isis-sub-af-id {
    type enumeration {
      enum "unicast" {
        value 0;
        description
          "Unicast";
      }
      enum "multicast" {
        value 1;
        description
          "Multicast";
      }
    }
    description
      "Isis sub af id";
  }

  typedef Isis-af-id {
    type enumeration {
      enum "ipv4" {
        value 0;
        description
          "IPv4";
      }
      enum "ipv6" {
        value 1;
        description
          "IPv6";
      }
    }
    description
      "Isis af id";
  }

  typedef Isis-media-class {
    type enumeration {
      enum "isis-media-class-lan" {
        value 0;
        description
          "LAN";
      }
      enum "isis-media-class-p2p" {
        value 1;
        description
          "P2P";
      }
      enum "isis-media-class-loop-back" {
        value 2;
        description
          "Loopback";
      }
      enum "isis-media-class-unknown" {
        value 3;
        description
          "Unknown";
      }
    }
    description
      "Isis media class";
  }

  typedef Isis-levels {
    type enumeration {
      enum "isis-levels-none" {
        value 0;
        description
          "isis levels none";
      }
      enum "isis-levels-1" {
        value 1;
        description
          "isis levels 1";
      }
      enum "isis-levels-2" {
        value 2;
        description
          "isis levels 2";
      }
      enum "isis-levels-12" {
        value 3;
        description
          "isis levels 12";
      }
      enum "isis-levels-total" {
        value 4;
        description
          "isis levels total";
      }
    }
    description
      "Isis levels";
  }

  typedef Isis-adj-state {
    type enumeration {
      enum "isis-adj-up-state" {
        value 0;
        description
          "Adjacency up";
      }
      enum "isis-adj-init-state" {
        value 1;
        description
          "Adjacency initializing";
      }
      enum "isis-adj-failed-state" {
        value 2;
        description
          "Adjacency down/failed";
      }
      enum "isis-adj-num-states" {
        value 3;
        description
          "Number of Valid Adjacency States";
      }
    }
    description
      "Isis adj state";
  }

  grouping ISIS-SH-CHKPT-TE-TUNNEL {
    description
      "Checkpointed TE tunnel";
    leaf checkpoint-te-level {
      type Isis-level;
      description
        "TE database level";
    }
    leaf checkpoint-te-system-id {
      type xr:Osi-system-id;
      description
        "Destination system ID";
    }
    leaf checkpoint-te-interface {
      type xr:Interface-name;
      description
        "Tunnel interface";
    }
    leaf checkpoint-te-flags {
      type uint32;
      description
        "Tunnel flags";
    }
    leaf checkpoint-te-nexthop {
      type Isis-ipv4-address;
      description
        "Tunnel next-hop IP address";
    }
    leaf checkpoint-te-metric {
      type int32;
      description
        "Tunnel metric";
    }
    leaf checkpoint-te-metric-mode {
      type Isis-metric-mode;
      description
        "Tunnel metric mode";
    }
    leaf checkpoint-te-bandwidth {
      type uint32;
      description
        "Tunnel bandwidth";
    }
    leaf checkpoint-te-object-id {
      type uint32;
      description
        "Tunnel checkpoint object ID";
    }
  }

  grouping NSR-STATS-GBL-TYPE {
    description
      "NSR STATS GBL TYPE";
    leaf no-of-l1-lsp {
      type uint32;
      description
        "no of l1 lsp";
    }
    leaf no-of-l2-lsp {
      type uint32;
      description
        "no of l2 lsp";
    }
    leaf no-of-l1-adj {
      type uint16;
      description
        "no of l1 adj";
    }
    leaf no-of-l2-adj {
      type uint16;
      description
        "no of l2 adj";
    }
    leaf no-of-live-interface {
      type uint16;
      description
        "no of live interface";
    }
    leaf no-of-ptp-interface {
      type uint16;
      description
        "no of ptp interface";
    }
    leaf no-of-lan-interface {
      type uint16;
      description
        "no of lan interface";
    }
    leaf no-of-loopback-interface {
      type uint16;
      description
        "no of loopback interface";
    }
    leaf no-of-te-tunnels {
      type uint16;
      description
        "no of te tunnels";
    }
    leaf no-of-te-links {
      type uint16;
      description
        "no of te links";
    }
    leaf no-of-ipv4-routes {
      type uint32;
      description
        "no of ipv4 routes";
    }
    leaf no-of-ipv6-routes {
      type uint32;
      description
        "no of ipv6 routes";
    }
    leaf seqnum {
      type uint32;
      description
        "seqnum";
    }
  }

  grouping NSR-STATS-GBL-ARR-TYPE {
    description
      "NSR STATS GBL ARR TYPE";
    container self {
      description
        "self";
      uses NSR-STATS-GBL-TYPE;
    }
    list peer {
      max-elements "3";
      description
        "peer";
      uses NSR-STATS-GBL-TYPE;
    }
  }

  grouping ISIS-SH-NSR-STATS-GLOBAL {
    description
      "IS-IS process NSR statistics";
    container isis-nsr-stats-data {
      description
        "ISIS NSR STATS Data";
      uses NSR-STATS-GBL-ARR-TYPE;
    }
    leaf isis-vm-state {
      type uint16;
      description
        "ISIS VM STATE";
    }
  }

  grouping ISIS-SH-MESH-ENTRY {
    description
      "Mesh-group informaiton for one interface";
    list isis-sh-mesh-entry {
      description
        "Next entry in list";
      leaf mesh-group-interface {
        type xr:Interface-name;
        description
          "This interface";
      }
      leaf mesh-group-number {
        type Isis-mesh-group-number;
        description
          "Mesh-group number";
      }
    }
  }

  grouping ISIS-SH-MESH-GROUPS {
    description
      "IS-IS mesh-group data";
    container mesh-group-configured-interface-list {
      description
        "List of mesh-group-configured interfaces";
      uses ISIS-SH-MESH-ENTRY;
    }
  }

  grouping ISIS-SH-INSTANCE-SUMMARY-DATA {
    description
      "Scaling Statistics data of an IS-IS instance";
    leaf running-levels {
      type Isis-levels;
      description
        "Levels Running";
    }
    leaf ipv4-running {
      type boolean;
      description
        "The IPv4 Unicast address family is running";
    }
    leaf ipv6-running {
      type boolean;
      description
        "The IPv6 Unicast address family is running";
    }
    leaf sys-mem-percentage {
      type int32;
      units "percentage";
      description
        "Percentage of Available Memory used, according
         to the System";
    }
    leaf system-mem-in-use {
      type uint64;
      description
        "Total Memory in use according to the System";
    }
    leaf malloced-mem-in-use {
      type uint64;
      description
        "Total Memory of Malloced IS-IS data-structures";
    }
    leaf chunks-mem-in-use {
      type uint64;
      description
        "Total Memory in use by IS-IS Chunk
         data-structures";
    }
  }

  grouping ISIS-SH-SCALE-LOG-AREA-AFI-SAMPLE {
    description
      "Information about Links and Prefixes in an area,
       per AFI";
    leaf num-reachable-nodes {
      type uint32;
      description
        "Number of Nodes Reachable in the Area";
    }
    leaf num-p2p-links {
      type uint32;
      description
        "Number of p2p Links in the Area";
    }
    leaf num-p2p-neighbor-pairs {
      type uint32;
      description
        "Number of p2p Neighbor Pairs in the Area";
    }
    leaf lan-attachments {
      type uint32;
      description
        "Number of Points of Attachments to LANs in the
         area";
    }
    leaf num-reachable-prefix-items {
      type uint32;
      description
        "Total Number of Reachable Prefixes Items in all
         LSPs in the area";
    }
    leaf num-unreachable-prefix-items {
      type uint32;
      description
        "Total Number of Unreachable Prefixes Items in
         all LSPs in the area";
    }
  }

  grouping ISIS-SH-INSTANCE-SUMMARY-AREA-AFI {
    description
      "Information about Links and Prefixes in an area,
       per AFI";
    container ent {
      description
        "ent";
      uses ISIS-SH-SCALE-LOG-AREA-AFI-SAMPLE;
    }
  }

  grouping ISIS-SH-INSTANCE-SUMMARY-AREA-DATA {
    description
      "Information about links in an Area";
    leaf number-of-adjacencies {
      type uint32;
      description
        "Number of Adjacencies in the Area";
    }
    leaf num-routers {
      type uint32;
      description
        "Number of Routers in the Area";
    }
    leaf num-pseudo-nodes {
      type uint32;
      description
        "Number of Pseudo-nodes in the Area";
    }
    leaf num-ls-ps {
      type uint32;
      description
        "Number of LSPs in the Area";
    }
    leaf num-own-sys-lsp-fragments {
      type uint8;
      description
        "Number of LSP-zero Fragments Generated";
    }
    leaf lsp-fragments-full {
      type boolean;
      description
        "Overflow of all 256 LSP-zero Fragments Generated";
    }
  }

  grouping ISIS-SH-SCALE-LOG-AFI-SAMPLE {
    description
      "Information about the IS-IS Routing Table, per
       AFI";
    leaf num-reachable-prefixes {
      type uint32;
      description
        "Number of Unique Prefixes that are Reachable, in
         the IS-IS RIB";
    }
    leaf num-unreachable-prefixes {
      type uint32;
      description
        "Number of Unique Prefixes that are not Reachable
         , in the IS-IS RIB";
    }
    leaf num-ecmp-paths {
      type uint32;
      description
        "Number of ECMP Paths in the IS-IS Routing Table";
    }
    leaf num-ucmp-paths {
      type uint32;
      description
        "Number of UCMP Paths in the IS-IS Routing Table";
    }
  }

  grouping ISIS-SH-INSTANCE-SUMMARY-AFI {
    description
      "Information about the IS-IS Routing Table, per
       AFI";
    container ent {
      description
        "ent";
      uses ISIS-SH-SCALE-LOG-AFI-SAMPLE;
    }
  }

  grouping ISIS-SH-CHKPT-LSP {
    description
      "Checkpointed LSP";
    leaf checkpoint-lsp-object-id {
      type uint32;
      description
        "LSP Checkpoint table object ID";
    }
    leaf checkpoint-lsp-level {
      type uint8;
      description
        "LSP level";
    }
    leaf checkpoint-lsp-local-flag {
      type boolean;
      description
        "TRUE if this is a local LSP";
    }
    leaf checkpoint-lsp-id {
      type xr:Isis-lsp-id;
      description
        "LSP ID";
    }
  }

  grouping ISIS-SH-NBRS-INTF-SUMMARY {
    description
      "Neighbor count summary per interface in Up, Init
       and Down State ";
    container level1-neighbors {
      description
        "Counters for L1-only neighbors in Up, Init and
         Down State";
      uses ISIS-SH-NBR-SUMM-LEVEL;
    }
    container level2-neighbors {
      description
        "Counters for L2-only neighbors in Up, Init and
         Down State";
      uses ISIS-SH-NBR-SUMM-LEVEL;
    }
    container level12-neigbors {
      description
        "Counters for L1L2 neighbors in Up, Init and Down
         State";
      uses ISIS-SH-NBR-SUMM-LEVEL;
    }
    container interface-status {
      description
        "Status of the Interface to form Adjacencies";
      uses ISIS-SH-IF-ADJ-FORM-STATUS;
    }
    leaf interface-name-xr {
      type Isis-sh-interface-name;
      description
        "Name of the Interface";
    }
  }

  grouping ISIS-SH-IP-RIB-TABLE {
    description
      "IP RIB Table";
    leaf description {
      type string;
      description
        "Routing Table Description";
    }
    leaf primary-vrf-name {
      type string;
      description
        "Primary VRF name";
    }
    leaf secondary-vrf-name {
      type string;
      description
        "Secondary VRF name";
    }
    leaf topo-name {
      type string;
      description
        "Topology name";
    }
    leaf af-name {
      type Isis-af-id;
      description
        "Address Family Identifier";
    }
    leaf saf-name {
      type Isis-sub-af-id;
      description
        "Sub Address Family Identifier";
    }
    leaf primary-table-id {
      type uint32;
      description
        "Primary Table ID";
    }
    leaf secondary-table-id {
      type uint32;
      description
        "Secondary Table ID";
    }
    leaf mcast-table-id {
      type uint32;
      description
        "Multicast Table ID";
    }
    leaf srv6-table-id {
      type uint32;
      description
        "SRv6 Table ID";
    }
    leaf primary-rib-handle {
      type uint32;
      description
        "Primary RIB Handle";
    }
    leaf secondary-rib-handle {
      type uint32;
      description
        "Secondary RIB Handle";
    }
    leaf mcast-rib-handle {
      type uint32;
      description
        "Multicast RIB Handle";
    }
    leaf srv6-rib-handle {
      type uint32;
      description
        "SRv6 RIB Handle";
    }
    leaf primary-complete-pending {
      type boolean;
      description
        "Primary Complete pending";
    }
    leaf secondary-complete-pending {
      type boolean;
      description
        "Secondary Complete pending";
    }
    leaf mcast-complete-pending {
      type boolean;
      description
        "Multicast Complete pending";
    }
    leaf srv6-complete-pending {
      type boolean;
      description
        "SRv6 Complete pending";
    }
    leaf ippaths-enabled {
      type boolean;
      description
        "IPpaths Enabled";
    }
  }

  grouping ISIS-SH-GLOBAL-AREA-TOPO-STATS {
    description
      "ISIS process traffic per area topo statistics
       data";
    container statistics {
      description
        "Statistics";
      uses ISIS-AREA-TOPO-STATS-TYPE;
    }
  }

  grouping ISIS-SH-GLOBAL-AREA-STATS {
    description
      "ISIS process traffic per area statistics data";
    container statistics {
      description
        "Statistics";
      uses ISIS-AREA-STATS-TYPE;
    }
  }

  grouping ISIS-SH-TRAFFIC-GLOBAL-TYPE-DATA {
    description
      "IS-IS process traffic statistics data";
    container hello-stats {
      description
        "Counters and statistics for Hello packets";
      uses ISIS-TRAFFIC-PDU-INFO-TYPE;
    }
    container lsp-stats {
      description
        "Counters and statistics for LSP packets";
      uses ISIS-TRAFFIC-PDU-INFO-TYPE;
    }
    container csnp-stats {
      description
        "Counters and statistics for CSNP packets";
      uses ISIS-TRAFFIC-PDU-INFO-TYPE;
    }
    container pspn-stats {
      description
        "Counters and statistics for PSNP packets";
      uses ISIS-TRAFFIC-PDU-INFO-TYPE;
    }
    container new-ls-ps-in-decision-lspdb {
      description
        "New LSPs installed in Decision LSPDB";
      uses ISIS-TRAFFIC-PDU-INFO-TYPE;
    }
    container stray-pdu-timestamp {
      description
        "Timestamp last time a PDU was received on a non
         IS-IS interface";
      uses ISIS-SH-TIMESTAMP-TYPE;
    }
    container events-handled-by-update-thread {
      description
        "Number of timers, incoming packets and other
         events in Hello thread";
      uses ISIS-THREAD-EVENTS-STATS;
    }
    container events-handled-by-hello-thread {
      description
        "Number of timers, incoming packets and other
         events in Update thread";
      uses ISIS-THREAD-EVENTS-STATS;
    }
    container events-handled-by-other-threads {
      description
        "Number of timers, incoming packets and other
         events in other threads";
      uses ISIS-THREAD-EVENTS-STATS;
    }
    leaf zero-holdtime-lsp-count {
      type uint32;
      description
        "LSPs received with holdtime 0";
    }
    leaf invalid-checksum-lsp-count {
      type uint32;
      description
        "LSPs received with invalid checksum";
    }
    leaf lsp-retransmit-count {
      type uint32;
      description
        "LSP retransmissions";
    }
    leaf psnp-schedule-delay {
      type uint32;
      description
        "Update PSNP schedule delay";
    }
    leaf purges-early-drops {
      type uint32;
      description
        "LSP Purges dropped because the Update Queue is
         filling up";
    }
    leaf num-stray-pd-us-recv {
      type uint32;
      description
        "Number of PDUs on interfaces that were not
         configured for IS-IS";
    }
    leaf stray-pdu-ifhandle {
      type xr:Interface-name;
      description
        "Last interface not configured for IS-IS that
         received an IS-IS PDU";
    }
    leaf msec-since-last-stray-pdu {
      type int32;
      description
        "Time in msec since last PDU was received on a
         non IS-IS interface";
    }
    leaf stray-pdu-size {
      type int32;
      description
        "Size of last PDU received on a non IS-IS
         interface";
    }
  }

  grouping ISIS-SH-TRAFFIC-QUEUE-COUNT-TYPE-DATA {
    description
      "Per-queue traffic statistics";
    container total-counts {
      description
        "Total max depth, current depth and drop-count";
      uses ISIS-TRAFFIC-QUEUE-PRIO-COUNT;
    }
    leaf max-combined-queue-size {
      type uint64;
      description
        "Max number of packets of any priority that can
         be stored in queue";
    }
    leaf pd-us-dropped-because-error {
      type uint64;
      description
        "Packets dropped because there was an internal
         error";
    }
  }

  grouping ISIS-SH-TRAFFIC-QUEUE-STATS-PRIO-COUNT-TYPE {
    description
      "Per-prioity traffic statistics";
    container timestamp-high-water-mark {
      description
        "When was the last time the High Watermark was
         set";
      uses ISIS-SH-TIMESTAMP-TYPE;
    }
    container timestamp-last-drop-burst {
      description
        "When was the last time a PDU was dropped";
      uses ISIS-SH-TIMESTAMP-TYPE;
    }
    leaf queue-priority {
      type Qos-pak-prio;
      description
        "Queue Priority";
    }
    leaf client-max-queue-size {
      type uint64;
      description
        "Max number of packets that can be stored in the
         queue";
    }
    leaf pd-us-currently-in-queue {
      type uint64;
      description
        "Current number of packets in the queue";
    }
    leaf queue-high-water-mark {
      type uint64;
      description
        "Largest number of PDUs in the queue in the past";
    }
    leaf total-pd-us-processed {
      type uint64;
      description
        "Number of packets processed by the queue";
    }
    leaf pd-us-dropped {
      type uint64;
      description
        "Packets dropped because the queue was full";
    }
    leaf num-drop-bursts {
      type uint32;
      description
        "Number of contiguous bursts of drops";
    }
    leaf current-drops-burst {
      type uint32;
      description
        "How many PDUs are currently dropped back-to-back";
    }
    leaf last-drops-burst {
      type uint32;
      description
        "How many PDUs were dropped in the last burst";
    }
    leaf drops-burst-high-water-mark {
      type uint32;
      description
        "What is the largest number of back-to-back drops
         there was";
    }
  }

  grouping ISIS-SH-NBRS-UP-SUMMARY {
    description
      "Neighbor count summary, counting adjacencies in
       Up State";
    leaf level-1-nbr-count {
      type uint32;
      description
        "L1-only neighbor count";
    }
    leaf level-2-nbr-count {
      type uint32;
      description
        "L2-only neighbor count";
    }
    leaf level12-nbr-count {
      type uint32;
      description
        "L1L2 neighbor count";
    }
  }

  grouping ISIS-SH-DDADJ-SID {
    description
      "Delay Deletion Protected Adj-SID data";
    container id {
      description
        "Topology ID";
      uses ISIS-TOPO-ID-TYPE;
    }
    container neighbor-ip-address {
      description
        "Neighbor IP address";
      uses ISIS-IP-ADDR-TYPE;
    }
    leaf adj-sid-value {
      type Isis-nodal-sid-value;
      description
        "Protected adjacency sid value";
    }
    leaf is-madj-sid {
      type boolean;
      description
        "Is manual adjacency sid";
    }
    leaf interface {
      type Isis-sh-interface-name;
      description
        "Interface";
    }
    leaf level {
      type Isis-level;
      description
        "Level this data applies to";
    }
    leaf neighbor-id {
      type xr:Osi-system-id;
      description
        "Neighbor ID";
    }
    leaf remaining-time {
      type uint32;
      description
        "Remaining time before deletion";
    }
  }

  grouping ISIS-SH-AREA {
    description
      "Per-area IS-IS protocol data";
    leaf lsp-mtu {
      type uint32;
      description
        "Configured LSP MTU";
    }
    leaf lsp-full {
      type boolean;
      description
        "Indicates whether LSP space is full";
    }
  }

  grouping ISIS-SH-OVRLD-TOPO-INFO {
    description
      "BGP Timer expiry Information per Topology";
    container id {
      description
        "Topology ID";
      uses ISIS-TOPO-ID-TYPE;
    }
    container overload-bit-b-gp-expiry-time-per-topo {
      description
        "Timestamp for BGP Timer Expiry per Topology";
      uses ISIS-SH-TIMESTAMP-TYPE;
    }
  }

  grouping ISIS-SH-OVRLD-BIT {
    description
      "Overload bit Configuration and Operational data";
    container overload-bit-status-change-time {
      description
        "Timestamp when status changes";
      uses ISIS-SH-TIMESTAMP-TYPE;
    }
    container overload-bit-startup-epiry-time {
      description
        "Timestamp for OnStartup Timer Expiry";
      uses ISIS-SH-TIMESTAMP-TYPE;
    }
    container overload-bit-bgp-expiry-time {
      description
        "Timestamp for BGP Timer Expiry";
      uses ISIS-SH-TIMESTAMP-TYPE;
    }
    leaf level {
      type Isis-level;
      description
        "Level this data applies to";
    }
    leaf currently-active {
      type boolean;
      description
        "Overload bit Currently Active";
    }
    leaf mode {
      type Isis-overload-bit-mode;
      description
        "Overload bit mode type";
    }
    leaf overload-bit-on-startup-secs {
      type uint32;
      description
        "Time after reboot";
    }
    leaf advertise-external-prefix {
      type boolean;
      description
        "Advertise Overload bit for external prefixes";
    }
    leaf advertise-inter-level-prefix {
      type boolean;
      description
        "Advertisze Overload bit for interlevel prefixes";
    }
    list overload-bit-expiry-per-topo {
      description
        "Timestamp for BGP Timer Expiry per Toplogy";
      uses ISIS-SH-OVRLD-TOPO-INFO;
    }
  }

  grouping ISIS-SH-MXM {
    description
      "Max Metric Operational data";
    container max-metric-status-change-time {
      description
        "Timestamp when status changes";
      uses ISIS-SH-TIMESTAMP-TYPE;
    }
    container max-metric-startup-epiry-time {
      description
        "Timestamp for OnStartup Timer Expiry";
      uses ISIS-SH-TIMESTAMP-TYPE;
    }
    container max-metric-bgp-expiry-time {
      description
        "Timestamp for BGP Timer Expiry";
      uses ISIS-SH-TIMESTAMP-TYPE;
    }
    leaf active {
      type boolean;
      description
        "Maximum Metric Currently Active";
    }
    leaf level {
      type Isis-level;
      description
        "Level this data applies to";
    }
    leaf max-metric-mode {
      type Isis-max-metric-mode;
      description
        "mode of the max-metric";
    }
    leaf max-metric-redist-pfx {
      type boolean;
      description
        "Override prefix metric from another protocol";
    }
    leaf max-metric-inter-level-pfx {
      type boolean;
      description
        "Override prefix metric from another ISIS Level";
    }
    leaf max-metric-default-route {
      type boolean;
      description
        "Override default route metric";
    }
    leaf max-metric-srv6-locators {
      type boolean;
      description
        "Override Segment routing ipv6 metric";
    }
    leaf max-metric-te-metric {
      type boolean;
      description
        "Override traffic-engineering metric";
    }
    leaf max-metric-delay-metric {
      type boolean;
      description
        "Override link delay metric";
    }
    leaf max-metric-trigger-expired {
      type boolean;
      description
        "Check MaxMetric Trigger Expiry";
    }
    leaf max-metric-on-startup-secs {
      type uint32;
      description
        "Time after reboot";
    }
  }

  grouping ISIS-SH-PROTO {
    description
      "Information about an IS-IS instance";
    container teonnection-timestamp {
      description
        "TE connection up timestamp";
      uses ISIS-SH-TIMESTAMP-TYPE;
    }
    container xtc-connection-timestamp {
      description
        "XTC connection up timestamp";
      uses ISIS-SH-TIMESTAMP-TYPE;
    }
    container mfi-registered-timestamp {
      description
        "MFI registered to LSD timestamp";
      uses ISIS-SH-TIMESTAMP-TYPE;
    }
    container gl-srgb-notif-timestamp {
      description
        "Global SRGB notification timestamp";
      uses ISIS-SH-TIMESTAMP-TYPE;
    }
    container system-memory-state-change-timestamp {
      description
        "System memory state last change timestamp";
      uses ISIS-SH-TIMESTAMP-TYPE;
    }
    container memory-state-change-timestamp {
      description
        "Memory state last change timestamp";
      uses ISIS-SH-TIMESTAMP-TYPE;
    }
    container timestamp-process-started {
      description
        "Timestamp process started";
      uses ISIS-SH-TIMESTAMP-TYPE;
    }
    container timestamp-n-ull0-ready {
      description
        "Timestamp Null0 interface became ready";
      uses ISIS-SH-TIMESTAMP-TYPE;
    }
    container bfd-connection-timestamp {
      description
        "BFD connection up timestamp";
      uses ISIS-SH-TIMESTAMP-TYPE;
    }
    container bfd-role-change-timestamp {
      description
        "BFD HA role change timestamp";
      uses ISIS-SH-TIMESTAMP-TYPE;
    }
    leaf vrf-context {
      type Isis-string;
      description
        "VRF context";
    }
    leaf nsap-system-id {
      type xr:Osi-system-id;
      description
        "Local system ID";
    }
    leaf valid-nsap-system-id {
      type boolean;
      description
        "Indicates if system ID valid";
    }
    leaf instance-id {
      type uint16;
      description
        "instance id";
    }
    leaf running-levels {
      type Isis-levels;
      description
        "Levels running";
    }
    leaf configured-nsf-flavor {
      type Isis-nsf-flavor;
      description
        "Configured NSF type";
    }
    leaf last-restart-nsf-flavor {
      type Isis-nsf-flavor;
      description
        "NSF type of last restart";
    }
    leaf last-restart-status {
      type Isis-startup-status;
      description
        "Last restart status";
    }
    leaf te-connection {
      type Isis-up;
      description
        "TE connection";
    }
    leaf te-connection-flaps {
      type uint32;
      description
        "TE connection flap count";
    }
    leaf xtc-connection {
      type Isis-up;
      description
        "XTC connection";
    }
    leaf xtc-connection-flaps {
      type uint32;
      description
        "XTC connection flap count";
    }
    leaf mfi-is-lsd-registered {
      type boolean;
      description
        "MFI is LSD registered";
    }
    leaf remaining-time-for-next-nsf-restart {
      type uint32;
      description
        "Time remaining until the next NSF restart may be
         attempted";
    }
    leaf adj-form-count {
      type uint32;
      description
        "Adj Forming count";
    }
    leaf adj-full-count {
      type uint32;
      description
        "Adj Full count";
    }
    leaf adj-stagger-enabled {
      type boolean;
      description
        "Adjacency Stagger Enabled";
    }
    leaf adj-stagger-init {
      type uint32;
      description
        "Adjacency Stagger Initiall Number of Forming
         Neighbors Allowed";
    }
    leaf adj-stagger-max {
      type uint32;
      description
        "Adjacency Stagger Max Number of Forming
         Neighbors Allowed";
    }
    leaf srgb-state {
      type yang:hex-string;
      description
        "SRGB State";
    }
    leaf srlb-allocated {
      type boolean;
      description
        "Is SRLB allocated ?";
    }
    leaf srlb-start {
      type uint32;
      description
        "First label in SRLB";
    }
    leaf srlb-end {
      type uint32;
      description
        "Last label in SRLB";
    }
    leaf job-id {
      type int32;
      description
        "Instance job-id";
    }
    leaf process-id {
      type int32;
      description
        "Instance process-id";
    }
    leaf system-memory-state {
      type uint32;
      description
        "System Memory state";
    }
    leaf memory-state {
      type uint32;
      description
        "Memory state";
    }
    leaf memory-state-change-memory-usage {
      type uint64;
      description
        "Memory usage at last memory state change";
    }
    leaf memory-state-change-memory-limit {
      type uint64;
      description
        "Memory limit at last memory state change";
    }
    leaf memory-check-interval {
      type uint32;
      units "second";
      description
        "Memory state monitoring interval in seconds";
    }
    leaf memory-usage {
      type uint64;
      description
        "Memory usage";
    }
    leaf memory-limit {
      type uint64;
      description
        "Memory limit";
    }
    leaf num-nodes {
      type uint32;
      description
        "Number of nodes";
    }
    leaf num-ls-ps {
      type uint32;
      description
        "Number of LSPs";
    }
    leaf num-links {
      type uint32;
      description
        "Number of links";
    }
    leaf num-prefixes {
      type uint32;
      description
        "Number of prefixes";
    }
    leaf num-nets {
      type uint32;
      description
        "Number of nets";
    }
    leaf num-paths {
      type uint32;
      description
        "Number of paths";
    }
    leaf mem-nodes {
      type uint64;
      description
        "Memory consumed by nodes";
    }
    leaf mem-ls-ps {
      type uint64;
      description
        "Memory consumed by LSPs";
    }
    leaf mem-links {
      type uint64;
      description
        "Memory consumed by links";
    }
    leaf mem-prefixes {
      type uint64;
      description
        "Memory consumed by prefixes";
    }
    leaf mem-nets {
      type uint64;
      description
        "Memory consumed by nets";
    }
    leaf mem-paths {
      type uint64;
      description
        "Memory consumed by paths";
    }
    leaf respawn-count {
      type uint32;
      description
        "Process respawn count";
    }
    leaf protocol-shutdown {
      type boolean;
      description
        "Protocol shutdown";
    }
    leaf host-name {
      type string;
      description
        "Local host name";
    }
    leaf rp-name {
      type string;
      description
        "Name of the RP on which this IS-IS process is
         running";
    }
    leaf bfd-connection {
      type Isis-up;
      description
        "BFD connection";
    }
    leaf bfd-connection-flaps {
      type uint32;
      description
        "BFD connection flap count";
    }
    leaf bfd-client-ha-role {
      type uint8;
      description
        "BFD client HA role";
    }
    leaf bfd-server-ha-role {
      type uint8;
      description
        "BFD server HA role";
    }
    leaf fast-flood {
      type boolean;
      description
        "LSP Fast flooding enabled";
    }
    leaf fast-flood-max-lsp-tx {
      type uint32;
      description
        "LSP Fast flooding Max Lsp Tx";
    }
    leaf fast-flood-psnp-delay {
      type uint32;
      description
        "LSP Fast flooding PSNP Delay in msec";
    }
    leaf psnp-interval {
      type uint32;
      description
        "PSNP interval in msec";
    }
    list manual-area-address {
      description
        "Manual area addresses";
      leaf entry {
        type xr:Osi-area-address;
        description
          "Manual area addresses";
      }
    }
    list active-area-address {
      description
        "Active area addresses";
      leaf entry {
        type xr:Osi-area-address;
        description
          "Active area addresses";
      }
    }
    list srgb-start {
      max-elements "8";
      description
        "First label in SRGB";
      leaf entry {
        type uint32;
        description
          "First label in SRGB";
      }
    }
    list srgb-end {
      max-elements "8";
      description
        "Last label in SRGB";
      leaf entry {
        type uint32;
        description
          "Last label in SRGB";
      }
    }
    list per-topo-data {
      description
        "Per-topology data";
      uses ISIS-SH-TOPO;
    }
    list per-level-max-metric-data {
      description
        "Per-level max-metric data";
      uses ISIS-SH-MXM;
    }
    list per-level-overload-bit-data {
      description
        "Per-level overload bit data";
      uses ISIS-SH-OVRLD-BIT;
    }
    list srgb-allocated {
      min-elements 8;
      max-elements "8";
      description
        "Is SRGB allocated ?";
      leaf entry {
        type boolean;
        description
          "Array entry.";
      }
    }
    list per-area-data {
      max-elements "2";
      description
        "Per-area data";
      uses ISIS-SH-AREA;
    }
    list dd-adj-sid-data {
      description
        "Delay Deletion Protected Adj-SID data";
      uses ISIS-SH-DDADJ-SID;
    }
  }

  grouping ISIS-SH-TRAFFIC-DROP-COUNTER {
    description
      "Array of counters why incoming PDUs were rejected";
    leaf rejection-reason {
      type Isis-sh-pdu-rejection-reason;
      description
        "Reason why incoming PDUs were rejected";
    }
    leaf rejection-count {
      type uint32;
      description
        "How often were PDUs rejected because of this
         reason?";
    }
  }

  grouping ISIS-TRAFFIC-INTF-AREA-LAN-TYPE {
    description
      "Per-interface, per-area LAN-only statistics";
    container iih-count {
      description
        "IIH statistics";
      uses ISIS-TRAFFIC-PDU-COUNT-TYPE;
    }
    leaf memory-exhausted-iih-count {
      type uint32;
      description
        "IIHs not sent due to memory exhaustion";
    }
    leaf dis-election-count {
      type uint32;
      description
        "DIS elections";
    }
  }

  grouping ISIS-TRAFFIC-INTF-AREA-TYPE {
    description
      "Per-interface, per-area statistics";
    container lsp-count {
      description
        "LSP statistics";
      uses ISIS-TRAFFIC-PDU-COUNT-TYPE;
    }
    container csnp-count {
      description
        "CSNP statistics";
      uses ISIS-TRAFFIC-PDU-COUNT-TYPE;
    }
    container psnp-count {
      description
        "PSNP statistics";
      uses ISIS-TRAFFIC-PDU-COUNT-TYPE;
    }
    leaf lsp-retransmit-count {
      type uint32;
      description
        "LSP retransmissions";
    }
  }

  grouping ISIS-SH-TRAFFIC-INTF-AREA {
    description
      "Per-interface, per-area data";
    container statistics {
      description
        "Statistics";
      uses ISIS-TRAFFIC-INTF-AREA-TYPE;
    }
    container lan-data {
      description
        "LAN interface statistics. NULL for non-LAN
         interfaces";
      uses ISIS-TRAFFIC-INTF-AREA-LAN-TYPE;
    }
    leaf level {
      type Isis-level;
      description
        "Level of the area this data relates to";
    }
  }

  grouping ISIS-TRAFFIC-INTF-P2P-TYPE {
    description
      "Per-interface point-to-point statistics";
    container iih-count {
      description
        "IIH statistics";
      uses ISIS-TRAFFIC-PDU-COUNT-TYPE;
    }
    leaf memory-exhausted-iih-count {
      type uint32;
      description
        "IIHs not sent due to memory exhaustion";
    }
  }

  grouping ISIS-SH-TRAFFIC-INTF {
    description
      "IS-IS interface traffic data";
    container p2p-statistics {
      description
        "P2P interface statistics. NULL for non-P2P
         interfaces";
      uses ISIS-TRAFFIC-INTF-P2P-TYPE;
    }
    leaf traffic-interface {
      type xr:Interface-name;
      description
        "Interface to which traffic statistics apply";
    }
    leaf peak-output-lsp-rate {
      type uint32;
      description
        "Peak output LSP rate";
    }
    leaf peak-input-lsp-rate {
      type uint32;
      description
        "Peak input LSP rate";
    }
    leaf interface-media-type {
      type Isis-media-class;
      description
        "Interface media class";
    }
    leaf lsp-flooding-dup-count {
      type uint32;
      description
        "Count of LSPs already received by neighbors and
         not flooded";
    }
    leaf pd-us-not-classified {
      type uint32;
      description
        "Dropped PDUs that could not be classified to
         increment a PDU counter";
    }
    list output-lsp-rate-hist {
      description
        "Output LSP rate";
      leaf entry {
        type uint32;
        description
          "Output LSP rate";
      }
    }
    list input-lsp-rate-hist {
      description
        "Input LSP rate";
      leaf entry {
        type uint32;
        description
          "Input LSP rate";
      }
    }
    list per-area-data {
      description
        "Per-area data";
      uses ISIS-SH-TRAFFIC-INTF-AREA;
    }
    list rejection-counter {
      description
        "Counters per reason why incoming PDUs were
         rejected";
      uses ISIS-SH-TRAFFIC-DROP-COUNTER;
    }
  }

  grouping ISIS-SH-CHKPT-IDB {
    description
      "Checkpointed interface";
    leaf checkpoint-object-id {
      type uint32;
      description
        "Checkpoint object ID";
    }
    leaf interface-name-xr {
      type Isis-sh-interface-name;
      description
        "Interface name";
    }
    leaf checkpoint-interface {
      type xr:Interface-name;
      description
        "Local interface";
    }
    leaf local-circuit-number {
      type Isis-circuit-number;
      description
        "Local circuit number";
    }
    leaf dis-areas {
      type Isis-levels;
      description
        "Areas in which this system is DIS";
    }
    leaf has-adjacency {
      type boolean;
      description
        "TRUE if there is an adjacency on this interface";
    }
    leaf local-snpa {
      type xr:Isis-snpa;
      description
        "SNPA of this interface";
    }
    leaf has-joined-mcast-group {
      type boolean;
      description
        "TRUE if multicast group registration succeeded
         on this interface";
    }
    leaf has-achieved-ldp-sync {
      type boolean;
      description
        "MPLS LDP sync status";
    }
    leaf has-achieved-ld-pv6-sync {
      type boolean;
      description
        "MPLS LDPv6 sync status";
    }
  }

  grouping ISIS-SH-NBR-SUMM-LEVEL {
    description
      "Neighbor states for one level";
    leaf neighbor-up-count {
      type uint32;
      description
        "Neighbors up";
    }
    leaf neighbor-init-count {
      type uint32;
      description
        "Neighbors being initialized";
    }
    leaf neighbor-down-count {
      type uint32;
      description
        "Neighbors down";
    }
  }

  grouping ISIS-SH-NBRS-ALL-SUMMARY {
    description
      "Neighbor count summary, counting adjacencies in
       Up, Init and Down State ";
    container level1-neighbors {
      description
        "Counters for L1-only neighbors in Up, Init and
         Down State";
      uses ISIS-SH-NBR-SUMM-LEVEL;
    }
    container level2-neighbors {
      description
        "Counters for L2-only neighbors in Up, Init and
         Down State";
      uses ISIS-SH-NBR-SUMM-LEVEL;
    }
    container level12-neigbors {
      description
        "Counters for L1L2 neighbors in Up, Init and Down
         State";
      uses ISIS-SH-NBR-SUMM-LEVEL;
    }
  }

  grouping ISIS-SH-ERR-LOG-ENT {
    description
      "An entry in the error-log or thread-log";
    container generic-data {
      description
        "Generic entry data";
      uses ISIS-SH-GENERIC-LOG-ENT;
    }
    leaf error-thread-index {
      type uint32;
      description
        "Reporting Thread Identified by Index";
    }
    leaf error-facility {
      type Isis-sh-err-facility;
      description
        "IS-IS subcomponent where the error occurred";
    }
    leaf error-severity {
      type int32;
      description
        "Severity of the warning or error";
    }
    leaf error-related-value {
      type uint64;
      description
        "Opaque numerical value, specific to the error";
    }
    leaf error-message {
      type string;
      description
        "Detailed description of the error";
    }
  }

  grouping ISIS-SH-ERR-LOG-STRUC {
    description
      "Error/Thread log structure";
    leaf log-capacity {
      type uint32;
      description
        "Log Capacity";
    }
    leaf log-size {
      type uint32;
      description
        "Log Size";
    }
    list log-entry {
      description
        "Error/Thread Log entries";
      uses ISIS-SH-ERR-LOG-ENT;
    }
  }

  grouping ISIS-MIB-CIRC-ENTRY {
    description
      "isisCircEntry";
    leaf isis-circ-index {
      type uint32;
      description
        "isisCircIndex";
    }
    leaf isis-circ-if-index {
      type int32;
      description
        "isisCircIfIndex";
    }
    leaf isis-circ-admin-state {
      type int32;
      description
        "isisCircAdminState";
    }
    leaf isis-circ-exist-state {
      type int32;
      description
        "isisCircExistState";
    }
    leaf isis-circ-type {
      type int32;
      description
        "isisCircType";
    }
    leaf isis-circ-ext-domain {
      type int32;
      description
        "isisCircExtDomain";
    }
    leaf isis-circ-level-type {
      type int32;
      description
        "isisCircLevelType";
    }
    leaf isis-circ-passive-circuit {
      type int32;
      description
        "isisCircPassiveCircuit";
    }
    leaf isis-circ-mesh-group-enabled {
      type int32;
      description
        "isisCircMeshGroupEnabled";
    }
    leaf isis-circ-mesh-group {
      type uint32;
      description
        "isisCircMeshGroup";
    }
    leaf isis-circ-small-hellos {
      type int32;
      description
        "isisCircSmallHellos";
    }
    leaf isis-circ-last-up-time {
      type uint32;
      description
        "isisCircLastUpTime";
    }
    leaf isis-circ3-way-enabled {
      type int32;
      description
        "isisCirc3WayEnabled";
    }
    leaf isis-circ-extended-circ-id {
      type uint32;
      description
        "isisCircExtendedCircID";
    }
  }

  grouping ISIS-MIB-SYS-OBJECT {
    description
      "isisSysObject";
    leaf isis-sys-version {
      type int32;
      description
        "isisSysVersion";
    }
    leaf isis-sys-level-type {
      type int32;
      description
        "isisSysLevelType";
    }
    leaf sys-id {
      type xr:Osi-system-id;
      description
        "sys id";
    }
    leaf isis-sys-max-path-splits {
      type uint32;
      description
        "isisSysMaxPathSplits";
    }
    leaf isis-sys-max-lsp-gen-int {
      type uint32;
      description
        "isisSysMaxLSPGenInt";
    }
    leaf isis-sys-poll-es-hello-rate {
      type uint32;
      description
        "isisSysPollESHelloRate";
    }
    leaf isis-sys-wait-time {
      type uint32;
      description
        "isisSysWaitTime";
    }
    leaf isis-sys-admin-state {
      type int32;
      description
        "isisSysAdminState";
    }
    leaf isis-sys-l2to-l1-leaking {
      type int32;
      description
        "isisSysL2toL1Leaking";
    }
    leaf isis-sys-max-age {
      type uint32;
      description
        "isisSysMaxAge";
    }
    leaf isis-sys-receive-lsp-buffer-size {
      type uint32;
      description
        "isisSysReceiveLSPBufferSize";
    }
    leaf isis-sys-notification-enable {
      type int32;
      description
        "isisSysNotificationEnable";
    }
    list sys-prot-supported {
      description
        "sys prot supported";
      leaf entry {
        type uint8;
        description
          "sys prot supported";
      }
    }
  }

  grouping ISIS-MIB-SUMM-ADDR-ENTRY {
    description
      "isisSummAddrEntry";
    container ip-prefix {
      description
        "ip prefix";
      uses ISIS-IP-PREFIX-TYPE;
    }
    leaf isis-summ-addr-metric {
      type uint32;
      description
        "isisSummAddrMetric";
    }
    leaf isis-summ-addr-full-metric {
      type uint32;
      description
        "isisSummAddrFullMetric";
    }
  }

  grouping ISIS-MIB-SUMM-ADDR-TABLE {
    description
      "isisSummAddrTable";
    list isis-summ-addr-entry {
      description
        "isis summ addr entry";
      uses ISIS-MIB-SUMM-ADDR-ENTRY;
    }
  }

  grouping ISIS-MIB-ADJ-ENTRY {
    description
      "isisISAdjEntry";
    leaf isis-is-adj-index {
      type uint32;
      description
        "isisISAdjIndex";
    }
    leaf isis-is-adj-state {
      type int32;
      description
        "isisISAdjState";
    }
    leaf isis-is-adj3-way-state {
      type int32;
      description
        "isisISAdj3WayState";
    }
    leaf nbr-snpa-addr {
      type xr:Isis-snpa;
      description
        "nbr snpa addr";
    }
    leaf isis-is-adj-neigh-sys-type {
      type int32;
      description
        "isisISAdjNeighSysType";
    }
    leaf nbr-system-id {
      type xr:Osi-system-id;
      description
        "nbr system id";
    }
    leaf isis-is-adj-nbr-extended-circ-id {
      type uint32;
      description
        "isisISAdjNbrExtendedCircID";
    }
    leaf isis-is-adj-usage {
      type int32;
      description
        "isisISAdjUsage";
    }
    leaf isis-is-adj-hold-timer {
      type uint32;
      description
        "isisISAdjHoldTimer";
    }
    leaf isis-is-adj-neigh-priority {
      type uint32;
      description
        "isisISAdjNeighPriority";
    }
    leaf isis-is-adj-last-up-time {
      type uint32;
      description
        "isisISAdjLastUpTime";
    }
    leaf isis-circ-index {
      type uint32;
      description
        "isisCircIndex";
    }
    leaf prot-supp {
      type Isis-prot-supp;
      description
        "prot supp";
    }
    list area-addr {
      description
        "area addr";
      leaf entry {
        type xr:Osi-area-address;
        description
          "area addr";
      }
    }
    list ip-addr {
      description
        "ip addr";
      uses ISIS-IP-ADDR-TYPE;
    }
  }

  grouping ISIS-MIB-CIRC-ADJ-TABLE {
    description
      "intermediateIsisISAdjTable";
    list circuit-adj {
      description
        "circuit adj";
      uses ISIS-MIB-ADJ-ENTRY;
    }
  }

  grouping ISIS-MIB-CIRC-LEVEL-ENTRY {
    description
      "isisCircLevelEntry";
    leaf isis-circ-level-index {
      type int32;
      description
        "isisCircLevelIndex";
    }
    leaf isis-circ-level-metric {
      type uint32;
      description
        "isisCircLevelMetric";
    }
    leaf isis-circ-level-wide-metric {
      type uint32;
      description
        "isisCircLevelWideMetric";
    }
    leaf isis-circ-level-is-priority {
      type uint32;
      description
        "isisCircLevelISPriority";
    }
    leaf isis-circ-level-id-octet {
      type uint32;
      description
        "isisCircLevelIDOctet";
    }
    leaf circuit-id {
      type Isis-circuit-id;
      description
        "circuit id";
    }
    leaf circuit-lan-id {
      type Isis-circuit-id;
      description
        "circuit lan id";
    }
    leaf isis-circ-level-hello-multiplier {
      type uint32;
      description
        "isisCircLevelHelloMultiplier";
    }
    leaf isis-circ-level-hello-timer {
      type uint32;
      description
        "isisCircLevelHelloTimer";
    }
    leaf isis-circ-level-dr-hello-timer {
      type uint32;
      description
        "isisCircLevelDRHelloTimer";
    }
    leaf isis-circ-level-lsp-throttle {
      type uint32;
      description
        "isisCircLevelLSPThrottle";
    }
    leaf isis-circ-level-min-lsp-retrans-int {
      type uint32;
      description
        "isisCircLevelMinLSPRetransInt";
    }
    leaf isis-circ-level-csnp-interval {
      type uint32;
      description
        "isisCircLevelCSNPInterval";
    }
    leaf isis-circ-level-part-snp-interval {
      type uint32;
      description
        "isisCircLevelPartSNPInterval";
    }
    leaf isis-circ-index {
      type uint32;
      description
        "isisCircIndex";
    }
  }

  grouping ISIS-MIB-IP-RA-ENTRY {
    description
      "isisIPRAEntry";
    container ip-prefix {
      description
        "ip prefix";
      uses ISIS-IP-PREFIX-TYPE;
    }
    leaf isis-ipra-next-hop-index {
      type uint32;
      description
        "isisIPRANextHopIndex";
    }
    leaf isis-ipra-metric {
      type uint32;
      description
        "isisIPRAMetric";
    }
    leaf isis-ipra-metric-type {
      type int32;
      description
        "isisIPRAMetricType";
    }
    leaf isis-ipra-full-metric {
      type uint32;
      description
        "isisIPRAFullMetric";
    }
    leaf isis-ipra-source-type {
      type int32;
      description
        "isisIPRASourceType";
    }
    leaf isis-sys-level-index {
      type int32;
      description
        "isisSysLevelIndex";
    }
  }

  grouping ISIS-MIB-IP-RA-TABLE {
    description
      "isisIPRATable";
    list route {
      description
        "route";
      uses ISIS-MIB-IP-RA-ENTRY;
    }
  }

  grouping ISIS-MIB-YANG-MODEL-LSP-ENTRY {
    description
      "isisLSPListEntry";
    leaf isis-lsp-level {
      type int32;
      description
        "isisLSPLevel";
    }
    leaf lsp-lspid {
      type xr:Isis-lsp-id;
      description
        "lsp lspid";
    }
    leaf isis-lsptlv-index {
      type uint32;
      description
        "isisLSPTLVIndex";
    }
    leaf isis-lsptlv-seq {
      type uint32;
      description
        "isisLSPTLVSeq";
    }
    leaf isis-lsptlv-checksum {
      type uint16;
      description
        "isisLSPTLVChecksum";
    }
    leaf isis-lsptlv-type {
      type uint8;
      description
        "isisLSPTLVType";
    }
    leaf isis-lsptlv-len {
      type uint8;
      description
        "isisLSPTLVLen";
    }
    leaf isis-lsptlv-value {
      type yang:hex-string;
      description
        "isisLSPTLVValue";
    }
  }

  grouping ISIS-MIB-LSP-SUMMARY-LIST-ENTRY {
    description
      "isisLSPSummaryListEntry";
    leaf isis-lsp-level {
      type int32;
      description
        "isisLSPLevel";
    }
    leaf summ-lspid {
      type xr:Isis-lsp-id;
      description
        "summ lspid";
    }
    leaf isis-lsp-seq {
      type uint32;
      description
        "isisLSPSeq";
    }
    leaf isis-lsp-zero-life {
      type int32;
      description
        "isisLSPZeroLife";
    }
    leaf isis-lsp-checksum {
      type uint32;
      description
        "isisLSPChecksum";
    }
    leaf isis-lsp-lifetime-remain {
      type uint32;
      description
        "isisLSPLifetimeRemain";
    }
    leaf isis-lsppdu-length {
      type uint32;
      description
        "isisLSPPDULength";
    }
    leaf isis-lsp-attributes {
      type uint8;
      description
        "isisLSPAttributes";
    }
  }

  grouping ISIS-MIB-SYS-STAT-LEVEL-ENTRY {
    description
      "isisSystemCounterEntry";
    leaf isis-sys-stat-level {
      type int32;
      description
        "isisSysStatLevel";
    }
    leaf isis-sys-stat-corr-ls-ps {
      type uint32;
      description
        "isisSysStatCorrLSPs";
    }
    leaf isis-sys-stat-auth-type-fails {
      type uint32;
      description
        "isisSysStatAuthTypeFails";
    }
    leaf isis-sys-stat-auth-fails {
      type uint32;
      description
        "isisSysStatAuthFails";
    }
    leaf isis-sys-stat-lsp-dbase-oloads {
      type uint32;
      description
        "isisSysStatLSPDbaseOloads";
    }
    leaf isis-sys-stat-man-addr-drop-from-areas {
      type uint32;
      description
        "isisSysStatManAddrDropFromAreas";
    }
    leaf isis-sys-stat-attmpt-to-ex-max-seq-nums {
      type uint32;
      description
        "isisSysStatAttmptToExMaxSeqNums";
    }
    leaf isis-sys-stat-seq-num-skips {
      type uint32;
      description
        "isisSysStatSeqNumSkips";
    }
    leaf isis-sys-stat-own-lsp-purges {
      type uint32;
      description
        "isisSysStatOwnLSPPurges";
    }
    leaf isis-sys-stat-id-field-len-mismatches {
      type uint32;
      description
        "isisSysStatIDFieldLenMismatches";
    }
    leaf isis-sys-stat-part-changes {
      type uint32;
      description
        "isisSysStatPartChanges";
    }
    leaf isis-sys-stat-spf-runs {
      type uint32;
      description
        "isisSysStatSPFRuns";
    }
    leaf isis-sys-stat-lsp-errors {
      type uint32;
      description
        "isisSysStatLSPErrors";
    }
  }

  grouping ISIS-MIB-SYS-LEVEL-ENTRY {
    description
      "isisSysLevelEntry";
    leaf isis-sys-level-index {
      type int32;
      description
        "isisSysLevelIndex";
    }
    leaf isis-sys-level-orig-lsp-buff-size {
      type uint32;
      description
        "isisSysLevelOrigLSPBuffSize";
    }
    leaf isis-sys-level-min-lsp-gen-int {
      type uint32;
      description
        "isisSysLevelMinLSPGenInt";
    }
    leaf isis-sys-level-state {
      type int32;
      description
        "isisSysLevelState";
    }
    leaf isis-sys-level-set-overload {
      type int32;
      description
        "isisSysLevelSetOverload";
    }
    leaf isis-sys-level-set-overload-until {
      type uint32;
      description
        "isisSysLevelSetOverloadUntil";
    }
    leaf isis-sys-level-metric-style {
      type int32;
      description
        "isisSysLevelMetricStyle";
    }
    leaf isis-sys-level-spf-considers {
      type int32;
      description
        "isisSysLevelSPFConsiders";
    }
    leaf isis-sys-level-te-enabled {
      type int32;
      description
        "isisSysLevelTEEnabled";
    }
  }

  grouping ISIS-MIB-PACKET-COUNTER-ENTRY {
    description
      "isisPacketCounterEntry";
    leaf isis-packet-count-level {
      type int32;
      description
        "isisPacketCountLevel";
    }
    leaf isis-packet-count-direction {
      type int32;
      description
        "isisPacketCountDirection";
    }
    leaf isis-packet-count-ii-hello {
      type uint32;
      description
        "isisPacketCountIIHello";
    }
    leaf isis-packet-count-is-hello {
      type uint32;
      description
        "isisPacketCountISHello";
    }
    leaf isis-packet-count-es-hello {
      type uint32;
      description
        "isisPacketCountESHello";
    }
    leaf isis-packet-count-lsp {
      type uint32;
      description
        "isisPacketCountLSP";
    }
    leaf isis-packet-count-csnp {
      type uint32;
      description
        "isisPacketCountCSNP";
    }
    leaf isis-packet-count-psnp {
      type uint32;
      description
        "isisPacketCountPSNP";
    }
    leaf isis-packet-count-unknown {
      type uint32;
      description
        "isisPacketCountUnknown";
    }
    leaf isis-circ-index {
      type uint32;
      description
        "isisCircIndex";
    }
  }

  grouping ISIS-AREA-ADDRESS-TYPE {
    description
      "IS-IS area address";
    leaf area-address-length {
      type uint8;
      units "byte";
      description
        "area address length (bytes)";
    }
    leaf area-address {
      type yang:hex-string;
      description
        "Encoded area address";
    }
  }

  grouping ISIS-MIB-AREA-ADDR-TABLE {
    description
      "isisAreaAddrTable";
    list area-addr {
      description
        "area addr";
      uses ISIS-AREA-ADDRESS-TYPE;
    }
  }

  grouping ISIS-MIB-CIRCUIT-COUNTER-ENTRY {
    description
      "isisCircuitCounterEntry";
    leaf isis-circuit-type {
      type int32;
      description
        "isisCircuitType";
    }
    leaf isis-circ-adj-changes {
      type uint32;
      description
        "isisCircAdjChanges";
    }
    leaf isis-circ-num-adj {
      type uint32;
      description
        "isisCircNumAdj";
    }
    leaf isis-circ-init-fails {
      type uint32;
      description
        "isisCircInitFails";
    }
    leaf isis-circ-rej-adjs {
      type uint32;
      description
        "isisCircRejAdjs";
    }
    leaf isis-circ-id-field-len-mismatches {
      type uint32;
      description
        "isisCircIDFieldLenMismatches";
    }
    leaf isis-circ-max-area-addr-mismatches {
      type uint32;
      description
        "isisCircMaxAreaAddrMismatches";
    }
    leaf isis-circ-auth-type-fails {
      type uint32;
      description
        "isisCircAuthTypeFails";
    }
    leaf isis-circ-auth-fails {
      type uint32;
      description
        "isisCircAuthFails";
    }
    leaf isis-circ-lan-des-is-changes {
      type uint32;
      description
        "isisCircLANDesISChanges";
    }
    leaf isis-circ-index {
      type uint32;
      description
        "isisCircIndex";
    }
  }

  grouping ISIS-SH-TOPO-PART-DET {
    description
      "Configured Partition-detect Tracks";
    container internal-ip-address {
      description
        "Internal IP address";
      uses ISIS-IP-ADDR-TYPE;
    }
    container external-ip-address {
      description
        "External IP address";
      uses ISIS-IP-ADDR-TYPE;
    }
    leaf external-address-set {
      type boolean;
      description
        "External Address Set";
    }
    leaf is-active {
      type boolean;
      description
        "Partition Active";
    }
  }

  grouping ISIS-SH-DEF-ORIG {
    description
      "Default Route Origination";
    container status-changed-time {
      description
        "Default route origination status change";
      uses ISIS-SH-TIMESTAMP-TYPE;
    }
    leaf enabled {
      type boolean;
      description
        "Default route origination enabled";
    }
    leaf active {
      type boolean;
      description
        "Default route origination currently active";
    }
  }

  grouping ISIS-SH-TOPO-LOCATOR {
    description
      "Configured SRv6 Locator";
    leaf locator-active {
      type boolean;
      description
        "Locator exists in global configuration";
    }
    leaf anycast-locator {
      type boolean;
      description
        "Anycast Locator";
    }
    leaf locator-out-of-resources {
      type boolean;
      description
        "Locator has no more SIDs available";
    }
    leaf locator-name {
      type string;
      description
        "Locator name";
    }
  }

  grouping ISIS-SH-TOPO-AREA {
    description
      "Per-topology, per-area IS-IS protocol data";
    leaf level {
      type Isis-level;
      description
        "The level this data refers to";
    }
    leaf uses-default-link-topo-flag {
      type boolean;
      description
        "Does this topology use the default link topology";
    }
    leaf generated-metric-style {
      type Isis-metric-style;
      description
        "Generate metric style";
    }
    leaf accepted-metric-style {
      type Isis-metric-style;
      description
        "Accept metric style";
    }
    leaf metric {
      type Isis-metric;
      description
        "Metric";
    }
    leaf ispf-state {
      type Isis-enabled;
      description
        "ISPF state";
    }
    leaf te-enabled {
      type boolean;
      description
        "Indicates whether MPLS TE is enabled";
    }
    leaf uloop-avoidance-type {
      type Isis-uloop-avoidance;
      description
        "Microloop avoidance type";
    }
    leaf uloop-policy-name {
      type string;
      description
        "Microloop avoidance Policy Name";
    }
    leaf rib-update-delay {
      type uint32;
      description
        "Microloop RIB update delay";
    }
    leaf sr-uloop-is-active {
      type boolean;
      description
        "Explicit paths installed in the RIB";
    }
    leaf duration {
      type uint32;
      description
        "SR microloop avoidance duration";
    }
    leaf sr-uloop-event {
      type Isis-uloop-event;
      description
        "SR microloop avoidance event";
    }
    leaf sr-uloop-near-node-id {
      type xr:Isis-node-id;
      description
        "SR microloop near node";
    }
    leaf sr-uloop-far-node-id {
      type xr:Isis-node-id;
      description
        "SR microloop far node";
    }
  }

  grouping ISIS-SH-REDIST-ENTRY {
    description
      "Redistributed protocol entry";
    list isis-sh-redist-entry {
      description
        "Next entry in list";
      container protocol-details {
        description
          "Relevant details of the redistributed protocol";
        uses ISIS-SH-REDIST-ENTRY-PROTO;
      }
    }
  }

  grouping ISIS-SH-TOPO {
    description
      "Per-topology IS-IS instance data";
    container id {
      description
        "Topology ID";
      uses ISIS-TOPO-ID-TYPE;
    }
    container redist-protocols-list {
      description
        "List of redistributed protocols";
      uses ISIS-SH-REDIST-ENTRY;
    }
    container default-origination {
      description
        "Default Origination";
      uses ISIS-SH-DEF-ORIG;
    }
    leaf default-admin-distance {
      type uint32;
      description
        "Default administrative distance";
    }
    leaf advertise-passive-only {
      type boolean;
      description
        "Advertise passive interface prefixes only";
    }
    leaf wait-redist-complete {
      type boolean;
      description
        "Waiting for redist complete RIB event";
    }
    leaf rib-connected {
      type boolean;
      description
        "Rib Connected";
    }
    leaf sr-mpls-enabled {
      type boolean;
      description
        "SR-MPLS is enabled";
    }
    leaf srv6-enabled {
      type boolean;
      description
        "SRv6 is enabled";
    }
    list per-area-data {
      description
        "Per-area data";
      uses ISIS-SH-TOPO-AREA;
    }
    list srv6-configured-locator {
      description
        "Configured SRv6 locators";
      uses ISIS-SH-TOPO-LOCATOR;
    }
    list partition-detect-track {
      description
        "Nodes to be tracked for area or domain partition
         detection";
      uses ISIS-SH-TOPO-PART-DET;
    }
  }

  grouping ISIS-SH-FLEX-ALGO-AREA {
    description
      "Flex Algo Area";
    leaf level {
      type Isis-level;
      description
        "Level";
    }
    leaf disabled {
      type boolean;
      description
        "Flex-Algo Disabled";
    }
    leaf definition-priority {
      type uint32;
      description
        "Flex-Algo Definition Priority";
    }
    leaf metric-type {
      type Isis-flex-algo-metric;
      description
        "Flex-Algo Metric Type";
    }
    leaf prefix-metric {
      type boolean;
      description
        "Flex-Algo Prefix Metric";
    }
    leaf definition-local {
      type boolean;
      description
        "Flex-Algo Definition Is Local";
    }
    leaf definition-equal-local {
      type boolean;
      description
        "Flex-Algo Definition Is Equal To Local";
    }
    leaf definition-node-id {
      type xr:Isis-node-id;
      description
        "Flex-Algo Definition Node-ID";
    }
    leaf minimum-bandwidth {
      type uint64;
      description
        "Flex-Algo Minimum Link Bandwidth";
    }
    leaf maximum-delay {
      type uint32;
      description
        "Flex-Algo Maximum Link Delay";
    }
    leaf auto-cost-ref-bandwidh {
      type uint64;
      description
        "Flex-Algo Auto-Cost Reference Bandwidth";
    }
    leaf auto-cost-granularity {
      type uint64;
      description
        "Flex-Algo Auto-Cost Granularity";
    }
    leaf auto-cost-group-mode {
      type boolean;
      description
        "Flex-Algo Auto-Cosy Group-mode";
    }
    list excl-affinity {
      description
        "ExclAffinity";
      leaf entry {
        type uint32;
        description
          "ExclAffinity";
      }
    }
    list incl-any-affinity {
      description
        "InclAnyAffinity";
      leaf entry {
        type uint32;
        description
          "InclAnyAffinity";
      }
    }
    list incl-all-affinity {
      description
        "InclAllAffinity";
      leaf entry {
        type uint32;
        description
          "InclAllAffinity";
      }
    }
    list exc-srlg {
      description
        "ExclSRLG";
      leaf entry {
        type uint32;
        description
          "ExclSRLG";
      }
    }
    list reverse-excl-affinity {
      description
        "ReverseExclAffinity";
      leaf entry {
        type uint32;
        description
          "ReverseExclAffinity";
      }
    }
    list reverse-incl-any-affinity {
      description
        "ReverseInclAnyAffinity";
      leaf entry {
        type uint32;
        description
          "ReverseInclAnyAffinity";
      }
    }
    list reverse-incl-all-affinity {
      description
        "ReverseInclAllAffinity";
      leaf entry {
        type uint32;
        description
          "ReverseInclAllAffinity";
      }
    }
  }

  grouping ISIS-SH-FLEX-ALGO {
    description
      "Flex Algo";
    leaf number {
      type uint32;
      description
        "Flex-Algo Number";
    }
    leaf local-priority {
      type uint32;
      description
        "Flex_algo Local Priority";
    }
    leaf frr-disabled {
      type boolean;
      description
        "Flex-Algo FRR Disabled";
    }
    leaf microloop-avoidance-disabled {
      type boolean;
      description
        "Flex-Algo Microloop Avoidance Disabled";
    }
    leaf ucmp-disabled {
      type boolean;
      description
        "Flex-Algo UCMP Disabled";
    }
    leaf data-plane-sr {
      type boolean;
      description
        "Flex-Algo Data Plane Segment Routing";
    }
    leaf data-plane-ip {
      type boolean;
      description
        "Flex-Algo Data Plane IP";
    }
    list area {
      description
        "Per Area Flex-Algo";
      uses ISIS-SH-FLEX-ALGO-AREA;
    }
    list per-topo-data {
      description
        "Per-topology data";
      uses ISIS-SH-TOPO;
    }
  }

  grouping ISIS-SH-CHKPT-ADJ {
    description
      "Checkpointed adjacency";
    leaf checkpoint-adjacency-object-id {
      type uint32;
      description
        "Checkpoint object ID";
    }
    leaf checkpoint-adjacency-system-id {
      type xr:Osi-system-id;
      description
        "Neighbor system ID";
    }
    leaf checkpoint-adjacency-snpa {
      type xr:Isis-snpa;
      description
        "Neighbor SNPA";
    }
    leaf checkpoint-adjacency-interface {
      type xr:Interface-name;
      description
        "Local interface";
    }
    leaf checkpoint-adjacency-level {
      type Isis-level;
      description
        "Adjacency level";
    }
    leaf checkpoint-adjacency-holdtime {
      type uint16;
      description
        "Adjacency holdtime (s)";
    }
    leaf checkpoint-adjacency-lan-priority {
      type Isis-dr-priority;
      description
        "Adjacency LAN priority";
    }
    leaf checkpoint-adjacency-circuit-number {
      type Isis-circuit-number;
      description
        "Neighbor circuit number";
    }
    list checkpoint-adjacency-per-address-family-next-hop {
      description
        "Per address family next hops";
      uses ISIS-IP-ADDR-TYPE;
    }
  }

  grouping ISIS-SH-IF-AF-PREFIX-DATA {
    description
      "Address prefix info";
    leaf is-unnumbered {
      type boolean;
      description
        "Is the interface unnumbered";
    }
    list algo {
      description
        "algo";
      leaf entry {
        type uint32;
        description
          "algo";
      }
    }
    list prefix {
      description
        "Array of global prefixes";
      uses ISIS-IP-PREFIX-TYPE;
    }
  }

  grouping ISIS-SH-IF-AF-PREFIX-UNKNOWN {
    description
      "Address prefix unknown info";
    leaf reason-code {
      type Isis-if-af-prefix-unknown-reason;
      description
        "Reason why the global prefix(es) is(are) unknown";
    }
  }

  grouping ISIS-SH-IF-AF-PREFIX-STATUS {
    description
      "ISIS SH IF AF PREFIX STATUS";
    container unknown {
      when "../status = 'isis-unknown'" {
        description
          "../Status = 'ISIS_UNKNOWN'";
      }
      description
        "Unknown state for the global prefixes";
      uses ISIS-SH-IF-AF-PREFIX-UNKNOWN;
    }
    container prefix-data {
      when "../status = 'isis-known'" {
        description
          "../Status = 'ISIS_KNOWN'";
      }
      description
        "Global prefix data for the Address Family";
      uses ISIS-SH-IF-AF-PREFIX-DATA;
    }
    leaf status {
      type Isis-known;
      description
        "Status";
    }
  }

  grouping ISIS-IP-ADDR-TYPE {
    description
      "ISIS IP ADDR TYPE";
    leaf af-name {
      type Isis-af-id;
      description
        "AFName";
    }
    leaf ipv4 {
      when "../af-name = 'ipv4'" {
        description
          "../AFName = 'IPv4'";
      }
      type Isis-ipv4-address;
      description
        "IPV4 address type";
    }
    leaf ipv6 {
      when "../af-name = 'ipv6'" {
        description
          "../AFName = 'IPv6'";
      }
      type Isis-ipv6-address;
      description
        "IPV6 address type";
    }
  }

  grouping ISIS-SH-IF-AF-FWD-ADDR-DATA {
    description
      "Address-family forwarding address data";
    leaf unnumbered-interface-name {
      type Isis-sh-interface-name;
      description
        "If the interface is unnumbered, then its name,
         else NULL";
    }
    list forwarding-address {
      description
        "Array of forwarding addresses";
      uses ISIS-IP-ADDR-TYPE;
    }
  }

  grouping ISIS-SH-IF-AF-FWD-ADDR-UNKNOWN {
    description
      "Forwarding address unknown data";
    leaf reason-code {
      type Isis-if-af-fwd-addr-unknown-reason;
      description
        "Reason why the forwarding address(es) of an AF
         is(are) unknown";
    }
  }

  grouping ISIS-SH-IF-AF-FWD-ADDR-STATUS {
    description
      "ISIS SH IF AF FWD ADDR STATUS";
    container unknown {
      when "../status = 'isis-unknown'" {
        description
          "../Status = 'ISIS_UNKNOWN'";
      }
      description
        "Unknown forwarding address data";
      uses ISIS-SH-IF-AF-FWD-ADDR-UNKNOWN;
    }
    container forwarding-address-data {
      when "../status = 'isis-known'" {
        description
          "../Status = 'ISIS_KNOWN'";
      }
      description
        "Known Forwarding address data";
      uses ISIS-SH-IF-AF-FWD-ADDR-DATA;
    }
    leaf status {
      type Isis-known;
      description
        "Status";
    }
  }

  grouping ISIS-SH-IF-AF-PROTO-DOWN {
    description
      "Address family protocol down info";
    leaf reason-code {
      type Isis-if-af-proto-down-reason;
      description
        "Reason why the Address Family protocol status is
         down";
    }
  }

  grouping ISIS-SH-IF-AF-PROTO-STATUS {
    description
      "ISIS SH IF AF PROTO STATUS";
    container disabled {
      when "../status = 'isis-down'" {
        description
          "../Status = 'ISIS_DOWN'";
      }
      description
        "Disabled state of the Address Family protocol";
      uses ISIS-SH-IF-AF-PROTO-DOWN;
    }
    leaf status {
      type Isis-up;
      description
        "Status";
    }
  }

  grouping ISIS-SH-IF-AF-ENABLED {
    description
      "Enabled address-family info of an interface";
    container protocol-status {
      description
        "Protocol status of the AF";
      uses ISIS-SH-IF-AF-PROTO-STATUS;
    }
    container forwarding-address-status {
      description
        "Forwarding status of the AF";
      uses ISIS-SH-IF-AF-FWD-ADDR-STATUS;
    }
    container prefix-status {
      description
        "Prefix status of the AF";
      uses ISIS-SH-IF-AF-PREFIX-STATUS;
    }
  }

  grouping ISIS-SH-IF-AF-DISABLED {
    description
      "Address family disabled info";
    leaf reason-code {
      type Isis-if-af-disabled-reason;
      description
        "Reason why the Address Family is disabled";
    }
  }

  grouping ISIS-SH-IF-AF-STATUS {
    description
      "ISIS SH IF AF STATUS";
    container disabled {
      when "../status = 'isis-disabled'" {
        description
          "../Status = 'ISIS_DISABLED'";
      }
      description
        "Disabled info for the AF of an interface";
      uses ISIS-SH-IF-AF-DISABLED;
    }
    container af-data {
      when "../status = 'isis-enabled'" {
        description
          "../Status = 'ISIS_ENABLED'";
      }
      description
        "Enabled data for the AF of an interface";
      uses ISIS-SH-IF-AF-ENABLED;
    }
    leaf status {
      type Isis-enabled;
      description
        "Status";
    }
  }

  grouping ISIS-SH-IF-AF {
    description
      "Per Address family info";
    container af-status {
      description
        "Address Family status of the interface";
      uses ISIS-SH-IF-AF-STATUS;
    }
    container last-im-state-change {
      description
        "Last time the Adress Family IM State changed";
      uses ISIS-SH-TIMESTAMP-TYPE;
    }
    leaf af-name {
      type Isis-af-id;
      description
        "Address Family Identifier of the interface";
    }
    leaf im-state {
      type Im-state;
      description
        "IP Interface State as reported by the Interface
         Manager";
    }
  }

  grouping ISIS-SH-MADJ-SID-IF {
    description
      "Manual Adjacency SID Interface Configuration and
       Operation";
    leaf manual-adjacency-sid-label {
      type Isis-nodal-sid-value;
      description
        "Manual Adjacency SID Label";
    }
    leaf manual-adjacency-sid-index {
      type Isis-nodal-sid-value;
      description
        "Manual Adjacency SID Index (if configured as
         index)";
    }
    leaf manual-adjacency-sid-type {
      type uint8;
      description
        "Manual Adjacency SID Type (Absolute or Index)";
    }
    leaf sid-protected {
      type boolean;
      description
        "SID configured as protected by backup path";
    }
    leaf sid-active {
      type boolean;
      description
        "SID is in use";
    }
  }

  grouping ISIS-FRR-TIEBREAKER-SORTED {
    description
      "FRR Tie Breaker Structure";
    leaf tie-breaker {
      type Isis-frr-tiebreaker;
      description
        "Tie Breaker Type";
    }
    leaf index {
      type uint8;
      description
        "Tie Breaker Index";
    }
  }

  grouping ISIS-SH-IF-FRR-LEVEL {
    description
      "Per level FRR information";
    leaf frr-type {
      type Isis-frr;
      description
        "FRR type configured per level for this interface";
    }
    leaf is-frr {
      type boolean;
      description
        "Is FRR enabled per level on this interface";
    }
    leaf is-remote-lfa {
      type boolean;
      description
        "Is FRR Remote LFA enabled per level for this
         interface";
    }
    leaf is-ti-lfa {
      type boolean;
      description
        "Is FRR TI LFA enabled per level for this
         interface";
    }
    leaf ti-lfa-node-tie-breaker-index {
      type uint8;
      description
        "TI LFA node-protecting Tie breaker index";
    }
    leaf ti-lfa-srlg-tie-breaker {
      type uint8;
      description
        "TI LFA srlg Tie breaker index";
    }
    leaf ti-lfa-linecard-disjoint-tie-breaker {
      type uint8;
      description
        "TI LFA Linecard Disjoint Tie breaker index";
    }
    leaf is-tie-breakers-configured {
      type boolean;
      description
        "Is Tiebreaker configured per level for this
         interface";
    }
    list frr-tie-breaker {
      max-elements "8";
      description
        "FRR TieBreakers array per level for this
         interface";
      uses ISIS-FRR-TIEBREAKER-SORTED;
    }
  }

  grouping ISIS-SH-GEN-METRIC {
    description
      "Generic Metric";
    leaf metric-type {
      type uint32;
      description
        "Generic-metric Type";
    }
    leaf metric-value {
      type uint32;
      description
        "Generic-metric Value";
    }
  }

  grouping ISIS-SH-IF-TOPO-ADV-PREFIX-DISABLED {
    description
      "Topology info when prefix advertisement is
       disabled";
    leaf reason-code {
      type Isis-if-topo-adv-prefix-disabled-reason;
      description
        "Reason why the prefix advertisement status of a
         topology is disabled";
    }
  }

  grouping ISIS-SH-IF-TOPO-ADV-PREFIX-STATUS {
    description
      "ISIS SH IF TOPO ADV PREFIX STATUS";
    container disabled {
      when "../status = 'isis-disabled'" {
        description
          "../Status = 'ISIS_DISABLED'";
      }
      description
        "Disabled state for the prefix advertisement
         status of a topology";
      uses ISIS-SH-IF-TOPO-ADV-PREFIX-DISABLED;
    }
    leaf status {
      type Isis-enabled;
      description
        "Status";
    }
  }

  grouping ISIS-SH-IF-TOPO-ADJ-FORM-DISABLED {
    description
      "Topology info when adjacency formation is
       disabled";
    leaf reason-code {
      type Isis-if-topo-adj-form-disabled-reason;
      description
        "Reason why the adjacency formation status of a
         topology is disabled";
    }
  }

  grouping ISIS-SH-IF-TOPO-ADJ-FORM-STATUS {
    description
      "ISIS SH IF TOPO ADJ FORM STATUS";
    container disabled {
      when "../status = 'isis-disabled'" {
        description
          "../Status = 'ISIS_DISABLED'";
      }
      description
        "Disabled state for the adjacency formation
         status of a topology";
      uses ISIS-SH-IF-TOPO-ADJ-FORM-DISABLED;
    }
    leaf status {
      type Isis-enabled;
      description
        "Status";
    }
  }

  grouping ISIS-SH-IF-TOPO-ENABLED {
    description
      "Enabled topology info of an interface";
    container adjacency-form-status {
      description
        "Adjacency formation status of a topology";
      uses ISIS-SH-IF-TOPO-ADJ-FORM-STATUS;
    }
    container adv-prefix-status {
      description
        "Prefix advertisement status of a topology";
      uses ISIS-SH-IF-TOPO-ADV-PREFIX-STATUS;
    }
    container level1-frr {
      description
        "Level1 FRR information";
      uses ISIS-SH-IF-FRR-LEVEL;
    }
    container level2-frr {
      description
        "Level2 FRR information";
      uses ISIS-SH-IF-FRR-LEVEL;
    }
    leaf level1-metric {
      type Isis-metric;
      description
        "L1 metric for this topology";
    }
    leaf level2-metric {
      type Isis-metric;
      description
        "L2 metric for this topology";
    }
    leaf level1te-metric {
      type Isis-metric;
      description
        "L1 TE metric for this topology";
    }
    leaf level2te-metric {
      type Isis-metric;
      description
        "L2 TE metric for this topology";
    }
    leaf level1bw-metric {
      type Isis-metric;
      description
        "L1 BW metric for this topology";
    }
    leaf level2bw-metric {
      type Isis-metric;
      description
        "L2 BW metric for this topology";
    }
    leaf level1-weight {
      type Isis-metric;
      description
        "L1 metric for this topology";
    }
    leaf level2-weight {
      type Isis-metric;
      description
        "L2 metric for this topology";
    }
    leaf level1-metric-fallback-bandwidth-activated {
      type boolean;
      description
        "L1 metric fallback bandwidth activated";
    }
    leaf level2-metric-fallback-bandwidth-activated {
      type boolean;
      description
        "L2 metric fallback bandwidth activated";
    }
    leaf level1-metric-fallback-anomaly-activated {
      type boolean;
      description
        "L1 metric fallback anomaly activated";
    }
    leaf level2-metric-fallback-anomaly-activated {
      type boolean;
      description
        "L2 metric fallback anomaly activated";
    }
    leaf max-label-supported {
      type uint8;
      description
        "MPLS maximum number of pri labels supported";
    }
    leaf max-bkp-label-supported {
      type uint8;
      description
        "MPLS maximum number of backup labels supported";
    }
    leaf max-srte-label-supported {
      type uint8;
      description
        "MPLS maximum number of srte labels supported";
    }
    leaf max-srat-label-supported {
      type uint8;
      description
        "MPLS maximum number of sr auto-tunnel labels
         supported";
    }
    leaf level1ldp-sync-enabled {
      type boolean;
      description
        "MPLS LDP sync enabled status for L1";
    }
    leaf level2ldp-sync-enabled {
      type boolean;
      description
        "MPLS LDP sync enabled status for L2";
    }
    leaf ldp-sync-status {
      type boolean;
      description
        "Status of MPLS LDP synchronization";
    }
    leaf ld-pv6-sync-status {
      type boolean;
      description
        "Status of MPLS LDPv6 synchronization";
    }
    leaf level1-offset-metric {
      type Isis-metric;
      description
        "L1 metric-offset for this topology";
    }
    leaf level2-offset-metric {
      type Isis-metric;
      description
        "L2 metric-offset for this topology";
    }
    leaf level1-lkgp-configured {
      type boolean;
      description
        "Link-Group configure status for L1";
    }
    leaf level2-lkgp-configured {
      type boolean;
      description
        "Link-Group configure status for L2";
    }
    leaf level1pp-metric {
      type Isis-metric;
      description
        "L1 PP-metric for this topology";
    }
    leaf level2pp-metric {
      type Isis-metric;
      description
        "L2 PP-metric for this topology";
    }
    leaf level1pp-configured {
      type boolean;
      description
        "PP configure status for L1";
    }
    leaf level2pp-configured {
      type boolean;
      description
        "PP configure status for L2";
    }
    leaf link-group-name {
      type string;
      description
        "Link-Group name";
    }
    leaf l1-adv-pfx-policy {
      type string;
      description
        "L1 Advertise Prefix Policy Name";
    }
    leaf l2-adv-pfx-policy {
      type string;
      description
        "L2 Advertise Prefix Policy Name";
    }
    leaf l1-adv-pfx-pass {
      type boolean;
      description
        "L1 Advertise Prefix Policy Pass";
    }
    leaf l2-adv-pfx-pass {
      type boolean;
      description
        "L2 Advertise Prefix Policy Pass";
    }
    list l1-generic-metric-flex-algo {
      description
        "Array of L1 Flex-algo Generic Metrics";
      uses ISIS-SH-GEN-METRIC;
    }
    list l2-generic-metric-flex-algo {
      description
        "Array of L2 Flex-algo Generic Metrics";
      uses ISIS-SH-GEN-METRIC;
    }
    list manual-adj-sid {
      description
        "Array of Manual Adjacency SIDs";
      uses ISIS-SH-MADJ-SID-IF;
    }
  }

  grouping ISIS-SH-IF-TOPO-DISABLED {
    description
      "Disabled topology info of an interface";
    leaf reason-code {
      type Isis-if-topo-disabled-reason;
      description
        "Reason why the topology is disabled";
    }
  }

  grouping ISIS-SH-IF-TOPO-STATUS {
    description
      "ISIS SH IF TOPO STATUS";
    container disabled {
      when "../status = 'isis-disabled'" {
        description
          "../Status = 'ISIS_DISABLED'";
      }
      description
        "Disabled information of a topology";
      uses ISIS-SH-IF-TOPO-DISABLED;
    }
    container enabled {
      when "../status = 'isis-enabled'" {
        description
          "../Status = 'ISIS_ENABLED'";
      }
      description
        "Enabled information of a topology";
      uses ISIS-SH-IF-TOPO-ENABLED;
    }
    leaf status {
      type Isis-enabled;
      description
        "Status";
    }
  }

  grouping ISIS-SH-IF-TOPO {
    description
      "Per topology info of an interface";
    container topology-id {
      description
        "Topology identifier";
      uses ISIS-TOPO-ID-TYPE;
    }
    container status {
      description
        "Status of the topology";
      uses ISIS-SH-IF-TOPO-STATUS;
    }
  }

  grouping ISIS-SH-IF-AREA-ACTIVE-LAN {
    description
      "Per-interface, per-area data for active LAN
       interface";
    leaf circuit-lan-id {
      type Isis-circuit-id;
      description
        "Circuit LAN ID";
    }
    leaf time-until-next-iih {
      type uint32;
      description
        "Time (ms) until next IIH";
    }
    leaf interface-priority {
      type Isis-dr-priority;
      description
        "Interface's DIS-election priority";
    }
    leaf dispriority {
      type Isis-dr-priority;
      description
        "Priority of current DIS on this LAN";
    }
    leaf are-we-dis {
      type boolean;
      description
        "Flag indicating if this LAN circuit is the DIS";
    }
  }

  grouping ISIS-SH-IF-AREA-ACTIVE {
    description
      "Per-area data for an interface";
    container lan-data {
      description
        "LAN data, NULL iff interface has non-LAN media
         type";
      uses ISIS-SH-IF-AREA-ACTIVE-LAN;
    }
    leaf level {
      type Isis-level;
      description
        "Level of the area";
    }
    leaf adjacency-count {
      type uint32;
      description
        "Number of adjacencies";
    }
    leaf lsp-pacing-interval {
      type uint32;
      description
        "LSP pacing time period (ms)";
    }
    leaf psnp-transmit-queue-size {
      type uint32;
      description
        "No. of SNP entries queued to be transmitted";
    }
    leaf hello-interval {
      type uint32;
      description
        "Hello interval";
    }
    leaf hello-multiplier {
      type uint32;
      description
        "Hello Multiplier";
    }
    leaf lsp-mtu {
      type uint32;
      description
        "When set, the interface MTU is smaller than the
         LSP MTU";
    }
    leaf adjacency-flaps {
      type uint32;
      description
        "Number of times an Adjacency changed state from
         Up to Down";
    }
  }

  grouping ISIS-SH-IF-CLNS-P2P-OVER-LAN {
    description
      "Point-to-point over LAN specific CLNS state";
    container multicast-status {
      description
        "Multicast group membership status";
      uses ISIS-SH-IF-MCAST-STATUS;
    }
  }

  grouping ISIS-SH-IF-CLNS-P2P {
    description
      "Point-to-point CLNS state";
    container p2p-over-lan-data {
      description
        "Point-to-point over LAN data";
      uses ISIS-SH-IF-CLNS-P2P-OVER-LAN;
    }
  }

  grouping ISIS-SH-IF-MCAST-INVALID {
    description
      "Invalid multicast info";
    leaf reason-code {
      type Isis-if-mcast-invalid-reason;
      description
        "Reason why the multicast status is invalid";
    }
  }

  grouping ISIS-SH-IF-MCAST-STATUS {
    description
      "ISIS SH IF MCAST STATUS";
    container invalid {
      when "../status = 'isis-invalid'" {
        description
          "../Status = 'ISIS_INVALID'";
      }
      description
        "Information pertaining to the invalid multicast
         status";
      uses ISIS-SH-IF-MCAST-INVALID;
    }
    leaf status {
      type Isis-valid;
      description
        "Status";
    }
  }

  grouping ISIS-SH-IF-AREA-CLNS {
    description
      "Per interface per area CLNS state";
    container multicast-status {
      description
        "Multicast group membership status";
      uses ISIS-SH-IF-MCAST-STATUS;
    }
    leaf level {
      type Isis-level;
      description
        "Level of the area";
    }
  }

  grouping ISIS-SH-IF-CLNS-LAN {
    description
      "LAN specific CLNS state";
    list per-area-data {
      description
        "Array of per area CLNS data";
      uses ISIS-SH-IF-AREA-CLNS;
    }
  }

  grouping ISIS-SH-IF-CLNS-MEDIA-SPECIFIC-STATUS {
    description
      "Media Specific CLNS state";
    container clns-lan-data {
      when "../clns-media-type = 'isis-media-class-lan'" {
        description
          "../CLNSMediaType = 'ISIS_MEDIA_CLASS_LAN'";
      }
      description
        "LAN state";
      uses ISIS-SH-IF-CLNS-LAN;
    }
    container clns-p2p-data {
      when "../clns-media-type = 'isis-media-class-p2p'" {
        description
          "../CLNSMediaType = 'ISIS_MEDIA_CLASS_P2P'";
      }
      description
        "Point-to-point state";
      uses ISIS-SH-IF-CLNS-P2P;
    }
    leaf clns-media-type {
      type Isis-media-class;
      description
        "CLNSMediaType";
    }
  }

  grouping ISIS-SH-IF-CLNS-SNPA-KNOWN {
    description
      "CLNS SNPA info";
    leaf snpa {
      type xr:Isis-snpa;
      description
        "Valid SNPA";
    }
  }

  grouping ISIS-SH-IF-CLNS-SNPA-UNKNOWN {
    description
      "Interface info with CLNS SNPA unknown";
    leaf reason-code {
      type Isis-if-clns-snpa-unknown-reason;
      description
        "Reason why the SNPA is unknown";
    }
  }

  grouping ISIS-SH-IF-CLNS-SNPA-STATUS {
    description
      "ISIS SH IF CLNS SNPA STATUS";
    container unknown {
      when "../status = 'isis-unknown'" {
        description
          "../Status = 'ISIS_UNKNOWN'";
      }
      description
        "Information pertaining to the unknown SNPA state";
      uses ISIS-SH-IF-CLNS-SNPA-UNKNOWN;
    }
    container known {
      when "../status = 'isis-known'" {
        description
          "../Status = 'ISIS_KNOWN'";
      }
      description
        "Information pertaining to the known SNPA state";
      uses ISIS-SH-IF-CLNS-SNPA-KNOWN;
    }
    leaf status {
      type Isis-known;
      description
        "Status";
    }
  }

  grouping ISIS-SH-IF-CLNS-MTU-INVALID {
    description
      "Interface info with invalid MTU";
    leaf reason-code {
      type Isis-if-clns-mtu-invalid-reason;
      description
        "Reason why the MTU is invalid";
    }
  }

  grouping ISIS-SH-IF-CLNS-MTU-STATUS {
    description
      "ISIS SH IF CLNS MTU STATUS";
    container invalid {
      when "../status = 'isis-invalid'" {
        description
          "../Status = 'ISIS_INVALID'";
      }
      description
        "Information pertaining to the invalid CLNS MTU";
      uses ISIS-SH-IF-CLNS-MTU-INVALID;
    }
    leaf status {
      type Isis-valid;
      description
        "Status";
    }
    leaf mtu {
      when "../status = 'isis-valid'" {
        description
          "../Status = 'ISIS_VALID'";
      }
      type uint32;
      description
        "Valid MTU";
    }
  }

  grouping ISIS-SH-IF-CLNS-PROTO-DOWN {
    description
      "Interface info when CLNS is down";
    leaf reason-code {
      type Isis-if-clns-proto-down-reason;
      description
        "Reason why CLNS is down";
    }
  }

  grouping ISIS-SH-IF-CLNS-STATUS {
    description
      "ISIS SH IF CLNS STATUS";
    container clns-down-info {
      when "../status = 'isis-down'" {
        description
          "../Status = 'ISIS_DOWN'";
      }
      description
        "State describing why CLNS is down";
      uses ISIS-SH-IF-CLNS-PROTO-DOWN;
    }
    leaf status {
      type Isis-up;
      description
        "Status";
    }
  }

  grouping ISIS-SH-IF-CLNS {
    description
      "CLNS I/O data for an interface";
    container clns-status {
      description
        "Is CLNS protcol up or if not, the reason why it
         is not up";
      uses ISIS-SH-IF-CLNS-STATUS;
    }
    container mtu-info {
      description
        "A valid MTU or the reason for the MTU being
         invalid";
      uses ISIS-SH-IF-CLNS-MTU-STATUS;
    }
    container snpa-state {
      description
        "SNPA state";
      uses ISIS-SH-IF-CLNS-SNPA-STATUS;
    }
    container media-specific-state {
      description
        "Media Specific CLNS state";
      uses ISIS-SH-IF-CLNS-MEDIA-SPECIFIC-STATUS;
    }
    container timestamp-last-iih-recv {
      description
        "Timestamp Last IIH Received";
      uses ISIS-SH-TIMESTAMP-TYPE;
    }
    container timestamp-last-iih-sent {
      description
        "Timestamp Last IIH Sent";
      uses ISIS-SH-TIMESTAMP-TYPE;
    }
    container timestamp-last-rej-pdu {
      description
        "Timestamp Last Rejected PDU";
      uses ISIS-SH-TIMESTAMP-TYPE;
    }
    container last-im-state-change {
      description
        "Last time the IM State changed";
      uses ISIS-SH-TIMESTAMP-TYPE;
    }
    leaf time-until-next-lsp {
      type uint32;
      description
        "Time until next LSP may be sent (ms)";
    }
    leaf lsp-transmit-requested-flag {
      type boolean;
      description
        "TRUE if an LSP transmission has been requested";
    }
    leaf lsp-transmitted-flag {
      type boolean;
      description
        "TRUE if an LSP transmission has been sent,
         indicates LastLSPLevelTransmitted and
         LastLSP_IDTransmitted valid";
    }
    leaf lsp-txmitd-b2b-limit {
      type uint32;
      description
        "Number of LSPs that can be sent back to back in
         the current window without exceeding the pacing
         limit";
    }
    leaf lsp-txmt-b2b-msecs {
      type uint32;
      units "millisecond";
      description
        "Time im msecs indicating the end of the window
         in which the 'back to back lsps to be sent'
         counter applies";
    }
    leaf last-lsp-level-transmitted {
      type Isis-level;
      description
        "Level of the Last LSP Transmitted";
    }
    leaf last-lsp-id-transmitted {
      type xr:Isis-lsp-id;
      description
        "Last LSP ID Transmitted";
    }
    leaf time-since-last-iih-recv {
      type int32;
      description
        "Time Since Last IIH Received in msec";
    }
    leaf time-since-last-iih-sent {
      type int32;
      description
        "Time Since Last IIH Sent in msec";
    }
    leaf pdu-size-last-iih-recv {
      type int32;
      description
        "Size of Last IIH Received in octets";
    }
    leaf pdu-size-last-iih-sent {
      type int32;
      description
        "Size of Last IIH Sent in octets";
    }
    leaf reason-last-rej-pdu {
      type Isis-sh-pdu-rejection-reason;
      description
        "Reason of Last PDU Rejection";
    }
    leaf time-since-last-rej-pdu {
      type int32;
      description
        "Time Since Last Rejected PDU in msec";
    }
    leaf pdu-type-last-rej-pdu {
      type uint8;
      description
        "PDU Code of Last Rejected PDU";
    }
    leaf pdu-size-last-rej-pdu {
      type int32;
      description
        "Size of Last Rejected PDU in octets";
    }
    leaf im-state {
      type Im-state;
      description
        "CLNS Interface State as reported by the
         Interface Manager";
    }
  }

  grouping ISIS-SH-IF-BFD-SESSION-INFO-TYPE {
    description
      "Per-interface, per-afi BFD data";
    container bfd-create-timestamp {
      description
        "Last time IS-IS requested BFD to create a
         session";
      uses ISIS-SH-TIMESTAMP-TYPE;
    }
    container bfd-delete-timestamp {
      description
        "Last time IS-IS requested BFD to delete a
         session";
      uses ISIS-SH-TIMESTAMP-TYPE;
    }
    container bfd-unconfig-timestamp {
      description
        "Last time IS-IS notified BFD that IS-IS has
         unconfigured BFD";
      uses ISIS-SH-TIMESTAMP-TYPE;
    }
    container bfd-snc-up-timestamp {
      description
        "Last time BFD notified IS-IS that BFD session
         went up";
      uses ISIS-SH-TIMESTAMP-TYPE;
    }
    container bfd-snc-down-timestamp {
      description
        "Last time BFD notified IS-IS that BFD session
         went down";
      uses ISIS-SH-TIMESTAMP-TYPE;
    }
    container bfd-snc-unconfig-timestamp {
      description
        "Last time BFD notified IS-IS that the peer
         unconfigured the session";
      uses ISIS-SH-TIMESTAMP-TYPE;
    }
    leaf bfd-create-status {
      type uint32;
      description
        "Returncode when IS-IS last requested a new
         session";
    }
    leaf bfd-delete-status {
      type uint32;
      description
        "Returncode when IS-IS last requested a session
         to be deleted";
    }
    leaf bfd-unconfig-status {
      type uint32;
      description
        "Returncode when IS-IS last notified a session
         was unconfigured";
    }
    leaf bfd-scn-count-up {
      type uint32;
      description
        "Number of BFD SCN session up messages received
         since session was requested";
    }
    leaf bfd-scn-count-down {
      type uint32;
      description
        "Number of BFD SCN session down messages received
         since session was requested";
    }
    leaf bfd-scn-count-unconfig {
      type uint32;
      description
        "Number of BFD SCN peer unconfigured session msgs
         received since session was requested";
    }
    leaf bfd-scn-total-count-up {
      type uint32;
      description
        "Total number of BFD SCN session up messages
         received";
    }
    leaf bfd-scn-total-count-down {
      type uint32;
      description
        "Total number of BFD SCN session down messages
         received";
    }
    leaf bfd-scn-total-count-unconfig {
      type uint32;
      description
        "Total number of BFD SCN peer unconfigured
         session messages received";
    }
    leaf bfd-request-count-create {
      type uint32;
      description
        "Number of requests by IS-IS to BFD to create a
         BFD session";
    }
    leaf bfd-request-count-delete {
      type uint32;
      description
        "Number of requests by IS-IS to BFD to delete a
         BFD session";
    }
    leaf bfd-request-count-unconfig {
      type uint32;
      description
        "Number of msgs from IS-IS to BFD that a BFD
         session was locally unconfigured";
    }
  }

  grouping ISIS-SH-IF-BFD-TYPE {
    description
      "Per-interface BFD data";
    leaf ipv4-enabled {
      type boolean;
      description
        "IPv4 BFD enabled status";
    }
    leaf ipv6-enabled {
      type boolean;
      description
        "IPv6 BFD enabled status";
    }
    leaf interval {
      type uint32;
      units "millisecond";
      description
        "BFD hello minimum interval in milliseconds";
    }
    leaf multiplier {
      type uint32;
      description
        "BFD hello multiplier";
    }
    list bfd-info-per-afi {
      max-elements "2";
      description
        "BFD Per AFI Session Status";
      uses ISIS-SH-IF-BFD-SESSION-INFO-TYPE;
    }
  }

  grouping ISIS-SH-IF-ACTIVE-P2P {
    description
      "Per-interface data";
    container timestamp-adj-up {
      description
        "Timestamp Adj Up";
      uses ISIS-SH-TIMESTAMP-TYPE;
    }
    container timestamp-csnp-complete {
      description
        "Timestamp Received CSNP Complete";
      uses ISIS-SH-TIMESTAMP-TYPE;
    }
    container timestamp-pacing-start {
      description
        "Timestamp LSP Pacing Start";
      uses ISIS-SH-TIMESTAMP-TYPE;
    }
    container lspfs-opt-iihpsnp-subtlv-timestamp {
      description
        "Flood speed optimization IIH PSNP subtlv
         received timestamp";
      uses ISIS-SH-TIMESTAMP-TYPE;
    }
    container lspfs-opt-snppsnp-subtlv-timestamp {
      description
        "Flood speed optimization SNP PSNP subtlv
         received timestamp";
      uses ISIS-SH-TIMESTAMP-TYPE;
    }
    leaf time-until-next-iih {
      type uint32;
      description
        "Time in ms before the next IIH can be sent";
    }
    leaf retransmit-lsp-queue-size {
      type uint32;
      description
        "No. of LSPs queued to be retransmitted";
    }
    leaf retransmit-lsp-interval {
      type uint32;
      description
        "Time in ms until the next scheduled LSP is
         retransmitted";
    }
    leaf extended-circuit-number {
      type Isis-extended-circuit-number;
      description
        "Extended Circuit Number valid for a P2P
         interface";
    }
    leaf lspfs-opt-enabled {
      type boolean;
      description
        "Flood speed optimization enabled";
    }
    leaf lspfs-opt-pacing-interval {
      type uint32;
      description
        "Flood speed optimization pacing interval in ms";
    }
    leaf lspfs-opt-current-tx-max {
      type uint32;
      description
        "Flood speed optimization current transmit max
         size";
    }
    leaf lspfs-opt-current-tx-burst {
      type uint32;
      description
        "Flood speed optimization current transmit burst
         size";
    }
    leaf lspfs-opt-tx-speed-average {
      type uint32;
      description
        "Flood speed optimization transmit speed average";
    }
    leaf lspfs-opt-rx-speed-average {
      type uint32;
      description
        "Flood speed optimization receive speed average";
    }
    leaf lspfs-opt-psnp-delay {
      type uint32;
      description
        "Flood speed optimization PSNP delay";
    }
    leaf lspfs-opt-psnp-delay-src {
      type Isis-sh-if-fsopt-psnp-delay-src;
      description
        "Flood speed optimization PSNP delay source";
    }
    leaf lspfs-opt-iihpsnp-subtlv {
      type uint32;
      description
        "Flood speed optimization IIH PSNP subtlv
         received";
    }
    leaf lspfs-opt-snppsnp-subtlv {
      type uint32;
      description
        "Flood speed optimization SNP PSNP subtlv
         received";
    }
    leaf lspfs-opt-iihpsnp-subtlv-valid {
      type boolean;
      description
        "Flood speed optimization IIH PSNP subtlv is
         valid";
    }
    leaf lspfs-opt-snppsnp-subtlv-valid {
      type boolean;
      description
        "Flood speed optimization SNP PSNP subtlv is
         valid";
    }
    leaf lspfs-opt-hold-time-active {
      type boolean;
      description
        "Flood speed optimization holdtime active";
    }
    leaf lspfs-opt-tx-speed-increase {
      type boolean;
      description
        "Flood speed optimization transmit speed increase";
    }
    leaf lspfs-opt-hold-time {
      type uint32;
      description
        "Flood speed optimization holdtime";
    }
    leaf lspfs-opt-hold-time-count {
      type uint32;
      description
        "Flood speed optimization holdtime count";
    }
    list lspfs-opt-tx-speed-hist {
      max-elements "7";
      description
        "Flood speed optimization transmit speed history
         
         buffer";
      leaf entry {
        type uint32;
        description
          "Flood speed optimization transmit speed history
           
           buffer";
      }
    }
    list lspfs-opt-rx-speed-hist {
      max-elements "7";
      description
        "Flood speed optimization receive speed history
         
         buffer";
      leaf entry {
        type uint32;
        description
          "Flood speed optimization receive speed history
           
           buffer";
      }
    }
  }

  grouping ISIS-SH-IF-ADV-PREFIX-DISABLED {
    description
      "Interface info when prefix advertisement is
       disabled";
    leaf reason-code {
      type Isis-if-adv-prefix-disabled-reason;
      description
        "Reason why the interface is not able to
         advertise prefixes";
    }
  }

  grouping ISIS-SH-IF-ADV-PREFIX-STATUS {
    description
      "ISIS SH IF ADV PREFIX STATUS";
    container disabled {
      when "../status = 'isis-disabled'" {
        description
          "../Status = 'ISIS_DISABLED'";
      }
      description
        "Disabled info for the prefix advertisement
         status";
      uses ISIS-SH-IF-ADV-PREFIX-DISABLED;
    }
    leaf status {
      type Isis-enabled;
      description
        "Status";
    }
  }

  grouping ISIS-SH-IF-ADJ-FORM-DISABLED {
    description
      "Interface info when adjacency formation is
       disabled";
    leaf reason-code {
      type Isis-if-adj-form-disabled-reason;
      description
        "Reason why the interface is not able to form
         adjacencies";
    }
  }

  grouping ISIS-SH-IF-ADJ-FORM-STATUS {
    description
      "ISIS SH IF ADJ FORM STATUS";
    container disabled {
      when "../status = 'isis-disabled'" {
        description
          "../Status = 'ISIS_DISABLED'";
      }
      description
        "Disabled info for the adjacency formation status";
      uses ISIS-SH-IF-ADJ-FORM-DISABLED;
    }
    leaf status {
      type Isis-enabled;
      description
        "Status";
    }
  }

  grouping ISIS-SH-IF-ENABLED {
    description
      "State of an enabled interface";
    container adjacency-form-status {
      description
        "Interface's Adjacency Formation status";
      uses ISIS-SH-IF-ADJ-FORM-STATUS;
    }
    container adv-prefix-status {
      description
        "Interface's Prefix Advertisement status";
      uses ISIS-SH-IF-ADV-PREFIX-STATUS;
    }
    container p2p-data {
      description
        "Data for an active P2P interface, NULL if not
         active or P2P";
      uses ISIS-SH-IF-ACTIVE-P2P;
    }
    container bfd-data {
      description
        "The BFD data for the given interface";
      uses ISIS-SH-IF-BFD-TYPE;
    }
    container clns-data {
      description
        "Interface data specific to CLNS I/O services";
      uses ISIS-SH-IF-CLNS;
    }
    leaf interface-media-type {
      type Isis-media-class;
      description
        "Media type of the interface";
    }
    leaf enabled-circuit-type {
      type Isis-levels;
      description
        "Enabled Circuit type of the interface";
    }
    leaf local-circuit-number {
      type Isis-circuit-number;
      description
        "Local Circuit Number of the interface";
    }
    leaf rsi-srlg-registered {
      type boolean;
      description
        "Rsi Srlg Registered";
    }
    leaf bandwidth {
      type uint64;
      description
        "Effective bandwidth of the interface";
    }
    leaf is-total-bandwidth-set {
      type boolean;
      description
        "Is total bandwidth set";
    }
    leaf total-bandwidth {
      type uint64;
      description
        "Total bandwidth of the interface";
    }
    leaf delay-norm-interval {
      type uint32;
      description
        "Delay Normalization Interval";
    }
    leaf delay-norm-offset {
      type uint32;
      description
        "Delay Normalization Offset";
    }
    leaf avg-delay {
      type uint32;
      description
        "Normalized Average Delay";
    }
    leaf avg-delay-raw {
      type uint32;
      description
        "Raw Average Delay";
    }
    leaf avg-delay-abit {
      type boolean;
      description
        "Average Delay Anomaly Flag";
    }
    leaf min-delay {
      type uint32;
      description
        "Normalized Minimum Delay";
    }
    leaf max-delay {
      type uint32;
      description
        "Normalized Maximum Delay";
    }
    leaf min-delay-raw {
      type uint32;
      description
        "Raw Minimum Delay";
    }
    leaf max-delay-raw {
      type uint32;
      description
        "Raw Maximum Delay";
    }
    leaf min-max-delay-abit {
      type boolean;
      description
        "Min/Max Delay Anomaly Flag";
    }
    leaf packet-loss-percentage {
      type uint32;
      description
        "Packet Loss";
    }
    leaf packet-loss-abit {
      type boolean;
      description
        "Packet Loss Anomaly Flag";
    }
    list underlying-interface {
      description
        "Underlying interface list for bundle interfaces";
      uses ISIS-SH-INTF-DET;
    }
    list per-area-data {
      description
        "Array of area information for an active
         interface";
      uses ISIS-SH-IF-AREA-ACTIVE;
    }
    list per-topology-data {
      description
        "Array of topology information";
      uses ISIS-SH-IF-TOPO;
    }
    list per-address-family-data {
      description
        "Array of address family information";
      uses ISIS-SH-IF-AF;
    }
  }

  grouping ISIS-SH-IF-DISABLED {
    description
      "Disabled interface info";
    leaf reason-code {
      type Isis-if-disabled-reason;
      description
        "Reason why the interface is disabled";
    }
  }

  grouping ISIS-SH-IF-STATUS {
    description
      "ISIS SH IF STATUS";
    container disabled {
      when "../status = 'isis-disabled'" {
        description
          "../Status = 'ISIS_DISABLED'";
      }
      description
        "The interface state if disabled";
      uses ISIS-SH-IF-DISABLED;
    }
    container enabled {
      when "../status = 'isis-enabled'" {
        description
          "../Status = 'ISIS_ENABLED'";
      }
      description
        "The interface state if enabled";
      uses ISIS-SH-IF-ENABLED;
    }
    leaf status {
      type Isis-enabled;
      description
        "Status";
    }
  }

  grouping ISIS-SH-IF-CFG-STATUS {
    description
      "Configured state of an interface";
    leaf adjacency-form-status {
      type boolean;
      description
        "Configured adjacency formation status";
    }
    leaf adv-prefix-status {
      type boolean;
      description
        "Configured prefix advertisement status";
    }
  }

  grouping ISIS-SH-IF {
    description
      "All the Information of an IS-IS interface";
    container configured-status {
      description
        "Configured interface status";
      uses ISIS-SH-IF-CFG-STATUS;
    }
    container interface-status-and-data {
      description
        "Information about the interface status and its
         data";
      uses ISIS-SH-IF-STATUS;
    }
    leaf configured-circuit-type {
      type Isis-levels;
      description
        "Configured circuit type for the interface";
    }
    leaf mesh-group {
      type Isis-mesh-group-number;
      description
        "Interface mesh group";
    }
    leaf is-type {
      type Isis-levels;
      description
        "IS-type of the router";
    }
    leaf nsr-intf {
      type boolean;
      description
        "ISIS NSR Interface";
    }
  }

  grouping ISIS-SH-SRLG-STATIC-NAME {
    description
      "ISIS Static Link SRLG Name ";
    leaf srlg-name {
      type string;
      description
        "SRLGName";
    }
  }

  grouping ISIS-SH-SRLG-STATIC {
    description
      "SRLG Static";
    leaf local-ipv4-addr {
      type Isis-ipv4-address;
      description
        "LocalIPv4Addr";
    }
    leaf remote-ipv4-addr {
      type Isis-ipv4-address;
      description
        "RemoteIPv4Addr";
    }
    list srlg-name-xr {
      description
        "SRLGNames";
      uses ISIS-SH-SRLG-STATIC-NAME;
    }
  }

  grouping NSR-STATUS-NII-INTF {
    description
      "NSR STATUS NII INTF";
    leaf exist {
      type boolean;
      description
        "exist";
    }
    leaf brought-up {
      type boolean;
      description
        "brought up";
    }
    leaf retry-timer {
      type boolean;
      description
        "retry timer";
    }
    leaf running {
      type boolean;
      description
        "running";
    }
    leaf has-adj {
      type boolean;
      description
        "has adj";
    }
  }

  grouping NSR-STATUS-TE {
    description
      "NSR STATUS TE";
    leaf enabled {
      type uint8;
      description
        "enabled";
    }
    leaf conn-up {
      type uint8;
      description
        "conn up";
    }
    leaf te-link-cb {
      type uint8;
      description
        "te link cb";
    }
    leaf te-tunnel-cb {
      type uint8;
      description
        "te tunnel cb";
    }
    leaf adv-sync-data {
      type uint8;
      description
        "adv sync data";
    }
    leaf link-purge-time-on {
      type uint8;
      description
        "link purge time on";
    }
    leaf tunnel-purge-time-on {
      type uint8;
      description
        "tunnel purge time on";
    }
    leaf has-info-from-te {
      type uint8;
      description
        "has info from te";
    }
  }

  grouping NSR-STATUS-DS {
    description
      "NSR STATUS DS";
    container conn-ts {
      description
        "conn ts";
      uses ISIS-SH-TIMESTAMP-TYPE;
    }
    container conn-cb-ts {
      description
        "conn cb ts";
      uses ISIS-SH-TIMESTAMP-TYPE;
    }
    container pub-ts {
      description
        "pub ts";
      uses ISIS-SH-TIMESTAMP-TYPE;
    }
    container pub-cb-ts {
      description
        "pub cb ts";
      uses ISIS-SH-TIMESTAMP-TYPE;
    }
    container reg-ts {
      description
        "reg ts";
      uses ISIS-SH-TIMESTAMP-TYPE;
    }
    container reg-cb-ts {
      description
        "reg cb ts";
      uses ISIS-SH-TIMESTAMP-TYPE;
    }
    container unreg-ts {
      description
        "unreg ts";
      uses ISIS-SH-TIMESTAMP-TYPE;
    }
    container unreg-cb-ts {
      description
        "unreg cb ts";
      uses ISIS-SH-TIMESTAMP-TYPE;
    }
    container disconn-cb-ts {
      description
        "disconn cb ts";
      uses ISIS-SH-TIMESTAMP-TYPE;
    }
    container notify-cb-ts {
      description
        "notify cb ts";
      uses ISIS-SH-TIMESTAMP-TYPE;
    }
    container del-cb-ts {
      description
        "del cb ts";
      uses ISIS-SH-TIMESTAMP-TYPE;
    }
    container remove-srv-ts {
      description
        "remove srv ts";
      uses ISIS-SH-TIMESTAMP-TYPE;
    }
    container conn-status-ts {
      description
        "conn status ts";
      uses ISIS-SH-TIMESTAMP-TYPE;
    }
    leaf conn {
      type uint8;
      description
        "conn";
    }
    leaf conn-cb {
      type uint8;
      description
        "conn cb";
    }
    leaf pub {
      type uint8;
      description
        "pub";
    }
    leaf pub-cb {
      type uint8;
      description
        "pub cb";
    }
    leaf reg {
      type uint8;
      description
        "reg";
    }
    leaf reg-cb {
      type uint8;
      description
        "reg cb";
    }
    leaf unreg {
      type uint8;
      description
        "unreg";
    }
    leaf unreg-cb {
      type uint8;
      description
        "unreg cb";
    }
    leaf disconn-cb {
      type uint8;
      description
        "disconn cb";
    }
    leaf notify-cb {
      type uint8;
      description
        "notify cb";
    }
    leaf notify-peer-xr {
      type yang:hex-string;
      description
        "notify peer xr";
    }
    leaf del-cb {
      type uint8;
      description
        "del cb";
    }
    leaf remove-srv {
      type uint8;
      description
        "remove srv";
    }
    leaf conn-status {
      type boolean;
      description
        "conn status";
    }
    list notify-peer {
      max-elements "4";
      description
        "notify peer";
      uses ISIS-SH-TIMESTAMP-TYPE;
    }
  }

  grouping NSR-STATUS-PM {
    description
      "NSR STATUS PM";
    leaf reg {
      type uint8;
      description
        "reg";
    }
    leaf conn-cb {
      type uint8;
      description
        "conn cb";
    }
    leaf disconn-cb {
      type uint8;
      description
        "disconn cb";
    }
    leaf conn-status {
      type boolean;
      description
        "conn status";
    }
  }

  grouping NSR-STATUS-NCD {
    description
      "NSR STATUS NCD";
    leaf vm-idx {
      type uint8;
      description
        "vm idx";
    }
    leaf conn-up {
      type boolean;
      description
        "conn up";
    }
    leaf endp-hdl {
      type uint8;
      description
        "endp hdl";
    }
    leaf chksum {
      type uint16;
      description
        "chksum";
    }
    leaf send-seqnum {
      type uint32;
      description
        "send seqnum";
    }
    leaf recv-cnt {
      type uint32;
      description
        "recv cnt";
    }
  }

  grouping NSR-STATUS-GEN {
    description
      "NSR STATUS GEN";
    leaf my-nodeid {
      type uint32;
      description
        "my nodeid";
    }
    leaf my-process-id {
      type uint32;
      description
        "my process id";
    }
    leaf pm-issu-role {
      type uint8;
      description
        "pm issu role";
    }
    leaf pm-ha-role {
      type uint8;
      description
        "pm ha role";
    }
    leaf sysmgr-ha-role {
      type uint8;
      description
        "sysmgr ha role";
    }
    leaf nsr-send-ready {
      type uint8;
      description
        "nsr send ready";
    }
    leaf nsr-send-unready {
      type uint8;
      description
        "nsr send unready";
    }
    leaf nsr-send-err {
      type uint32;
      description
        "nsr send err";
    }
    leaf nsr-recv-err {
      type uint32;
      description
        "nsr recv err";
    }
    leaf retry-flag {
      type uint32;
      description
        "retry flag";
    }
    leaf nsr-enabled {
      type boolean;
      description
        "nsr enabled";
    }
    leaf nsr-configured {
      type boolean;
      description
        "nsr configured";
    }
    leaf nsf-configured {
      type boolean;
      description
        "nsf configured";
    }
    leaf failover {
      type boolean;
      description
        "failover";
    }
    leaf lanid-req-needed {
      type boolean;
      description
        "lanid req needed";
    }
  }

  grouping NSR-STATUS-INFRA-TYPE {
    description
      "NSR STATUS INFRA TYPE";
    container gen {
      description
        "gen";
      uses NSR-STATUS-GEN;
    }
    container pm {
      description
        "pm";
      uses NSR-STATUS-PM;
    }
    container ds {
      description
        "ds";
      uses NSR-STATUS-DS;
    }
    container te {
      description
        "te";
      uses NSR-STATUS-TE;
    }
    list ncd {
      max-elements "5";
      description
        "ncd";
      uses NSR-STATUS-NCD;
    }
    list nii-idb {
      max-elements "3";
      description
        "nii idb";
      uses NSR-STATUS-NII-INTF;
    }
  }

  grouping NSR-STATUS-GBL-TYPE {
    description
      "NSR STATUS GBL TYPE";
    list full-sync-achieved {
      max-elements "3";
      description
        "full sync achieved";
      leaf entry {
        type uint32;
        description
          "full sync achieved";
      }
    }
    list man-sync-count {
      max-elements "3";
      description
        "man sync count";
      leaf entry {
        type uint32;
        description
          "man sync count";
      }
    }
    list nsr-chg-count {
      max-elements "3";
      description
        "nsr chg count";
      leaf entry {
        type uint32;
        description
          "nsr chg count";
      }
    }
    list uptime {
      max-elements "3";
      description
        "uptime";
      leaf entry {
        type uint32;
        description
          "uptime";
      }
    }
    list uptime-valid {
      min-elements 3;
      max-elements "3";
      description
        "uptime valid";
      leaf entry {
        type boolean;
        description
          "Array entry.";
      }
    }
  }

  grouping ISIS-SH-NSR-STATUS-GLOBAL {
    description
      "IS-IS process NSR status";
    container isis-nsr-peer {
      description
        "ISIS NSR PEER STATUS";
      uses NSR-STATUS-GBL-TYPE;
    }
    container isis-nsr-infra {
      description
        "ISIS NSR Infra";
      uses NSR-STATUS-INFRA-TYPE;
    }
    leaf isis-vm-state {
      type uint16;
      description
        "ISIS VM STATE";
    }
  }

  grouping ISIS-SH-SRLG {
    description
      "ISIS SRLG";
    leaf srlg-name-xr {
      type string;
      description
        "SRLG Name";
    }
    leaf srlg-value {
      type uint32;
      description
        "SRLG Value";
    }
    leaf srlg-admin-weight {
      type uint32;
      description
        "SRLG Admin Weight";
    }
    leaf srlg-value-set {
      type boolean;
      description
        "SRLG value set";
    }
    leaf srlg-admin-weight-set {
      type boolean;
      description
        "SRLG Admin Weight Set";
    }
    leaf srlg-isis-cfg {
      type boolean;
      description
        "SRLG ISIS Configuration";
    }
    leaf srlg-global-cfg {
      type boolean;
      description
        "SRLG Global Configuration";
    }
  }

  grouping ISIS-LBL-PREFIX-TYPE {
    description
      "ISIS Label  prefix info";
    container prefix {
      description
        "Prefix associated with Label";
      uses ISIS-IP-PREFIX-TYPE;
    }
    leaf algo {
      type uint32;
      description
        "Algorithm";
    }
  }

  grouping ISIS-SH-LABEL {
    description
      "Label data";
    container label-prefix {
      description
        "label prefix";
      uses ISIS-IP-PREFIX-TYPE;
    }
    leaf label-type {
      type Isis-edm-label-type-enum;
      description
        "label type";
    }
    leaf label-flags {
      type uint8;
      description
        "label flags";
    }
    leaf label-refcount {
      type uint8;
      description
        "label refcount";
    }
    leaf label-value {
      type uint32;
      description
        "label value";
    }
    leaf label-algo {
      type uint8;
      description
        "label algo";
    }
    leaf label-interface {
      type Isis-sh-interface-name;
      description
        "label interface";
    }
    leaf label-ifh {
      type xr:Interface-name;
      description
        "label ifh";
    }
    leaf label-table-id {
      type uint32;
      description
        "label table id";
    }
    leaf label-af-id {
      type Isis-af-id;
      description
        "label af id";
    }
    list conflict-label-prefix {
      description
        "conflict label prefix";
      uses ISIS-LBL-PREFIX-TYPE;
    }
  }

  grouping ISIS-SH-TE-TUNNEL {
    description
      "MPLS TE tunnel";
    leaf te-system-id {
      type xr:Osi-system-id;
      description
        "Destination system ID";
    }
    leaf te-interface {
      type Isis-sh-interface-name;
      description
        "Tunnel interface";
    }
    leaf te-bandwidth {
      type uint32;
      description
        "Tunnel bandwidth";
    }
    leaf teigp-metric {
      type int32;
      description
        "Tunnel metric";
    }
    leaf te-next-hop-ip-address {
      type inet:ipv4-address;
      description
        "Tunnel next-hop IP address";
    }
    leaf te-mode-type {
      type Isis-metric-mode;
      description
        "Tunnel metric mode";
    }
    leaf teipv4fa-enabled {
      type boolean;
      description
        "Indicates whether MPLS TE IPv4 forwarding
         adjacency is enabled";
    }
    leaf teipv6fa-enabled {
      type boolean;
      description
        "Indicates whether MPLS TE IPv6 forwarding
         adjacency is enabled";
    }
    leaf teipv4aa-enabled {
      type boolean;
      description
        "Indicates whether MPLS TE IPv4 autoroute
         announce is enabled";
    }
    leaf teipv6aa-enabled {
      type boolean;
      description
        "Indicates whether MPLS TE IPv6 autoroute
         announce is enabled";
    }
    leaf te-segment-routing-enabled {
      type boolean;
      description
        "Indicates whether MPLS TE segment routing is
         enabled";
    }
    leaf te-segment-routing-strict-spf {
      type boolean;
      description
        "Indicates whether MPLS TE segment routing strict
         SPF is enabled";
    }
    leaf te-segment-routing-exclude-mode {
      type Isis-sr-exclude;
      description
        "Tunnel SR-exclusion mode";
    }
    leaf te-checkpoint-object-id {
      type uint32;
      description
        "Tunnel checkpoint object ID. Not used for the
         tunnel-log";
    }
    leaf te-is-new-tunnel {
      type boolean;
      description
        "Tunnel going up. Only used for the tunnel-log";
    }
    leaf te-tunnel-has-changed {
      type boolean;
      description
        "Tunnel was up, but properties have changed. Only
         for the tunnel-log";
    }
  }

  grouping ISIS-SH-SPF-LOG-TRIGGER-RECORD {
    description
      "Information about an individual SPF trigger";
    container trigger-timestamp {
      description
        "Trigger time in UTC relative to Jan 1st, 1970";
      uses ISIS-SH-TIMESTAMP-TYPE;
    }
    container trigger-prefix {
      description
        "Changed prefix in the trigger LSP, if any";
      uses ISIS-IP-PREFIX-TYPE;
    }
    leaf trigger-lsp-id {
      type xr:Isis-lsp-id;
      description
        "ID of the LSP to trigger the calculation, if any";
    }
    leaf trigger-link {
      type xr:Isis-node-id;
      description
        "ID of a changed link in the trigger LSP, if any";
    }
    list trigger {
      description
        "Triggers applying to this log entry";
      leaf entry {
        type Isis-spf-trigger;
        description
          "Triggers applying to this log entry";
      }
    }
  }

  grouping ISIS-SH-SPF-LOG-ROUTE-UPDATE-PREFIX-COUNTS {
    description
      "Prefix item counts for the route update phase";
    container unreachable {
      description
        "Number of unreachable prefixes in the database";
      uses ISIS-PER-PRIORITY-COUNTS;
    }
    container reachable {
      description
        "Number of reachable prefixes in the database";
      uses ISIS-PER-PRIORITY-COUNTS;
    }
    container added {
      description
        "Number of prefixes added during calculation";
      uses ISIS-PER-PRIORITY-COUNTS;
    }
    container deleted {
      description
        "Number of prefixes deleted during calculation";
      uses ISIS-PER-PRIORITY-COUNTS;
    }
    container modified {
      description
        "Number of prefixes modified, i.e. a first hop
         and/or metric change";
      uses ISIS-PER-PRIORITY-COUNTS;
    }
    container touched {
      description
        "Number of prefixes considered whilst updating
         the routing table";
      uses ISIS-PER-PRIORITY-COUNTS;
    }
  }

  grouping ISIS-SH-SPF-LOG-ROUTE-UPDATE-NODE-COUNTS {
    description
      "Node counts for the route update phase";
    container per-priority-touched {
      description
        "Per-priority count of nodes considered during
         route update";
      uses ISIS-PER-PRIORITY-COUNTS;
    }
    leaf total-touched {
      type uint32;
      description
        "Total number of nodes considered during route
         update";
    }
  }

  grouping ISIS-PER-PRIORITY-TIMINGS {
    description
      "Per-priority timings";
    container critical {
      description
        "Critical priority";
      uses ISIS-TIMINGS-TYPE;
    }
    container high {
      description
        "High priority";
      uses ISIS-TIMINGS-TYPE;
    }
    container medium {
      description
        "Medium priority";
      uses ISIS-TIMINGS-TYPE;
    }
    container low {
      description
        "Low priority";
      uses ISIS-TIMINGS-TYPE;
    }
  }

  grouping ISIS-SH-SPF-LOG-ROUTE-UPDATE-TIMINGS-BREAKDOWN {
    description
      "Breakdown of the time taken to perform the route
       update";
    container local-rib-update {
      description
        "Time to update IS-IS's local RIB";
      uses ISIS-PER-PRIORITY-TIMINGS;
    }
    container global-rib-build {
      description
        "Time to build the update to send to the global
         RIB";
      uses ISIS-PER-PRIORITY-TIMINGS;
    }
    container global-rib-send {
      description
        "Time to send the update to the global RIB";
      uses ISIS-PER-PRIORITY-TIMINGS;
    }
  }

  grouping ISIS-SH-SPF-LOG-ROUTE-UPDATE {
    description
      "Statistics for the route update phase of the
       calculation";
    container duration {
      description
        "Duration of the routing table update";
      uses ISIS-TIMINGS-TYPE;
    }
    container duration-breakdown {
      description
        "Breakdown of the time taken by the routing table
         update";
      uses ISIS-SH-SPF-LOG-ROUTE-UPDATE-TIMINGS-BREAKDOWN;
    }
    container node-counts {
      description
        "Node counts";
      uses ISIS-SH-SPF-LOG-ROUTE-UPDATE-NODE-COUNTS;
    }
    container item-counts {
      description
        "Prefix item counts";
      uses ISIS-SH-SPF-LOG-ROUTE-UPDATE-PREFIX-COUNTS;
    }
    container route-counts {
      description
        "Distinct prefix counts";
      uses ISIS-SH-SPF-LOG-ROUTE-UPDATE-PREFIX-COUNTS;
    }
    container rib-batch-counts {
      description
        "Number of RIB batches sent";
      uses ISIS-PER-PRIORITY-COUNTS;
    }
  }

  grouping ISIS-SH-SPF-LOG-SPT-CALC-NODE-COUNTS {
    description
      "Node counts for the SPT calculation phase";
    leaf unreachable {
      type uint32;
      description
        "Number of unreachable nodes in the database";
    }
    leaf reachable {
      type uint32;
      description
        "Number of reachable nodes in the database";
    }
    leaf added {
      type uint32;
      description
        "Number of nodes added to the SPT";
    }
    leaf deleted {
      type uint32;
      description
        "Number of nodes deleted from the SPT";
    }
    leaf modified {
      type uint32;
      description
        "Number of modified nodes (first hop and/or
         metric change)";
    }
    leaf touched {
      type uint32;
      description
        "Number of nodes touched whilst calculating the
         SPT";
    }
  }

  grouping ISIS-TIMINGS-TYPE {
    description
      "Duration of an event in real and CPU time";
    leaf real-duration {
      type uint32;
      units "millisecond";
      description
        "Real time duration in milliseconds";
    }
    leaf cpu-duration {
      type uint32;
      units "millisecond";
      description
        "CPU time duration in milliseconds";
    }
  }

  grouping ISIS-SH-SPF-LOG-SPT-CALC {
    description
      "Statistics for the SPT calculation phase";
    container duration {
      description
        "Duration of the SPT calculation";
      uses ISIS-TIMINGS-TYPE;
    }
    container node-counts {
      description
        "Node counts";
      uses ISIS-SH-SPF-LOG-SPT-CALC-NODE-COUNTS;
    }
  }

  grouping ISIS-SH-SPF-LOG-TRIGGERS {
    description
      "The reasons for running a calculation";
    container trigger-prefix {
      description
        "ID of a changed prefix in the first trigger LSP,
         if any";
      uses ISIS-IP-PREFIX-TYPE;
    }
    leaf unique-trigger-count {
      type uint32;
      description
        "Number of unique triggers on this run";
    }
    leaf trigger-lsp-count {
      type uint32;
      description
        "Number of triggering LSPs";
    }
    leaf first-trigger-lsp-id {
      type xr:Isis-lsp-id;
      description
        "ID of the first LSP to trigger the calculation,
         if any";
    }
    leaf trigger-link {
      type xr:Isis-node-id;
      description
        "ID of a changed link in the first trigger LSP,
         if any";
    }
    leaf trigger-next-hop-id {
      type xr:Osi-system-id;
      description
        "ID of a changed next hop, if any";
    }
    leaf is-sr-uloop-calculation {
      type boolean;
      description
        "Is this SR micro loop calculation?";
    }
    leaf is-sr-uloop-link-down {
      type boolean;
      description
        "Is this SR micro loop calculation for link down?";
    }
    list trigger {
      description
        "Triggers applying to this log entry";
      leaf entry {
        type Isis-spf-trigger;
        description
          "Triggers applying to this log entry";
      }
    }
  }

  grouping ISIS-SH-SPF-LOG-ENT {
    description
      "IS-IS route calculation log entry";
    container generic-data {
      description
        "Generic entry data.";
      uses ISIS-SH-GENERIC-LOG-ENT;
    }
    container triggers {
      description
        "Trigger information";
      uses ISIS-SH-SPF-LOG-TRIGGERS;
    }
    container spt-calculation-statistics {
      description
        "Statistics for the SPT calculation phase";
      uses ISIS-SH-SPF-LOG-SPT-CALC;
    }
    container route-update-statistics {
      description
        "Statistics for the route update phase";
      uses ISIS-SH-SPF-LOG-ROUTE-UPDATE;
    }
    leaf class {
      type Isis-spf-class;
      description
        "Type of calculation.";
    }
    leaf wait-enforced {
      type uint32;
      units "millisecond";
      description
        "Time between the first trigger and the start of
         the route calculation, in milliseconds.";
    }
    leaf next-wait-interval {
      type uint32;
      units "millisecond";
      description
        "Minimum time from end of this route calculation
         until the start of the next, in milliseconds";
    }
    leaf updated-lsp-count {
      type uint32;
      description
        "Number of LSPs which arrived during the route
         calculation";
    }
    list trigger-log {
      description
        "Information about individual triggers";
      uses ISIS-SH-SPF-LOG-TRIGGER-RECORD;
    }
  }

  grouping ISIS-SH-SPF-LOG-STRUC {
    description
      "Log of IS-IS route calculations";
    leaf log-capacity {
      type uint32;
      description
        "Log Capacity";
    }
    leaf log-size {
      type uint32;
      description
        "Log Size";
    }
    list log-entry {
      description
        "SPF Log entries";
      uses ISIS-SH-SPF-LOG-ENT;
    }
  }

  grouping ISIS-SH-TE-ADJ-LOG-ENT {
    description
      "MPLS TE Adjacency-log entry";
    container generic-data {
      description
        "Generic entry data";
      uses ISIS-SH-GENERIC-LOG-ENT;
    }
    leaf neighbor-ip-address {
      type inet:ipv4-address;
      description
        "Neighbor ip address";
    }
    leaf status {
      type boolean;
      description
        "Up (TRUE) or down";
    }
    leaf log-interface {
      type Isis-sh-interface-name;
      description
        "Interface";
    }
    leaf te-log-neighbor-system-id {
      type xr:Osi-system-id;
      description
        "Neighbor system ID";
    }
  }

  grouping ISIS-SH-TE-ADJ-LOG-STRUC {
    description
      "MPLS TE Adjacency-log";
    leaf log-capacity {
      type uint32;
      description
        "Log Capacity";
    }
    leaf log-size {
      type uint32;
      description
        "Log Size";
    }
    list log-entry {
      description
        "Log entries";
      uses ISIS-SH-TE-ADJ-LOG-ENT;
    }
  }

  grouping ISIS-SH-TE-PCE-ADV {
    description
      "TE PCE advertisements for an IS-IS level";
    leaf pce-adv-data-present {
      type boolean;
      description
        "Indicates whether any PCE advertisements are
         present";
    }
    leaf pce-flooding-scope {
      type Isis-sh-te-pce-flooding-scope;
      description
        "Flooding scope for PCE advertisement";
    }
    leaf pce-address-ipv4 {
      type inet:ipv4-address;
      description
        "IPv4 PCE address";
    }
    leaf pce-path-scope-bits {
      type uint8;
      description
        "PCE path scope bits";
    }
    leaf pce-path-scope-prefs {
      type uint16;
      description
        "PCE path scope preferences";
    }
  }

  grouping ISIS-SH-TE-ADV-SUB-TLV {
    description
      "MPLS TE advertisement sub TLV";
    leaf te-sub-tlv-type {
      type uint16;
      description
        "Type of sub TLV";
    }
    leaf te-sub-tlv-length {
      type uint16;
      description
        "Length of sub TLV";
    }
    leaf te-sub-tlv-value {
      type yang:hex-string;
      description
        "Value of sub TLV";
    }
  }

  grouping ISIS-SH-TE-ADV-ENTRY {
    description
      "MPLS TE advertisement";
    leaf te-neighbor-system-id {
      type xr:Osi-system-id;
      description
        "Neighbor system ID";
    }
    leaf link-type {
      type Isis-sh-te-link;
      description
        "Link type";
    }
    leaf local-ip-address {
      type inet:ipv4-address;
      description
        "Local IP address";
    }
    leaf te-neighbor-ip-address {
      type inet:ipv4-address;
      description
        "Neighbor IP address";
    }
    leaf te-metric {
      type uint32;
      description
        "TE metric";
    }
    leaf te-physical-link-bandwidth {
      type uint32;
      description
        "Physical link bandwidth";
    }
    leaf te-reserved-link-bandwidth {
      type uint32;
      description
        "Reservable link bandwidth in global pool";
    }
    leaf te-subpool-reserved-link-bandwidth {
      type uint32;
      description
        "Reservable link bandwidth in subpool";
    }
    leaf te-affinity {
      type uint32;
      description
        "Affinity bits";
    }
    leaf te-ext-admin-num {
      type uint32;
      description
        "TE Ext Admin Number";
    }
    leaf te-sub-tlv-data-present {
      type boolean;
      description
        "Indicates whether any TE sub TLVs are present";
    }
    list te-transmitted-bandwidth {
      max-elements "8";
      description
        "Bandwidth in use in global pool";
      leaf entry {
        type uint32;
        description
          "Bandwidth in use in global pool";
      }
    }
    list te-subpool-transmitted-bandwidth {
      max-elements "8";
      description
        "Bandwidth in use in subpool";
      leaf entry {
        type uint32;
        description
          "Bandwidth in use in subpool";
      }
    }
    list te-ext-admin-sub {
      max-elements "8";
      description
        "TE Extended Admin Group";
      leaf entry {
        type uint32;
        description
          "TE Extended Admin Group";
      }
    }
    list te-sub-tlv {
      description
        "List of TE sub TLVs";
      uses ISIS-SH-TE-ADV-SUB-TLV;
    }
  }

  grouping ISIS-SH-TE-ADV {
    description
      "TE advertisements for an IS-IS level";
    container tepceadv {
      description
        "TE PCE advertisements";
      uses ISIS-SH-TE-PCE-ADV;
    }
    leaf te-adv-data-present {
      type boolean;
      description
        "Indicates whether any TE advertisements are
         present";
    }
    leaf te-system-id {
      type xr:Osi-system-id;
      description
        "Local system ID";
    }
    leaf te-local-router-id {
      type inet:ipv4-address;
      description
        "Local TE router ID";
    }
    list te-adv {
      description
        "List of TE advertisement entries";
      uses ISIS-SH-TE-ADV-ENTRY;
    }
  }

  grouping ISIS-SH-IPV6-TOPO-REACHABLE-DETAILS {
    description
      "Status of a reachable IPv6 IS";
    leaf root-distance {
      type Isis-metric;
      description
        "Distance to the IS";
    }
    leaf multicast-root-distance {
      type Isis-metric;
      description
        "Distance to the IS";
    }
    list paths {
      description
        "First hops towards the IS";
      uses ISIS-SH-IPV6-PATH;
    }
    list multicast-path {
      description
        "Multicast intact first hops towards the IS";
      uses ISIS-SH-IPV6-PATH;
    }
    list parent {
      description
        "Parents of the IS within the SPT";
      uses ISIS-SH-TOPO-NEIGHBOR;
    }
    list children {
      description
        "Children of the IS within the SPT";
      uses ISIS-SH-TOPO-NEIGHBOR;
    }
  }

  grouping ISIS-SH-IPV6-TOPO-REACHABLE-STATUS {
    description
      "Reachability status of an IPv6 IS";
    container reachable-details {
      when "../reachable-status = 'isis-reachable'" {
        description
          "../ReachableStatus = 'ISIS_REACHABLE'";
      }
      description
        "Status of the IS within the SPT";
      uses ISIS-SH-IPV6-TOPO-REACHABLE-DETAILS;
    }
    leaf reachable-status {
      type Isis-reachable;
      description
        "ReachableStatus";
    }
  }

  grouping ISIS-SH-IPV6-TOPO-ENTRY {
    description
      "IPv6 IS Link Topology Entry";
    container reachability-status {
      description
        "Is the IS reachable, and, if so, its status
         within the SPT";
      uses ISIS-SH-IPV6-TOPO-REACHABLE-STATUS;
    }
    container advertised-prefix-item-counts {
      description
        "Per-priority counts of prefix items advertised
         by the IS";
      uses ISIS-PER-PRIORITY-COUNTS;
    }
    leaf source-address {
      type Isis-ipv6-address;
      description
        "Source Address";
    }
    leaf is-participant {
      type boolean;
      description
        "Does the IS participate in the topology?";
    }
    leaf is-algo-participant {
      type boolean;
      description
        "Does the IS participate in the Algorithm?";
    }
    leaf is-overloaded {
      type boolean;
      description
        "Is the IS overloaded?";
    }
    leaf is-attached {
      type boolean;
      description
        "Is the IS attached?";
    }
    leaf is-sr-capable {
      type boolean;
      description
        "Is SR Capable";
    }
    leaf is-srv6-capable {
      type boolean;
      description
        "Is SRv6 Capable";
    }
    leaf algorithm {
      type uint32;
      description
        "Algorithm";
    }
  }

  grouping ISIS-SH-TOPO-NEIGHBOR {
    description
      "SPT Neighbor";
    leaf neighbor-id {
      type xr:Osi-system-id;
      description
        "Neighbor ID";
    }
    leaf intermediate-pseudonode {
      type xr:Isis-node-id;
      description
        "Pseudonode between system and its neighbor";
    }
  }

  grouping ISIS-SH-IPV4-TOPO-REACHABLE-DETAILS {
    description
      "Status of a reachable IPv4 IS";
    leaf root-distance {
      type Isis-metric;
      description
        "Distance to the IS";
    }
    leaf multicast-root-distance {
      type Isis-metric;
      description
        "Distance to the IS";
    }
    list paths {
      description
        "First hops towards the IS";
      uses ISIS-SH-IPV4-PATH;
    }
    list multicast-path {
      description
        "Multicast intact first hops towards the IS";
      uses ISIS-SH-IPV4-PATH;
    }
    list parent {
      description
        "Parents of the IS within the SPT";
      uses ISIS-SH-TOPO-NEIGHBOR;
    }
    list children {
      description
        "Children of the IS within the SPT";
      uses ISIS-SH-TOPO-NEIGHBOR;
    }
  }

  grouping ISIS-SH-IPV4-TOPO-REACHABLE-STATUS {
    description
      "Reachability status of an IPv4 IS";
    container reachable-details {
      when "../reachable-status = 'isis-reachable'" {
        description
          "../ReachableStatus = 'ISIS_REACHABLE'";
      }
      description
        "Status of the IS within the SPT";
      uses ISIS-SH-IPV4-TOPO-REACHABLE-DETAILS;
    }
    leaf reachable-status {
      type Isis-reachable;
      description
        "ReachableStatus";
    }
  }

  grouping ISIS-SH-IPV4-TOPO-ENTRY {
    description
      "IPv4 IS Link Topology Entry";
    container reachability-status {
      description
        "Is the IS reachable, and, if so, its status
         within the SPT";
      uses ISIS-SH-IPV4-TOPO-REACHABLE-STATUS;
    }
    container advertised-prefix-item-counts {
      description
        "Per-priority counts of prefix items advertised
         by the IS";
      uses ISIS-PER-PRIORITY-COUNTS;
    }
    leaf source-address {
      type Isis-ipv4-address;
      description
        "Source Address";
    }
    leaf is-participant {
      type boolean;
      description
        "Does the IS participate in the topology?";
    }
    leaf is-algo-participant {
      type boolean;
      description
        "Does the IS participate in the Algorithm?";
    }
    leaf is-overloaded {
      type boolean;
      description
        "Is the IS overloaded?";
    }
    leaf is-attached {
      type boolean;
      description
        "Is the IS attached?";
    }
    leaf is-sr-capable {
      type boolean;
      description
        "Is SR Capable";
    }
    leaf algorithm {
      type uint32;
      description
        "Algorithm";
    }
  }

  grouping ISIS-SH-TOPO-SUMMARY-NODE-STATS {
    description
      "Reachability counters";
    leaf reachable-node-count {
      type uint32;
      description
        "Number of nodes reachable in SPT";
    }
    leaf unreachable-node-count {
      type uint32;
      description
        "Number of nodes unreachable in SPT";
    }
    leaf unreachable-participant-node-count {
      type uint32;
      description
        "Number of participating nodes unreachable in SPT";
    }
  }

  grouping ISIS-SH-TOPO-SUMMARY {
    description
      "Summary Statistics for an IS Topology";
    container router-node-count {
      description
        "Node Counts for System nodes";
      uses ISIS-SH-TOPO-SUMMARY-NODE-STATS;
    }
    container pseudonode-node-count {
      description
        "Node Counts for Pseudonode nodes";
      uses ISIS-SH-TOPO-SUMMARY-NODE-STATS;
    }
  }

  grouping ISIS-SH-LOC-DETAIL {
    description
      "Per-level SRv6 Locator data";
    leaf locator-metric {
      type Isis-metric;
      description
        "Configured Locator Metric";
    }
    leaf locator-administrative-tag {
      type Isis-admin-tag;
      description
        "Configured Locator Admin Tag";
    }
  }

  grouping MGMT-SRV6-ENDPOINT-BEHAVIOR {
    description
      "SRv6 Endpoint Behavior Info";
    leaf type {
      type Mgmt-srv6-endpoint;
      description
        "Behavior type";
    }
    leaf description {
      type string;
      description
        "Behavior description";
    }
    leaf iana-type {
      type uint16;
      description
        "IANA assigned value";
    }
  }

  grouping ISIS-SRV6-RSVD-OPCODE {
    description
      "ISIS SRV6 RSVD OPCODE";
    container sid-behavior {
      description
        "SID Endpoint Behavior";
      uses MGMT-SRV6-ENDPOINT-BEHAVIOR;
    }
    leaf sid {
      type Isis-ipv6-address;
      description
        "SID";
    }
    leaf block-length {
      type uint8;
      description
        "Block Length";
    }
    leaf node-length {
      type uint8;
      description
        "Node Length";
    }
    leaf func-length {
      type uint8;
      description
        "Func Length";
    }
    leaf args-length {
      type uint8;
      description
        "Args Length";
    }
  }

  grouping MGMT-SRV6-SID-FMT {
    description
      "SRv6 SID Format Info";
    leaf type {
      type Mgmt-srv6-sid-fmt;
      description
        "Format type";
    }
    leaf description {
      type string;
      description
        "Format description";
    }
  }

  grouping ISIS-IP-PREFIX-TYPE {
    description
      "ISIS IP PREFIX TYPE";
    container ipv4 {
      when "../af-name = 'ipv4'" {
        description
          "../AFName = 'IPv4'";
      }
      description
        "ipv4";
      uses ISIS-IPV4-PREFIX-TYPE;
    }
    container ipv6 {
      when "../af-name = 'ipv6'" {
        description
          "../AFName = 'IPv6'";
      }
      description
        "ipv6";
      uses ISIS-IPV6-PREFIX-TYPE;
    }
    leaf af-name {
      type Isis-af-id;
      description
        "AFName";
    }
  }

  grouping ISIS-SH-SRV6-LOCATOR {
    description
      "SRv6 Locator";
    container locator-prefix {
      description
        "LocatorPrefix";
      uses ISIS-IP-PREFIX-TYPE;
    }
    container locator-format {
      description
        "LocatorFormat";
      uses MGMT-SRV6-SID-FMT;
    }
    leaf locator-name {
      type string;
      description
        "LocatorName";
    }
    leaf locator-id {
      type uint32;
      description
        "LocatorID";
    }
    leaf locator-flags {
      type uint16;
      description
        "LocatorFlags";
    }
    leaf number-of-auto-sids {
      type uint8;
      description
        "NumberOfAutoSIDs";
    }
    leaf algorithm {
      type uint8;
      description
        "Algorithm";
    }
    leaf locator-active {
      type boolean;
      description
        "Currently active";
    }
    leaf anycast-locator {
      type boolean;
      description
        "Anycast Locator";
    }
    leaf locator-out-of-resources {
      type boolean;
      description
        "Out of resources";
    }
    leaf instance-level {
      type Isis-levels;
      description
        "Isis Instance Level";
    }
    leaf locator-advertised-level {
      type Isis-level;
      description
        "Configured Locator Level";
    }
    list auto-sid {
      max-elements "5";
      description
        "Reserved Opcodes";
      uses ISIS-SRV6-RSVD-OPCODE;
    }
    list per-level-data {
      max-elements "2";
      description
        "Per-Level data";
      uses ISIS-SH-LOC-DETAIL;
    }
  }

  grouping ISIS-PER-PRIORITY-COUNTS {
    description
      "Per-priority counts";
    leaf critical {
      type uint32;
      description
        "Critical priority";
    }
    leaf high {
      type uint32;
      description
        "High priority";
    }
    leaf medium {
      type uint32;
      description
        "Medium priority";
    }
    leaf low {
      type uint32;
      description
        "Low priority";
    }
  }

  grouping ISIS-SH-FRR-LEVEL-SUMMARY {
    description
      "FRR backup statistics for one level";
    container all-paths-protected {
      description
        "Number of prefixes with all paths having FRR
         backup";
      uses ISIS-PER-PRIORITY-COUNTS;
    }
    container some-paths-protected {
      description
        "Number of prefixes with some paths having FRR
         backup";
      uses ISIS-PER-PRIORITY-COUNTS;
    }
    container unprotected {
      description
        "Number of reachable prefixes without FRR backup";
      uses ISIS-PER-PRIORITY-COUNTS;
    }
  }

  grouping ISIS-SH-FRR-SUMMARY {
    description
      "FRR summary for an ISIS topology";
    container level1-prefixes {
      description
        "FRR summary for prefixes reachable in L1";
      uses ISIS-SH-FRR-LEVEL-SUMMARY;
    }
    container level2-prefixes {
      description
        "FRR summary for prefixes reachable in L2";
      uses ISIS-SH-FRR-LEVEL-SUMMARY;
    }
    container unreachable-prefixes {
      description
        "Unreachable prefixes";
      uses ISIS-PER-PRIORITY-COUNTS;
    }
  }

  grouping ISIS-SH-IPV6-ROUTE-SUMMARIZATION-STATUS {
    description
      "Summarization status";
    container summary-prefix {
      when "../is-valid = 'isis-valid'" {
        description
          "../IsValid = 'ISIS_VALID'";
      }
      description
        "Summarizing Prefix";
      uses ISIS-IPV6-PREFIX-TYPE;
    }
    leaf is-valid {
      type Isis-valid;
      description
        "IsValid";
    }
  }

  grouping ISIS-SH-IPV6-ROUTE-ADV {
    description
      "How a prefix is advertised in a particular level";
    container summarization-status {
      description
        "Status of summarization for the prefix";
      uses ISIS-SH-IPV6-ROUTE-SUMMARIZATION-STATUS;
    }
    leaf level {
      type Isis-level;
      description
        "Level in which the prefix is advertised";
    }
    leaf advertising-origin {
      type Isis-sh-route-adv-origin;
      description
        "The origin of the advertisement";
    }
    leaf metric {
      type Isis-metric;
      description
        "Metric with which the prefix is advertised";
    }
    leaf is-propagated {
      type boolean;
      description
        "Has the prefix been propagated from another
         level?";
    }
    leaf is-external-metric {
      type boolean;
      description
        "Is the metric an external metric?";
    }
    leaf is-external-reachability {
      type boolean;
      description
        "Is the prefix external to the IS-IS domain?";
    }
    leaf is-interarea {
      type boolean;
      description
        "Is the up/down bit set?";
    }
    leaf algorithm {
      type uint32;
      description
        "Algorithm";
    }
    list tags {
      description
        "Tags associated with the prefix";
      leaf entry {
        type Isis-prefix-tag;
        description
          "Tags associated with the prefix";
      }
    }
    list nodal-sid {
      description
        "Nodal SIDs with the prefix item";
      uses ISIS-NODAL-SID-TYPE;
    }
    list flex-sid {
      description
        "Flex-Algo SIDs with the prefix item";
      uses ISIS-SID-METRIC-TYPE;
    }
  }

  grouping ISIS-SH-IPV6-ROUTE-NATIVE-SOURCE {
    description
      "Source of a native route";
    leaf source-lsp-id {
      type xr:Isis-lsp-id;
      description
        "ID of the LSP advertising the prefix";
    }
    leaf source-address {
      type Isis-ipv6-address;
      description
        "Source address of the IS advertising the prefix";
    }
    list tags {
      description
        "Tags associated with the prefix item";
      leaf entry {
        type Isis-prefix-tag;
        description
          "Tags associated with the prefix item";
      }
    }
    list nodal-sid {
      description
        "Nodal SIDs with the prefix item";
      uses ISIS-NODAL-SID-TYPE;
    }
  }

  grouping ISIS-SH-IPV6-UCMP-PATH {
    description
      "IPv6 path to a destination";
    container frr-backup {
      description
        "FRR backup for this path";
      uses ISIS-SH-IPV6-FRR-BACKUP;
    }
    leaf neighbor-id {
      type xr:Osi-system-id;
      description
        "Next hop neighbor ID";
    }
    leaf egress-interface {
      type Isis-sh-interface-name;
      description
        "Interface to send the packet out of";
    }
    leaf neighbor-address {
      type Isis-ipv6-address;
      description
        "Next hop neighbor's forwarding address";
    }
    leaf neighbor-snpa {
      type xr:Isis-snpa;
      description
        "Next hop neighbor's SNPA";
    }
    leaf tag {
      type Isis-prefix-tag;
      description
        "Tag associated with the path";
    }
    leaf total-ucmp-distance {
      type Isis-metric;
      description
        "Distance to the network via this UCMP next hop";
    }
    leaf segment-routing-sid-value {
      type Isis-nodal-sid-value;
      description
        "Segment routing sid value received from first
         hop";
    }
    leaf weight {
      type Isis-metric;
      description
        "Weight configured on the interface";
    }
    leaf is-te-tunnel-interface {
      type boolean;
      description
        "Is path via a TE tunnel";
    }
    leaf tunnel-sr-exclude-mode {
      type Isis-sr-exclude;
      description
        "Tunnel SR-exclusion mode";
    }
    leaf outgoing-label {
      type uint32;
      description
        "SR-MPLS label";
    }
  }

  grouping ISIS-SH-IPV6-FRR-BACKUP {
    description
      "FRR backup path";
    leaf neighbor-id {
      type xr:Osi-system-id;
      description
        "Next hop neighbor ID";
    }
    leaf egress-interface {
      type Isis-sh-interface-name;
      description
        "Interface to send the packet out of";
    }
    leaf neighbor-address {
      type Isis-ipv6-address;
      description
        "Next hop neighbor's forwarding address";
    }
    leaf tunnel-egress-interface {
      type Isis-sh-interface-name;
      description
        "Tunnel interface to send the packet out of";
    }
    leaf neighbor-snpa {
      type xr:Isis-snpa;
      description
        "Next hop neighbor's SNPA";
    }
    leaf remote-lfa-system-id {
      type xr:Osi-system-id;
      description
        "Remote LFA PQ Node's ID";
    }
    leaf remote-lfa-router-id {
      type Isis-ipv6-address;
      description
        "Remote LFA Router ID";
    }
    leaf remote-lfa-system-pid {
      type xr:Osi-system-id;
      description
        "Remote LFA PQ Node's ID";
    }
    leaf remote-lfa-router-pid {
      type Isis-ipv6-address;
      description
        "Remote LFA Router ID";
    }
    leaf total-backup-distance {
      type Isis-metric;
      description
        "Distance to the network via this backup path";
    }
    leaf segment-routing-sid-value {
      type Isis-nodal-sid-value;
      description
        "Segment routing sid value received from first
         hop";
    }
    leaf num-sids {
      type uint32;
      description
        "Number of SIDs in TI-LFA/rLFA";
    }
    leaf backup-repair-list-size {
      type uint32;
      description
        "Backup Repair List Size";
    }
    leaf tilfa-computation {
      type Isis-tilfa-computation;
      description
        "Ti LFA computation which provided backup path";
    }
    leaf prefix-source-node-id {
      type string;
      description
        "PrefixSourceNodeID";
    }
    leaf is-downstream {
      type boolean;
      description
        "Is the backup path via downstream node?";
    }
    leaf is-lc-disjoint {
      type boolean;
      description
        "Is the backup path line card disjoint with
         primary?";
    }
    leaf is-node-protecting {
      type boolean;
      description
        "Is the backup path node protecting?";
    }
    leaf is-primary-path {
      type boolean;
      description
        "Is the backup path an ECMP to the network?";
    }
    leaf is-srlg-disjoint {
      type boolean;
      description
        "Is the backup path SRLG disjoint with primary?";
    }
    leaf is-remote-lfa {
      type boolean;
      description
        "Is the backup path via a Remote LFA?";
    }
    leaf is-epcfrr-lfa {
      type boolean;
      description
        "Is the backup path via a TI-LFA?";
    }
    leaf is-strict-spflfa {
      type boolean;
      description
        "Is the backup path TI-LFA strict SPF?";
    }
    leaf is-srv6 {
      type boolean;
      description
        "Is the backup path SRv6?";
    }
    leaf is-tunnel-requested {
      type boolean;
      description
        "Is SR TE tunnel requested";
    }
    leaf weight {
      type Isis-metric;
      description
        "Weight configured on the interface";
    }
    leaf outgoing-label {
      type uint32;
      description
        "SR-MPLS label";
    }
    leaf tilfa-calc-path-states {
      type yang:hex-string;
      description
        "TILFA Calculation paths state";
    }
    list segment-routing-sid-value-entry {
      max-elements "3";
      description
        "Segment routing sid values for TI-LFA/rLFA";
      leaf entry {
        type Isis-nodal-sid-value;
        description
          "Segment routing sid values for TI-LFA/rLFA";
      }
    }
    list tilfa-calc-path-states-id {
      max-elements "5";
      description
        "TILFA Calculation paths state ID";
      leaf entry {
        type xr:Isis-node-id;
        description
          "TILFA Calculation paths state ID";
      }
    }
    list backup-repair {
      description
        "BAckup Repair List";
      uses ISIS-SH-REP-EL;
    }
  }

  grouping ISIS-SH-IPV6-PATH {
    description
      "IPv6 path to a destination";
    container frr-backup {
      description
        "FRR backup for this path";
      uses ISIS-SH-IPV6-FRR-BACKUP;
    }
    leaf neighbor-id {
      type xr:Osi-system-id;
      description
        "Next hop neighbor ID";
    }
    leaf egress-interface {
      type Isis-sh-interface-name;
      description
        "Interface to send the packet out of";
    }
    leaf neighbor-address {
      type Isis-ipv6-address;
      description
        "Next hop neighbor's forwarding address";
    }
    leaf neighbor-snpa {
      type xr:Isis-snpa;
      description
        "Next hop neighbor's SNPA";
    }
    leaf tag {
      type Isis-prefix-tag;
      description
        "Tag associated with the path";
    }
    leaf tunnel-interface {
      type Isis-sh-interface-name;
      description
        "Explicit path tunnel interface";
    }
    leaf segment-routing-sid-value {
      type Isis-nodal-sid-value;
      description
        "Segment routing sid value received from first
         hop";
    }
    leaf weight {
      type Isis-metric;
      description
        "Weight configured on the interface";
    }
    leaf is-te-tunnel-interface {
      type boolean;
      description
        "Is path via a TE tunnel";
    }
    leaf tunnel-sr-exclude-mode {
      type Isis-sr-exclude;
      description
        "Tunnel SR-exclusion mode";
    }
    leaf is-srv6 {
      type boolean;
      description
        "Is the path SRv6?";
    }
    leaf outgoing-label {
      type uint32;
      description
        "SR-MPLS label";
    }
    list uloop-explicit {
      description
        "Uloop Explicit List";
      uses ISIS-SH-REP-EL;
    }
    list nnh {
      description
        "Next next hops";
      uses ISIS-SH-NNH;
    }
  }

  grouping ISIS-SH-IPV6-ROUTE-NATIVE-PREFERENCE {
    description
      "Paths and sources for a native route at a
       particular preference";
    leaf origin {
      type Isis-prefix-origin;
      description
        "Origin of route";
    }
    leaf metric {
      type Isis-metric;
      description
        "Distance to network";
    }
    leaf multicast-metric {
      type Isis-metric;
      description
        "Multicast-intact distance to network";
    }
    leaf is-external-metric {
      type boolean;
      description
        "Is the metric an external metric?";
    }
    leaf administrative-distance {
      type uint16;
      description
        "Administrative Distance";
    }
    list paths {
      description
        "First hops toward the prefix";
      uses ISIS-SH-IPV6-PATH;
    }
    list ucmp-next-hop {
      description
        "UCMP first hops toward the prefix";
      uses ISIS-SH-IPV6-UCMP-PATH;
    }
    list multicast-path {
      description
        "Multicast intact first hops toward the prefix";
      uses ISIS-SH-IPV6-PATH;
    }
    list srte-path {
      description
        "SR-TE native first hops toward the prefix";
      uses ISIS-SH-IPV6-PATH;
    }
    list explicit-path {
      description
        "SR microloop avoidance paths";
      uses ISIS-SH-IPV6-PATH;
    }
    list source {
      description
        "Sources advertising the prefix";
      uses ISIS-SH-IPV6-ROUTE-NATIVE-SOURCE;
    }
    list multicast-source {
      description
        "Multicast-intact sources advertising the prefix";
      uses ISIS-SH-IPV6-ROUTE-NATIVE-SOURCE;
    }
  }

  grouping ISIS-SH-IPV6-ROUTE-NATIVE-DETAILS {
    description
      "Details of a native IS-IS route to a prefix";
    container primary {
      description
        "Primary paths to prefix";
      uses ISIS-SH-IPV6-ROUTE-NATIVE-PREFERENCE;
    }
    leaf priority {
      type Isis-prefix-priority;
      description
        "Relative importance of the prefix";
    }
    leaf is-installed-in-rib {
      type boolean;
      description
        "Is the prefix installed in the primary rib?";
    }
    leaf is-installed-in-sec-rib {
      type boolean;
      description
        "Is the prefix installed in the secondary rib?";
    }
    leaf is-filtered-by-dl {
      type boolean;
      description
        "Is the prefix filtered out by distribution list?";
    }
    leaf local-label {
      type uint32;
      description
        "Prefix local label for SR-MPLS";
    }
    leaf local-label-state {
      type Isis-local-label-state;
      description
        "Status of the SR-MPLS local label";
    }
    list backup {
      description
        "Backup paths to prefix";
      uses ISIS-SH-IPV6-ROUTE-NATIVE-PREFERENCE;
    }
  }

  grouping ISIS-SH-IPV6-ROUTE-NATIVE-STATUS {
    description
      "Status of a native IS-IS route to a prefix";
    container native-details {
      when "../is-valid = 'isis-valid'" {
        description
          "../IsValid = 'ISIS_VALID'";
      }
      description
        "Details of the native route";
      uses ISIS-SH-IPV6-ROUTE-NATIVE-DETAILS;
    }
    leaf is-valid {
      type Isis-valid;
      description
        "IsValid";
    }
  }

  grouping ISIS-SH-IPV6-ROUTE {
    description
      "IS-IS IPv6 route";
    container route-timestamp {
      description
        "Timestamp of last route update";
      uses ISIS-SH-TIMESTAMP-TYPE;
    }
    container connected-status {
      description
        "Status of IS-IS directly connected routes to the
         prefix";
      uses ISIS-SH-ROUTE-CONN-STATUS;
    }
    container redistributed-status {
      description
        "Status of other protocols' routes redistributed
         into IS-IS";
      uses ISIS-SH-ROUTE-REDIST-STATUS;
    }
    container native-status {
      description
        "Status of native IS-IS routes to the prefix";
      uses ISIS-SH-IPV6-ROUTE-NATIVE-STATUS;
    }
    leaf route-age {
      type uint32;
      units "second";
      description
        "Seconds since last route update";
    }
    list per-level-advertising-detail {
      description
        "Per level details of how the local system
         advertises the prefix";
      uses ISIS-SH-IPV6-ROUTE-ADV;
    }
  }

  grouping ISIS-SID-METRIC-TYPE {
    description
      "ISIS SID METRIC TYPE";
    container nodal-sid {
      description
        "nodal sid";
      uses ISIS-NODAL-SID-TYPE;
    }
    leaf metric {
      type uint32;
      description
        "metric";
    }
  }

  grouping ISIS-IPV4-PREFIX-TYPE {
    description
      "IPv4 address and prefix length";
    leaf prefix {
      type Isis-ipv4-address;
      description
        "prefix";
    }
    leaf prefix-length {
      type Isis-ip-prefix-length;
      description
        "prefix length";
    }
  }

  grouping ISIS-SH-IPV4-ROUTE-SUMMARIZATION-STATUS {
    description
      "Summarization status";
    container summary-prefix {
      when "../is-valid = 'isis-valid'" {
        description
          "../IsValid = 'ISIS_VALID'";
      }
      description
        "Summarizing Prefix";
      uses ISIS-IPV4-PREFIX-TYPE;
    }
    leaf is-valid {
      type Isis-valid;
      description
        "IsValid";
    }
  }

  grouping ISIS-SH-IPV4-ROUTE-ADV {
    description
      "How a prefix is advertised in a particular level";
    container summarization-status {
      description
        "Status of summarization for the prefix";
      uses ISIS-SH-IPV4-ROUTE-SUMMARIZATION-STATUS;
    }
    leaf level {
      type Isis-level;
      description
        "Level in which the prefix is advertised";
    }
    leaf advertising-origin {
      type Isis-sh-route-adv-origin;
      description
        "The origin of the advertisement";
    }
    leaf metric {
      type Isis-metric;
      description
        "Metric with which the prefix is advertised";
    }
    leaf is-propagated {
      type boolean;
      description
        "Has the prefix been propagated from another
         level?";
    }
    leaf is-external-metric {
      type boolean;
      description
        "Is the metric an external metric?";
    }
    leaf is-external-reachability {
      type boolean;
      description
        "Is the prefix external to the IS-IS domain?";
    }
    leaf is-interarea {
      type boolean;
      description
        "Is the up/down bit set?";
    }
    leaf algorithm {
      type uint32;
      description
        "Algorithm";
    }
    list tags {
      description
        "Tags associated with the prefix";
      leaf entry {
        type Isis-prefix-tag;
        description
          "Tags associated with the prefix";
      }
    }
    list nodal-sid {
      description
        "Nodal SIDs with the prefix item";
      uses ISIS-NODAL-SID-TYPE;
    }
    list flex-sid {
      description
        "Flex-Algo SIDs with the prefix item";
      uses ISIS-SID-METRIC-TYPE;
    }
  }

  grouping ISIS-NODAL-SID-TYPE {
    description
      "ISIS NODAL SID TYPE";
    leaf sid-value {
      type Isis-nodal-sid-value;
      description
        "sid value";
    }
    leaf rflag {
      type uint8;
      description
        "rflag";
    }
    leaf nflag {
      type uint8;
      description
        "nflag";
    }
    leaf pflag {
      type uint8;
      description
        "pflag";
    }
    leaf eflag {
      type uint8;
      description
        "eflag";
    }
    leaf vflag {
      type uint8;
      description
        "vflag";
    }
    leaf lflag {
      type uint8;
      description
        "lflag";
    }
    leaf algorithm {
      type uint8;
      description
        "algorithm";
    }
  }

  grouping ISIS-SH-IPV4-ROUTE-NATIVE-SOURCE {
    description
      "Source of a native route";
    leaf source-lsp-id {
      type xr:Isis-lsp-id;
      description
        "ID of the LSP advertising the prefix";
    }
    leaf source-address {
      type Isis-ipv4-address;
      description
        "Source address of the IS advertising the prefix";
    }
    list tags {
      description
        "Tags associated with the prefix item";
      leaf entry {
        type Isis-prefix-tag;
        description
          "Tags associated with the prefix item";
      }
    }
    list nodal-sid {
      description
        "Nodal SIDs with the prefix item";
      uses ISIS-NODAL-SID-TYPE;
    }
  }

  grouping ISIS-SH-IPV4-UCMP-PATH {
    description
      "IPv4 path to a destination";
    container frr-backup {
      description
        "FRR backup for this path";
      uses ISIS-SH-IPV4-FRR-BACKUP;
    }
    leaf neighbor-id {
      type xr:Osi-system-id;
      description
        "Next hop neighbor ID";
    }
    leaf egress-interface {
      type Isis-sh-interface-name;
      description
        "Interface to send the packet out of";
    }
    leaf neighbor-address {
      type Isis-ipv4-address;
      description
        "Next hop neighbor's forwarding address";
    }
    leaf neighbor-snpa {
      type xr:Isis-snpa;
      description
        "Next hop neighbor's SNPA";
    }
    leaf tag {
      type Isis-prefix-tag;
      description
        "Tag associated with the path";
    }
    leaf total-ucmp-distance {
      type Isis-metric;
      description
        "Distance to the network via this UCMP next hop";
    }
    leaf segment-routing-sid-value {
      type Isis-nodal-sid-value;
      description
        "Segment routing sid value received from first
         hop";
    }
    leaf weight {
      type Isis-metric;
      description
        "Weight configured on the interface";
    }
    leaf is-te-tunnel-interface {
      type boolean;
      description
        "Is path via a TE tunnel";
    }
    leaf tunnel-sr-exclude-mode {
      type Isis-sr-exclude;
      description
        "Tunnel SR-exclusion mode";
    }
    leaf outgoing-label {
      type uint32;
      description
        "SR-MPLS label";
    }
  }

  grouping ISIS-SH-NNH {
    description
      "Next next hops for a prefix";
    leaf link-id-set {
      type boolean;
      description
        "If link_id is given";
    }
    leaf ipv4-set {
      type boolean;
      description
        "If ipv4 address is given";
    }
    leaf link-id {
      type uint32;
      description
        "link ID of the next next hop";
    }
    leaf ipv4-address {
      type Isis-ipv4-address;
      description
        "Ipv4 address of the next next hop";
    }
  }

  grouping ISIS-SH-REP-EL {
    description
      "OSPF Repair Element";
    leaf repair-element-node-id {
      type string;
      description
        "RepairElementNodeID";
    }
    leaf repair-ipv4-addr {
      type Isis-ipv4-address;
      description
        "RepairIPv4Addr";
    }
    leaf repair-ipv6-addr {
      type Isis-ipv6-address;
      description
        "RepairIPv6Addr";
    }
    leaf repair-label {
      type uint32;
      description
        "Repair Label";
    }
    leaf repair-element-type {
      type uint32;
      description
        "Repair Element Type";
    }
    leaf repair-strict-spf-label {
      type uint32;
      description
        "Repair Strict SPF Label";
    }
    leaf repair-srv6-sid {
      type Isis-ipv6-address;
      description
        "Repair SRv6 SID";
    }
    leaf repair-srv6-end-func {
      type Isis-srv6-endpoint-func;
      description
        "Repair SRv6 End Function";
    }
    leaf repair-srv6-strict-spf-sid {
      type Isis-ipv6-address;
      description
        "Repair SRv6 Strict SPF SID";
    }
    leaf repair-srv6-strict-spf-end-func {
      type Isis-srv6-endpoint-func;
      description
        "Repair SRv6 Strict SPF End Function";
    }
  }

  grouping ISIS-SH-IPV4-FRR-BACKUP {
    description
      "FRR backup path";
    leaf neighbor-id {
      type xr:Osi-system-id;
      description
        "Next hop neighbor ID";
    }
    leaf egress-interface {
      type Isis-sh-interface-name;
      description
        "Interface to send the packet out of";
    }
    leaf neighbor-address {
      type Isis-ipv4-address;
      description
        "Next hop neighbor's forwarding address";
    }
    leaf tunnel-egress-interface {
      type Isis-sh-interface-name;
      description
        "Tunnel Interface to send the packet out of";
    }
    leaf neighbor-snpa {
      type xr:Isis-snpa;
      description
        "Next hop neighbor's SNPA";
    }
    leaf remote-lfa-system-id {
      type xr:Osi-system-id;
      description
        "Remote LFA PQ Node's ID";
    }
    leaf remote-lfa-router-id {
      type Isis-ipv4-address;
      description
        "Remote LFA Router ID";
    }
    leaf remote-lfa-system-pid {
      type xr:Osi-system-id;
      description
        "Remote LFA PQ Node's ID";
    }
    leaf remote-lfa-router-pid {
      type Isis-ipv4-address;
      description
        "Remote LFA Router ID";
    }
    leaf total-backup-distance {
      type Isis-metric;
      description
        "Distance to the network via this backup path";
    }
    leaf segment-routing-sid-value {
      type Isis-nodal-sid-value;
      description
        "Segment routing sid value received from first
         hop";
    }
    leaf num-sids {
      type uint32;
      description
        "Number of SIDs in TI-LFA/rLFA";
    }
    leaf backup-repair-list-size {
      type uint32;
      description
        "Backup Repair List Size";
    }
    leaf tilfa-computation {
      type Isis-tilfa-computation;
      description
        "Ti LFA computation which provided backup path";
    }
    leaf prefix-source-node-id {
      type string;
      description
        "PrefixSourceNodeID";
    }
    leaf is-downstream {
      type boolean;
      description
        "Is the backup path via downstream node?";
    }
    leaf is-lc-disjoint {
      type boolean;
      description
        "Is the backup path line card disjoint with
         primary?";
    }
    leaf is-node-protecting {
      type boolean;
      description
        "Is the backup path node protecting?";
    }
    leaf is-primary-path {
      type boolean;
      description
        "Is the backup path an ECMP to the network?";
    }
    leaf is-srlg-disjoint {
      type boolean;
      description
        "Is the backup path SRLG disjoint with primary?";
    }
    leaf is-remote-lfa {
      type boolean;
      description
        "Is the backup path via a Remote LFA?";
    }
    leaf is-epcfrr-lfa {
      type boolean;
      description
        "Is the backup path via a TI-LFA?";
    }
    leaf is-strict-spflfa {
      type boolean;
      description
        "Is the backup path TI-LFA strict SPF?";
    }
    leaf is-tunnel-requested {
      type boolean;
      description
        "Is SR TE tunnel requested";
    }
    leaf weight {
      type Isis-metric;
      description
        "Weight configured on the interface";
    }
    leaf outgoing-label {
      type uint32;
      description
        "SR-MPLS label";
    }
    leaf tilfa-calc-path-states {
      type yang:hex-string;
      description
        "TILFA Calculation paths state";
    }
    list segment-routing-sid-value-entry {
      max-elements "3";
      description
        "Segment routing sid values for TI-LFA/rLFA";
      leaf entry {
        type Isis-nodal-sid-value;
        description
          "Segment routing sid values for TI-LFA/rLFA";
      }
    }
    list tilfa-calc-path-states-id {
      max-elements "5";
      description
        "TILFA Calculation paths state ID";
      leaf entry {
        type xr:Isis-node-id;
        description
          "TILFA Calculation paths state ID";
      }
    }
    list backup-repair {
      description
        "Backup Repair List";
      uses ISIS-SH-REP-EL;
    }
  }

  grouping ISIS-SH-IPV4-PATH {
    description
      "IPv4 path to a destination";
    container frr-backup {
      description
        "FRR backup for this path";
      uses ISIS-SH-IPV4-FRR-BACKUP;
    }
    leaf neighbor-id {
      type xr:Osi-system-id;
      description
        "Next hop neighbor ID";
    }
    leaf egress-interface {
      type Isis-sh-interface-name;
      description
        "Interface to send the packet out of";
    }
    leaf neighbor-address {
      type Isis-ipv4-address;
      description
        "Next hop neighbor's forwarding address";
    }
    leaf neighbor-snpa {
      type xr:Isis-snpa;
      description
        "Next hop neighbor's SNPA";
    }
    leaf tag {
      type Isis-prefix-tag;
      description
        "Tag associated with the path";
    }
    leaf tunnel-interface {
      type Isis-sh-interface-name;
      description
        "Explicit path tunnel interface";
    }
    leaf segment-routing-sid-value {
      type Isis-nodal-sid-value;
      description
        "Segment routing sid value received from first
         hop";
    }
    leaf weight {
      type Isis-metric;
      description
        "Weight configured on the interface";
    }
    leaf is-te-tunnel-interface {
      type boolean;
      description
        "Is path via a TE tunnel";
    }
    leaf tunnel-sr-exclude-mode {
      type Isis-sr-exclude;
      description
        "Tunnel SR-exclusion mode";
    }
    leaf outgoing-label {
      type uint32;
      description
        "SR-MPLS label";
    }
    list uloop-explicit {
      description
        "Uloop Explicit List";
      uses ISIS-SH-REP-EL;
    }
    list nnh {
      description
        "Next next hops";
      uses ISIS-SH-NNH;
    }
  }

  grouping ISIS-SH-IPV4-ROUTE-NATIVE-PREFERENCE {
    description
      "Paths and sources for a native route at a
       particular preference";
    leaf origin {
      type Isis-prefix-origin;
      description
        "Origin of route";
    }
    leaf metric {
      type Isis-metric;
      description
        "Distance to network";
    }
    leaf multicast-metric {
      type Isis-metric;
      description
        "Multicast-intact distance to network";
    }
    leaf is-external-metric {
      type boolean;
      description
        "Is the metric an external metric?";
    }
    leaf administrative-distance {
      type uint16;
      description
        "Administrative Distance";
    }
    list paths {
      description
        "First hops toward the prefix";
      uses ISIS-SH-IPV4-PATH;
    }
    list ucmp-next-hop {
      description
        "UCMP first hops toward the prefix";
      uses ISIS-SH-IPV4-UCMP-PATH;
    }
    list multicast-path {
      description
        "Multicast intact first hops toward the prefix";
      uses ISIS-SH-IPV4-PATH;
    }
    list srte-path {
      description
        "SR-TE native first hops toward the prefix";
      uses ISIS-SH-IPV4-PATH;
    }
    list explicit-path {
      description
        "SR microloop avoidance paths";
      uses ISIS-SH-IPV4-PATH;
    }
    list source {
      description
        "Sources advertising the prefix";
      uses ISIS-SH-IPV4-ROUTE-NATIVE-SOURCE;
    }
    list multicast-source {
      description
        "Multicast-intact sources advertising the prefix";
      uses ISIS-SH-IPV4-ROUTE-NATIVE-SOURCE;
    }
  }

  grouping ISIS-SH-IPV4-ROUTE-NATIVE-DETAILS {
    description
      "Details of a native IS-IS route to a prefix";
    container primary {
      description
        "Primary paths to prefix";
      uses ISIS-SH-IPV4-ROUTE-NATIVE-PREFERENCE;
    }
    leaf priority {
      type Isis-prefix-priority;
      description
        "Relative importance of the prefix";
    }
    leaf is-installed-in-rib {
      type boolean;
      description
        "Is the prefix installed in the primary rib?";
    }
    leaf is-installed-in-sec-rib {
      type boolean;
      description
        "Is the prefix installed in the secondary rib?";
    }
    leaf is-filtered-by-dl {
      type boolean;
      description
        "Is the prefix filtered out by distribution list?";
    }
    leaf local-label {
      type uint32;
      description
        "Prefix local label for SR-MPLS";
    }
    leaf local-label-state {
      type Isis-local-label-state;
      description
        "Status of the SR-MPLS local label";
    }
    list backup {
      description
        "Backup paths to prefix";
      uses ISIS-SH-IPV4-ROUTE-NATIVE-PREFERENCE;
    }
  }

  grouping ISIS-SH-IPV4-ROUTE-NATIVE-STATUS {
    description
      "Status of a native IS-IS route to a prefix";
    container native-details {
      when "../is-valid = 'isis-valid'" {
        description
          "../IsValid = 'ISIS_VALID'";
      }
      description
        "Details of the native route";
      uses ISIS-SH-IPV4-ROUTE-NATIVE-DETAILS;
    }
    leaf is-valid {
      type Isis-valid;
      description
        "IsValid";
    }
  }

  grouping ISIS-SH-REDIST-ENTRY-PROTO {
    description
      "Redistributed protocol information";
    leaf protocol {
      type Isis-redist-proto;
      description
        "Protocol";
    }
    leaf isis-instance-id {
      when "../protocol = 'isis-redist-isis'" {
        description
          "../Protocol = 'ISIS_REDIST_ISIS'";
      }
      type Isis-string;
      description
        "IS-IS instance identifier";
    }
    leaf ospf-process-id {
      when "../protocol = 'isis-redist-ospf'" {
        description
          "../Protocol = 'ISIS_REDIST_OSPF'";
      }
      type Isis-string;
      description
        "OSPF process identifier";
    }
    leaf ospfv3-process-id {
      when "../protocol = 'isis-redist-ospfv3'" {
        description
          "../Protocol = 'ISIS_REDIST_OSPFV3'";
      }
      type Isis-string;
      description
        "OSPFv3 process identifier";
    }
    leaf bgp-as-number {
      when "../protocol = 'isis-redist-bgp'" {
        description
          "../Protocol = 'ISIS_REDIST_BGP'";
      }
      type Isis-string;
      description
        "BGP Autonomous System number";
    }
    leaf eigrp-as-number {
      when "../protocol = 'isis-redist-eigrp'" {
        description
          "../Protocol = 'ISIS_REDIST_EIGRP'";
      }
      type Isis-string;
      description
        "EIGRP Autonomous System number";
    }
    leaf application-name {
      when "../protocol = 'isis-redist-application'" {
        description
          "../Protocol = 'ISIS_REDIST_APPLICATION'";
      }
      type Isis-string;
      description
        "Application Name";
    }
  }

  grouping ISIS-SH-ROUTE-REDIST-LEVEL-DETAILS {
    description
      "Details of a route redistributed into a
       particular level";
    container owner {
      description
        "Protocol redistributing the route";
      uses ISIS-SH-REDIST-ENTRY-PROTO;
    }
    leaf level {
      type Isis-level;
      description
        "Level into which the route is redistributed";
    }
  }

  grouping ISIS-SH-ROUTE-REDIST-DETAILS {
    description
      "ISIS SH ROUTE REDIST DETAILS";
    list isis-sh-route-redist-detail {
      description
        "isis sh route redist detail";
      uses ISIS-SH-ROUTE-REDIST-LEVEL-DETAILS;
    }
  }

  grouping ISIS-SH-ROUTE-REDIST-STATUS {
    description
      "Status of redistributed routes to a prefix";
    container redistribution-details {
      when "../is-valid = 'isis-valid'" {
        description
          "../IsValid = 'ISIS_VALID'";
      }
      description
        "Per level details of the redistributed route";
      uses ISIS-SH-ROUTE-REDIST-DETAILS;
    }
    leaf is-valid {
      type Isis-valid;
      description
        "IsValid";
    }
  }

  grouping ISIS-SH-ROUTE-CONN-DETAILS {
    description
      "Details of an IS-IS directly connected prefix";
    list interface {
      description
        "Interfaces";
      leaf entry {
        type Isis-sh-interface-name;
        description
          "Interfaces";
      }
    }
  }

  grouping ISIS-SH-ROUTE-CONN-STATUS {
    description
      "Status of an IS-IS directly connected prefix";
    container connected-details {
      when "../is-valid = 'isis-valid'" {
        description
          "../IsValid = 'ISIS_VALID'";
      }
      description
        "Details of the directly connected prefix";
      uses ISIS-SH-ROUTE-CONN-DETAILS;
    }
    leaf is-valid {
      type Isis-valid;
      description
        "IsValid";
    }
  }

  grouping ISIS-SH-IPV4-ROUTE {
    description
      "IS-IS IPv4 route";
    container route-timestamp {
      description
        "Timestamp of last route update";
      uses ISIS-SH-TIMESTAMP-TYPE;
    }
    container connected-status {
      description
        "Status of IS-IS directly connected routes to the
         prefix";
      uses ISIS-SH-ROUTE-CONN-STATUS;
    }
    container redistributed-status {
      description
        "Status of other protocols' routes redistributed
         into IS-IS";
      uses ISIS-SH-ROUTE-REDIST-STATUS;
    }
    container native-status {
      description
        "Status of native IS-IS routes to the prefix";
      uses ISIS-SH-IPV4-ROUTE-NATIVE-STATUS;
    }
    leaf route-age {
      type uint32;
      units "second";
      description
        "Seconds since last route update";
    }
    list per-level-advertising-detail {
      description
        "Per level details of how the local system
         advertises the prefix";
      uses ISIS-SH-IPV4-ROUTE-ADV;
    }
  }

  grouping ISIS-SH-LSP-LOG-ENT {
    description
      "LSP-log entry";
    container generic-data {
      description
        "Generic entry data";
      uses ISIS-SH-GENERIC-LOG-ENT;
    }
    leaf trigger-count {
      type uint32;
      description
        "Number of triggers on this run. May not be equal
         to the number of trigger event types if one or
         more trigger events has occurred more than once.";
    }
    leaf delayed-trigger-count {
      type uint32;
      description
        "Number of delayed triggers";
    }
    leaf log-interface {
      type xr:Interface-name;
      description
        "Appropriate interface, if any";
    }
    leaf pseudo-node-number {
      type Isis-pseudo-node-number;
      description
        "Pseudo-node number";
    }
    list trigger {
      description
        "Triggers applying to this log entry.";
      leaf entry {
        type Isis-lsp-trigger;
        description
          "Triggers applying to this log entry.";
      }
    }
  }

  grouping ISIS-SH-LSP-LOG-STRUC {
    description
      "LSP log";
    leaf log-capacity {
      type uint32;
      description
        "Log Capacity";
    }
    leaf log-size {
      type uint32;
      description
        "Log Size";
    }
    list log-entry {
      description
        "Log entries";
      uses ISIS-SH-LSP-LOG-ENT;
    }
  }

  grouping ISIS-SH-LSP-FLOODING-STATE {
    description
      "Interfaces where either the SRM or SSN bit set,
       or the LSP is on the rexmit queue";
    leaf num-interfaces {
      type uint32;
      description
        "Number of Interfaces that have this bit set for
         this LSP";
    }
    list interface {
      description
        "The Interfaces that have this bit set for this
         
         LSP";
      leaf entry {
        type Isis-sh-interface-name;
        description
          "The Interfaces that have this bit set for this
           
           LSP";
      }
    }
  }

  grouping ISIS-SH-LSP-FLOODING-DATA {
    description
      "LSP meta-data";
    container time-stamp-received {
      description
        "When this LSP was first received and installed
         in the LSPDB";
      uses ISIS-SH-TIMESTAMP-TYPE;
    }
    container srm-bits {
      description
        "List of Interfaces where the Send Routing
         Message bit is set";
      uses ISIS-SH-LSP-FLOODING-STATE;
    }
    container ssn-bits {
      description
        "List of Interfaces where the Send Sequence
         Number bit is set";
      uses ISIS-SH-LSP-FLOODING-STATE;
    }
    container rexmit-interfaces {
      description
        "List of Interfaces where this LSP is on the
         Rexmit Queue";
      uses ISIS-SH-LSP-FLOODING-STATE;
    }
    leaf incoming-neighbor-id {
      type xr:Osi-system-id;
      description
        "Neighbor who sent us this LSP first";
    }
    leaf incoming-interface {
      type Isis-sh-interface-name;
      description
        "First interface this LSP was received on";
    }
    leaf reason-lsp-was-installed {
      type Isis-sh-lsp-db-install-reason;
      description
        "Reason why a new (version of an) LSP was
         installed in LSPDB";
    }
    leaf time-since-received {
      type int32;
      description
        "Time Since LSP was First Received in msec";
    }
    leaf bit-masks-are-set {
      type boolean;
      description
        "Bitmasks in this bag hold valid data";
    }
  }

  grouping ISIS-SH-LSP {
    description
      "An IS-IS LSP";
    container lsp-header-data {
      description
        "Information from the LSP header";
      uses ISIS-SH-LSP-HEADER;
    }
    container lsp-flooding-data {
      description
        "LSP flooding-data: sending neighbor, receiving
         intf, install reason";
      uses ISIS-SH-LSP-FLOODING-DATA;
    }
    leaf lsp-body {
      type yang:hex-string;
      description
        "LSP as received/sent over the wire, starting
         from the LSP ID field";
    }
  }

  grouping ISIS-SH-ADJ-BFD-ITEM {
    description
      "BFD TLV item";
    leaf mtid {
      type uint16;
      description
        "Topology ID";
    }
    leaf nlpid {
      type uint8;
      description
        "Network Layer Protocol ID";
    }
  }

  grouping ISIS-SH-ADJ-TOPO {
    description
      "Per-topology per-adjacency data";
    container id {
      description
        "Topology ID";
      uses ISIS-TOPO-ID-TYPE;
    }
    leaf topology-status {
      type Isis-adj-topo-status;
      description
        "Status of topology in adjacency";
    }
    leaf parallel-p2p-link-suppressed-flag {
      type boolean;
      description
        "TRUE if suppressed parallel point-to-point link";
    }
    list useable-flex-algo-nr {
      description
        "Flexible algorithms that can make use of this
         
         adjacency";
      leaf entry {
        type uint8;
        description
          "Flexible algorithms that can make use of this
           
           adjacency";
      }
    }
  }

  grouping ISIS-SH-ADJ {
    description
      "An IS-IS adjacency";
    leaf adjacency-system-id {
      type xr:Osi-system-id;
      description
        "Neighbor system ID";
    }
    leaf adjacency-snpa {
      type xr:Isis-snpa;
      description
        "Neighbor SNPA";
    }
    leaf adjacency-interface {
      type xr:Interface-name;
      description
        "Local interface";
    }
    leaf adjacency-media-type {
      type Isis-media-class;
      description
        "Link media type";
    }
    leaf adjacency-state {
      type Isis-adj-state;
      description
        "Adjacency state";
    }
    leaf adjacency-bfd-state {
      type Isis-adj-bfd-state;
      description
        "Adjacency IPv4 BFD state";
    }
    leaf adjacency-ipv6bfd-state {
      type Isis-adj-bfd-state;
      description
        "Adjacency IPv6 BFD state";
    }
    leaf adj-ipv4-bfd-configured {
      type boolean;
      description
        "Is IPv4 BFD Configured on the Interface of this
         Adjacency";
    }
    leaf adj-ipv6-bfd-configured {
      type boolean;
      description
        "Is IPv6 BFD Configured on the Interface of this
         Adjacency";
    }
    leaf adj-ipv4bfd-retry-running {
      type boolean;
      description
        "Is IPv4 BFD retry timer running";
    }
    leaf adj-ipv6bfd-retry-running {
      type boolean;
      description
        "Is IPv6 BFD retry timer running";
    }
    leaf adj-ipv4bfd-retry-exp {
      type uint32;
      description
        "Time to expiration of IPv4 BFD retry timer (s)";
    }
    leaf adj-ipv6bfd-retry-exp {
      type uint32;
      description
        "Time to expiration of IPv6 BFD retry timer (s)";
    }
    leaf adj-ipv4bfd-retry-count {
      type uint32;
      description
        "IPv4 BFD retry counter";
    }
    leaf adj-ipv6bfd-retry-count {
      type uint32;
      description
        "IPv6 BFD retry counter";
    }
    leaf adjacency-uptime-valid-flag {
      type boolean;
      description
        "TRUE if AdjacencyUptime is set";
    }
    leaf adjacency-uptime {
      type uint32;
      description
        "How long the adjacency has been up (s)";
    }
    leaf adjacency-holdtime {
      type uint32;
      description
        "Time (s) until adjacency declared down if no IIH
         received";
    }
    leaf adjacency-checkpoint-object-id {
      type uint32;
      description
        "Adjacency checkpoint object ID";
    }
    leaf adjacency-ietf-nsf-capable-flag {
      type boolean;
      description
        "TRUE if neighbor is IETF-NSF capable";
    }
    leaf adjacency-dispriority {
      type Isis-dr-priority;
      description
        "Priority of DIS on this LAN. Valid only if
         aj_media_class is ISIS_MEDIA_CLASS_LAN";
    }
    leaf adjacency-neighbor-priority {
      type Isis-dr-priority;
      description
        "Neighbor IS priority. Valid only if
         aj_media_class is ISIS_MEDIA_CLASS_LAN";
    }
    leaf adjacency-local-priority {
      type Isis-dr-priority;
      description
        "Local IS priority. Valid only if aj_media_class
         is ISIS_MEDIA_CLASS_LAN";
    }
    leaf local-dis-flag {
      type boolean;
      description
        "TRUE if local system is DIS. Valid only if
         AdjacencyMediaType is ISIS_MEDIA_CLASS_LAN";
    }
    leaf neighbor-dis-flag {
      type boolean;
      description
        "TRUE if neighbor is DIS. Valid only if
         AdjacencyMediaType is ISIS_MEDIA_CLASS_LAN";
    }
    leaf nsr-standby {
      type uint8;
      description
        "ISIS NSR STANDBY";
    }
    leaf bfd-required {
      type boolean;
      description
        "ISIS BFD Required";
    }
    leaf neighbor-useable {
      type boolean;
      description
        "ISIS Neighbor Useable";
    }
    leaf bfd-change-pending {
      type boolean;
      description
        "ISIS BFD change pending";
    }
    leaf cs-boot-integrity-pass {
      type boolean;
      description
        "CS Boot Integrity Pass";
    }
    leaf cs-boot-integrity-fail {
      type boolean;
      description
        "CS Boot Integrity Fail";
    }
    leaf cs-failures-found {
      type boolean;
      description
        "CS Failures Found";
    }
    leaf estimated-neighbor-mtu {
      type uint32;
      description
        "Estimated Neighbor MTU";
    }
    leaf own-interface-mtu {
      type uint32;
      description
        "Our own Interface MTU";
    }
    leaf adjacency-flaps {
      type uint32;
      description
        "Nr of times an Adjacency went Down on this intf";
    }
    list adjacency-area-address {
      description
        "Area addresses active over this adjacency";
      leaf entry {
        type xr:Osi-area-address;
        description
          "Area addresses active over this adjacency";
      }
    }
    list adjacency-topology {
      description
        "Per-topology data";
      uses ISIS-SH-ADJ-TOPO;
    }
    list adjacency-per-address-family-data {
      description
        "Per-address-family data";
      uses ISIS-SH-ADJ-AF;
    }
    list bfdtlv {
      description
        "BFD TLV content";
      uses ISIS-SH-ADJ-BFD-ITEM;
    }
  }

  grouping ISIS-SH-LSP-HEADER {
    description
      "Contents of an IS-IS LSP header";
    leaf lsp-id {
      type xr:Isis-lsp-id;
      description
        "The LSP ID";
    }
    leaf local-lsp-flag {
      type boolean;
      description
        "TRUE if this is a locally generated LSP";
    }
    leaf lsp-active-flag {
      type boolean;
      description
        "TRUE if this LSP has not expired";
    }
    leaf lsp-holdtime {
      type uint16;
      units "second";
      description
        "Time, in seconds, until LSP expiry (if active)
         or deletion (if expired) ";
    }
    leaf lsp-rcvd-holdtime {
      type uint16;
      units "second";
      description
        "Time, in seconds, for the received LSP it will
         be zero for the local LSP ";
    }
    leaf lsp-sequence-number {
      type uint32;
      description
        "The LSP sequence number";
    }
    leaf lsp-checksum {
      type uint16;
      description
        "The LSP checksum";
    }
    leaf lsp-partition-repair-supported-flag {
      type boolean;
      description
        "TRUE if partition repair is supported";
    }
    leaf lsp-attached-flag {
      type boolean;
      description
        "TRUE if attached bit is set";
    }
    leaf lsp-overloaded-flag {
      type boolean;
      description
        "TRUE if the overload bit is set";
    }
    leaf lsp-nonv1a-flag {
      type uint16;
      description
        "TRUE if the LSP is non-v1a, XXX for testing";
    }
    leaf lsp-level {
      type Isis-levels;
      description
        "The type of the IS sourcing the LSP";
    }
    leaf lsp-length {
      type uint16;
      description
        "The total length of the LSP";
    }
    leaf max-area-addresses {
      type uint8;
      description
        "max area addresses";
    }
    leaf id-length {
      type uint8;
      description
        "System Id length";
    }
    leaf version {
      type uint8;
      description
        "isis version";
    }
    leaf version2 {
      type uint8;
      description
        "isis version2";
    }
    leaf unauthenticated-flag {
      type boolean;
      description
        "TRUE if the LSP does not have valid
         authentication";
    }
  }

  grouping ISIS-SH-LSP-DB-LOG-ENT {
    description
      "LSP Database Log Entry";
    container generic-data {
      description
        "Generic entry data";
      uses ISIS-SH-GENERIC-LOG-ENT;
    }
    container new-lsp-entry {
      description
        "Entry being inserted or the updated version of
         an old entry.";
      uses ISIS-SH-LSP-HEADER;
    }
    container old-lsp-entry {
      description
        "Entry being replaced.";
      uses ISIS-SH-LSP-HEADER;
    }
    leaf lspdb-operation {
      type Isis-lsp-db-op;
      description
        "Operation applying to this entry.";
    }
    leaf reason-lsp-was-installed {
      type Isis-sh-lsp-db-install-reason;
      description
        "Reason why a new (version of an) LSP was
         installed in LSPDB";
    }
    leaf incoming-interface {
      type Isis-sh-interface-name;
      description
        "First interface this LSP was received on";
    }
    leaf incoming-neighbor-sys-id {
      type xr:Osi-system-id;
      description
        "Neighbor who sent us this LSP first";
    }
    leaf lsp-is-purged {
      type boolean;
      description
        "The received LSP is a Purge";
    }
    leaf poi-present {
      type boolean;
      description
        "Purge Originator ID TLV is included in the
         purged LSP";
    }
    leaf poi-originator {
      type xr:Osi-system-id;
      description
        "System ID of the router that inserted the POI
         TLV";
    }
    leaf poi-received-from {
      type xr:Osi-system-id;
      description
        "The router from which the purge first was first
         received from";
    }
  }

  grouping ISIS-SH-LSP-DB-LOG-STRUC {
    description
      "LSP Database Log";
    leaf log-capacity {
      type uint32;
      description
        "Log Capacity";
    }
    leaf log-size {
      type uint32;
      description
        "Log Size";
    }
    list log-entry {
      description
        "Entries";
      uses ISIS-SH-LSP-DB-LOG-ENT;
    }
  }

  grouping ISIS-SH-LSP-DB-SUMMARY-ALL-FRAGMENTS-STATS {
    description
      "All fragment counters";
    container node-counters {
      description
        "Summary by class of node";
      uses ISIS-SH-LSP-DB-SUMMARY-NODE-CLASS-COUNTERS;
    }
  }

  grouping ISIS-SH-LSP-DB-SUMMARY-TOPO-CLASS-COUNTERS {
    description
      "Per-topology related info";
    container id {
      description
        "Topology ID";
      uses ISIS-TOPO-ID-TYPE;
    }
    container overloaded-lsp-count {
      description
        "Number of LSPs with their per-topology overload
         bit set";
      uses ISIS-SH-LSP-DB-SUMMARY-STATUS-CLASS-COUNTERS;
    }
    container attached-lsp-count {
      description
        "Number of LSPs with their per-topology attached
         bit set";
      uses ISIS-SH-LSP-DB-SUMMARY-STATUS-CLASS-COUNTERS;
    }
  }

  grouping ISIS-SH-LSP-DB-SUMMARY-STATUS-CLASS-COUNTERS {
    description
      "LSP status counters";
    leaf active-lsp-count {
      type uint32;
      description
        "Number of active LSPs";
    }
    leaf purged-lsp-count {
      type uint32;
      description
        "Number of purged LSPs";
    }
  }

  grouping ISIS-SH-LSP-DB-SUMMARY-NODE-CLASS-COUNTERS {
    description
      "LSP node type counters";
    container route-lsp-count {
      description
        "Router LSPs";
      uses ISIS-SH-LSP-DB-SUMMARY-STATUS-CLASS-COUNTERS;
    }
    container pseudo-node-lsp-count {
      description
        "Pseudonode LSPs";
      uses ISIS-SH-LSP-DB-SUMMARY-STATUS-CLASS-COUNTERS;
    }
  }

  grouping ISIS-SH-LSP-DB-SUMMARY-FRAGMENT-0-STATS {
    description
      "Fragment-0 counters";
    container node-counters {
      description
        "Summary by class of node";
      uses ISIS-SH-LSP-DB-SUMMARY-NODE-CLASS-COUNTERS;
    }
    list per-topology-counter {
      description
        "Per topology counters";
      uses ISIS-SH-LSP-DB-SUMMARY-TOPO-CLASS-COUNTERS;
    }
  }

  grouping ISIS-SH-LSP-DB-SUMMARY {
    description
      "Summary Statistics for an IS-IS LSP Database";
    container fragment0lsp-stats {
      description
        "Statistics for fragment 0 LSPs";
      uses ISIS-SH-LSP-DB-SUMMARY-FRAGMENT-0-STATS;
    }
    container all-fragment-lsp-stats {
      description
        "Statistics for all LSP fragments";
      uses ISIS-SH-LSP-DB-SUMMARY-ALL-FRAGMENTS-STATS;
    }
  }

  grouping ISIS-ADJ-LOG-TOPO-TYPE {
    description
      "Per-topology per-adjacency log data";
    container id {
      description
        "Topology ID";
      uses ISIS-TOPO-ID-TYPE;
    }
    leaf change {
      type Isis-adj-topo-change;
      description
        "Change";
    }
  }

  grouping ISIS-SH-GENERIC-LOG-ENT {
    description
      "Generic portion of a log entry";
    container timestamp {
      description
        "Time in UTC relative to Jan 1st, 1970";
      uses ISIS-SH-TIMESTAMP-TYPE;
    }
  }

  grouping ISIS-SH-ADJ-LOG-ENT {
    description
      "An adjacency log entry";
    container generic-data {
      description
        "Generic entry data";
      uses ISIS-SH-GENERIC-LOG-ENT;
    }
    leaf adj-log-neighbor-system-id {
      type xr:Osi-system-id;
      description
        "Neighbor system ID";
    }
    leaf interface-name {
      type Isis-sh-interface-name;
      description
        "Interface name";
    }
    leaf prev-adj-state {
      type Isis-adj-state;
      description
        "Previous adjacency state";
    }
    leaf cur-adj-state {
      type Isis-adj-state;
      description
        "Current adjacency state";
    }
    leaf state-reason {
      type Isis-adj-state-reason;
      description
        "Reason adjacency changed state";
    }
    list adjacency-per-topology-change {
      description
        "Per-topology changes";
      uses ISIS-ADJ-LOG-TOPO-TYPE;
    }
  }

  grouping ISIS-SH-ADJ-LOG-STRUC {
    description
      "Adjacency log structure";
    leaf log-capacity {
      type uint32;
      description
        "Log Capacity";
    }
    leaf log-size {
      type uint32;
      description
        "Log Size";
    }
    list log-entry {
      description
        "Adjacency Log entries";
      uses ISIS-SH-ADJ-LOG-ENT;
    }
  }

  grouping ISIS-AREA-TOPO-STATS-TYPE {
    description
      "Per-area, per-topology traffic statistics";
    leaf spf-run-count {
      type uint32;
      description
        "Number of full SPF calculations run";
    }
    leaf ispf-run-count {
      type uint32;
      description
        "Number of ISPF calculations run";
    }
    leaf nhc-run-count {
      type uint32;
      description
        "Number of Next Hop Calculations run";
    }
    leaf prc-run-count {
      type uint32;
      description
        "Number of PRCs run";
    }
    leaf periodic-run-count {
      type uint32;
      description
        "Number of periodic SPF calculations run";
    }
  }

  grouping ISIS-SH-TRAFFIC-AREA-TOPO {
    description
      "Per-area, per-topology traffic data";
    container id {
      description
        "Topology ID";
      uses ISIS-TOPO-ID-TYPE;
    }
    container statistics {
      description
        "Statistics";
      uses ISIS-AREA-TOPO-STATS-TYPE;
    }
  }

  grouping ISIS-AREA-STATS-TYPE {
    description
      "Per-area traffic statistics";
    leaf system-lsp-build-count {
      type uint32;
      description
        "Number of times system LSP rebuilt";
    }
    leaf system-lsp-refresh-count {
      type uint32;
      description
        "Number of times system LSP refreshed";
    }
    leaf system-lsp-fragment-count {
      type uint32;
      description
        "Number of system LSP fragments in use";
    }
  }

  grouping ISIS-SH-TRAFFIC-AREA {
    description
      "Per-area traffic data";
    container statistics {
      description
        "Statistics";
      uses ISIS-AREA-STATS-TYPE;
    }
    leaf level {
      type Isis-level;
      description
        "Level this data applies to";
    }
    list per-topology-data {
      description
        "Per-topoogy statistics";
      uses ISIS-SH-TRAFFIC-AREA-TOPO;
    }
  }

  grouping ISIS-THREAD-EVENTS-STATS {
    description
      "IS-IS Thread event counters";
    leaf wake-up-triggers {
      type uint64;
      description
        "Number of times thread was triggered about
         incoming PDUs";
    }
    leaf wake-up-triggers-noop {
      type uint64;
      description
        "Number of times thread was not triggered about
         incoming PDUs";
    }
    leaf wake-up-triggers-error {
      type uint64;
      description
        "Number of times Wake Up trigger failed";
    }
    leaf timer-triggers {
      type uint64;
      description
        "Number of times thread was triggered about
         expiring timers";
    }
    leaf fop-triggers {
      type uint64;
      description
        "Number of times thread was triggered about
         incoming FOPs";
    }
    leaf async-msg-handler-calls {
      type uint64;
      description
        "Number of times the Async Msg Handler was called";
    }
    leaf wake-up-handler-calls {
      type uint64;
      description
        "Number of times the Wake Up Handler was called";
    }
    leaf processed-incoming-pd-us {
      type uint64;
      description
        "Number of processed Incoming PDUs";
    }
    leaf processed-timers {
      type uint64;
      description
        "Number of processed Timers";
    }
    leaf processed-pdu-out-timers {
      type uint64;
      description
        "Number of processed Timers that send a PDU out";
    }
    leaf processed-rexmit-timers {
      type uint64;
      description
        "Number of processed Retransmit Timers";
    }
    leaf processed-fo-ps {
      type uint64;
      description
        "Number of processed Incoming FOPs";
    }
    leaf main-outer-loops {
      type uint64;
      description
        "Number of times thread ran through the main
         outer loop";
    }
    leaf main-inner-loops {
      type uint64;
      description
        "Number of times thread ran through the main
         inner loop";
    }
    leaf drained-events {
      type uint64;
      description
        "Number of Events drained from Event Queue";
    }
    leaf repulses {
      type uint64;
      description
        "Number of the Thread repulsed itself";
    }
    leaf timer-count-yields {
      type uint64;
      description
        "Number of times we yielded because we ran out of
         time";
    }
    leaf timer-time-yields {
      type uint64;
      description
        "Number of times we yielded because we exceeded
         number of actions";
    }
    leaf timer-conman-yields {
      type uint64;
      description
        "Number of times we yielded because ConMan is
         acquiring a write-lock";
    }
  }

  grouping ISIS-SH-INTENTIONAL-DROPS-TYPE {
    description
      "Incoming PDUs dropped intentionally for testing
       purposes";
    container start-time {
      description
        "Time when starting to drop incoming PDUs for
         testing purposes";
      uses ISIS-SH-TIMESTAMP-TYPE;
    }
    container end-time {
      description
        "Time when stopped dropping incoming PDUs for
         testing purposes";
      uses ISIS-SH-TIMESTAMP-TYPE;
    }
    leaf intentional-drops-enabled {
      type boolean;
      description
        "Dropping intentionally a percentage of incoming
         PDUs";
    }
    leaf drop-percentage {
      type uint32;
      units "percentage";
      description
        "Percentage of incoming PDUs that are dropped for
         testing pursposes";
    }
    leaf previous-drop-percentage {
      type uint32;
      units "percentage";
      description
        "Percentage of incoming PDUs that were dropped
         previously";
    }
    leaf pd-us-dropped {
      type uint64;
      description
        "Number of PDUs intentionally dropped during this
         test period";
    }
    leaf pd-us-not-dropped {
      type uint64;
      description
        "Number of PDUs not intentionally dropped during
         this test period";
    }
  }

  grouping ISIS-TRAFFIC-QUEUE-PRIO-COUNT {
    description
      "Per-queue per-priority traffic statistics";
    container timestamp-high-water-mark {
      description
        "When was the last time the High Watermark was
         set";
      uses ISIS-SH-TIMESTAMP-TYPE;
    }
    container timestamp-last-drop-burst {
      description
        "When was the last time a PDU was dropped";
      uses ISIS-SH-TIMESTAMP-TYPE;
    }
    leaf client-max-queue-size {
      type uint64;
      description
        "Max number of packets that can be stored in the
         queue";
    }
    leaf pd-us-currently-in-queue {
      type uint64;
      description
        "Current number of packets in the queue";
    }
    leaf queue-high-water-mark {
      type uint64;
      description
        "Largest number of PDUs in the queue in the past";
    }
    leaf total-pd-us-processed {
      type uint64;
      description
        "Number of packets processed by the queue";
    }
    leaf pd-us-dropped {
      type uint64;
      description
        "Packets dropped because the queue was full";
    }
    leaf num-drop-bursts {
      type uint32;
      description
        "Number of contiguous bursts of drops";
    }
    leaf current-drops-burst {
      type uint32;
      description
        "How many PDUs are currently dropped back-to-back";
    }
    leaf last-drops-burst {
      type uint32;
      description
        "How many PDUs were dropped in the last burst";
    }
    leaf drops-burst-high-water-mark {
      type uint32;
      description
        "What is the largest number of back-to-back drops
         there was";
    }
  }

  grouping ISIS-TRAFFIC-QUEUE-COUNT-TYPE {
    description
      "Per-queue traffic statistics";
    container total-counts {
      description
        "Total max depth, current depth and drop-count";
      uses ISIS-TRAFFIC-QUEUE-PRIO-COUNT;
    }
    leaf max-combined-queue-size {
      type uint64;
      description
        "Max number of packets of any priority that can
         be stored in queue";
    }
    leaf pd-us-dropped-because-error {
      type uint64;
      description
        "Packets dropped because there was an internal
         error";
    }
    list per-priority {
      max-elements "5";
      description
        "Max depth, current depth and drop-count per
         priority";
      uses ISIS-TRAFFIC-QUEUE-PRIO-COUNT;
    }
  }

  grouping ISIS-TIMINGS-TIMESTAMP-TYPE {
    description
      "Performance timestamp";
    leaf real-nsec {
      type uint64;
      units "nanosecond";
      description
        "Wallclock timestamp value (nanoseconds)";
    }
    leaf cpu-nsec {
      type uint64;
      units "nanosecond";
      description
        "CPU timestamp value (nanoseconds)";
    }
  }

  grouping ISIS-TRAFFIC-PDU-COUNT-TYPE {
    description
      "Per-PDU packet counters";
    leaf pdu-receive-count {
      type uint64;
      description
        "PDUs received";
    }
    leaf pdu-send-count {
      type uint64;
      description
        "PDUs sent";
    }
    leaf pdu-dropped-count {
      type uint32;
      description
        "PDUs dropped";
    }
  }

  grouping ISIS-TRAFFIC-PDU-INFO-TYPE {
    description
      "Per-PDU traffic statistics";
    container pdu-counters {
      description
        "Per PDU-type packet counters";
      uses ISIS-TRAFFIC-PDU-COUNT-TYPE;
    }
    container pdu-recv-time {
      description
        "Cumulative PDU receive time";
      uses ISIS-TIMINGS-TIMESTAMP-TYPE;
    }
    container pdu-transmit-time {
      description
        "Cumulative PDU transmit time";
      uses ISIS-TIMINGS-TIMESTAMP-TYPE;
    }
    leaf pdu-avg-recv-rate {
      type uint32;
      units "packet/s";
      description
        "Average PDU receive rate in packets per second";
    }
    leaf pdu-avg-send-rate {
      type uint32;
      units "packet/s";
      description
        "Average PDU send rate in packets per second";
    }
    leaf pdu-peak-recv-rate {
      type uint32;
      units "packet/s";
      description
        "Peak PDU receive rate in packets per second";
    }
    leaf pdu-peak-send-rate {
      type uint32;
      units "packet/s";
      description
        "Peak PDU send rate in packets per second";
    }
  }

  grouping ISIS-TRAFFIC-GLOBAL-TYPE {
    description
      "IS-IS process traffic statistics";
    container hello-stats {
      description
        "Counters and statistics for Hello packets";
      uses ISIS-TRAFFIC-PDU-INFO-TYPE;
    }
    container lsp-stats {
      description
        "Counters and statistics for LSP packets";
      uses ISIS-TRAFFIC-PDU-INFO-TYPE;
    }
    container csnp-stats {
      description
        "Counters and statistics for CSNP packets";
      uses ISIS-TRAFFIC-PDU-INFO-TYPE;
    }
    container pspn-stats {
      description
        "Counters and statistics for PSNP packets";
      uses ISIS-TRAFFIC-PDU-INFO-TYPE;
    }
    container new-ls-ps-in-decision-lspdb {
      description
        "New LSPs installed in Decision LSPDB";
      uses ISIS-TRAFFIC-PDU-INFO-TYPE;
    }
    container process-input-queue {
      description
        "Input Queue from CLNS/NetIO to the IS-IS process";
      uses ISIS-TRAFFIC-QUEUE-COUNT-TYPE;
    }
    container process-output-queue {
      description
        "Output Queue from the IS-IS process to
         CLNS/NetIO";
      uses ISIS-TRAFFIC-QUEUE-COUNT-TYPE;
    }
    container update-input-queue {
      description
        "Input Queue from Hello Thread to Update Thread";
      uses ISIS-TRAFFIC-QUEUE-COUNT-TYPE;
    }
    container stray-pdu-timestamp {
      description
        "Timestamp last time a PDU was received on a non
         IS-IS interface";
      uses ISIS-SH-TIMESTAMP-TYPE;
    }
    container oversized-pdu-out-timestamp {
      description
        "Timestamp last time IS-IS sent an oversized PDU
         out";
      uses ISIS-SH-TIMESTAMP-TYPE;
    }
    container own-lsp-purge-timestamp {
      description
        "Last time we purged on of our own LSPs";
      uses ISIS-SH-TIMESTAMP-TYPE;
    }
    container other-lsp-purge-timestamp {
      description
        "Last time we purged an LSP fragment from another
         router";
      uses ISIS-SH-TIMESTAMP-TYPE;
    }
    container intentional-drops {
      description
        "Incoming PDUs dropped intentionally for testing
         purposes";
      uses ISIS-SH-INTENTIONAL-DROPS-TYPE;
    }
    container events-handled-by-update-thread {
      description
        "Number of timers, incoming packets and other
         events in Hello thread";
      uses ISIS-THREAD-EVENTS-STATS;
    }
    container events-handled-by-hello-thread {
      description
        "Number of timers, incoming packets and other
         events in Update thread";
      uses ISIS-THREAD-EVENTS-STATS;
    }
    container events-handled-by-other-threads {
      description
        "Number of timers, incoming packets and other
         events in other threads";
      uses ISIS-THREAD-EVENTS-STATS;
    }
    container last-clear-statistics {
      description
        "Last time a 'clear isis statistics' was issued";
      uses ISIS-SH-TIMESTAMP-TYPE;
    }
    leaf zero-holdtime-lsp-count {
      type uint32;
      description
        "LSPs received with holdtime 0";
    }
    leaf invalid-checksum-lsp-count {
      type uint32;
      description
        "LSPs received with invalid checksum";
    }
    leaf lsp-retransmit-count {
      type uint32;
      description
        "LSP retransmissions";
    }
    leaf psnp-schedule-delay {
      type uint32;
      description
        "Update PSNP schedule delay";
    }
    leaf purges-early-drops {
      type uint32;
      description
        "LSP Purges dropped because the Update Queue is
         filling up";
    }
    leaf num-stray-pd-us-recv {
      type uint32;
      description
        "Number of PDUs on interfaces that were not
         configured for IS-IS";
    }
    leaf stray-pdu-ifhandle {
      type xr:Interface-name;
      description
        "Last interface not configured for IS-IS that
         received an IS-IS PDU";
    }
    leaf msec-since-last-stray-pdu {
      type int32;
      description
        "Time in msec since last PDU was received on a
         non IS-IS interface";
    }
    leaf stray-pdu-size {
      type int32;
      description
        "Size of last PDU received on a non IS-IS
         interface";
    }
    leaf num-oversized-pd-us-out {
      type int32;
      description
        "Number of oversized PDUs that IS-IS sent out";
    }
    leaf oversized-pdu-out-ifhandle {
      type xr:Interface-name;
      description
        "Last interface where IS-IS sent an oversized PDU
         out";
    }
    leaf msec-since-last-oversized-pdu-out {
      type int32;
      description
        "Time in msec since last oversized PDU that IS-IS
         sent out";
    }
    leaf oversized-pdu-out-size {
      type int32;
      description
        "Size of last oversized PDU that IS-IS sent out";
    }
    leaf oversized-pdu-out-code {
      type uint8;
      description
        "PDU Type of last oversized PDU that IS-IS sent
         out";
    }
    leaf own-lsp-purges {
      type uint32;
      description
        "Number of times we have purged one of our own
         LSP fragments";
    }
    leaf own-lsp-purge-ls-pid {
      type xr:Isis-lsp-id;
      description
        "LSP Identifier of our own last LSP fragment that
         we have purged";
    }
    leaf own-lsp-purge-level {
      type Isis-level;
      description
        "Level of our own last LSP fragment that we have
         purged";
    }
    leaf other-lsp-purges {
      type uint32;
      description
        "Number of times we have purged an LSP fragment
         from another router";
    }
    leaf other-lsp-purge-ls-pid {
      type xr:Isis-lsp-id;
      description
        "LSP Identifier of the last LSP from another
         router we have purged";
    }
    leaf other-lsp-purge-level {
      type Isis-level;
      description
        "Level of the last LSP fragment from another
         router that we have purged";
    }
    leaf msec-since-last-clear-statistics {
      type int32;
      units "millisecond";
      description
        "Milliseconds since the last 'clear isis
         statistics' was issued";
    }
    leaf num-clear-statistics {
      type uint32;
      description
        "Number of times a 'clear isis statistics' was
         issued";
    }
  }

  grouping ISIS-SH-TRAFFIC-GLOBAL {
    description
      "IS-IS process traffic data";
    container statistics {
      description
        "IS-IS Global Statistics about packets, queues,
         events and more";
      uses ISIS-TRAFFIC-GLOBAL-TYPE;
    }
    list per-area-data {
      description
        "IS-IS per Area Statistics about LSPs and SPFs";
      uses ISIS-SH-TRAFFIC-AREA;
    }
  }

  grouping ISIS-SH-TIMESTAMP-TYPE {
    description
      "Timestamp for an event";
    leaf seconds {
      type uint32;
      units "second";
      description
        "Timestamp value (seconds)";
    }
    leaf nano-seconds {
      type uint32;
      units "nanosecond";
      description
        "Timestamp value (nanoseconds)";
    }
  }

  grouping ISIS-SH-STATIC-NBR-AREA {
    description
      "Per-Area Static Neighbor Data";
    list advertised {
      min-elements 3;
      max-elements "3";
      description
        "True if Advertsied";
      leaf entry {
        type boolean;
        description
          "Array entry.";
      }
    }
    list last-trnsition-time {
      max-elements "3";
      description
        "Last Transition Time";
      uses ISIS-SH-TIMESTAMP-TYPE;
    }
  }

  grouping ISIS-SH-STATIC-NBR {
    description
      "A static-neighbor IS";
    leaf neighbor-system-id {
      type xr:Osi-system-id;
      description
        "Static neighbor system ID";
    }
    leaf local-interface {
      type xr:Interface-name;
      description
        "Local interface";
    }
    leaf remote-ipv6-address {
      type Isis-ipv6-address;
      description
        "Remote IPv6 Address";
    }
    leaf remote-ipv4-address {
      type Isis-ipv4-address;
      description
        "Remote IPv4 address";
    }
    leaf state {
      type Isis-up;
      description
        "Static neigbor state";
    }
    leaf down-reason {
      type Isis-static-nbr-down-reason;
      description
        "Down reason";
    }
    leaf affinity-name {
      type string;
      description
        "AffinityName";
    }
    leaf policy-name {
      type string;
      description
        "Policy Name";
    }
    leaf policy-pass {
      type boolean;
      description
        "Policy Pass";
    }
    list per-area-data {
      max-elements "2";
      description
        "Per-Area Data";
      uses ISIS-SH-STATIC-NBR-AREA;
    }
  }

  grouping ISIS-SH-HOST {
    description
      "Bag representing a host (IS)";
    leaf local-is-flag {
      type boolean;
      description
        "TRUE if this is the local IS";
    }
    leaf host-levels {
      type Isis-levels;
      description
        "Host levels";
    }
    leaf host-name {
      type string;
      description
        "Host name";
    }
  }

  grouping ISIS-IPV6-ENDX-SID-BACKUP-INFO {
    description
      "IPv6 End.X SID backup information";
    leaf backup-stack-size {
      type uint8;
      description
        "Number of SIDs in the backup path stack";
    }
    leaf backup-node-address {
      type Isis-ipv6-address;
      description
        "Neighbor address used as adjacency backup target";
    }
    leaf backup-nexthop {
      type Isis-ipv6-address;
      description
        "Backup path nexthop address";
    }
    leaf backup-interface {
      type xr:Interface-name;
      description
        "Backup path interface";
    }
    list backup-stack {
      description
        "Backup path SID stack";
      uses ISIS-IPV6-PREFIX-TYPE;
    }
  }

  grouping ISIS-IPV6-PREFIX-TYPE {
    description
      "IPv4 address and prefix length";
    leaf prefix {
      type Isis-ipv6-address;
      description
        "prefix";
    }
    leaf prefix-length {
      type Isis-ip-prefix-length;
      description
        "prefix length";
    }
  }

  grouping ISIS-IPV6-ENDX-SID {
    description
      "IPv6 End.X SID";
    container end-x-sid {
      description
        "End.X SID value";
      uses ISIS-IPV6-PREFIX-TYPE;
    }
    container end-x-sid-backup {
      description
        "End.X SID Backup Info";
      uses ISIS-IPV6-ENDX-SID-BACKUP-INFO;
    }
    leaf end-x-sid-function {
      type Isis-srv6-endpoint-func;
      description
        "End.X SID Function";
    }
    leaf algorithm {
      type uint32;
      description
        "End.X SID Algorithm";
    }
    leaf block-length {
      type uint8;
      description
        "Block Length";
    }
    leaf node-length {
      type uint8;
      description
        "Node Length";
    }
    leaf func-length {
      type uint8;
      description
        "Func Length";
    }
    leaf args-length {
      type uint8;
      description
        "Args Length";
    }
  }

  grouping ISIS-SH-ADJ-PER-LOCATOR {
    description
      "IPv6 Adjacency Per-Locator Data";
    container end-x-sid {
      description
        "SRv6 End.X SID";
      uses ISIS-IPV6-ENDX-SID;
    }
    container non-frr-end-x-sid {
      description
        "SRv6 End.X SID not eligible for FRR protection";
      uses ISIS-IPV6-ENDX-SID;
    }
    leaf algorithm {
      type uint32;
      description
        "Algorithm";
    }
  }

  grouping ISIS-IPV6-ADJ-SID-BACKUP-INFO {
    description
      "IPv6 Adjacency SID backup information";
    leaf backup-label-stack-size {
      type uint8;
      description
        "Number of labels in the backup path label stack";
    }
    leaf backup-node-address {
      type Isis-ipv6-address;
      description
        "Neighbor address used as adjacency backup target";
    }
    leaf backup-nexthop {
      type Isis-ipv6-address;
      description
        "Backup path nexthop address";
    }
    leaf backup-interface {
      type xr:Interface-name;
      description
        "Backup path interface";
    }
    list backup-label-stack {
      description
        "Backup path label stack";
      leaf entry {
        type uint32;
        description
          "Backup path label stack";
      }
    }
  }

  grouping ISIS-IPV6-ADJ-SID {
    description
      "IPv6 Adjacency SID";
    container adjacency-sid-backup {
      description
        "Adjacency SID Backup Info";
      uses ISIS-IPV6-ADJ-SID-BACKUP-INFO;
    }
    container adjacency-sid-backup-te {
      description
        "Adjacency SID Backup Info TE";
      uses ISIS-IPV6-ADJ-SID-BACKUP-INFO;
    }
    leaf adjacency-sid-value {
      type Isis-nodal-sid-value;
      description
        "Adjacency SID value";
    }
  }

  grouping ISIS-SH-ADJ-IPV6 {
    description
      "IPv6 Specific Per-Adjacency Data";
    container adjacency-sid {
      description
        "Adjacency SID";
      uses ISIS-IPV6-ADJ-SID;
    }
    container non-frr-adjacency-sid {
      description
        "Adjacency SID not eligible for FRR protection";
      uses ISIS-IPV6-ADJ-SID;
    }
    leaf next-hop {
      type Isis-ipv6-address;
      description
        "Adjacency next hop";
    }
    list interface-address {
      description
        "Adjacency interface addresses";
      leaf entry {
        type Isis-ipv6-address;
        description
          "Adjacency interface addresses";
      }
    }
    list underlying-adjacency-sid {
      description
        "Per bundle member Adjacency sid";
      leaf entry {
        type Isis-nodal-sid-value;
        description
          "Per bundle member Adjacency sid";
      }
    }
    list underlying-interface {
      description
        "Underlying interface list for bundle interfaces";
      uses ISIS-SH-INTF-DET;
    }
    list end-x-sid {
      description
        "Per Locator ENDX SID";
      uses ISIS-SH-ADJ-PER-LOCATOR;
    }
  }

  grouping ISIS-SH-INTF-DET {
    description
      "Interface Detail";
    leaf interface-index {
      type uint32;
      description
        "Interface SNMP index";
    }
    leaf interface-name {
      type Isis-sh-interface-name;
      description
        "Interface name";
    }
  }

  grouping ISIS-IPV4-ADJ-SID-BACKUP-INFO {
    description
      "IPv4 Adjacency SID backup information";
    leaf backup-label-stack-size {
      type uint8;
      description
        "Number of labels in the backup path label stack";
    }
    leaf backup-node-address {
      type Isis-ipv4-address;
      description
        "Neighbor address used as adjacency backup target";
    }
    leaf backup-nexthop {
      type Isis-ipv4-address;
      description
        "Backup path nexthop address";
    }
    leaf backup-interface {
      type xr:Interface-name;
      description
        "Backup path interface";
    }
    list backup-label-stack {
      description
        "Backup path label stack";
      leaf entry {
        type uint32;
        description
          "Backup path label stack";
      }
    }
  }

  grouping ISIS-IPV4-ADJ-SID {
    description
      "IPv4 Adjacency SID";
    container adjacency-sid-backup {
      description
        "Adjacency SID Backup Info";
      uses ISIS-IPV4-ADJ-SID-BACKUP-INFO;
    }
    container adjacency-sid-backup-te {
      description
        "Adjacency SID Backup Info TE";
      uses ISIS-IPV4-ADJ-SID-BACKUP-INFO;
    }
    leaf adjacency-sid-value {
      type Isis-nodal-sid-value;
      description
        "Adjacency SID value";
    }
  }

  grouping ISIS-SH-ADJ-IPV4 {
    description
      "IPv4 Specific Per-Adjacency Data";
    container adjacency-sid {
      description
        "Adjacency SID";
      uses ISIS-IPV4-ADJ-SID;
    }
    container non-frr-adjacency-sid {
      description
        "Adjacency SID not eligible for FRR protection";
      uses ISIS-IPV4-ADJ-SID;
    }
    leaf next-hop {
      type Isis-ipv4-address;
      description
        "Adjacency next hop";
    }
    list interface-address {
      description
        "Adjacency interface addresses";
      leaf entry {
        type Isis-ipv4-address;
        description
          "Adjacency interface addresses";
      }
    }
    list underlying-adjacency-sid {
      description
        "Per bundle member Adjacency sid";
      leaf entry {
        type Isis-nodal-sid-value;
        description
          "Per bundle member Adjacency sid";
      }
    }
    list underlying-interface {
      description
        "Underlying interface list for bundle interfaces";
      uses ISIS-SH-INTF-DET;
    }
  }

  grouping ISIS-SH-ADJ-AF {
    description
      "ISIS SH ADJ AF";
    container ipv4 {
      when "../af-name = 'ipv4'" {
        description
          "../AFName = 'IPv4'";
      }
      description
        "IPV4 neighbor info";
      uses ISIS-SH-ADJ-IPV4;
    }
    container ipv6 {
      when "../af-name = 'ipv6'" {
        description
          "../AFName = 'IPv6'";
      }
      description
        "IPV6 neighbor info";
      uses ISIS-SH-ADJ-IPV6;
    }
    leaf af-name {
      type Isis-af-id;
      description
        "AFName";
    }
  }

  grouping ISIS-TOPO-ID-TYPE {
    description
      "Identification of an IS-IS topology";
    leaf af-name {
      type Isis-af-id;
      description
        "AF name";
    }
    leaf saf-name {
      type Isis-sub-af-id;
      description
        "Sub-AF name";
    }
    leaf vrf-name {
      type string;
      description
        "VRF Name";
    }
    leaf topology-name {
      type string;
      description
        "Topology Name";
    }
    leaf display-name {
      type string {
        length "0..64";
      }
      description
        "Display name";
    }
  }

  grouping ISIS-SH-NBR {
    description
      "A neighbor IS";
    leaf neighbor-system-id {
      type xr:Osi-system-id;
      description
        "Neighbor system ID";
    }
    leaf neighbor-snpa {
      type xr:Isis-snpa;
      description
        "Neighbor SNPA";
    }
    leaf local-interface {
      type xr:Interface-name;
      description
        "Local interface";
    }
    leaf neighbor-state {
      type Isis-adj-state;
      description
        "Neighbor (adjacency) state";
    }
    leaf neighbor-circuit-type {
      type Isis-levels;
      description
        "Circuit type";
    }
    leaf neighbor-ietf-nsf-capable-flag {
      type uint32;
      description
        "TRUE if neighbor is IETF-NSF capable";
    }
    leaf neighbor-media-type {
      type Isis-media-class;
      description
        "Link media type";
    }
    leaf neighbor-holdtime {
      type uint32;
      description
        "Time (s) until neighbor declared down if no IIH
         received";
    }
    leaf neighbor-uptime-valid-flag {
      type boolean;
      description
        "TRUE if NeighborUptime is set";
    }
    leaf neighbor-uptime {
      type uint32;
      description
        "How long the neighbor has been up (s)";
    }
    leaf nsr-standby {
      type boolean;
      description
        "ISIS NSR STANDBY";
    }
    list neighbor-active-area-address {
      description
        "Active area addresses";
      leaf entry {
        type xr:Osi-area-address;
        description
          "Active area addresses";
      }
    }
    list topologies-supported {
      description
        "Topologies supported by both neighbor and local
         system";
      uses ISIS-TOPO-ID-TYPE;
    }
    list neighbor-per-address-family-data {
      description
        "Per address-family data";
      uses ISIS-SH-ADJ-AF;
    }
  }
}
