module Cisco-IOS-XR-aaa-ldapd-oper {
  namespace "http://cisco.com/ns/yang/Cisco-IOS-XR-aaa-ldapd-oper";
  prefix aaa-ldapd-oper;

  import cisco-semver {
    prefix semver;
  }
  include Cisco-IOS-XR-aaa-ldapd-oper-sub1 {
    revision-date 2022-05-20;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR aaa-ldapd package operational data.
     
     Copyright (c) 2013-2022 by Cisco Systems, Inc.
     All rights reserved.";

  revision 2022-05-20 {
    description
      "Dynamic NACM feature commit.";
    semver:module-version "1.0.0";
  }
  revision 2019-04-05 {
    description
      "Establish semantic version baseline.";
  }
  revision 2015-11-09 {
    description
      "IOS XR 6.0 revision.";
  }
}
