module Cisco-IOS-XR-lpts-pre-ifib-act {
  namespace "http://cisco.com/ns/yang/Cisco-IOS-XR-lpts-pre-ifib-act";
  prefix lpts-pre-ifib-act;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR action package configuration.
     
     Copyright (c) 2016-2025 by Cisco Systems, Inc., and/or its affiliates.
     All rights reserved.";

  revision 2025-07-23 {
    description
      "Fixed canonical order.";
    semver:module-version "1.0.0";
  }
  revision 2020-09-20 {
    description
      "Initial revision.";
    semver:module-version "1.0.0";
  }

  rpc clear-lpts-pifib-statistics-location {
    description
      "Clear lpts pre-ifib stats location";
    input {
      leaf node-location {
        type string;
        description
          "Node location";
      }
    }
  }
  rpc clear-lpts-punt-statistics-interface {
    description
      "Clear LPTS punt stats interface";
    input {
      leaf interface {
        type string;
        mandatory true;
        description
          "Interface name";
      }
      leaf node-location {
        type string;
        mandatory true;
        description
          "Location name";
      }
    }
  }
  rpc clear-lpts-punt-statistics-location {
    description
      "Clear lpts punt stats location";
    input {
      leaf node-location {
        type string;
        mandatory true;
        description
          "Node location";
      }
    }
  }
}
