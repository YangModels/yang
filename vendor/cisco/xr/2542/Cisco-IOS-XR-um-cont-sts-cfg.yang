module Cisco-IOS-XR-um-cont-sts-cfg {
  namespace "http://cisco.com/ns/yang/Cisco-IOS-XR-um-cont-sts-cfg";
  prefix um-cont-sts-cfg;

  import Cisco-IOS-XR-um-interface-cfg {
    prefix a1;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR cont-sts package configuration.
     
     This YANG module augments the
     modules with configuration data.
     
     Copyright (c) 2021-2025 by Cisco Systems, Inc., and/or its affiliates.
     All rights reserved.";

  revision 2022-07-11 {
    description
      "Added missing description statement to nodes
       2022-06-01
         Adjusted controller augmentation hierarchy";
    semver:module-version "1.1.0";
  }
  revision 2021-05-07 {
    description
      "Initial release";
    semver:module-version "1.0.0";
  }

  grouping CONT-BODY {
    description
      "Grouping for controller";
    container overhead {
      description
        "Configure SONET/SDH POH byte/bit values";
      container j1 {
        description
          "Configure SONET/SDH path trace (J1) buffer";
        container send {
          description
            "Set transmit trace Identifier";
          leaf sixteen-bytes {
            type string {
              length "1..15" {
                description
                  "ASCII text ";
              }
            }
            must "not(../sixtyfour-bytes)";
            description
              "Configure a 16 bytes path trace";
          }
          leaf sixtyfour-bytes {
            type string {
              length "1..62" {
                description
                  "ASCII text ";
              }
            }
            must "not(../sixteen-bytes)";
            description
              "Configure a 64 byte path trace";
          }
        }
        container expected {
          description
            "Set expected trace Identifier";
          leaf sixteen-bytes {
            type string {
              length "1..15" {
                description
                  "ASCII text ";
              }
            }
            must "not(../sixtyfour-bytes)";
            description
              "Configure a 16 bytes path trace";
          }
          leaf sixtyfour-bytes {
            type string {
              length "1..62" {
                description
                  "ASCII text ";
              }
            }
            must "not(../sixteen-bytes)";
            description
              "Configure a 64 byte path trace";
          }
        }
      }
    }
    container threshold {
      description
        "Configure SONET/SDH path BER threshold values";
      leaf b3-tca {
        type uint32 {
          range "3..9" {
            description
              "Bit error rate (10 to the minus n) (default 6)";
          }
        }
        description
          "Set B3 BER Threshold Crossing Alert (TCA) threshold";
      }
    }
    container perf-mon {
      description
        "Enable/Disable Performance Monitoring";
      container disable {
        must "not(../enable)";
        presence "Indicates a disable node is configured.";
        description
          "Disable performance monitoring";
      }
      container enable {
        must "not(../disable)";
        presence "Indicates a enable node is configured.";
        description
          "Enable performance monitoring";
      }
    }
  }

  augment "/a1:controllers/a1:controller" {
    description
      "This augment extends active nodes configuration";
    uses CONT-BODY;
  }
  augment "/a1:controllers/a1:controller-preconfigure" {
    description
      "This augment extends preconfigured nodes
       configuration";
    uses CONT-BODY;
  }
}
