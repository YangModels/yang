module Cisco-IOS-XR-sysadmin-fpd-infra-cli-shhwfpd-iosxrwbd {
  namespace "http://www.cisco.com/ns/yang/Cisco-IOS-XR-sysadmin-fpd-infra-cli-shhwfpd-iosxrwbd";
  prefix shhwfpd;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains definitions
     for the Calvados model objects.
     
     Copyright (c) 2012-2020 by Cisco Systems, Inc.
     All rights reserved.";

  revision 2023-05-09 {
    description
      "Namespace and module change to fix platform inconsistencies";
    semver:module-version "1.0.0";
  }
  revision 2019-04-15 {
    description
      "Establish semantic version baseline.";
  }
  revision 2017-05-01 {
    description
      "Namespace change to comply with Cisco guidelines on namespace";
  }

  grouping hw-module-oper-group {
    container shhwfpd {
      config false;
      list alocation {
        key "locs";
        leaf locs {
          type string;
        }
        list fpd {
          key "fpdname";
          leaf fpdname {
            type string;
          }
          leaf state {
            type string;
            description
              "Status";
          }
          leaf hwver {
            type string;
            description
              "HWver";
          }
          leaf fpdver {
            type string;
            description
              "FPD ver";
          }
          leaf cardname {
            type string;
            description
              "Card type";
          }
          leaf attr {
            type string;
            description
              "Attribute";
          }
          leaf fpddnld {
            type string;
            description
              "FPD Programed";
          }
        }
      }
      list fpd {
        key "fpdname";
        leaf fpdname {
          type string;
        }
      }
    }
  }
}
