module Cisco-IOS-XR-sysadmin-obfl {
  namespace "http://www.cisco.com/ns/yang/Cisco-IOS-XR-sysadmin-obfl";
  prefix obfl;

  import Cisco-IOS-XR-sysadmin-show-trace {
    prefix show_trace;
  }
  import cisco-semver {
    prefix semver;
  }

  organization
    "Cisco Systems Inc.";
  contact
    "Cisco Systems, Inc.
     Customer Service
     
     Postal: 170 West Tasman Drive
     San Jose, CA 95134
     
     Tel: +1 800 553-NETS
     
     E-mail: cs-yang@cisco.com";
  description
    "This module holds OBFL data.
     
     Copyright (c) 2012-2020 by Cisco Systems, Inc.
     All rights reserved.";

  revision 2019-04-15 {
    description
      "Establish semantic version baseline.";
    semver:module-version "1.0.0";
  }
  revision 2017-07-31 {
    description
      "Changed namespace to follow Cisco guidelines on naming convention";
  }
  revision 2012-10-10 {
    description
      "Initial revision of show obfl related commands";
  }

  grouping obfl_trace {
    container obfl_mgr {
      uses show_trace:traceable;
    }
    container obfl_show {
      uses show_trace:traceable;
    }
  }

  container obfl {
    config false;
    uses obfl_trace;
  }
}
