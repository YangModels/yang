submodule Cisco-IOS-XR-health-oper-sub1 {
  belongs-to Cisco-IOS-XR-health-oper {
    prefix Cisco-IOS-XR-health-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR health package operational data.
     
     Copyright (c) 2013-2025 by Cisco Systems, Inc.
     All rights reserved.";

  revision 2025-03-12 {
    description
      "Updated data type to enum for health status to make it descriptive";
    semver:module-version "1.0.0";
  }
  revision 2024-05-29 {
    description
      "Initial native yang support for operational data related to Health functionality";
  }
  revision 2019-04-05 {
    description
      "Establish semantic version baseline.";
  }
  revision 2015-11-09 {
    description
      "IOS XR 6.0 revision.";
  }

  typedef Health-status {
    type enumeration {
      enum "healthy" {
        value 0;
        description
          "HEALTHY";
      }
      enum "unhealthy" {
        value 1;
        description
          "UNHEALTHY";
      }
    }
    description
      "Health status";
  }

  grouping XRHEALTH-OC-INTERFACE {
    description
      "xrhealth stats";
    leaf status {
      type Health-status;
      description
        "Health status of the component";
    }
  }
}
