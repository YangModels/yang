module Cisco-IOS-XR-sysadmin-wd-memmon {
  namespace "http://www.cisco.com/ns/yang/Cisco-IOS-XR-sysadmin-wd-memmon";
  prefix wd-memmon;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains definitions
     for the Calvados model objects.
     
     Copyright (c) 2012-2020 by Cisco Systems, Inc.
     All rights reserved.";

  revision 2021-12-16 {
    description
      "Adopt Cisco YANG model namespace naming standard";
    semver:module-version "1.0.0";
  }
  revision 2019-04-15 {
    description
      "Establish semantic version baseline.";
  }
  revision 2018-04-09 {
    description
      "Required changes for ConfD 6.4.5";
  }

  typedef percent {
    type int32 {
      range "0 .. 100";
    }
    description
      "Percentage";
  }

  container memory_status_config {
    must " (critical > severe and severe > minor)" {
      error-message " ERROR: Threshold values are not matching condition: minor < severe < critical";
    }
    leaf minor {
      type percent;
      default "80";
      description
        "Memory  Monitoring Minor Threshold";
    }
    leaf severe {
      type percent;
      default "90";
      description
        "Memory Monitoring Severe Threshold";
    }
    leaf critical {
      type percent;
      default "95";
      description
        "Memory Monitoring Critial Threshold";
    }
    leaf recovery_enabled {
      type boolean;
      default "false";
      description
        "In case of Critical Memory Usage, Recovery Action Enabled/Disabled";
    }
  }
  container memory_status {
    config false;
    description
      "Memory Info";
    list all-locations {
      key "location";
      leaf location {
        type string;
      }
      list all-device {
        key "device";
        leaf device {
          type string;
        }
        leaf minor {
          type string;
          description
            "Mem  Monitoring Minor Threshold";
        }
        leaf severe {
          type string;
          description
            "Mem  Monitoring severe Threshold";
        }
        leaf critical {
          type string;
          description
            "Mem  Monitoring Critical Threshold";
        }
        leaf current_state {
          type string;
          description
            " Current state of Physical Memory ";
        }
        leaf total_used {
          type string;
          description
            " Total Used Memory ";
        }
        leaf available {
          type string;
          description
            " Total Available Physical Memory ";
        }
      }
    }
  }
}
