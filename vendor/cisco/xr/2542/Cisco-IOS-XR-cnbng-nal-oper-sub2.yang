submodule Cisco-IOS-XR-cnbng-nal-oper-sub2 {
  belongs-to Cisco-IOS-XR-cnbng-nal-oper {
    prefix Cisco-IOS-XR-cnbng-nal-oper;
  }

  import ietf-inet-types {
    prefix inet;
  }
  import ietf-yang-types {
    prefix yang;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR cnbng-nal package operational data.
     
     Copyright (c) 2013-2025 by Cisco Systems, Inc.
     All rights reserved.";

  revision 2025-07-15 {
    description
      "Added new bag to display warm standby subscriber brief and detail
       2025-07-03
         Added support to get L2TP tunnel context
       2025-07-01
         Added distance leaf in dynamic framed route
       2025-06-30
         Added warm create inprogress and pending information
       2025-04-14
         Added oper support for warm standby feature
       2025-04-03
         Updated timestamp data type from unit32 to unit64
       2025-03-28
         Control-plane subscriber ID datatype updated to uint64
       2025-01-07
         Updated counter name string length in counters and recon history statistics
       2024-12-05
         Added Service params in NAL subscriber detail
       2024-11-15
         Added ipoe-l2-connected option in subscriber and parent interface CLIs
       2024-10-14
         Updated dynamic route summary to include v6 owner channel statistics
       2024-09-18
         Updated subscriber detail and dynamic route data to include next-hop IP information for routed subscribers
       2024-09-05
         Added SRG group subscriber count for keep alive start
       2024-08-28
         Added support to publish subscriber User-Plane, Control-Plane ,transaction id mapping
       2024-08-04
         Updated SLAAC prefix and prefix length fields in NAL subscriber brief and detail
       2024-06-18
         Added Rib statistics under srg group detail
       2024-06-10
         Added slaac counters support.
       2024-05-03
         Included SRG role change counters part of SRG group detail
       2024-02-10
         Updated subscriber detail and subscriber internal detail filtered based on UPID information
       2023-12-10
         Added support to publish CPS(Calls per second) stats
       2023-10-24
         Removed SRG role change counters.
       2023-10-12
         Updated CP-UP connection information to include PFCP and GTPu socket bind result.
       2023-10-03
         Interface name length size is updated.
       2023-07-24
         Annotated process readiness and control-plane/user-plane connection data for EDT support.
       2023-04-07
         Added field to display api-stats viz err status, last fail time, upid for all API used by cnbng nal.
       2023-03-30
         Changed String in dynamic route bag
       2023-03-28
         Reduced failed entry bag description length from 256 to 65 bytes.
       2023-01-11
         Added counters for cp-up spa recon stats.
       2022-12-14
         Added the new field desciption in auto-loopback vrf and srg group configuration.
       2022-12-02
         Updated the data type of node feature-id to String.
       2022-11-21
         Added block size in chunk statistics and session replay response as dynamic data in bag.
       2022-11-03
         Updated binary data associated with each event in event history entry as private.
       2022-10-20
         Changed readable strings like interface/vrf names from type char to string.
       2022-09-06
         Renamed structure in bag file.
       2022-08-31
         Migrated XR library event history to internal history library.
       2022-08-30
         Added key meta-data into oper yang lists.
       2022-08-08
         Added new element outstanding_ka_expiry_cnt in bag file.
       2022-08-04
         Removed dynamic route history query from schema.
       2022-07-27
         Updated SRG group admin state datatype
       2022-07-21
         Updated nal_subscriber_session_info gateway IP format from uint32_t to in_addr_t
       2022-05-16
         added new elements in bag
       2022-03-16
         Added SRG group summary support
       2022-03-15
         Counters arrays made dynamic.
       2022-03-15
         Added counter for fast switchover timer expiry.
       2022-03-10
         Added counters for SRG group recon start and end.
       2022-03-07
         Added additional NAL disconnect types
       2022-03-04
         Added counter for zero subscribers in recon replay request.
       2022-03-02
         Added new counters for SRG stats retry enqueue.
       2022-03-02
         Added new counter for SRG group state is not ready.
       2022-02-23
         Updated SRG show command bag with reconciliation information.
       2022-02-10
         Added SRG show commands.
       2022-01-27
         Updated length of interface name string length from 64 to 72
       2022-01-20
         Updated process info bag with in-flight configuration values
       2021-12-21
         Added access interface event history
       2021-12-01
         Updated xml tree definitions
       2021-11-11
         Dynamic Route info addition in route provision flow.
       2021-10-20
         AIPC server stats display command updated.
       2021-10-10
         Added schema support for multiple show CLIs
       2021-09-30
         Added new counter for tracking empty pulses in nal_main_edm_nal_counters lac_stats.
       2021-09-29
         Added batch counter for spio resync";
    semver:module-version "3.0.0";
  }
  revision 2021-09-27 {
    description
      "Updated transport and association status enum in yang model.
       2021-07-22
          Updated nal_main_edm_process_info to include SPIO connection information.
       2021-07-06
          Added schema support for all address family in show dynamic route command.
       2021-07-02
          Added connection status information and interface counters.
       2021-06-30
          Added process readiness and transaction pending flags in nal_main_edm_process_readiness.
       2021-06-26
          Updated nal_main_edm_process_info bag to include features supported from platform.
       2021-06-20
          Added new path for getting subscriber summary based on VRF name.
       2021-06-14
          Added tunnel vrf for LAC/LNS subscriber bag
       2021-06-11
          Updated subscriber brief bag with subscriber interface handle.
       2021-05-31
          Added new NAL counter type client api
       2021-05-29
          Added new bag for getting subscriber count and global routes installed.
       2021-05-05
          Added tr459 mode enable flag in bag structure.
       2021-04-01
          added LNS subcriber info in bag
       2021-03-15
          added details for LAC subcriber in bag";
    semver:module-version "2.0.0";
  }
  revision 2021-02-17 {
    description
      "Added AFI only filters";
    semver:module-version "1.0.0";
  }
  revision 2021-02-10 {
    description
      "Removed redundant fail route index";
  }
  revision 2021-02-04 {
    description
      "Added multi framed route support, metric and tag";
  }
  revision 2021-01-23 {
    description
      "Added new NAL counter type thread_stats";
  }
  revision 2020-12-13 {
    description
      "NAL SVM service final timestamp.";
  }
  revision 2020-12-08 {
    description
      "modify Disconnect History Filter keys.";
  }
  revision 2020-11-27 {
    description
      "NAL counters.";
  }
  revision 2020-11-10 {
    description
      "Update bgen path for dynamic routes and removed schema for dynamic routes history.";
  }
  revision 2020-10-26 {
    description
      "Update bag type for AIPC server stats.";
  }
  revision 2020-10-15 {
    description
      "Added schema support for cnbng-nal filter oper commands.";
  }
  revision 2020-10-08 {
    description
      "Moved counter and AIPC stats to new bag files.";
  }
  revision 2020-10-02 {
    description
      "Modified alter gen script to modify leaf list to list.";
  }
  revision 2020-09-18 {
    description
      "Added schema support for cnbng-nal access-interface oper commands.";
  }
  revision 2020-09-15 {
    description
      "adding schema support for NAL chunk statistics oper bag.";
  }
  revision 2020-09-10 {
    description
      "Updated schema for filtering subscriber summary.";
  }
  revision 2020-09-03 {
    description
      "adding schema support for NAL Counters, Dynamic routes, summary and history bag.";
  }
  revision 2020-07-24 {
    description
      "adding schema support for disconect uniuqe and modifying unique summary.";
  }
  revision 2020-06-06 {
    description
      "adding schema support for NAL Process-Info Bag";
  }
  revision 2020-05-29 {
    description
      "adding schema support for Disconnect History Filter.";
  }
  revision 2020-05-15 {
    description
      "adding schema support for NAL CP Transport Connection Status Bag";
  }
  revision 2020-04-30 {
    description
      "adding schema support for NAL VRF Table records";
  }
  revision 2020-04-23 {
    description
      "added new elements in bag";
  }
  revision 2020-04-09 {
    description
      "modified class name for FADB records";
  }
  revision 2020-04-03 {
    description
      "adding schema support for subsriber summary and FADB records";
  }
  revision 2020-04-02 {
    description
      "adding schema support for service profiles and process readiness";
  }
  revision 2020-03-30 {
    description
      "adding schema support for v4 and v6 framed route";
  }
  revision 2019-04-05 {
    description
      "Establish semantic version baseline.";
  }
  revision 2015-11-09 {
    description
      "IOS XR 6.0 revision.";
  }

  typedef Spa-edm-session {
    type enumeration {
      enum "spa-edm-session-type-ipoe" {
        description
          "spa edm session type ipoe";
      }
      enum "spa-edm-session-type-pppoe" {
        description
          "spa edm session type pppoe";
      }
      enum "spa-edm-session-type-lac" {
        description
          "spa edm session type lac";
      }
      enum "spa-edm-session-type-lns" {
        description
          "spa edm session type lns";
      }
      enum "spa-edm-session-type-routed" {
        description
          "spa edm session type routed";
      }
      enum "spa-edm-session-type-max" {
        description
          "spa edm session type max";
      }
    }
    description
      "SPA Session Type";
  }

  typedef Spa-edm-sub-afi-cap {
    type enumeration {
      enum "spa-edm-sub-afi-invalid" {
        description
          "spa edm sub afi invalid";
      }
      enum "spa-edm-sub-afi-ipv4" {
        description
          "spa edm sub afi ipv4";
      }
      enum "spa-edm-sub-afi-ipv6" {
        description
          "spa edm sub afi ipv6";
      }
      enum "spa-edm-sub-afi-ipv4-ipv6" {
        description
          "spa edm sub afi ipv4 ipv6";
      }
      enum "spa-edm-sub-afi-max" {
        description
          "spa edm sub afi max";
      }
    }
    description
      "SPA sub afi cap";
  }

  typedef Spa-edm-oper {
    type enumeration {
      enum "spa-edm-oper-type-create" {
        description
          "spa edm oper type create";
      }
      enum "spa-edm-oper-type-modify" {
        description
          "spa edm oper type modify";
      }
      enum "spa-edm-oper-type-delete" {
        description
          "spa edm oper type delete";
      }
      enum "spa-edm-oper-type-replay" {
        description
          "spa edm oper type replay";
      }
      enum "spa-edm-oper-type-max" {
        description
          "spa edm oper type max";
      }
    }
    description
      "SPA oper type";
  }

  grouping SPA-EDM-SUBSCRIBER-ROUTE-IPV6 {
    description
      "SPA EDM SUBSCRIBER ROUTE IPV6";
    leaf oper {
      type Spa-edm-oper;
      description
        "oper";
    }
    leaf vrf {
      type string {
        length "0..33";
      }
      description
        "vrf";
    }
    leaf ipv6-addr {
      type inet:ipv6-address;
      description
        "ipv6 addr";
    }
    leaf ipv6-prefix-len {
      type uint8;
      description
        "ipv6 prefix len";
    }
    leaf next-hop {
      type inet:ipv6-address;
      description
        "next hop";
    }
    leaf next-hop-vrf {
      type string {
        length "0..33";
      }
      description
        "next hop vrf";
    }
    leaf metric {
      type uint32;
      description
        "metric";
    }
    leaf tag {
      type uint32;
      description
        "tag";
    }
    leaf srg-group-name {
      type string {
        length "0..65";
      }
      description
        "srg group name";
    }
    leaf distance {
      type uint32;
      description
        "distance";
    }
  }

  grouping SPA-EDM-SUBSCRIBER-ROUTE-IPV4 {
    description
      "SPA EDM SUBSCRIBER ROUTE IPV4";
    leaf oper {
      type Spa-edm-oper;
      description
        "oper";
    }
    leaf vrf {
      type string {
        length "0..33";
      }
      description
        "vrf";
    }
    leaf ipv4-addr {
      type inet:ipv4-address;
      description
        "ipv4 addr";
    }
    leaf ipv4-prefix-len {
      type uint8;
      description
        "ipv4 prefix len";
    }
    leaf next-hop {
      type inet:ipv4-address;
      description
        "next hop";
    }
    leaf next-hop-vrf {
      type string {
        length "0..33";
      }
      description
        "next hop vrf";
    }
    leaf metric {
      type uint32;
      description
        "metric";
    }
    leaf tag {
      type uint32;
      description
        "tag";
    }
    leaf srg-group-name {
      type string {
        length "0..65";
      }
      description
        "srg group name";
    }
    leaf distance {
      type uint32;
      description
        "distance";
    }
  }

  grouping SPA-EDM-SUBSCRIBER-ACCT {
    description
      "SPA Subscriber Accounting";
    leaf feat-flag {
      type uint8;
      description
        "Feature Flag";
    }
    leaf periodic-interval {
      type uint32;
      description
        "Periodic Interval";
    }
    leaf session-stats-enabled {
      type boolean;
      description
        "Session Stats Enabled";
    }
  }

  grouping NAL-SPA-BAG-SUBSCRIBER-MTU {
    description
      "NAL SPA BAG SUBSCRIBER MTU";
    leaf mtu {
      type uint32;
      description
        "MTU Value";
    }
  }

  grouping NAL-SPA-BAG-SUBSCRIBER-ICMP {
    description
      "NAL SPA BAG SUBSCRIBER ICMP";
    leaf enabled {
      type boolean;
      description
        "ICMP Enabled";
    }
  }

  grouping SPA-EDM-SUBSCRIBER-URPF {
    description
      "SPA Subscriber URPF";
    leaf oper {
      type Spa-edm-oper;
      description
        "Oper Type";
    }
    leaf mode {
      type uint8;
      description
        "Mode";
    }
  }

  grouping SPA-EDM-SUBSCRIBER-LI {
    description
      "SPA Subscriber LI";
    leaf oper {
      type Spa-edm-oper;
      description
        "Oper Type";
    }
    leaf dscp {
      type uint32;
      description
        "DSCP";
    }
    leaf port {
      type uint16;
      description
        "Port";
    }
    leaf intercept-id {
      type yang:mac-address;
      description
        "Intercept ID";
    }
    leaf protocol {
      type int32;
      description
        "Protocol";
    }
    leaf af-type {
      type uint8;
      description
        "Af Type";
    }
    leaf ipv4-address {
      type inet:ipv4-address;
      description
        "IPv4 Address";
    }
    leaf ipv6-address {
      type inet:ipv6-address;
      description
        "IPv6 Address";
    }
  }

  grouping SPA-EDM-SUBSCRIBER-HTTPR {
    description
      "SPA Subscriber HTTPR";
    leaf oper {
      type Spa-edm-oper;
      description
        "Oper Type";
    }
    leaf pbr-ingress-policy {
      type string {
        length "0..256";
      }
      description
        "PBR Ingress Policy";
    }
  }

  grouping SPA-EDM-SUBSCRIBER-ACL {
    description
      "SPA Subscriber ACL";
    leaf oper {
      type Spa-edm-oper;
      description
        "Oper Type";
    }
    leaf ipv4-ingress {
      type string {
        length "0..65";
      }
      description
        "IPv4 Ingress";
    }
    leaf ipv4-egress {
      type string {
        length "0..65";
      }
      description
        "IPv4 Egress";
    }
    leaf ipv6-ingress {
      type string {
        length "0..65";
      }
      description
        "IPv6 Ingress";
    }
    leaf ipv6-egress {
      type string {
        length "0..65";
      }
      description
        "IPv6 Egress";
    }
  }

  grouping SPA-EDM-SUBSCRIBER-QOS {
    description
      "SPA Subscriber QOS";
    leaf oper {
      type Spa-edm-oper;
      description
        "Oper Type";
    }
    leaf plain-qos {
      type boolean;
      description
        "plain qos";
    }
    leaf service-id {
      type string {
        length "0..65";
      }
      description
        "Service ID";
    }
    leaf qos-policy-ingress {
      type string {
        length "0..256";
      }
      description
        "QOS Policy Ingress";
    }
    leaf qos-policy-egress {
      type string {
        length "0..256";
      }
      description
        "QOS Policy Egress";
    }
    leaf merge-priority-in {
      type uint16;
      description
        "Merge Priority In";
    }
    leaf merge-priority-out {
      type uint16;
      description
        "Merge Priority Out";
    }
    leaf service-stats-enable {
      type boolean;
      description
        "Service Stats Enable";
    }
    leaf svc-params {
      type string {
        length "0..65";
      }
      description
        "Service Parameters";
    }
    leaf spi-ingress {
      type string {
        length "0..65";
      }
      description
        "SPI Ingress";
    }
    leaf spi-egress {
      type string {
        length "0..65";
      }
      description
        "SPI Egress";
    }
  }

  grouping SPA-EDM-VLAN-INFO {
    description
      "SPA EDM VLAN INFO";
    leaf outer-vlan {
      type uint16;
      description
        "outer vlan";
    }
    leaf inner-vlan {
      type uint16;
      description
        "inner vlan";
    }
  }

  grouping SPA-EDM-L2TP-DATA {
    description
      "SPA EDM L2TP DATA";
    leaf af-type {
      type uint8;
      description
        "af type";
    }
    leaf local-tun-ipv4 {
      type inet:ipv4-address;
      description
        "local tun ipv4";
    }
    leaf remote-tun-ipv4 {
      type inet:ipv4-address;
      description
        "remote tun ipv4";
    }
    leaf local-tun-ipv6 {
      type inet:ipv6-address;
      description
        "local tun ipv6";
    }
    leaf remote-tun-ipv6 {
      type inet:ipv6-address;
      description
        "remote tun ipv6";
    }
    leaf local-tunnel-id {
      type uint16;
      description
        "local tunnel id";
    }
    leaf remote-tunnel-id {
      type uint16;
      description
        "remote tunnel id";
    }
    leaf local-session-id {
      type uint16;
      description
        "local session id";
    }
    leaf remote-session-id {
      type uint16;
      description
        "remote session id";
    }
    leaf set-tos {
      type uint8;
      description
        "set tos";
    }
    leaf reflect-tos {
      type boolean;
      description
        "reflect tos";
    }
    leaf set-df {
      type boolean;
      description
        "set df";
    }
    leaf reflect-df {
      type boolean;
      description
        "reflect df";
    }
    leaf tcp-mss-adjust {
      type uint32;
      description
        "tcp mss adjust";
    }
    leaf tunnel-stats {
      type boolean;
      description
        "tunnel stats";
    }
    leaf tunnel-stats-interval {
      type uint32;
      description
        "tunnel stats interval";
    }
    leaf session-stats {
      type boolean;
      description
        "session stats";
    }
    leaf session-stats-interval {
      type uint32;
      description
        "session stats interval";
    }
    leaf tunnel-vrf {
      type string {
        length "0..33";
      }
      description
        "tunnel vrf";
    }
  }

  grouping SPA-EDM-PPP-DATA {
    description
      "SPA EDM PPP DATA";
    leaf retry-count {
      type uint32;
      description
        "retry count";
    }
    leaf local-magic-number {
      type uint32;
      description
        "local magic number";
    }
    leaf peer-magic-number {
      type uint32;
      description
        "peer magic number";
    }
    leaf keep-alive-interval {
      type uint32;
      description
        "keep alive interval";
    }
    leaf ipv6-intf-id {
      type string {
        length "0..9";
      }
      description
        "ipv6 intf id";
    }
    leaf pppoe-session-id {
      type uint16;
      description
        "pppoe session id";
    }
  }

  grouping SPA-EDM-SESSION-DATA {
    description
      "SPA Session Data";
    container ppp-info {
      description
        "PPP Info";
      uses SPA-EDM-PPP-DATA;
    }
    container l2tp-info {
      description
        "L2TP Info";
      uses SPA-EDM-L2TP-DATA;
    }
    container subscriber-vlan-info {
      description
        "Subscriber VLAN Info";
      uses SPA-EDM-VLAN-INFO;
    }
    leaf session-type {
      type Spa-edm-session;
      description
        "Session Type";
    }
    leaf cp-subscriber-id {
      type uint64;
      description
        "CP Subscriber ID";
    }
    leaf access-interface {
      type string {
        length "0..65";
      }
      description
        "Access Interface";
    }
    leaf subscriber-mac {
      type yang:mac-address;
      description
        "Subscriber MAC";
    }
    leaf subscriber-vrf {
      type string {
        length "0..33";
      }
      description
        "Subscriber VRF";
    }
    leaf srg-group-name {
      type string {
        length "0..65";
      }
      description
        "SRG Group Name";
    }
    leaf srg-report-id {
      type uint16;
      description
        "SRG Report ID";
    }
    leaf up-subscriber-id {
      type uint32;
      description
        "UP Subscriber ID";
    }
  }

  grouping SPA-EDM-SUBSCRIBER-V6 {
    description
      "SPA Subscriber ipv6";
    leaf oper {
      type Spa-edm-oper;
      description
        "Oper Type";
    }
    leaf ipv6-iana-address {
      type inet:ipv6-address;
      description
        "IPv6 Iana Address";
    }
    leaf ipv6-iapd-address {
      type inet:ipv6-address;
      description
        "IPv6 Iapd Address";
    }
    leaf cpe-link-local-address {
      type inet:ipv6-address;
      description
        "CPE Link Local Address";
    }
    leaf ipv6-slaac-address {
      type inet:ipv6-address;
      description
        "IPv6 Slaac Address";
    }
    leaf prefix-length {
      type uint8;
      description
        "Prefix Length";
    }
    leaf ipv6-slaac-prefix-len {
      type uint8;
      description
        "IPv6 Slaac Prefix Length";
    }
    leaf slaac-flags {
      type uint8;
      description
        "Slaac Flags";
    }
  }

  grouping SPA-EDM-SUBSCRIBER-V4 {
    description
      "SPA Subscriber ipv4";
    leaf oper {
      type Spa-edm-oper;
      description
        "Oper Type";
    }
    leaf ipv4-address {
      type inet:ipv4-address;
      description
        "IPv4 Address";
    }
  }

  grouping SPA-EDM-SESSION-CONTEXT {
    description
      "SPA session context data";
    container ipv4 {
      description
        "Subscriber Ipv4";
      uses SPA-EDM-SUBSCRIBER-V4;
    }
    container ipv6 {
      description
        "Subscriber Ipv6";
      uses SPA-EDM-SUBSCRIBER-V6;
    }
    container session-entry {
      description
        "Session Entry";
      uses SPA-EDM-SESSION-DATA;
    }
    container subscriber-acl-entry {
      description
        "Subscriber Acl Entry";
      uses SPA-EDM-SUBSCRIBER-ACL;
    }
    container subscriber-httpr-entry {
      description
        "Subscriber Httpr Entry";
      uses SPA-EDM-SUBSCRIBER-HTTPR;
    }
    container subscriber-li-entry {
      description
        "Subscriber Li Entry";
      uses SPA-EDM-SUBSCRIBER-LI;
    }
    container urpf-v4 {
      description
        "Urpf V4";
      uses SPA-EDM-SUBSCRIBER-URPF;
    }
    container urpf-v6 {
      description
        "Urpf V6";
      uses SPA-EDM-SUBSCRIBER-URPF;
    }
    container icmp-v4 {
      description
        "Icmp V4";
      uses NAL-SPA-BAG-SUBSCRIBER-ICMP;
    }
    container icmp-v6 {
      description
        "Icmp V6";
      uses NAL-SPA-BAG-SUBSCRIBER-ICMP;
    }
    container mtu-v4 {
      description
        "Mtu V4";
      uses NAL-SPA-BAG-SUBSCRIBER-MTU;
    }
    container mtu-v6 {
      description
        "Mtu V6";
      uses NAL-SPA-BAG-SUBSCRIBER-MTU;
    }
    container ppp-mtu {
      description
        "PPP Mtu";
      uses NAL-SPA-BAG-SUBSCRIBER-MTU;
    }
    container subscriber-acct-entry {
      description
        "Subscriber Acct Entry";
      uses SPA-EDM-SUBSCRIBER-ACCT;
    }
    leaf oper {
      type Spa-edm-oper;
      description
        "Oper Type";
    }
    leaf message-txn-id {
      type uint32;
      description
        "Message Transaction ID";
    }
    leaf src-port {
      type uint16;
      description
        "Source Port";
    }
    leaf sess-txn-id {
      type uint32;
      description
        "Session Transaction ID";
    }
    leaf feature-mask {
      type uint32;
      description
        "Feature mask";
    }
    leaf ipoe-afi-cap {
      type Spa-edm-sub-afi-cap;
      description
        "IPOE afi cap";
    }
    leaf num-subscriber-qos {
      type uint8;
      description
        "Number of Subscriber Qos";
    }
    leaf ipv4-route-count {
      type uint8;
      description
        "Number of ipv4 routes";
    }
    leaf ipv6-route-count {
      type uint8;
      description
        "Number of ipv6 routes";
    }
    list subscriber-qos-entry {
      description
        "Subscriber Qos Entry";
      uses SPA-EDM-SUBSCRIBER-QOS;
    }
    list subscriber-route-entry-ipv4 {
      description
        "Subscriber Route Entry ipv4";
      uses SPA-EDM-SUBSCRIBER-ROUTE-IPV4;
    }
    list subscriber-route-entry-ipv6 {
      description
        "Subscriber Route Entry ipv6";
      uses SPA-EDM-SUBSCRIBER-ROUTE-IPV6;
    }
  }

  grouping NAL-MAIN-EDM-WARM-SUB-DETAIL-DATA {
    description
      "NAL MAIN EDM WARM SUB DETAIL DATA";
    container spa-session-context {
      description
        "SPA session context";
      uses SPA-EDM-SESSION-CONTEXT;
    }
    leaf user-plane-id {
      type uint32;
      description
        "User-plane ID";
    }
    leaf control-plane-id {
      type uint64;
      description
        "Control-plane ID";
    }
    leaf state {
      type uint32;
      description
        "Warm subscriber state";
    }
  }

  grouping NAL-SUBS-WARM-AFI-SUMMARY {
    description
      "Subscriber afi summary data";
    leaf none {
      type uint32;
      description
        "No afi";
    }
    leaf ipv4 {
      type uint32;
      description
        "IPv4 count";
    }
    leaf ipv6 {
      type uint32;
      description
        "IPv6 count";
    }
    leaf dual {
      type uint32;
      description
        "Dual count";
    }
    leaf lac {
      type uint32;
      description
        "LAC count";
    }
    leaf total {
      type uint32;
      description
        "Total";
    }
  }

  grouping NAL-WARM-SUBSCRIBER-STATE-SUMMARY {
    description
      "Subscriber state summary data";
    leaf active {
      type uint32;
      description
        "Active";
    }
    leaf inactive {
      type uint32;
      description
        "InActive";
    }
    leaf activating {
      type uint32;
      description
        "Activating";
    }
    leaf total {
      type uint32;
      description
        "Total";
    }
  }

  grouping NAL-WARM-SUBSCRIBER-SUMMARY {
    description
      "Warm Subscriber summary data";
    container ipoe-state-summary {
      description
        "IPoE State Summary";
      uses NAL-WARM-SUBSCRIBER-STATE-SUMMARY;
    }
    container pppoe-state-summary {
      description
        "PPPoE State Summary";
      uses NAL-WARM-SUBSCRIBER-STATE-SUMMARY;
    }
    container lac-state-summary {
      description
        "LAC State Summary";
      uses NAL-WARM-SUBSCRIBER-STATE-SUMMARY;
    }
    container lns-state-summary {
      description
        "LNS State Summary";
      uses NAL-WARM-SUBSCRIBER-STATE-SUMMARY;
    }
    container routed-state-summary {
      description
        "Routed State Summary";
      uses NAL-WARM-SUBSCRIBER-STATE-SUMMARY;
    }
    container ipoe-afi-summary {
      description
        "IPoE AFI Summary";
      uses NAL-SUBS-WARM-AFI-SUMMARY;
    }
    container pppoe-afi-summary {
      description
        "PPPoE AFI Summary";
      uses NAL-SUBS-WARM-AFI-SUMMARY;
    }
    container lac-afi-summary {
      description
        "LAC AFI Summary";
      uses NAL-SUBS-WARM-AFI-SUMMARY;
    }
    container lns-afi-summary {
      description
        "LNS AFI Summary";
      uses NAL-SUBS-WARM-AFI-SUMMARY;
    }
    container routed-afi-summary {
      description
        "Routed AFI Summary";
      uses NAL-SUBS-WARM-AFI-SUMMARY;
    }
  }
}
