module Cisco-IOS-XR-um-auto-ip-ring-cfg {
  namespace "http://cisco.com/ns/yang/Cisco-IOS-XR-um-auto-ip-ring-cfg";
  prefix um-auto-ip-ring-cfg;

  import ietf-inet-types {
    prefix inet;
  }
  import Cisco-IOS-XR-um-interface-cfg {
    prefix a1;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR auto-ip-ring package configuration.
     
     This YANG module augments the
     modules with configuration data.
     
     Copyright (c) 2020-2025 by Cisco Systems, Inc., and/or its affiliates.
     All rights reserved.";

  revision 2022-07-11 {
    description
      "Added missing description statement to nodes
       2022-02-04
         Model Deprecated";
    semver:module-version "1.1.0";
  }
  revision 2020-12-15 {
    description
      "Initial release";
    semver:module-version "1.0.0";
  }

  grouping IF-BODY {
    description
      "Grouping for interface";
    container auto-ip-ring {
      presence "Indicates a auto-ip-ring node is configured.";
      status deprecated;
      description
        "Auto-IP-Ring interface configuration commands";
      leaf auto-ip-ring-id {
        type uint32 {
          range "1..255" {
            description
              "Ring ID number";
          }
        }
        mandatory true;
        description
          "Auto-IP-Ring interface configuration commands";
      }
      leaf ipv4-address {
        type inet:ipv4-address-no-zone;
        mandatory true;
        description
          "auto-ip address";
      }
    }
  }

  augment "/a1:interfaces/a1:interface" {
    description
      "This augment extends active nodes configuration";
    uses IF-BODY;
  }
  augment "/a1:interfaces/a1:interface-preconfigure" {
    description
      "This augment extends preconfigured nodes
       configuration";
    uses IF-BODY;
  }
  container auto-ip-ring {
    presence "Indicates a auto-ip-ring node is configured.";
    status deprecated;
    description
      "Enable auto-ip-ring";
  }
}
