module Cisco-IOS-XR-shellutil-filesystem-oper {
  namespace "http://cisco.com/ns/yang/Cisco-IOS-XR-shellutil-filesystem-oper";
  prefix shellutil-filesystem-oper;

  import Cisco-IOS-XR-types {
    prefix xr;
  }
  import cisco-semver {
    prefix semver;
  }
  include Cisco-IOS-XR-shellutil-filesystem-oper-sub1 {
    revision-date 2021-03-22;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR shellutil-filesystem package operational data.
     
     This module contains definitions
     for the following management objects:
       file-system: List of filesystems
     
     Copyright (c) 2013-2021 by Cisco Systems, Inc.
     All rights reserved.";

  revision 2021-03-22 {
    description
      "Changing type of size and free from string to uint64_t.";
    semver:module-version "2.0.0";
  }
  revision 2019-04-05 {
    description
      "Establish semantic version baseline.";
    semver:module-version "1.0.1";
  }
  revision 2015-11-09 {
    description
      "IOS XR 6.0 revision.";
  }

  container file-system {
    config false;
    description
      "List of filesystems";
    list node {
      key "node-name";
      description
        "Node ID";
      leaf node-name {
        type xr:Node-id;
        description
          "Node name";
      }
      uses FILESYSTEM;
    }
  }
}
