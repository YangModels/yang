module Cisco-IOS-XR-um-l2tp-class-cfg {
  namespace "http://cisco.com/ns/yang/Cisco-IOS-XR-um-l2tp-class-cfg";
  prefix um-l2tp-class-cfg;

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR l2tp-class package configuration.
     
     This YANG module augments the
     modules with configuration data.
     
     Copyright (c) 2020-2025 by Cisco Systems, Inc., and/or its affiliates.
     All rights reserved.";

  revision 2020-12-14 {
    description
      "Initial release";
    semver:module-version "1.0.0";
  }

  container l2tp-classes {
    description
      "L2TPv3 class used for L2VPNs";
    list l2tp-class {
      key "l2tp-class-name";
      description
        "The l2tp-class name";
      leaf l2tp-class-name {
        type xr:Cisco-ios-xr-string {
          length "1..31" {
            description
              "The l2tp-class name";
          }
          pattern "[a-z0-9A-Z][-_.a-z0-9A-Z]*";
        }
        description
          "The l2tp-class name";
      }
      container authentication {
        presence "Indicates a authentication node is configured.";
        description
          "Authenticate the L2TP control connection";
        container disable {
          presence "Indicates a disable node is configured.";
          description
            "Disable L2TP control connection authentication";
        }
      }
      leaf receive-window {
        type uint32 {
          range "1..16384" {
            description
              "size in bytes";
          }
        }
        description
          "Receive window size for the control connection";
      }
      container retransmit {
        description
          "Control message retransmission parameters";
        container initial {
          description
            "SCCRQ message retries/timeout settings";
          leaf retries {
            type uint32 {
              range "1..1000" {
                description
                  "retries number";
              }
            }
            description
              "Number of initial retries before halting attempts";
          }
          container timeout {
            description
              "SCCRQ retransmission timeout parameters";
            leaf min {
              type uint32 {
                range "1..8" {
                  description
                    "Seconds";
                }
              }
              description
                "Minimum timeout";
            }
            leaf max {
              type uint32 {
                range "1..8" {
                  description
                    "Seconds";
                }
              }
              description
                "Maximum timeout";
            }
          }
        }
        leaf retries {
          type uint32 {
            range "5..1000" {
              description
                "retries number";
            }
          }
          description
            "Number of initial retries before halting attempts";
        }
        container timeout {
          description
            "Control packet retransmission timeout parameters";
          leaf min {
            type uint32 {
              range "1..8" {
                description
                  "Seconds";
              }
            }
            description
              "Minimum timeout";
          }
          leaf max {
            type uint32 {
              range "1..8" {
                description
                  "Seconds";
              }
            }
            description
              "Maximum timeout";
          }
        }
      }
      container timeout {
        description
          "Control connection timeout parameters";
        leaf setup {
          type uint32 {
            range "60..6000" {
              description
                "timeout value in seconds";
            }
          }
          description
            "Time permitted to set up a control connection";
        }
        container no-user {
          description
            "No-user timeout for tunnel";
          leaf timeout {
            type uint32 {
              range "0..86400" {
                description
                  "timeout value in seconds";
              }
            }
            must "not(../never)";
            description
              "timeout value in seconds";
          }
          container never {
            must "not(../timeout)";
            presence "Indicates a never node is configured.";
            description
              "tunnel remains up even without any user";
          }
        }
      }
      leaf hostname {
        type xr:Cisco-ios-xr-string {
          length "1..800" {
            description
              "Local hostname string";
          }
        }
        description
          "Local hostname for control connection authentication";
      }
      container hidden {
        presence "Indicates a hidden node is configured.";
        description
          "Hide AVPs in outgoing control messages";
      }
      container password {
        description
          "Password for control connection authentication, L2TPv2 AVP hiding";
        leaf encrypted {
          type xr:Proprietary-password;
          description
            "Specifies that an encrypted password will follow";
        }
      }
      leaf hello-interval {
        type uint32 {
          range "0..1000" {
            description
              "interval time in seconds";
          }
        }
        description
          "Set HELLO message interval";
      }
      container digest {
        description
          "Message Digest configuration for L2TPv3 control connection";
        container check {
          description
            "Enable Message Digest validation";
          container disable {
            presence "Indicates a disable node is configured.";
            description
              "Disable Message Digest validation";
          }
        }
        container secret {
          description
            "Shared secret for L2TPv3 control message authentication, AVP hiding";
          list encrypted-secret {
            key "encrypted";
            description
              "Specifies that an encrypted secret will follow";
            leaf encrypted {
              type xr:Proprietary-password;
              description
                "Specifies that an encrypted secret will follow";
            }
            container hash {
              description
                "set hash method for authentication";
              container md5 {
                must "not(../sha1)";
                presence "Indicates a md5 node is configured.";
                description
                  "use MD5 for hash";
              }
              container sha1 {
                must "not(../md5)";
                presence "Indicates a sha1 node is configured.";
                description
                  "use SHA1 for hash";
              }
            }
          }
        }
        container hash {
          description
            "set hash method for L2TPv3 control message integrity check";
          container md5 {
            must "not(../sha1)";
            presence "Indicates a md5 node is configured.";
            description
              "use MD5 for hash";
          }
          container sha1 {
            must "not(../md5)";
            presence "Indicates a sha1 node is configured.";
            description
              "use SHA1 for hash";
          }
        }
      }
      container ip {
        description
          "settings for tunnel";
        leaf tos {
          type uint32 {
            range "0..255" {
              description
                "IP TOS value (decimal or hex with 0x prefix)";
            }
          }
          description
            "set IP ToS value for control traffic";
        }
      }
      container tunnel {
        description
          "Settings for tunnel";
        leaf accounting {
          type xr:Cisco-ios-xr-string {
            length "1..800" {
              description
                "AAA accounting method list name";
            }
          }
          description
            "Method list to use for tunnel accounting";
        }
      }
      container security {
        description
          "L2TP security command";
        container ip {
          description
            "IP address check for L2TP";
          container address-check {
            presence "Indicates a address-check node is configured.";
            description
              "IP address check for L2TP packets";
          }
        }
      }
      container congestion-control {
        presence "Indicates a congestion-control node is configured.";
        description
          "Enable l2tp congestion control";
      }
    }
  }
}
