submodule Cisco-IOS-XR-ipv4-ping-act {
  belongs-to Cisco-IOS-XR-ping-act {
    prefix ping-act;
  }

  import cisco-semver {
    prefix semver;
  }
  import Cisco-IOS-XR-types {
    prefix xr;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR IPv4 ping action package configuration.
     
     Copyright (c) 2016-2025 by Cisco Systems, Inc., and/or its affiliates.
     All rights reserved.";

  revision 2025-12-02 {
    description
      "Restored common ipv4 and ipv6 data-size leaf in destination container with min value 36
       2025-08-14
         Updated data-size leaf in destination container.
       2025-07-31
         Updated data-size range for IPv6 ping.
       2023-10-19
         Updated repeat-count range for IPv4 and IPv6 ping.
       2023-09-13
         Corrected grouping for ping response.
       2022-08-11
         Addition of new leaves.";
    semver:module-version "2.0.0";
  }
  revision 2021-03-05 {
    description
      "Removed support for use-srv6-op-sid";
    semver:module-version "1.1.0";
  }
  revision 2019-10-01 {
    description
      "Made changes to be RFC6087 compliant";
    semver:module-version "1.1.0";
  }
  revision 2019-04-05 {
    description
      "Establish semantic version baseline.";
    semver:module-version "1.0.0";
  }
  revision 2016-08-20 {
    description
      "IOS XR 6.2.1 revision.";
  }

  grouping PING-COMMON-INPUT-OUTPUT-OPTIONS {
    description
      "Ping Common Input Output Options";
    leaf destination {
      type string;
      mandatory true;
      description
        "Ping destination address or hostname";
    }
    leaf repeat-count {
      type uint64 {
        range "1..2147483647";
      }
      default "5";
      description
        "Number of ping packets to be sent out";
    }
    leaf timeout {
      type uint64 {
        range "0..36";
      }
      default "2";
      description
        "Timeout in seconds";
    }
    leaf interval {
      type uint32 {
        range "0..3600";
      }
      default "10";
      description
        "Ping interval in milli seconds";
    }
    leaf pattern {
      type xr:Hex-integer;
      description
        "Pattern of payload data";
    }
    leaf sweep {
      type boolean;
      description
        "Sweep is enabled";
    }
    leaf do-not-resolve {
      type boolean;
      description
        "Do not resolve hostname. When this leaf is set, hostname will not be resolved";
    }
  }

  grouping PING-OPTIONS {
    description
      "Ping Options";
    uses PING-COMMON-INPUT-OUTPUT-OPTIONS;
    leaf source {
      type string;
      description
        "Source address or interface";
    }
    leaf verbose {
      type boolean;
      description
        "Validate return packet";
    }
  }

  grouping IPV4-SPECIFIC-OPTIONS {
    description
      "Ping IPv4 Specific Options";
    leaf type-of-service {
      type uint8 {
        range "0..255";
      }
      description
        "Type of Service";
    }
    leaf do-not-frag {
      type boolean;
      description
        "Do Not Fragment";
    }
    leaf validate {
      type boolean;
      description
        "Validate return packet";
    }
  }

  grouping IPV4-PING-OPTIONS {
    description
      "Ping IPv4 Options";
    uses PING-OPTIONS;
    uses IPV4-SPECIFIC-OPTIONS;
    leaf vrf-name {
      type string;
      description
        "VRF name";
    }
  }

  grouping IPV4-PING-INPUT {
    description
      "Ping IPv4 Input";
    uses IPV4-PING-OPTIONS;
    leaf data-size {
      type uint64 {
        range "36..18024";
      }
      default "100";
      description
        "Size of ping packet";
    }
  }

  grouping IPV4-PING-OUTPUT {
    description
      "Ping IPv4 Output";
    uses PING-OPTIONS;
    container replies {
      description
        "IPv4 ping replies";
      list reply {
        key "reply-index";
        description
          "IPv4 ping reply";
        leaf reply-index {
          type uint64 {
            range "1..2147483647";
          }
          description
            "Index of the reply list";
        }
        leaf result {
          type string;
          description
            "Response for each packet";
        }
        leaf reply-source {
          type string;
          description
            "Source of each response packet";
        }
        leaf time {
          type uint64 {
            range "1..2147483647";
          }
          description
            "Time taken to receive each response packet in nanoseconds";
        }
        leaf ttl {
          type uint64 {
            range "1..2147483647";
          }
          description
            "TTL value for each packet";
        }
        leaf bytes {
          type uint64 {
            range "1..2147483647";
          }
          description
            "Number of bytes for each packet";
        }
        container broadcast-reply-addresses {
          description
            "IPv4 ping broadcast reply addresses";
          list broadcast-reply-address {
            key "reply-address";
            description
              "IPv4 ping broadcast reply address";
            leaf reply-address {
              type string;
              description
                "Broadcast reply address";
            }
            leaf result {
              type string;
              description
                "Sign for each reply packet";
            }
          }
        }
      }
    }
    leaf hits {
      type uint64;
      description
        "Number of packets reach to destination and get reply back";
    }
    leaf total {
      type uint64;
      description
        "Total number of packets sent out";
    }
    leaf success-rate {
      type uint64;
      description
        "Successful rate of ping";
    }
    leaf rtt-min {
      type uint64;
      description
        "Minimum value of Round Trip Time";
    }
    leaf rtt-avg {
      type uint64;
      description
        "Average value of Round Trip Time";
    }
    leaf rtt-max {
      type uint64;
      description
        "Maximum value of Round Trip Time";
    }
    leaf std-dev {
      type uint64;
      units "msec";
      description
        "standard deviation of Ping responses";
    }
    leaf sweep-min {
      type uint32;
      description
        "Minimum value of sweep size";
    }
    leaf sweep-max {
      type uint64;
      description
        "Maximum value of sweep size";
    }
    leaf rotate-pattern {
      type boolean;
      description
        "Rotate Pattern is enabled";
    }
    leaf ping-error-response {
      type string;
      description
        "Error response for each ping, in case of bulk ping";
    }
    leaf data-size {
      type uint64 {
        range "36..18024";
      }
      default "100";
      description
        "Size of ping packet";
    }
  }
}
