module Cisco-IOS-XR-tty-show-terminal-oper {
  namespace "http://cisco.com/ns/yang/Cisco-IOS-XR-tty-show-terminal-oper";
  prefix tty-show-terminal-oper;

  import cisco-semver {
    prefix semver;
  }
  include Cisco-IOS-XR-tty-show-terminal-oper-sub1 {
    revision-date 2021-08-27;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR tty-show-terminal package operational data.
     
     This module contains definitions
     for the following management objects:
       show-terminal: Show terminal statistics
     
     Copyright (c) 2013-2021 by Cisco Systems, Inc.
     All rights reserved.";

  revision 2021-08-27 {
    description
      "yang support for show terminal";
    semver:module-version "1.0.0";
  }
  revision 2019-04-05 {
    description
      "Establish semantic version baseline.";
  }
  revision 2015-11-09 {
    description
      "IOS XR 6.0 revision.";
  }

  container show-terminal {
    config false;
    description
      "Show terminal statistics";
    container terminals {
      description
        "Show terminal statistics";
      list terminal {
        key "terminal-id";
        description
          "Show terminal statistics";
        leaf terminal-id {
          type uint32 {
            range "0..4294967295";
          }
          description
            "Terminal ID";
        }
        uses SHOWTERMINAL-ENTRY;
      }
    }
  }
}
