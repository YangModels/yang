module Cisco-IOS-XR-um-mibs-subscriber-cfg {
  namespace "http://cisco.com/ns/yang/Cisco-IOS-XR-um-mibs-subscriber-cfg";
  prefix um-mibs-subscriber-cfg;

  import Cisco-IOS-XR-types {
    prefix xr;
  }
  import Cisco-IOS-XR-um-snmp-server-cfg {
    prefix a1;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR mibs-subscriber package configuration.
     
     This YANG module augments the
     modules with configuration data.
     
     Copyright (c) 2020-2022 by Cisco Systems, Inc.
     All rights reserved.";

  revision 2022-07-11 {
    description
      "Added missing description statement to nodes";
    semver:module-version "1.0.0";
  }
  revision 2020-12-14 {
    description
      "Initial release";
    semver:module-version "1.0.0";
  }

  augment "/a1:snmp-server/a1:traps" {
    description
      "This augment extends snmp-server traps nodes
       configuration";
    container subscriber {
      description
        "Subscriber notification commands";
      container session-agg {
        description
          "Session aggregation";
        container access-interface {
          presence "Indicates a access-interface node is configured.";
          description
            "Subscriber notification at access interface level";
        }
        container node {
          presence "Indicates a node node is configured.";
          description
            "Subscriber notification at node level";
        }
      }
    }
  }
  augment "/a1:snmp-server-mibs" {
    description
      "This augment extends snmp-server-mibs nodes
       configuration";
    container subscriber {
      description
        "Subscriber threshold commands";
      container threshold {
        description
          "Subscriber threshold commands";
        container rising {
          description
            "Rising threshold";
          container access-ifs {
            description
              "Access interface";
            list access-if {
              key "access-if-name";
              description
                "Access interface";
              leaf access-if-name {
                type xr:Interface-name;
                description
                  "Access interface";
              }
              leaf session-count {
                type uint32 {
                  range "1..4294967294" {
                    description
                      "Session count";
                  }
                }
                mandatory true;
                description
                  "Session count";
              }
            }
          }
          container locations {
            description
              "Rising node level";
            list location {
              key "location-name";
              description
                "Rising node level";
              leaf location-name {
                type xr:Node-id;
                description
                  "Rising node level";
              }
              leaf session-count {
                type uint32 {
                  range "1..4294967294" {
                    description
                      "Session count";
                  }
                }
                mandatory true;
                description
                  "Session count";
              }
            }
          }
        }
        container falling {
          description
            "Falling threshold";
          container access-ifs {
            description
              "Access interface";
            list access-if {
              key "access-if-name";
              description
                "Access interface";
              leaf access-if-name {
                type xr:Interface-name;
                description
                  "Access interface";
              }
              leaf session-count {
                type uint32 {
                  range "1..4294967294" {
                    description
                      "Session count";
                  }
                }
                mandatory true;
                description
                  "Session count";
              }
            }
          }
          container locations {
            description
              "Falling node level";
            list location {
              key "location-name";
              description
                "Falling node level";
              leaf location-name {
                type xr:Node-id;
                description
                  "Falling node level";
              }
              leaf session-count {
                type uint32 {
                  range "1..4294967294" {
                    description
                      "Session count";
                  }
                }
                mandatory true;
                description
                  "Session count";
              }
            }
          }
        }
        container delta-loss {
          description
            "Delta loss keyword";
          container percent {
            description
              "Delta loss percent";
            container access-ifs {
              description
                "Access interface";
              list access-if {
                key "access-if-name";
                description
                  "Access interface";
                leaf access-if-name {
                  type xr:Interface-name;
                  description
                    "Access interface";
                }
                leaf session-count {
                  type uint32 {
                    range "1..100" {
                      description
                        "Loss of percentage";
                    }
                  }
                  mandatory true;
                  description
                    "Percentage";
                }
              }
            }
            container locations {
              description
                "Node Level";
              list location {
                key "location-name";
                description
                  "Node Level";
                leaf location-name {
                  type xr:Node-id;
                  description
                    "Node Level";
                }
                leaf session-count {
                  type uint32 {
                    range "1..100" {
                      description
                        "Percentage";
                    }
                  }
                  mandatory true;
                  description
                    "Percentage";
                }
              }
            }
          }
          container evaluation {
            description
              "Evaluation keyword";
            container access-ifs {
              description
                "Access interface";
              list access-if {
                key "access-if-name";
                description
                  "Access interface";
                leaf access-if-name {
                  type xr:Interface-name;
                  description
                    "Access interface";
                }
                leaf interval {
                  type uint32 {
                    range "30..3600" {
                      description
                        "Interval value in multiples of 10";
                    }
                  }
                  mandatory true;
                  description
                    "interval";
                }
              }
            }
            container locations {
              description
                "Node Level";
              list location {
                key "location-name";
                description
                  "Node Level";
                leaf location-name {
                  type xr:Node-id;
                  description
                    "Node Level";
                }
                leaf interval {
                  type uint32 {
                    range "30..3600" {
                      description
                        "interval value in multiples of 10";
                    }
                  }
                  mandatory true;
                  description
                    "Interval";
                }
              }
            }
          }
        }
        container access-if {
          description
            "Access interface for regular expression";
          container subsets {
            description
              "Subset command";
            list subset {
              key "subset-id";
              description
                "Subset command";
              leaf subset-id {
                type uint32 {
                  range "1..255" {
                    description
                      "Subset number";
                  }
                }
                description
                  "Subset command";
              }
              leaf regular-expression {
                type string {
                  length "1..800" {
                    description
                      "Regular expression to match interfae name";
                  }
                }
                description
                  "Regular expression";
              }
            }
          }
        }
      }
    }
  }
}
