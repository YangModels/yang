module Cisco-IOS-XR-um-cont-otu-cfg {
  namespace "http://cisco.com/ns/yang/Cisco-IOS-XR-um-cont-otu-cfg";
  prefix um-cont-otu-cfg;

  import Cisco-IOS-XR-types {
    prefix xr;
  }
  import Cisco-IOS-XR-um-interface-cfg {
    prefix a1;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR cont-otu package configuration.
     
     This YANG module augments the
     modules with configuration data.
     
     Copyright (c) 2021-2025 by Cisco Systems, Inc., and/or its affiliates.
     All rights reserved.";

  revision 2022-07-11 {
    description
      "Added missing description statement to nodes
       2022-06-01
         Adjusted controller augmentation hierarchy";
    semver:module-version "1.1.0";
  }
  revision 2021-05-07 {
    description
      "Initial release";
    semver:module-version "1.0.0";
  }

  feature otu_config_supp_check {
    description
      "otu config supp check";
  }

  grouping CONT-BODY {
    description
      "Grouping for controller";
    container perf-mon {
      description
        "Performance Monitoring";
      container disable {
        must "not(../enable)";
        presence "Indicates a disable node is configured.";
        description
          "Disable performance monitoring";
      }
      container enable {
        must "not(../disable)";
        presence "Indicates a enable node is configured.";
        description
          "Enable performance monitoring";
      }
    }
    container gcc0 {
      presence "Indicates a gcc0 node is configured.";
      description
        "Configure GCC0(General Communication Channel)";
    }
    container threshold {
      description
        "Configure threshold for Signal Failure and Signal Degrade";
      leaf sd {
        type uint32 {
          range "5..9" {
            description
              "Signal Degrade Threshold Value(Range 1.0e-n)";
          }
        }
        description
          "Configure SD(Signal Degrade) Threshold";
      }
      leaf sf {
        type uint32 {
          range "5..9" {
            description
              "Signal Failure Threshold Value(Range 1.0e-n)";
          }
        }
        description
          "Configure SF(Signal Failure) Threshold";
      }
      leaf sm-tca {
        type uint32 {
          range "3..9" {
            description
              "TCA Threshold Value(Range 10e-n, Default 3)";
          }
        }
        description
          "Configure TCA(Threshold crossing alert) Threshold";
      }
    }
    leaf secondary-admin-state {
      type enumeration {
        enum "normal" {
          value 0;
          description
            "Normal, Admin-state in normal";
        }
        enum "maintenance" {
          value 1;
          description
            "Maintenance, Admin-state under maintenance";
        }
      }
      description
        "Configure the secondary admin state of the controller";
    }
    container tti {
      description
        "Configure TTI(Trail Trace Identifier)";
      container sent {
        description
          "Set transmit Trail Trace Identifier";
        container sapi {
          description
            "Enter Source Access Point Identifier field 1-15";
          leaf ascii {
            type string {
              length "1..15" {
                description
                  "ASCII text (Max 15 characters)";
              }
            }
            description
              "Enter ascii string";
          }
        }
        container dapi {
          description
            "Enter Destination Access Point Identifier field 1-15";
          leaf ascii {
            type string {
              length "1..15" {
                description
                  "ASCII text (Max 15 characters)";
              }
            }
            description
              "Enter ascii string";
          }
        }
        container operator-specific {
          description
            "Enter Operator Specific field";
          leaf ascii {
            type string {
              length "1..32" {
                description
                  "ASCII text (Max 32 characters)";
              }
            }
            must "not(../hex)";
            description
              "Enter ascii string";
          }
          leaf hex {
            type string {
              length "1..64" {
                description
                  "Hex Text (Max 64 - The string length should be an even number)";
              }
            }
            must "not(../ascii)";
            description
              "Enter hex string of even length";
          }
        }
      }
      container expected {
        description
          "Set expected Trail Trace Identifier";
        container sapi {
          description
            "Enter Source Access Point Identifier field 1-15";
          leaf ascii {
            type string {
              length "1..15" {
                description
                  "ASCII text (Max 15 characters)";
              }
            }
            description
              "Enter ascii string";
          }
        }
        container dapi {
          description
            "Enter Destination Access Point Identifier field 1-15";
          leaf ascii {
            type string {
              length "1..15" {
                description
                  "ASCII text (Max 15 characters)";
              }
            }
            description
              "Enter ascii string";
          }
        }
        container operator-specific {
          description
            "Enter Operator Specific field";
          leaf ascii {
            type string {
              length "1..32" {
                description
                  "ASCII text (Max 32 characters)";
              }
            }
            must "not(../hex)";
            description
              "Enter ascii string";
          }
          leaf hex {
            type string {
              length "1..64" {
                description
                  "Hex Text (Max 64 - The string length should be an even number)";
              }
            }
            must "not(../ascii)";
            description
              "Enter hex string of even length";
          }
        }
      }
    }
    leaf fec {
      type enumeration {
        enum "none" {
          value 1;
          description
            "No Forward Error Correction";
        }
        enum "Standard" {
          value 2;
          description
            "Forward Error Correction Standard";
        }
        enum "EnhancedI7" {
          value 4;
          description
            "Forward Error Correction Enhanced_I_7";
        }
        enum "EnhancedI4" {
          value 8;
          description
            "Forward Error Correction Enhanced_I_4";
        }
        enum "EnhancedSwizzle" {
          value 16;
          description
            "Forward Error Correction Enhanced_Swizzle";
        }
        enum "EnhancedHG20" {
          value 32;
          description
            "Forward Error Correction Enhanced_HG20";
        }
        enum "EnhancedHG7" {
          value 64;
          description
            "Forward Error Correction Enhanced_HG7";
        }
        enum "EnhancedSD20" {
          value 128;
          description
            "Forward Error Correction Soft-Decision 20";
        }
        enum "EnhancedSD7" {
          value 256;
          description
            "Forward Error Correction Soft-Decision 7";
        }
        enum "EnhancedSD15" {
          value 512;
          description
            "Forward Error Correction Soft-Decision 15";
        }
        enum "EnhancedSD27" {
          value 1024;
          description
            "Forward Error Correction Soft-Decision 27";
        }
        enum "EnhancedSD15DE" {
          value 2048;
          description
            "Forward Error Correction Soft-Decision 15 with DE";
        }
        enum "EnhancedStaircaseDE" {
          value 4096;
          description
            "Forward Error Correction Enhanced Staircase FEC with DE";
        }
        enum "OFEC" {
          value 8192;
          description
            "Forward Error Correction O_FEC";
        }
        enum "CFEC" {
          value 16384;
          description
            "Forward Error Correction C_FEC";
        }
      }
      description
        "Configure Forward Error Correction mode";
    }
    leaf loopback {
      type enumeration {
        enum "line" {
          value 2;
          description
            "Select network (facility) loopback";
        }
        enum "internal" {
          value 4;
          description
            "Select network (terminal) loopback";
        }
      }
      description
        "Configure OTU controller loopback mode";
    }
    container srlg {
      description
        "Submode to configure shared risks for the OTU connection";
      container sets {
        description
          "Configure Network SRLG sets";
        list set {
          must "network-srlg-values";
          key "set-id";
          description
            "Configure Network SRLG sets";
          leaf set-id {
            type uint32 {
              range "1..17" {
                description
                  "Set index";
              }
            }
            description
              "Configure Network SRLG sets";
          }
          leaf-list network-srlg-values {
            type uint32 {
              range "0..4294967294" {
                description
                  "Network SRLG values (max 6 per set)";
              }
            }
            max-elements "6";
            description
              "Network SRLG values (max 6 per set)";
          }
        }
      }
    }
    container proactive {
      presence "Indicates a proactive node is configured.";
      description
        "Enable Proactive Protection Feature";
      container trigger {
        description
          "Configure trigger thresholds";
        leaf threshold {
          type uint32 {
            range "1..9" {
              description
                "Bit error rate coefficient (x of xE-y)";
            }
          }
          must "../bit-error-rate-power";
          description
            "Set values x and y of xE-y";
        }
        leaf bit-error-rate-power {
          type uint32 {
            range "3..9" {
              description
                "Bit error rate power (y of xE-y)";
            }
          }
          must "../threshold";
          description
            "Bit error rate power (y of xE-y)";
        }
        leaf window {
          type uint32 {
            range "10..10000" {
              description
                "Integration window for FRR trigger in MS";
            }
          }
          description
            "Number of times threshold crossing is tested";
        }
      }
      container revert {
        description
          "Configure Revert thresholds";
        leaf threshold {
          type uint32 {
            range "1..9" {
              description
                "Bit error rate coefficient (x of xE-y)";
            }
          }
          must "../bit-error-rate-power";
          description
            "Set values x and y of xE-y";
        }
        leaf bit-error-rate-power {
          type uint32 {
            range "4..10" {
              description
                "Bit error rate power (y of xE-y)";
            }
          }
          must "../threshold";
          description
            "Bit error rate power (y of xE-y)";
        }
        leaf window {
          type uint32 {
            range "2000..10000" {
              description
                "Integration window for FRR revert in MS";
            }
          }
          description
            "Number of times threshold crossing is tested";
        }
      }
    }
    container flexo {
      description
        "Configure flexo layer";
      leaf gid {
        type uint32 {
          range "1..1048575" {
            description
              "Set group id value for flexo";
          }
        }
        description
          "Set Group ID";
      }
      leaf iid {
        type xr:Cisco-ios-xr-string {
          length "1..800" {
            description
              "iid string separated by (,) from 1 to 256 ";
          }
        }
        must "../gid";
        description
          "Configure IID ";
      }
    }
    container prbs {
      description
        "Configure pseudo random bit sequence test";
      container mode {
        description
          "prbs-mode for the interface";
        container source {
          presence "Indicates a source node is configured.";
          description
            "source mode";
          container pattern {
            description
              "Select pattern for prbs mode";
            container pn31 {
              presence "Indicates a pn31 node is configured.";
              description
                "prbs pattern pn31";
            }
          }
          container pn23 {
            presence "Indicates a pn23 node is configured.";
            description
              "prbs pattern pn23";
          }
          container pn11 {
            presence "Indicates a pn11 node is configured.";
            description
              "prbs pattern pn11";
          }
          container pn7 {
            presence "Indicates a pn7 node is configured.";
            description
              "prbs pattern pn7";
          }
          container pn15 {
            presence "Indicates a pn15 node is configured.";
            description
              "prbs pattern pn15";
          }
          container invertedpn31 {
            presence "Indicates a invertedpn31 node is configured.";
            description
              "prbs pattern inverted pn31";
          }
          container invertedpn11 {
            presence "Indicates a invertedpn11 node is configured.";
            description
              "prbs pattern inverted pn11";
          }
        }
        container sink {
          presence "Indicates a sink node is configured.";
          description
            "sink mode";
          container pattern {
            description
              "Select pattern for prbs mode";
            container pn31 {
              presence "Indicates a pn31 node is configured.";
              description
                "prbs pattern pn31";
            }
          }
        }
        container source-sink {
          presence "Indicates a source-sink node is configured.";
          description
            "source-sink mode";
          container pattern {
            description
              "Select pattern for prbs mode";
            container pn31 {
              presence "Indicates a pn31 node is configured.";
              description
                "prbs pattern pn31";
            }
          }
        }
      }
    }
  }

  augment "/a1:controllers/a1:controller" {
    description
      "This augment extends active nodes configuration";
    uses CONT-BODY;
  }
  augment "/a1:controllers/a1:controller-preconfigure" {
    description
      "This augment extends preconfigured nodes
       configuration";
    uses CONT-BODY;
  }
}
