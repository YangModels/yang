module Cisco-IOS-XR-um-ip-virtual-cfg {
  namespace "http://cisco.com/ns/yang/Cisco-IOS-XR-um-ip-virtual-cfg";
  prefix um-ip-virtual-cfg;

  import Cisco-IOS-XR-types {
    prefix xr;
  }
  import ietf-inet-types {
    prefix inet;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ip-virtual package configuration.
     
     This YANG module augments the
     modules with configuration data.
     
     Copyright (c) 2020-2025 by Cisco Systems, Inc., and/or its affiliates.
     All rights reserved.";

  revision 2020-04-02 {
    description
      "Initial release";
    semver:module-version "1.0.0";
  }

  container ipv4 {
    description
      "Global IPv4 configuration commands";
    container virtual {
      description
        "virtual address for management interfaces options";
      container address {
        description
          "virtual address for management interfaces";
        leaf ip-address {
          type inet:ipv4-address-no-zone;
          description
            "IPv4 address/prefix";
        }
        leaf prefix-length {
          type xr:Ipv4-prefix-length;
          must "../ip-address";
          description
            "IPv4 address/prefix";
        }
        container vrfs {
          description
            "Select VRF for which the virtual ip address is configured";
          list vrf {
            key "vrf-name";
            description
              "Select VRF for which the virtual ip address is configured";
            leaf vrf-name {
              type xr:Cisco-ios-xr-string {
                length "1..32" {
                  description
                    " A VRF name";
                }
              }
              description
                "Select VRF for which the virtual ip address is configured";
            }
            leaf ip-address {
              type inet:ipv4-address-no-zone;
              mandatory true;
              description
                "IPv4 address/prefix";
            }
            leaf prefix-length {
              type xr:Ipv4-prefix-length;
              mandatory true;
              description
                "IPv4 address/prefix";
            }
          }
        }
        container use-as-src-addr {
          presence "Indicates a use-as-src-addr node is configured.";
          description
            "Use as default src address on sourced packets?";
        }
      }
    }
  }
  container ipv6 {
    description
      "Global IPv6 configuration commands";
    container virtual {
      description
        "virtual address for management interfaces options";
      container address {
        description
          "virtual address for management interfaces";
        leaf ip-address {
          type inet:ipv6-address-no-zone;
          description
            "IPv6 address/prefix";
        }
        leaf prefix-length {
          type xr:Ipv6-prefix-length;
          must "../ip-address";
          description
            "IPv6 address/prefix";
        }
        container vrfs {
          description
            "Select VRF for which the virtual ip address is configured";
          list vrf {
            key "vrf-name";
            description
              "Select VRF for which the virtual ip address is configured";
            leaf vrf-name {
              type xr:Cisco-ios-xr-string {
                length "1..32" {
                  description
                    " A VRF name";
                }
              }
              description
                "Select VRF for which the virtual ip address is configured";
            }
            leaf ip-address {
              type inet:ipv6-address-no-zone;
              mandatory true;
              description
                "IPv6 address/prefix";
            }
            leaf prefix-length {
              type xr:Ipv6-prefix-length;
              mandatory true;
              description
                "IPv6 address/prefix";
            }
          }
        }
        container use-as-src-addr {
          presence "Indicates a use-as-src-addr node is configured.";
          description
            "Use as default src address on sourced packets?";
        }
      }
    }
  }
}
