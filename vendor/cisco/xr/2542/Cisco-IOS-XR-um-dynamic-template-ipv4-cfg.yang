module Cisco-IOS-XR-um-dynamic-template-ipv4-cfg {
  namespace "http://cisco.com/ns/yang/Cisco-IOS-XR-um-dynamic-template-ipv4-cfg";
  prefix um-dynamic-template-ipv4-cfg;

  import Cisco-IOS-XR-types {
    prefix xr;
  }
  import Cisco-IOS-XR-um-dynamic-template-cfg {
    prefix a1;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR dynamic-template-ipv4 package configuration.
     
     This YANG module augments the
     modules with configuration data.
     
     Copyright (c) 2020-2025 by Cisco Systems, Inc., and/or its affiliates.
     All rights reserved.";

  revision 2022-07-11 {
    description
      "Added missing description statement to nodes";
    semver:module-version "1.1.0";
  }
  revision 2020-03-27 {
    description
      "Initial release";
    semver:module-version "1.0.0";
  }

  grouping TEMPLATE-BODY {
    description
      "Grouping for template";
    container ipv4 {
      description
        "ipv4 subcommands";
      leaf mtu {
        type uint32 {
          range "68..65535" {
            description
              "MTU (bytes)";
          }
        }
        description
          "Set IPv4 Maximum Transmission Unit";
      }
      leaf unnumbered {
        type xr:Interface-name;
        description
          "Enable IPv4 processing without an explicit address";
      }
      container verify {
        description
          "Enable per packet validation";
        container unicast {
          description
            "Enable per packet validation for unicast";
          container source {
            description
              "Validation of source address";
            container reachable-via {
              description
                "Specify reachability check to apply to the source address";
              container rx {
                presence "Indicates a rx node is configured.";
                description
                  "Source is reachable via interface on which packet was received";
              }
            }
          }
        }
      }
      container unreachables {
        description
          "Enable sending ICMP Unreachable messages";
        container disable {
          presence "Indicates a disable node is configured.";
          description
            "Suppress ICMPv4 Unreachable messages on subscriber interfaces";
        }
      }
    }
  }

  augment "/a1:dynamic-template/a1:type/a1:ppp/a1:template" {
    description
      "This augment extends dynamic-template ppp nodes
       configuration";
    uses TEMPLATE-BODY;
  }
  augment "/a1:dynamic-template/a1:type/a1:ipsubscriber/a1:template" {
    description
      "This augment extends dynamic-template ipsubscriber nodes
       configuration";
    uses TEMPLATE-BODY;
  }
  augment "/a1:dynamic-template/a1:type/a1:service/a1:template" {
    description
      "This augment extends dynamic-template service nodes
       configuration";
    uses TEMPLATE-BODY;
  }
}
