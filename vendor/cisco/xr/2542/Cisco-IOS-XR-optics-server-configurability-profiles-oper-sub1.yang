submodule Cisco-IOS-XR-optics-server-configurability-profiles-oper-sub1 {
  belongs-to Cisco-IOS-XR-optics-server-configurability-profiles-oper {
    prefix Cisco-IOS-XR-optics-server-configurability-profiles-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR optics-server-configurability-profiles package operational data.
     
     Copyright (c) 2013-2025 by Cisco Systems, Inc.
     All rights reserved.";

  revision 2025-03-27 {
    description
      "Schema added.";
    semver:module-version "1.0.0";
  }
  revision 2019-04-05 {
    description
      "Establish semantic version baseline.";
  }
  revision 2015-11-09 {
    description
      "IOS XR 6.0 revision.";
  }

  grouping GENERIC-STRING {
    description
      "Generic string";
    leaf str {
      type string;
      description
        "String Type";
    }
  }

  grouping ACTIVE-PROFILE-DATA {
    description
      "List of profiles activate per vendor";
    leaf part-number {
      type string;
      description
        "Activated Part Number";
    }
    leaf profile-name {
      type string;
      description
        "Activated Profile Name";
    }
    list active-port {
      description
        "Array of Active ports";
      uses GENERIC-STRING;
    }
    list inactive-port {
      description
        "Array of Inactive ports";
      uses GENERIC-STRING;
    }
  }

  grouping ACTIVE-VENDOR-PROFILES {
    description
      "List of profiles activate per vendor";
    leaf vendor-name {
      type string;
      description
        "Vendor Name";
    }
    list active-profile {
      description
        "Array of Activated Profiles";
      uses ACTIVE-PROFILE-DATA;
    }
  }

  grouping OPTICS-CONFIGURABILITY-PROFILE {
    description
      "All Configurability Data, including common, SFF,
       and CMIS parameters";
    container configurability-data {
      description
        "All configurability data associated with profile";
      uses OPTICS-CONFIGURABILITY;
    }
    leaf profile-name {
      type string;
      description
        "Name of custom profile";
    }
  }

  grouping OPTICS-DEFAULT-TIMING-TABLE {
    description
      "Table to Further Define Default CMIS Timing
       Params";
    leaf min-time {
      type uint64;
      description
        "The minimum or bottom of the timing interval";
    }
    leaf max-time {
      type uint64;
      description
        "The maximum or top of the timing interval";
    }
  }

  grouping OPTICS-CMIS-STATE-DUR-TABLE {
    description
      "Default CMIS Timing Params in State Duration
       Table";
    leaf encoding {
      type uint32;
      description
        "Byte encoding indexing the state duration table";
    }
    list entry {
      description
        "Array of entries in the state duration table";
      uses OPTICS-DEFAULT-TIMING-TABLE;
    }
  }

  grouping OPTICS-TIMING-TABLE {
    description
      "Table to Further Define CMIS Timing Params";
    leaf min-time {
      type uint64;
      description
        "The minimum or bottom of the timing interval";
    }
    leaf max-time {
      type uint64;
      description
        "The maximum or top of the timing interval";
    }
    leaf time-interval {
      type uint64;
      description
        "Time interval between polling times";
    }
    leaf max-time-increment {
      type uint64;
      description
        "Time to increment on each round of polling";
    }
  }

  grouping OPTICS-CMIS-PARAMS {
    description
      "CMIS Timing Params";
    container module-power-up-time {
      description
        "Duration needed for module to go to Power Up
         state";
      uses OPTICS-TIMING-TABLE;
    }
    container module-power-down-time {
      description
        "Duration needed for module to go to Power Down
         state";
      uses OPTICS-TIMING-TABLE;
    }
    container datapath-deinit-time {
      description
        "Duration needed for module to go to Datapath
         deinitialized state";
      uses OPTICS-TIMING-TABLE;
    }
    container datapath-init-time {
      description
        "Duration needed for module to go to Datapath
         initialized state";
      uses OPTICS-TIMING-TABLE;
    }
    container datapath-tx-turn-on-time {
      description
        "Duration needed for module to go to Transmit
         turn on state";
      uses OPTICS-TIMING-TABLE;
    }
    container datapath-tx-turn-off-time {
      description
        "Duration needed for module to go to Transmit
         turn off state";
      uses OPTICS-TIMING-TABLE;
    }
    leaf active-parameters {
      type uint32;
      description
        "Bitmap of cmis parameters in use for profile";
    }
    leaf state-machine-execution-count {
      type uint64;
      description
        "Number of times state machine will execute in
         event of failure";
    }
  }

  grouping OPTICS-SFF-PARAMS {
    description
      "SFF Optics Timing Parameters";
    leaf active-parameters {
      type uint32;
      description
        "Bitmap of sff parameters in use for profile";
    }
    leaf ton-lp-mode {
      type uint64;
      description
        "Time from when the host releases LPMode to high
         until module power consumption reaches Power
         Class 1";
    }
    leaf toff-lp-mode {
      type uint64;
      description
        "Time from when the host pulls LPMode low until
         the module is fully functional";
    }
    leaf ton-flag {
      type uint64;
      description
        "Time from condition triggering flag to
         associated flag bit set to 1 and IntL pulled low
         by the module";
    }
    leaf ton-txsq {
      type uint64;
      description
        "Time from loss of Rx input signal until the
         squel ched output condition is reached";
    }
    leaf toff-rxsq {
      type uint64;
      description
        "";
    }
    leaf ton-sq-dis {
      type uint64;
      description
        "This applies to Rx and Tx Squelch and is the
         time from bit cleared to 0 until squelch
         functionality is disabled ";
    }
    leaf ton-rxdis {
      type uint64;
      description
        "";
    }
    leaf toff-rx-dis {
      type uint64;
      description
        "This applies to Rx and Tx Squel ch and is the
         time from bit set to 1 until squelch
         functionality is enabled";
    }
    leaf tec-stabilization-time {
      type uint64;
      description
        "Time it take for TEC to stabalize";
    }
  }

  grouping OPTICS-PARAMS {
    description
      "Generic Optics Timing Parameters";
    leaf active-parameters {
      type uint32;
      description
        "Bitmap of common parameters in use for profile";
    }
    leaf init-time {
      type uint64;
      description
        "Time from power on or hot plug until the module
         is fully functional";
    }
    leaf toff-tx-dis {
      type uint64;
      description
        "Time from Tx Disable bit cleared to 0 until
         optical output rises above 90 % of nominal";
    }
    leaf ton-tx-dis {
      type uint64;
      description
        "Time from Tx Disable bit set to 1 until optical
         output falls below 10 % of nominal";
    }
    leaf ton-int-l {
      type uint64;
      description
        "Time from occurrence of condition triggering an
         interrupt until IntL is low";
    }
    leaf toff-int-l {
      type uint64;
      description
        "Time from clear on read operation of associated
         flag until module releases IntL to high. This
         includes the time to clear Rx LOS, Tx Fault and
         other flag bits";
    }
    leaf rx-enable-disable {
      type uint64;
      description
        "Non-standard parameter to control en/dis Rx
         power along with Tx";
    }
  }

  grouping OPTICS-CONFIGURABILITY {
    description
      "All Configurability Data, including common, SFF,
       and CMIS parameters";
    container common {
      description
        "Configurable common items";
      uses OPTICS-PARAMS;
    }
    container sff {
      description
        "Configurable SFF items";
      uses OPTICS-SFF-PARAMS;
    }
    container cmis {
      description
        "Configurable CMIS items";
      uses OPTICS-CMIS-PARAMS;
    }
  }

  grouping OPTICS-CONFIGURABILITY-SHOW {
    description
      "Configurability Data Present on Router";
    container default-data {
      description
        "Default Profile Data";
      uses OPTICS-CONFIGURABILITY;
    }
    container state-dur-table {
      description
        "Table of default state duration table";
      uses OPTICS-CMIS-STATE-DUR-TABLE;
    }
    list profile-data {
      description
        "Array of Custom Profile Data";
      uses OPTICS-CONFIGURABILITY-PROFILE;
    }
    list vendor-profile {
      description
        "Array of Custom Profiles Activated";
      uses ACTIVE-VENDOR-PROFILES;
    }
  }
}
