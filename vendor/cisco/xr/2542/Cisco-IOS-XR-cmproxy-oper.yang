module Cisco-IOS-XR-cmproxy-oper {
  namespace "http://cisco.com/ns/yang/Cisco-IOS-XR-cmproxy-oper";
  prefix cmproxy-oper;

  import Cisco-IOS-XR-types {
    prefix xr;
  }
  import cisco-semver {
    prefix semver;
  }
  include Cisco-IOS-XR-cmproxy-oper-sub1 {
    revision-date 2020-03-25;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR cmproxy package operational data.
     
     This module contains definitions
     for the following management objects:
       sdr-inventory-vm: Platform VM information
     
     Copyright (c) 2013-2020 by Cisco Systems, Inc.
     All rights reserved.";

  revision 2020-03-25 {
    description
      "Moved few of the bag fields to private";
    semver:module-version "2.0.0";
  }
  revision 2019-04-05 {
    description
      "Establish semantic version baseline.";
    semver:module-version "1.0.1";
  }
  revision 2018-03-04 {
    description
      "Added good description for bag fields";
  }
  revision 2015-11-09 {
    description
      "IOS XR 6.0 revision.";
  }

  container sdr-inventory-vm {
    config false;
    description
      "Platform VM information";
    container nodes {
      description
        "Node directory";
      list node {
        key "name";
        description
          "Node name";
        container node-entries {
          description
            "VM Information";
          list node-entry {
            key "name";
            description
              "VM information for a node";
            leaf name {
              type xr:Cisco-ios-xr-string;
              description
                "Node name";
            }
            uses CMP-INV-ST;
          }
        }
        leaf name {
          type xr:Cisco-ios-xr-string;
          description
            "Node name";
        }
      }
    }
  }
}
