module cisco-xr-openconfig-spanning-tree-deviations {

  namespace "http://cisco.com/ns/yang/Cisco-IOS-XR-oc-spanning-tree-cfg-deviations";
  prefix  "oc-stp-cfg-deviations";

  import openconfig-spanning-tree { prefix "oc-stp"; }

  organization "Cisco Systems, Inc.";

  contact
    "Cisco Systems, Inc.
     Customer Service

     Postal: 170 West Tasman Drive
     San Jose, CA 95134

     Tel: +1 800 553-NETS

     E-mail: cs-yang@cisco.com";

  description
    "This module contains a set of deviations for

    openconfig-spanning-tree.yang

    on Cisco IOS-XR devices.

    Copyright (c) 2023-2024 by Cisco Systems, Inc.
    All rights reserved.";

  revision "2023-04-13" {
    description
      "Initial release applicable to IOS-XR 7.11.1";
  }

  deviation /oc-stp:stp/oc-stp:rstp {
    deviate not-supported;
  }

  deviation /oc-stp:stp/oc-stp:global/oc-stp:state {
    deviate not-supported;
  }

  deviation /oc-stp:stp/oc-stp:mstp/oc-stp:state {
    deviate not-supported;
  }

  deviation /oc-stp:stp/oc-stp:mstp/oc-stp:mst-instances/oc-stp:mst-instance/oc-stp:state {
    deviate not-supported;
  }

  deviation /oc-stp:stp/oc-stp:mstp/oc-stp:mst-instances/oc-stp:mst-instance/oc-stp:interfaces/oc-stp:interface/oc-stp:state {
    deviate not-supported;
  }

  deviation /oc-stp:stp/oc-stp:mstp/oc-stp:mst-instances/oc-stp:mst-instance/oc-stp:interfaces/oc-stp:interface/oc-stp:config/oc-stp:cost {
    deviate not-supported;
  }

  deviation /oc-stp:stp/oc-stp:global/oc-stp:config/oc-stp:bridge-assurance {
    deviate not-supported;
  }

  deviation /oc-stp:stp/oc-stp:global/oc-stp:config/oc-stp:etherchannel-misconfig-guard {
    deviate not-supported;
  }

  deviation /oc-stp:stp/oc-stp:global/oc-stp:config/oc-stp:bpduguard-timeout-recovery {
    deviate not-supported;
  }

  deviation /oc-stp:stp/oc-stp:global/oc-stp:config/oc-stp:loop-guard {
    deviate not-supported;
  }

  deviation /oc-stp:stp/oc-stp:global/oc-stp:config/oc-stp:bpdu-filter {
    deviate not-supported;
  }

  deviation /oc-stp:stp/oc-stp:rapid-pvst/oc-stp:vlan/oc-stp:state {
    deviate not-supported;
  }

  deviation /oc-stp:stp/oc-stp:rapid-pvst/oc-stp:vlan/oc-stp:config/oc-stp:hello-time {
    deviate not-supported;
  }

  deviation /oc-stp:stp/oc-stp:rapid-pvst/oc-stp:vlan/oc-stp:config/oc-stp:max-age {
    deviate not-supported;
  }

  deviation /oc-stp:stp/oc-stp:rapid-pvst/oc-stp:vlan/oc-stp:config/oc-stp:forwarding-delay {
    deviate not-supported;
  }

  deviation /oc-stp:stp/oc-stp:rapid-pvst/oc-stp:vlan/oc-stp:config/oc-stp:hold-count {
    deviate not-supported;
  }
  deviation /oc-stp:stp/oc-stp:rapid-pvst/oc-stp:vlan/oc-stp:interfaces/oc-stp:interface/oc-stp:state {
    deviate not-supported;
  }

  deviation /oc-stp:stp/oc-stp:interfaces/oc-stp:interface/oc-stp:state {
    deviate not-supported;
  }

  deviation /oc-stp:stp/oc-stp:interfaces/oc-stp:interface/oc-stp:config/oc-stp:bpdu-filter {
    deviate not-supported;
  }
}
