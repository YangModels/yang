submodule Cisco-IOS-XR-fretta-bcm-dpa-qos-rate-profile-resources-oper-sub1 {
  belongs-to Cisco-IOS-XR-fretta-bcm-dpa-qos-rate-profile-resources-oper {
    prefix Cisco-IOS-XR-fretta-bcm-dpa-qos-rate-profile-resources-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR fretta-bcm-dpa-qos-rate-profile-resources package operational data.
     
     Copyright (c) 2013-2023 by Cisco Systems, Inc.
     All rights reserved.";

  revision 2023-06-06 {
    description
      "Added schema for qos rate profile resource utilization cli";
    semver:module-version "1.0.0";
  }
  revision 2019-04-05 {
    description
      "Establish semantic version baseline.";
  }
  revision 2015-11-09 {
    description
      "IOS XR 6.0 revision.";
  }

  grouping BCMDPA-QOS-RATE-PROFILE-RESOURCES-INFO {
    description
      "BCMDPA QOS RATE PROFILE RESOURCES INFO";
    leaf db-entry {
      type uint32;
      description
        "db entry";
    }
    leaf high-count {
      type uint32;
      description
        "high count";
    }
    leaf max-count {
      type uint32;
      description
        "max count";
    }
  }
}
