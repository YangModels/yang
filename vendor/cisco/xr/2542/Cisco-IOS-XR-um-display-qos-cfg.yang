module Cisco-IOS-XR-um-display-qos-cfg {
  namespace "http://cisco.com/ns/yang/Cisco-IOS-XR-um-display-qos-cfg";
  prefix um-display-qos-cfg;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR display-qos package configuration.
     
     This YANG module augments the
     modules with configuration data.
     
     Copyright (c) 2020-2025 by Cisco Systems, Inc., and/or its affiliates.
     All rights reserved.";

  revision 2020-12-01 {
    description
      "Initial release";
    semver:module-version "1.0.0";
  }

  container display {
    description
      "Configure QoS display options ";
    container qos {
      description
        "Configure global QoS options ";
      container precedence {
        description
          "Set the display format for precedence values in QoS configuration";
        container string {
          must "not(../numeric)";
          presence "Indicates a string node is configured.";
          description
            "Display format is string";
        }
        container numeric {
          must "not(../string)";
          presence "Indicates a numeric node is configured.";
          description
            "Display format is numeric";
        }
      }
      container dscp {
        description
          "Set the display format for dscp values in QoS configuration";
        container string {
          must "not(../numeric)";
          presence "Indicates a string node is configured.";
          description
            "Display format is string";
        }
        container numeric {
          must "not(../string)";
          presence "Indicates a numeric node is configured.";
          description
            "Display format is numeric";
        }
      }
    }
  }
}
