submodule Cisco-IOS-XR-controller-t1e1-oper-sub1 {
  belongs-to Cisco-IOS-XR-controller-t1e1-oper {
    prefix Cisco-IOS-XR-controller-t1e1-oper;
  }

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR controller-t1e1 package operational data.
     
     Copyright (c) 2013-2022 by Cisco Systems, Inc.
     All rights reserved.";

  revision 2022-01-12 {
    description
      "Added Oper Schema for T1E1";
    semver:module-version "1.0.0";
  }
  revision 2019-04-05 {
    description
      "Establish semantic version baseline.";
  }
  revision 2015-11-09 {
    description
      "IOS XR 6.0 revision.";
  }

  typedef T1e1-ui-clock {
    type enumeration {
      enum "invalid" {
        value 0;
        description
          "Clock Not Valid";
      }
      enum "internal" {
        value 1;
        description
          "Internal";
      }
      enum "line" {
        value 2;
        description
          "Line";
      }
      enum "recovered-acr" {
        value 3;
        description
          "Adaptive Clock Recovery (ACR)";
      }
      enum "recovered-dcr" {
        value 4;
        description
          "Differential Clock Recovery (DCR)";
      }
    }
    description
      "T1e1 ui clock";
  }

  typedef T1e1-prbs-mode {
    type enumeration {
      enum "t1e1-prbs-mode-source" {
        value 1;
        description
          "Source";
      }
      enum "t1e1-prbs-mode-sink" {
        value 2;
        description
          "Sink";
      }
      enum "t1e1-prbs-mode-source-sink" {
        value 3;
        description
          "Source Sink";
      }
    }
    description
      "T1e1 prbs mode";
  }

  typedef T1e1-prbs-sync-status {
    type enumeration {
      enum "t1e1-prbs-status-sync" {
        value 0;
        description
          "Sync";
      }
      enum "t1e1-prbs-status-not-sync" {
        value 1;
        description
          "Not Sync";
      }
    }
    description
      "T1e1 prbs sync status";
  }

  typedef T1e1-prbs-pattern {
    type enumeration {
      enum "t1e1-prbs-pattern-pn15" {
        value 1;
        description
          "PN15(2^15)";
      }
    }
    description
      "T1e1 prbs pattern";
  }

  typedef T1e1-prbs-direction {
    type enumeration {
      enum "t1e1-prbs-direct-ion-line" {
        value 1;
        description
          "Line";
      }
      enum "t1e1-prbs-direct-ion-system" {
        value 2;
        description
          "System";
      }
    }
    description
      "T1e1 prbs direction";
  }

  typedef T1e1-ui-clock-state {
    type enumeration {
      enum "freerun" {
        value 0;
        description
          "Free run";
      }
      enum "hold-over" {
        value 1;
        description
          "Hold over";
      }
      enum "locked" {
        value 2;
        description
          "Locked";
      }
      enum "disabled" {
        value 3;
        description
          "Disabled";
      }
    }
    description
      "T1e1 ui clock state";
  }

  typedef T1e1-ui-frame {
    type enumeration {
      enum "e1t1-crc" {
        value 0;
        description
          "CRC";
      }
      enum "e1t1-nocrc" {
        value 1;
        description
          "NOCRC";
      }
      enum "e1t1-unframed" {
        value 2;
        description
          "Unframed";
      }
    }
    description
      "T1e1 ui frame";
  }

  typedef T1e1-ui-loopback {
    type enumeration {
      enum "loop-back-none" {
        value 0;
        description
          "None";
      }
      enum "loop-back-local" {
        value 1;
        description
          "Local loopback";
      }
      enum "loop-back-line" {
        value 2;
        description
          "Line side loopback";
      }
    }
    description
      "T1e1 ui loopback";
  }

  typedef Linecoding {
    type enumeration {
      enum "line-code-none" {
        value 0;
        description
          "None";
      }
      enum "line-code-ami" {
        value 1;
        description
          "Alternate Mark Inversion(AMI)";
      }
      enum "line-code-hdb3" {
        value 2;
        description
          "High Density Bipolar Order 3";
      }
    }
    description
      "Linecoding";
  }

  typedef T1e1-controller-state {
    type enumeration {
      enum "t1e1-state-up" {
        value 0;
        description
          "Up";
      }
      enum "t1e1-state-down" {
        value 1;
        description
          "Down";
      }
      enum "t1e1-state-admin-down" {
        value 2;
        description
          "Administratively Down";
      }
    }
    description
      "T1e1 controller state";
  }

  typedef T1e1tas {
    type enumeration {
      enum "tas-ui-oos" {
        value 0;
        description
          "Out Of Service";
      }
      enum "tas-ui-main" {
        value 1;
        description
          "Maintenance";
      }
      enum "tas-ui-is" {
        value 2;
        description
          "In Service";
      }
    }
    description
      "T1e1tas";
  }

  grouping T1E1-PRBS-INFO {
    description
      "PRBS Test results";
    leaf prbs-direct-ion {
      type T1e1-prbs-direction;
      description
        "PRBS pattern injection direction";
    }
    leaf pattern {
      type T1e1-prbs-pattern;
      description
        "PRBS patterns";
    }
    leaf sync-status {
      type T1e1-prbs-sync-status;
      description
        " PRBS Test Sync status";
    }
    leaf prbs-mode {
      type T1e1-prbs-mode;
      description
        "PRBS test mode";
    }
    leaf sync-detected-counter {
      type uint64;
      description
        "Counter for sync event detection";
    }
    leaf bit-errors {
      type uint64;
      description
        "Counter for bit error detected";
    }
    leaf bit-recieved {
      type uint64;
      description
        "Counter for bit recieved";
    }
    leaf bit-error-sync {
      type uint64;
      description
        "Counter for bit error detected since sync";
    }
    leaf bit-recieved-sync {
      type uint64;
      description
        "Counter for bit recieved since sync";
    }
    leaf prbs-start-time-units {
      type uint64;
      units "second";
      description
        "Timeunits(in Seconds) since prbs started";
    }
    leaf prbs-last-sync-time-units {
      type uint64;
      units "second";
      description
        "Timeunits(In Seconds) since last-sync for this
         prbs test";
    }
  }

  grouping T1E1-CEM-STATS {
    description
      "E1 cem stats information";
    leaf ingress-pkts {
      type uint64;
      description
        "Ingress packets count";
    }
    leaf ingress-droped {
      type uint64;
      description
        "Ingress droped packets count";
    }
    leaf egress-pkts {
      type uint64;
      description
        "Egress packets count";
    }
    leaf egress-droped {
      type uint64;
      description
        "Egress droped packets count";
    }
    leaf input-errors {
      type uint64;
      description
        "Counter for errors in cem packet";
    }
    leaf out-put-errors {
      type uint64;
      description
        "Counter for errors in  cem packet";
    }
    leaf packet-missing {
      type uint64;
      description
        "Missing packets";
    }
    leaf pkts-reordered {
      type uint64;
      description
        "Reorder packets";
    }
    leaf misordered-droped {
      type uint64;
      description
        "Miss ordered dropped packets";
    }
    leaf jitter-buffer-underrun {
      type uint64;
      description
        "Counter for Jitter buffer underrun packets";
    }
    leaf malformed-packets {
      type uint64;
      description
        "Counter for malformed packets";
    }
    leaf jitter-buffer-overun {
      type uint64;
      description
        "Counter for jitter buffer over run packets";
    }
  }

  grouping T1E1-ROOT-ALARM-INFO {
    description
      "T1E1 Root Alarm Information";
    container los {
      description
        "Loss of signal";
      uses T1E1-ALARM-DETAIL;
    }
    container ais {
      description
        "Alarm indication signal";
      uses T1E1-ALARM-DETAIL;
    }
    container lof {
      description
        "Loss of frame";
      uses T1E1-ALARM-DETAIL;
    }
  }

  grouping T1E1-ALARM-DETAIL {
    description
      " T1E1 Alarm Detail";
    leaf is-detected {
      type boolean;
      description
        "Is defect detected?";
    }
    leaf counter {
      type uint64;
      description
        "Alarm counter";
    }
  }

  grouping T1E1-ALARM-INFO {
    description
      "T1E1 Alarm Information";
    container los {
      description
        "Loss of singnal";
      uses T1E1-ALARM-DETAIL;
    }
    container ais {
      description
        "Alarm indication signal";
      uses T1E1-ALARM-DETAIL;
    }
    container lof {
      description
        "Loss of frame";
      uses T1E1-ALARM-DETAIL;
    }
    container rai {
      description
        "Remote Alarm Indication";
      uses T1E1-ALARM-DETAIL;
    }
  }

  grouping T1E1-INFO {
    description
      "t1e1 transponder information";
    container t1e1-alarm-info {
      description
        "T1E1 Alarm Information";
      uses T1E1-ALARM-INFO;
    }
    container t1e1-root-alarm-info {
      description
        "T1E1 Root Alarm Information";
      uses T1E1-ROOT-ALARM-INFO;
    }
    container cem-stats {
      description
        "cem packets statatics";
      uses T1E1-CEM-STATS;
    }
    container prbs {
      description
        "pseudorandom binary sequence (PRBS) test results";
      uses T1E1-PRBS-INFO;
    }
    leaf transport-admin-state {
      type T1e1tas;
      description
        "Transport Admin State";
      xr:event-telemetry "Subscribe Telemetry Event";
    }
    leaf controller-state {
      type T1e1-controller-state;
      description
        "T1E1 controller state: Up, Down or
         Administratively Down";
      xr:event-telemetry "Subscribe Telemetry Event";
    }
    leaf linecoding {
      type Linecoding;
      description
        "Linecoding";
    }
    leaf loopback {
      type T1e1-ui-loopback;
      description
        "Loopback";
    }
    leaf frame-type {
      type T1e1-ui-frame;
      description
        "Frame Type";
    }
    leaf vlan-id {
      type uint16;
      description
        "Vlan ID";
    }
    leaf channel-id {
      type uint16;
      description
        "Channel ID";
    }
    leaf description {
      type string;
      description
        "Controller description string";
    }
    leaf clock-state {
      type T1e1-ui-clock-state;
      description
        "Current state of clock";
    }
    leaf clock-type {
      type T1e1-ui-clock;
      description
        "Configured Clock type (LINE,INTERNAL, ACR etc)";
    }
  }
}
