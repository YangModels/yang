module Cisco-IOS-XR-snmp-ifmib-oper {
  namespace "http://cisco.com/ns/yang/Cisco-IOS-XR-snmp-ifmib-oper";
  prefix snmp-ifmib-oper;

  import Cisco-IOS-XR-types {
    prefix xr;
  }
  import cisco-semver {
    prefix semver;
  }
  import Cisco-IOS-XR-snmp-agent-oper {
    prefix a1;
  }
  include Cisco-IOS-XR-snmp-ifmib-oper-sub1 {
    revision-date 2022-02-14;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR snmp-ifmib package operational data.
     
     This YANG module augments the
       Cisco-IOS-XR-snmp-agent-oper
     module with state data.
     
     Copyright (c) 2013-2022 by Cisco Systems, Inc.
     All rights reserved.";

  revision 2022-02-14 {
    description
      "Deprecated and unused hidden operational data removed.";
    semver:module-version "2.0.0";
  }
  revision 2019-04-05 {
    description
      "Establish semantic version baseline.";
    semver:module-version "1.0.1";
  }
  revision 2015-01-07 {
    description
      "IOS XR 5.3.1 revision.";
  }

  augment "/a1:snmp" {
    description
      "This augment extends the operational data of
       'Cisco-IOS-XR-snmp-agent-oper'";
    container interface-mib {
      description
        "SNMP IF-MIB information";
      container interfaces {
        description
          "Interfaces ifIndex information";
        list interface {
          key "interface-name";
          description
            "ifIndex for a specific Interface Name";
          leaf interface-name {
            type xr:Interface-name;
            description
              "Interface Name";
          }
          uses IFMIB-IFNAME-IFINDEX-ENTRY;
        }
      }
      container notification-interfaces {
        description
          "Interfaces Notification information";
        list notification-interface {
          key "interface-name";
          description
            "Notification for specific Interface Name";
          leaf interface-name {
            type xr:Interface-name;
            description
              "Interface Name";
          }
          uses IFMIB-NOTIF-STATUS-ENTRY;
        }
      }
    }
  }
}
