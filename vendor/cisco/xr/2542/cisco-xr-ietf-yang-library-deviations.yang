module cisco-xr-ietf-yang-library-deviations {

  /*** NAMESPACE / PREFIX DEFINITION ***/

  namespace "http://cisco.com/ns/yang/cisco-xr-ietf-yang-library-deviations";

  prefix "cisco-xr-ietf-yanglib-devs";

  /*** LINKAGE (IMPORTS / INCLUDES) ***/
  import ietf-yang-library { prefix yanglib; }

  /*** META INFORMATION ***/
  organization "Cisco Systems, Inc.";

  contact
    "Cisco Systems, Inc.
     Customer Service

     Postal: 170 West Tasman Drive
     San Jose, CA 95134

     Tel: +1 800 553-NETS

     E-mail: cs-yang@cisco.com";

  description 
    "This module contains a set of deviations of IETF YANG Library data
     model set for Cisco IOS-XR.

     Copyright (c) 2019-2025 by Cisco Systems, Inc., and/or its affiliates.
     All rights reserved.";

  revision "2025-02-10" {
    description
      "Remove type deviations for leaves:
       - /yanglib:yang-library/yanglib:module-set/yanglib:module/yanglib:name
       - /yanglib:yang-library/yanglib:module-set/yanglib:module/yanglib:submodule/yanglib:name
       - /yanglib:yang-library/yanglib:module-set/yanglib:module/yanglib:feature
       - /yanglib:yang-library/yanglib:module-set/yanglib:module/yanglib:deviation
       - /yanglib:yang-library/yanglib:schema/yanglib:module-set
       - /yanglib:yang-library/yanglib:datastore/yanglib:name
       - /yanglib:yang-library/yanglib:datastore/yanglib:schema";
  }

  revision "2024-07-24" {
    description
      "Migrate manual model edits to be represented as deviations";
  }

  revision "2019-10-21" {
    description
      "Initial revision applicable to IOS-XR 7.2.1 and older releases";
  }

  /*
   * If in the future this deviations file only contains RPC or notification
   * nodes, it will stop appearing in Yang Library or capabilities/hello
   * output.
   * See CSCwn84289 for more details. This comment can be removed once the
   * issue is resolved.
   */

  deviation /yanglib:modules-state {
    deviate not-supported;
  }

  deviation /yanglib:yang-library-update {
    deviate not-supported;
  }

  deviation /yanglib:yang-library-change {
    deviate not-supported;
  }

  deviation /yanglib:yang-library/yanglib:module-set/yanglib:module/yanglib:location {
    deviate not-supported;
  }

  deviation /yanglib:yang-library/yanglib:module-set/yanglib:module/yanglib:submodule/yanglib:location {
    deviate not-supported;
  }

  deviation /yanglib:yang-library/yanglib:module-set/yanglib:import-only-module {
    deviate not-supported;
  }
}
