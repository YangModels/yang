submodule Cisco-IOS-XR-drivers-media-eth-oper-sub1 {
  belongs-to Cisco-IOS-XR-drivers-media-eth-oper {
    prefix Cisco-IOS-XR-drivers-media-eth-oper;
  }

  import ietf-yang-types {
    prefix yang;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR drivers-media-eth package operational data.
     
     Copyright (c) 2013-2025 by Cisco Systems, Inc.
     All rights reserved.";

  revision 2025-09-25 {
    description
      "Addition of swizzle token to PRBS parameters
       2025-05-06
         Added new Ethernet media type definition for 4x100G CU and 100G CR2 optics
       2025-05-02
         Added Coherent CFP2 DCO optics
       2025-04-21
         Added new media type definition for QSFP28 ZR pluto optics
       2025-04-01
         Updated serdes holdoff max time field
       2025-03-11
         Added ETHERNET_25G_50GBASE_SL
       2025-01-25
         added serdes holdoff time field
       2024-10-28
         Removed state transition count field
       2024-10-14
         Added ETHERNET_100GBASE_BX20_BD
       2024-10-11
         Added state transition count and link flap fields
       2024-08-06
         Added new media type definination for 25G/50G LR-S optics
       2024-07-19
         Added additional PRBS support parameters
       2024-05-31
         Added ETHERNET_100GBASE_BX40_BD
       2024-03-01
         Added support for SFP-50G-ER-I, SFP-50G-BX40U, SFP-50G-BX40D
       2024-01-23
         Added support for Pre FEC and Post FEC BER
       2023-12-13
         Added new Ethernet media type definition for QSFP-DD 400G SR4-BD
       2023-11-16
         Add pfc_statistics and pfc_watchdog_statistics
       2023-11-07
         Addition of Base-R fec type
       2023-08-24
         Added new pfc type definition
       2022-12-20
         Added new Ethernet media type definition
       2022-12-02
         Added new Ethernet media type definition for 100GE SR_1.2 optics
       2022-10-15
         Added new Ethernet media type definition for 400G Bright ZRP
       2022-09-10
         Added new Ethernet media type definition for 2x400G LR4 optics
       2022-08-26
         Added new Ethernet media type definition for 100GE ZR optics
       2022-08-10
         Added new Ethernet media type definition for SFP 10/25G BXD-I, BXU-I optics
       2022-06-08
         Added new Ethernet media type definition for 1G LH optics
       2022-05-10
         Added new Ethernet media type definition for Credo 800G AEC
       2022-04-25
         Added new Ethernet media type definition for 100GE ZR4S optics
       2022-04-22
         Start timestamp and validity support added for ethernet ports.
       2022-04-22
         Added new Ethernet media type definition for 8x100G FR
       2022-03-14
         Updated media type string
       2022-03-07
         Added new Ethernet media type definition for SFP 25G SL
       2021-11-19
         Added new Ethernet media type definition for 24GE ER-I optics
       2021-11-04
         Enums added for new module 800G Passive Loopback
       2021-10-07
         Enums added for new module 2x400G FR4 and 8x100G DR.
       2021-09-30
         Added new Ethernet media type definition.";
    semver:module-version "3.0.0";
  }
  revision 2021-09-29 {
    description
      "Removed list rx_drop_data_frames_per_tc and added leaf total_rx_drop_data_frames.
       2021-08-24
          Support added for last data time for generic stats.
       2021-08-16
          Added new Ethernet media type definition.
       2021-07-19
          Removed leaf total_rx_drop_data_frames and added list rx_drop_data_frames_per_tc to maintain backward compatibility.
       2021-07-01
          Support added for hardware timestamp for generic stats.";
    semver:module-version "2.1.0";
  }
  revision 2021-02-12 {
    description
      "Added support for PFC per TC Rx drop Data Frames.
       2020-11-04
           Added support for SER alarms.
       2020-09-08
           Added new ethernet speed values.";
    semver:module-version "2.0.0";
  }
  revision 2020-02-19 {
    description
      "Description updated.
       2019-11-27
         Adding operational value for power m-factor.
       2019-08-15
         Adding PFC watchdog support.";
    semver:module-version "1.2.0";
  }
  revision 2019-05-21 {
    description
      "Added new leaf for frame preemption configuration.";
    semver:module-version "1.1.0";
  }
  revision 2019-04-05 {
    description
      "Establish semantic version baseline.";
    semver:module-version "1.0.0";
  }
  revision 2017-05-01 {
    description
      "Fixing backward compatibility error in module.";
  }
  revision 2017-04-04 {
    description
      "Added new fields to phy data.";
  }
  revision 2015-01-07 {
    description
      "IOS XR 5.3.1 revision.";
  }

  typedef Ethernet-dev-if {
    type enumeration {
      enum "no-interface" {
        description
          "no interface";
      }
      enum "xgmii" {
        description
          "xgmii";
      }
      enum "xaui" {
        description
          "xaui";
      }
      enum "ethernet-num-dev-if" {
        description
          "ethernet num dev if";
      }
    }
    description
      "Ethernet dev if";
  }

  typedef Ethernet-dev {
    type enumeration {
      enum "no-device" {
        description
          "no device";
      }
      enum "pma-pmd" {
        description
          "pma pmd";
      }
      enum "wis" {
        description
          "wis";
      }
      enum "pcs" {
        description
          "pcs";
      }
      enum "phy-xs" {
        description
          "phy xs";
      }
      enum "dte-xs" {
        description
          "dte xs";
      }
      enum "ethernet-num-dev" {
        description
          "ethernet num dev";
      }
    }
    description
      "Ethernet dev";
  }

  typedef Ethernet-bert-pattern {
    type enumeration {
      enum "no-test-pattern" {
        description
          "no test pattern";
      }
      enum "high-frequency" {
        description
          "high frequency";
      }
      enum "low-frequency" {
        description
          "low frequency";
      }
      enum "mixed-frequency" {
        description
          "mixed frequency";
      }
      enum "continuous-random" {
        description
          "continuous random";
      }
      enum "continuous-jitter" {
        description
          "continuous jitter";
      }
      enum "long-continuous-random" {
        description
          "long continuous random";
      }
      enum "short-continuous-random" {
        description
          "short continuous random";
      }
      enum "pseudorandom-seed-a" {
        description
          "pseudorandom seed a";
      }
      enum "pseudorandom-seed-b" {
        description
          "pseudorandom seed b";
      }
      enum "prbs31" {
        description
          "prbs31";
      }
      enum "square-wave" {
        description
          "square wave";
      }
      enum "pseudorandom" {
        description
          "pseudorandom";
      }
      enum "ethernet-bert-pattern-types" {
        description
          "ethernet bert pattern types";
      }
    }
    description
      "Ethernet test patterns (IEEE spec 36A/48A)";
  }

  typedef Ethernet-bert-err-cnt {
    type enumeration {
      enum "no-count-type" {
        description
          "no count type";
      }
      enum "bit-error-count" {
        description
          "bit error count";
      }
      enum "frame-error-count" {
        description
          "frame error count";
      }
      enum "block-error-count" {
        description
          "block error count";
      }
      enum "ethernet-bert-err-cnt-types" {
        description
          "ethernet bert err cnt types";
      }
    }
    description
      "Ethernet bert err cnt";
  }

  typedef Ethernet-bert-mask {
    type uint32;
    description
      "Ethernet bert mask";
  }

  typedef Ether-prbs-status {
    type enumeration {
      enum "prbs-status-not-running" {
        description
          "PRBS Status Not running";
      }
      enum "prbs-status-unlocked" {
        description
          "PRBS Status unlocked";
      }
      enum "prbs-status-locked" {
        description
          "PRBS Status locked";
      }
      enum "prbs-status-not-available" {
        description
          "PRBS Status not available";
      }
    }
    description
      "Ether prbs status";
  }

  typedef Ether-prbs-swizzle {
    type enumeration {
      enum "prbs-swizzle-enabled" {
        description
          "PRBS Swizzle enabled";
      }
      enum "prbs-swizzle-disabled" {
        description
          "PRBS Swizzle disabled";
      }
    }
    description
      "Ether prbs swizzle";
  }

  typedef Ether-prbs-framing {
    type enumeration {
      enum "prbs-framing-not-configured" {
        description
          "PRBS Framing not configured";
      }
      enum "prbs-framing-unframed" {
        description
          "PRBS Unframed mode";
      }
      enum "prbs-framing-framed" {
        description
          "PRBS framed mode";
      }
    }
    description
      "Ether prbs framing";
  }

  typedef Ether-prbs-error-inject {
    type enumeration {
      enum "prbs-error-inject-none" {
        description
          "PRBS Error inject none";
      }
      enum "prbs-error-inject-single" {
        description
          "PRBS Error inject single";
      }
      enum "prbs-error-inject-continuous" {
        description
          "PRBS Error inject continuous";
      }
    }
    description
      "Ether prbs error inject";
  }

  typedef Ether-prbs-direction {
    type enumeration {
      enum "prbs-direction-not-configured" {
        description
          "PRBS Direction not configured";
      }
      enum "prbs-direction-line" {
        description
          "PRBS Direction towards line side";
      }
      enum "prbs-direction-system" {
        description
          "PRBS Direction towards system side";
      }
    }
    description
      "Ether prbs direction";
  }

  typedef Ether-prbs-pattern {
    type enumeration {
      enum "prbs-pattern-none" {
        description
          "PRBS Pattern None";
      }
      enum "prbs-pattern-pn7" {
        description
          "PRBS Polynomial pattern PN7";
      }
      enum "prbs-pattern-pn9" {
        description
          "PRBS Polynomial pattern PN9";
      }
      enum "prbs-pattern-pn11" {
        description
          "PRBS Polynomial pattern PN11";
      }
      enum "prbs-pattern-pn15" {
        description
          "PRBS Polynomial pattern PN15";
      }
      enum "prbs-pattern-pn23" {
        description
          "PRBS Polynomial pattern PN23";
      }
      enum "prbs-pattern-pn31" {
        description
          "PRBS Polynomial pattern PN31";
      }
      enum "prbs-pattern-user-defined" {
        description
          "PRBS user defined pattern";
      }
    }
    description
      "Ether prbs pattern";
  }

  typedef Ether-prbs-mode {
    type enumeration {
      enum "prbs-mode-none" {
        description
          "PRBS Mode none";
      }
      enum "prbs-mode-source" {
        description
          "PRBS Mode source";
      }
      enum "prbs-mode-sink" {
        description
          "PRBS Mode sink";
      }
      enum "prbs-mode-source-sink" {
        description
          "PRBS Mode source-sink";
      }
    }
    description
      "Ether prbs mode";
  }

  typedef Ether-ains-status {
    type enumeration {
      enum "ains-soak-status-none" {
        description
          "AINS Soak timer not running";
      }
      enum "ains-soak-status-pending" {
        description
          "AINS Soak timer pending";
      }
      enum "ains-soak-status-running" {
        description
          "AINS Soak timer running";
      }
    }
    description
      "Ether ains status";
  }

  typedef Mac-addr {
    type yang:mac-address;
    description
      "Mac addr";
  }

  typedef Ether-pfc-wd {
    type enumeration {
      enum "ether-pfc-wd-not-cfg" {
        description
          "Not Configured";
      }
      enum "off" {
        description
          "No priority flow control watchdog (disabled)";
      }
      enum "on" {
        description
          "Priority flow control watchdog enabled";
      }
    }
    description
      "Priority flowcontrol watchdog type";
  }

  typedef Ether-pfc {
    type enumeration {
      enum "no-pfc" {
        description
          "No priority flow control (disabled)";
      }
      enum "on" {
        description
          "Priority flow control enabled";
      }
    }
    description
      "Priority flowcontrol type";
  }

  typedef Eth-ctrlr-alarm-state {
    type enumeration {
      enum "alarm-not-supported" {
        value 0;
        description
          "Not supported on this interface";
      }
      enum "alarm-set" {
        value 1;
        description
          "Alarm set";
      }
      enum "alarm-not-set" {
        value 2;
        description
          "Alarm not set";
      }
    }
    description
      "Ethernet alarm state";
  }

  typedef Ethernet-ipg {
    type enumeration {
      enum "standard" {
        description
          "IEEE standard value of 12";
      }
      enum "non-standard" {
        description
          "Non-standard value of 16";
      }
    }
    description
      "Inter packet gap";
  }

  typedef Ether-flowcontrol {
    type enumeration {
      enum "no-flowcontrol" {
        description
          "No flow control (disabled)";
      }
      enum "egress" {
        description
          "Traffic egress (pause frames ingress)";
      }
      enum "ingress" {
        description
          "Traffic ingress (pause frames egress)";
      }
      enum "bidirectional" {
        description
          "On both ingress and egress";
      }
    }
    description
      "Flowcontrol type";
  }

  typedef Ethernet-duplex {
    type enumeration {
      enum "ethernet-duplex-invalid" {
        description
          "ethernet duplex invalid";
      }
      enum "half-duplex" {
        description
          "half duplex";
      }
      enum "full-duplex" {
        description
          "full duplex";
      }
    }
    description
      "Duplexity";
  }

  typedef Ethernet-speed {
    type enumeration {
      enum "ethernet-speed-invalid" {
        value 0;
        description
          "ethernet speed invalid";
      }
      enum "ten-mbps" {
        value 1;
        description
          "ten mbps";
      }
      enum "hundred-mbps" {
        value 2;
        description
          "hundred mbps";
      }
      enum "one-gbps" {
        value 3;
        description
          "one gbps";
      }
      enum "ten-gbps" {
        value 4;
        description
          "ten gbps";
      }
      enum "twenty-five-gbps" {
        value 5;
        description
          "twenty five gbps";
      }
      enum "forty-gbps" {
        value 6;
        description
          "forty gbps";
      }
      enum "fifty-gbps" {
        value 7;
        description
          "fifty gbps";
      }
      enum "hundred-gbps" {
        value 8;
        description
          "hundred gbps";
      }
      enum "two-hundred-gbps" {
        value 9;
        description
          "two hundred gbps";
      }
      enum "four-hundred-gbps" {
        value 10;
        description
          "four hundred gbps";
      }
      enum "six-hundred-gbps" {
        value 11;
        description
          "six hundred gbps";
      }
      enum "eight-hundred-gbps" {
        value 12;
        description
          "eight hundred gbps";
      }
      enum "ethernet-speed-types-count" {
        value 13;
        description
          "ethernet speed types count";
      }
    }
    description
      "Speed";
  }

  typedef Ether-autoneg-mask {
    type uint32;
    description
      "Ether autoneg mask";
  }

  typedef Ether-led-state {
    type enumeration {
      enum "led-state-unknown" {
        description
          "LED state is unknown";
      }
      enum "led-off" {
        description
          "LED is off";
      }
      enum "green-on" {
        description
          "LED is green";
      }
      enum "green-flashing" {
        description
          "LED is flashing green";
      }
      enum "yellow-on" {
        description
          "LED is yellow";
      }
      enum "yellow-flashing" {
        description
          "LED is flashing yellow";
      }
      enum "red-on" {
        description
          "LED is red";
      }
      enum "red-flashing" {
        description
          "LED is flashing red";
      }
      enum "na" {
        description
          "LED is Not Applicable";
      }
    }
    description
      "Ether led state";
  }

  typedef Ether-link-state {
    type enumeration {
      enum "state-undefined" {
        description
          "State undefined";
      }
      enum "unknown-state" {
        description
          "Initializing, true state not yet known";
      }
      enum "available" {
        description
          "Link or light normal, loopback normal";
      }
      enum "not-available" {
        description
          "Link loss or low light, no loopback";
      }
      enum "remote-fault" {
        description
          "Remote fault with no detail";
      }
      enum "invalid-signal" {
        description
          "Invalid signal, applies only to 10BASE-FB";
      }
      enum "remote-jabber" {
        description
          "Remote fault, reason known to be jabber";
      }
      enum "link-loss" {
        description
          "Remote fault, reason known to be far-end link
           loss";
      }
      enum "remote-test" {
        description
          "Remote fault, reason known to be test";
      }
      enum "offline" {
        description
          "Offline (applies to auto-negotiation)";
      }
      enum "auto-neg-error" {
        description
          "Auto-Negotiation Error";
      }
      enum "pmd-link-fault" {
        description
          "PMD/PMA receive link fault";
      }
      enum "frame-loss" {
        description
          "WIS loss of frames";
      }
      enum "signal-loss" {
        description
          "WIS loss of signal";
      }
      enum "link-fault" {
        description
          "PCS receive link fault";
      }
      enum "excessive-ber" {
        description
          "PCS Bit Error Rate monitor reporting excessive
           error rate";
      }
      enum "dxs-link-fault" {
        description
          "DTE XGXS receive link fault";
      }
      enum "pxs-link-fault" {
        description
          "PHY XGXS transmit link fault";
      }
      enum "security" {
        description
          "Security failure (not a valid part)";
      }
      enum "phy-not-present" {
        description
          "The optics for the port are not present";
      }
      enum "no-optic-license" {
        description
          "License error (No advanced optical license)";
      }
      enum "unsupported-module" {
        description
          "Module is not supported";
      }
      enum "dwdm-laser-shut" {
        description
          "DWDM Laser shutdown";
      }
      enum "wanphy-laser-shut" {
        description
          "WANPHY Laser shutdown";
      }
      enum "incompatible-config" {
        description
          "Incompatible configuration";
      }
      enum "system-error" {
        description
          "System error";
      }
      enum "wan-framing-error" {
        description
          "WAN Framing Error";
      }
      enum "otn-framing-error" {
        description
          "OTN Framing Error";
      }
      enum "shutdown" {
        description
          "Link is shutdown";
      }
    }
    description
      "Ethernet link state: IEEE 802.3/802.3ae clause 30
       .5.1.1.4";
  }

  typedef Ethernet-fec {
    type enumeration {
      enum "not-configured" {
        description
          "FEC not configured";
      }
      enum "standard" {
        description
          "Reed-Solomon encoding";
      }
      enum "disabled" {
        description
          "FEC explicitly disabled";
      }
      enum "base-r" {
        description
          "BASE-R encoding";
      }
    }
    description
      "FEC type";
  }

  typedef Ethernet-loopback {
    type enumeration {
      enum "no-loopback" {
        description
          "Disabled";
      }
      enum "internal" {
        description
          "Loopback in the framer";
      }
      enum "line" {
        description
          "Loops peer's packets back to them";
      }
      enum "external" {
        description
          "tx externally connected to rx";
      }
    }
    description
      "Loopback type";
  }

  typedef Ether-dom-alarm {
    type enumeration {
      enum "no-information" {
        description
          "DOM Alarm information is not available";
      }
      enum "alarm-high" {
        description
          "Alarm high";
      }
      enum "warning-high" {
        description
          "Warning high";
      }
      enum "normal" {
        description
          "Within normal parameters";
      }
      enum "warning-low" {
        description
          "Warning low";
      }
      enum "alarm-low" {
        description
          "Alarm low";
      }
    }
    description
      "Ether dom alarm";
  }

  typedef Ether-phy-present {
    type enumeration {
      enum "phy-not-present" {
        description
          "No PHY present";
      }
      enum "phy-present" {
        description
          "PHY is present";
      }
      enum "no-information" {
        description
          "State is unknown";
      }
    }
    description
      "Ether phy present";
  }

  typedef Ethernet-media {
    type enumeration {
      enum "ethernet-other" {
        description
          "IEEE 802.3/802.3ae clause 30.2.5";
      }
      enum "ethernet-unknown" {
        description
          "Initializing, true state or type not yet known";
      }
      enum "ethernet-aui" {
        description
          "No internal MAU, view from AUI";
      }
      enum "ethernet-10base5" {
        description
          "Thick coax MAU";
      }
      enum "ethernet-foirl" {
        description
          "FOIRL MAU as specified in 9.9";
      }
      enum "ethernet-10base2" {
        description
          "Thin coax MAU";
      }
      enum "ethernet-10broad36" {
        description
          "Broadband DTE MAU";
      }
      enum "ethernet-10base" {
        description
          "UTP MAU, duplexity unknown";
      }
      enum "ethernet-10base-thd" {
        description
          "UTP MAU, half duplex";
      }
      enum "ethernet-10base-tfd" {
        description
          "UTP MAU, full duplex";
      }
      enum "ethernet-10base-fp" {
        description
          "Passive fiber MAU";
      }
      enum "ethernet-10base-fb" {
        description
          "Synchronous fiber MAU";
      }
      enum "ethernet-10base-fl" {
        description
          "Asynchronous fiber MAU, duplexity unknown";
      }
      enum "ethernet-10base-flhd" {
        description
          "Asynchronous fiber MAU, half duplex";
      }
      enum "ethernet-10base-flfd" {
        description
          "Asynchronous fiber MAU, full duplex";
      }
      enum "ethernet-100base-t4" {
        description
          "Four-pair Category 3 UTP";
      }
      enum "ethernet-100base-tx" {
        description
          "Two-pair Category 5 UTP, duplexity unknown";
      }
      enum "ethernet-100base-txhd" {
        description
          "Two-pair Category 5 UTP, half duplex";
      }
      enum "ethernet-100base-txfd" {
        description
          "Two-pair Category 5 UTP, full duplex";
      }
      enum "ethernet-100base-fx" {
        description
          "X fiber over PMD, duplexity unknown";
      }
      enum "ethernet-100base-fxhd" {
        description
          "X fiber over PMD, half duplex";
      }
      enum "ethernet-100base-fxfd" {
        description
          "X fiber over PMD, full duplex";
      }
      enum "ethernet-100base-ex" {
        description
          "X fiber over PMD (40km), duplexity unknown";
      }
      enum "ethernet-100base-exhd" {
        description
          "X fiber over PMD (40km), half duplex";
      }
      enum "ethernet-100base-exfd" {
        description
          "X fiber over PMD (40km), full duplex";
      }
      enum "ethernet-100base-t2" {
        description
          "Two-pair Category 3 UTP, duplexity unknown";
      }
      enum "ethernet-100base-t2hd" {
        description
          "Two-pair Category 3 UTP, half duplex";
      }
      enum "ethernet-100base-t2fd" {
        description
          "Two-pair Category 3 UTP, full duplex";
      }
      enum "ethernet-1000base-x" {
        description
          "X PCS/PMA, duplexity unknown";
      }
      enum "ethernet-1000base-xhd" {
        description
          "X 1000BASE-XHDX PCS/PMA, half duplex";
      }
      enum "ethernet-1000base-xfd" {
        description
          "X PCS/PMA, full duplex";
      }
      enum "ethernet-1000base-lx" {
        description
          "X fiber over long-wl laser PMD, duplexity
           unknown";
      }
      enum "ethernet-1000base-lxhd" {
        description
          "X fiber over long-wl laser PMD, half duplex";
      }
      enum "ethernet-1000base-lxfd" {
        description
          "X fiber over long-wl laser PMD, full duplex";
      }
      enum "ethernet-1000base-sx" {
        description
          "X fiber over short-wl laser PMD, duplexity
           unknown";
      }
      enum "ethernet-1000base-sxhd" {
        description
          "X fiber over short-wl laser PMD, half duplex";
      }
      enum "ethernet-1000base-sxfd" {
        description
          "X fiber over short-wl laser PMD, full duplex";
      }
      enum "ethernet-1000base-cx" {
        description
          "X copper over 150-Ohm balanced PMD, duplexity
           unknown";
      }
      enum "ethernet-1000base-cxhd" {
        description
          "X copper over 150-Ohm balancedPMD, half duplex";
      }
      enum "ethernet-1000base-cxfd" {
        description
          "X copper over 150-Ohm balancedPMD, full duplex";
      }
      enum "ethernet-1000base" {
        description
          "Four-pair Category 5 UTP PHY, duplexity unknown";
      }
      enum "ethernet-1000base-thd" {
        description
          "Four-pair Category 5 UTP PHY, half duplex";
      }
      enum "ethernet-1000base-tfd" {
        description
          "Four-pair Category 5 UTP PHY, full duplex";
      }
      enum "ethernet-10gbase-x" {
        description
          "X PCS/PMA ";
      }
      enum "ethernet-10gbase-lx4" {
        description
          "X fiber over 4 lane 1310nm optics";
      }
      enum "ethernet-10gbase-r" {
        description
          "R PCS/PMA";
      }
      enum "ethernet-10gbase-er" {
        description
          "R fiber over 1550nm optics";
      }
      enum "ethernet-10gbase-lr" {
        description
          "R fiber over 1310nm optics";
      }
      enum "ethernet-10gbase-sr" {
        description
          "R fiber over 850nm optics";
      }
      enum "ethernet-10gbase-csr" {
        description
          "R fiber over 850nm optics";
      }
      enum "ethernet-10gbase-w" {
        description
          "W PCS/PMA";
      }
      enum "ethernet-10gbase-ew" {
        description
          "W fiber over 1550nm optics";
      }
      enum "ethernet-10gbase-lw" {
        description
          "W fiber over 1310nm optics";
      }
      enum "ethernet-10gbase-sw" {
        description
          "W fiber over 850nm optics";
      }
      enum "ethernet-1000base-zx" {
        description
          "Single-mode fiber over 1550nm optics (Cisco)";
      }
      enum "ethernet-1000base-cwdm" {
        description
          "CWDM with unknown wavelength optics";
      }
      enum "ethernet-1000base-cwdm-1470" {
        description
          "CWDM with 1470nm optics";
      }
      enum "ethernet-1000base-cwdm-1490" {
        description
          "CWDM with 1490nm optics";
      }
      enum "ethernet-1000base-cwdm-1510" {
        description
          "CWDM with 1510nm optics";
      }
      enum "ethernet-1000base-cwdm-1530" {
        description
          "CWDM with 1530nm optics";
      }
      enum "ethernet-1000base-cwdm-1550" {
        description
          "CWDM with 1550nm optics";
      }
      enum "ethernet-1000base-cwdm-1570" {
        description
          "CWDM with 1570nm optics";
      }
      enum "ethernet-1000base-cwdm-1590" {
        description
          "CWDM with 1590nm optics";
      }
      enum "ethernet-1000base-cwdm-1610" {
        description
          "CWDM with 1610nm optics";
      }
      enum "ethernet-10gbase-zr" {
        description
          "Cisco-defined, over 1550nm optics";
      }
      enum "ethernet-10gbase-dwdm" {
        description
          "DWDM optics";
      }
      enum "ethernet-100gbase-lr4" {
        description
          "fiber over 4 lane optics (long reach)";
      }
      enum "ethernet-1000base-dwdm" {
        description
          "DWDM optics";
      }
      enum "ethernet-1000base-dwdm-1533" {
        description
          "DWDM with 1533nm optics";
      }
      enum "ethernet-1000base-dwdm-1537" {
        description
          "DWDM with 1537nm optics";
      }
      enum "ethernet-1000base-dwdm-1541" {
        description
          "DWDM with 1541nm optics";
      }
      enum "ethernet-1000base-dwdm-1545" {
        description
          "DWDM with 1545nm optics";
      }
      enum "ethernet-1000base-dwdm-1549" {
        description
          "DWDM with 1549nm optics";
      }
      enum "ethernet-1000base-dwdm-1553" {
        description
          "DWDM with 1553nm optics";
      }
      enum "ethernet-1000base-dwdm-1557" {
        description
          "DWDM with 1557nm optics";
      }
      enum "ethernet-1000base-dwdm-1561" {
        description
          "DWDM with 1561nm optics";
      }
      enum "ethernet-40gbase-lr4" {
        description
          "fiber over 4 lane optics (long reach)";
      }
      enum "ethernet-40gbase-er4" {
        description
          "fiber over 4 lane optics (extended reach)";
      }
      enum "ethernet-100gbase-er4" {
        description
          "fiber over 4 lane optics (extended reach)";
      }
      enum "ethernet-1000base-ex" {
        description
          "X fiber over 1310nm optics";
      }
      enum "ethernet-1000base-bx10-d" {
        description
          "X fiber (D, 10km)";
      }
      enum "ethernet-1000base-bx10-u" {
        description
          "X fiber (U, 10km)";
      }
      enum "ethernet-1000base-dwdm-1561-42" {
        description
          "DWDM with 1561.42nm optics";
      }
      enum "ethernet-1000base-dwdm-1560-61" {
        description
          "DWDM with 1560.61nm optics";
      }
      enum "ethernet-1000base-dwdm-1559-79" {
        description
          "DWDM with 1559.79nm optics";
      }
      enum "ethernet-1000base-dwdm-1558-98" {
        description
          "DWDM with 1558.98nm optics";
      }
      enum "ethernet-1000base-dwdm-1558-17" {
        description
          "DWDM with 1558.17nm optics";
      }
      enum "ethernet-1000base-dwdm-1557-36" {
        description
          "DWDM with 1557.36nm optics";
      }
      enum "ethernet-1000base-dwdm-1556-55" {
        description
          "DWDM with 1556.55nm optics";
      }
      enum "ethernet-1000base-dwdm-1555-75" {
        description
          "DWDM with 1555.75nm optics";
      }
      enum "ethernet-1000base-dwdm-1554-94" {
        description
          "DWDM with 1554.94nm optics";
      }
      enum "ethernet-1000base-dwdm-1554-13" {
        description
          "DWDM with 1554.13nm optics";
      }
      enum "ethernet-1000base-dwdm-1553-33" {
        description
          "DWDM with 1553.33nm optics";
      }
      enum "ethernet-1000base-dwdm-1552-52" {
        description
          "DWDM with 1552.52nm optics";
      }
      enum "ethernet-1000base-dwdm-1551-72" {
        description
          "DWDM with 1551.72nm optics";
      }
      enum "ethernet-1000base-dwdm-1550-92" {
        description
          "DWDM with 1550.92nm optics";
      }
      enum "ethernet-1000base-dwdm-1550-12" {
        description
          "DWDM with 1550.12nm optics";
      }
      enum "ethernet-1000base-dwdm-1549-32" {
        description
          "DWDM with 1549.32nm optics";
      }
      enum "ethernet-1000base-dwdm-1548-51" {
        description
          "DWDM with 1548.51nm optics";
      }
      enum "ethernet-1000base-dwdm-1547-72" {
        description
          "DWDM with 1547.72nm optics";
      }
      enum "ethernet-1000base-dwdm-1546-92" {
        description
          "DWDM with 1546.92nm optics";
      }
      enum "ethernet-1000base-dwdm-1546-12" {
        description
          "DWDM with 1546.12nm optics";
      }
      enum "ethernet-1000base-dwdm-1545-32" {
        description
          "DWDM with 1545.32nm optics";
      }
      enum "ethernet-1000base-dwdm-1544-53" {
        description
          "DWDM with 1544.53nm optics";
      }
      enum "ethernet-1000base-dwdm-1543-73" {
        description
          "DWDM with 1543.73nm optics";
      }
      enum "ethernet-1000base-dwdm-1542-94" {
        description
          "DWDM with 1542.94nm optics";
      }
      enum "ethernet-1000base-dwdm-1542-14" {
        description
          "DWDM with 1542.14nm optics";
      }
      enum "ethernet-1000base-dwdm-1541-35" {
        description
          "DWDM with 1541.35nm optics";
      }
      enum "ethernet-1000base-dwdm-1540-56" {
        description
          "DWDM with 1540.56nm optics";
      }
      enum "ethernet-1000base-dwdm-1539-77" {
        description
          "DWDM with 1539.77nm optics";
      }
      enum "ethernet-1000base-dwdm-1538-98" {
        description
          "DWDM with 1538.98nm optics";
      }
      enum "ethernet-1000base-dwdm-1538-19" {
        description
          "DWDM with 1538.19nm optics";
      }
      enum "ethernet-1000base-dwdm-1537-40" {
        description
          "DWDM with 1537.40nm optics";
      }
      enum "ethernet-1000base-dwdm-1536-61" {
        description
          "DWDM with 1536.61nm optics";
      }
      enum "ethernet-1000base-dwdm-1535-82" {
        description
          "DWDM with 1535.82nm optics";
      }
      enum "ethernet-1000base-dwdm-1535-04" {
        description
          "DWDM with 1535.04nm optics";
      }
      enum "ethernet-1000base-dwdm-1534-25" {
        description
          "DWDM with 1534.25nm optics";
      }
      enum "ethernet-1000base-dwdm-1533-47" {
        description
          "DWDM with 1533.47nm optics";
      }
      enum "ethernet-1000base-dwdm-1532-68" {
        description
          "DWDM with 1532.68nm optics";
      }
      enum "ethernet-1000base-dwdm-1531-90" {
        description
          "DWDM with 1531.90nm optics";
      }
      enum "ethernet-1000base-dwdm-1531-12" {
        description
          "DWDM with 1531.12nm optics";
      }
      enum "ethernet-1000base-dwdm-1530-33" {
        description
          "DWDM with 1530.33nm optics";
      }
      enum "ethernet-1000base-dwdm-tunable" {
        description
          "DWDM with tunable optics";
      }
      enum "ethernet-10gbase-dwdm-1561-42" {
        description
          "DWDM with 1561.42nm optics";
      }
      enum "ethernet-10gbase-dwdm-1560-61" {
        description
          "DWDM with 1560.61nm optics";
      }
      enum "ethernet-10gbase-dwdm-1559-79" {
        description
          "DWDM with 1559.79nm optics";
      }
      enum "ethernet-10gbase-dwdm-1558-98" {
        description
          "DWDM with 1558.98nm optics";
      }
      enum "ethernet-10gbase-dwdm-1558-17" {
        description
          "DWDM with 1558.17nm optics";
      }
      enum "ethernet-10gbase-dwdm-1557-36" {
        description
          "DWDM with 1557.36nm optics";
      }
      enum "ethernet-10gbase-dwdm-1556-55" {
        description
          "DWDM with 1556.55nm optics";
      }
      enum "ethernet-10gbase-dwdm-1555-75" {
        description
          "DWDM with 1555.75nm optics";
      }
      enum "ethernet-10gbase-dwdm-1554-94" {
        description
          "DWDM with 1554.94nm optics";
      }
      enum "ethernet-10gbase-dwdm-1554-13" {
        description
          "DWDM with 1554.13nm optics";
      }
      enum "ethernet-10gbase-dwdm-1553-33" {
        description
          "DWDM with 1553.33nm optics";
      }
      enum "ethernet-10gbase-dwdm-1552-52" {
        description
          "DWDM with 1552.52nm optics";
      }
      enum "ethernet-10gbase-dwdm-1551-72" {
        description
          "DWDM with 1551.72nm optics";
      }
      enum "ethernet-10gbase-dwdm-1550-92" {
        description
          "DWDM with 1550.92nm optics";
      }
      enum "ethernet-10gbase-dwdm-1550-12" {
        description
          "DWDM with 1550.12nm optics";
      }
      enum "ethernet-10gbase-dwdm-1549-32" {
        description
          "DWDM with 1549.32nm optics";
      }
      enum "ethernet-10gbase-dwdm-1548-51" {
        description
          "DWDM with 1548.51nm optics";
      }
      enum "ethernet-10gbase-dwdm-1547-72" {
        description
          "DWDM with 1547.72nm optics";
      }
      enum "ethernet-10gbase-dwdm-1546-92" {
        description
          "DWDM with 1546.92nm optics";
      }
      enum "ethernet-10gbase-dwdm-1546-12" {
        description
          "DWDM with 1546.12nm optics";
      }
      enum "ethernet-10gbase-dwdm-1545-32" {
        description
          "DWDM with 1545.32nm optics";
      }
      enum "ethernet-10gbase-dwdm-1544-53" {
        description
          "DWDM with 1544.53nm optics";
      }
      enum "ethernet-10gbase-dwdm-1543-73" {
        description
          "DWDM with 1543.73nm optics";
      }
      enum "ethernet-10gbase-dwdm-1542-94" {
        description
          "DWDM with 1542.94nm optics";
      }
      enum "ethernet-10gbase-dwdm-1542-14" {
        description
          "DWDM with 1542.14nm optics";
      }
      enum "ethernet-10gbase-dwdm-1541-35" {
        description
          "DWDM with 1541.35nm optics";
      }
      enum "ethernet-10gbase-dwdm-1540-56" {
        description
          "DWDM with 1540.56nm optics";
      }
      enum "ethernet-10gbase-dwdm-1539-77" {
        description
          "DWDM with 1539.77nm optics";
      }
      enum "ethernet-10gbase-dwdm-1538-98" {
        description
          "DWDM with 1538.98nm optics";
      }
      enum "ethernet-10gbase-dwdm-1538-19" {
        description
          "DWDM with 1538.19nm optics";
      }
      enum "ethernet-10gbase-dwdm-1537-40" {
        description
          "DWDM with 1537.40nm optics";
      }
      enum "ethernet-10gbase-dwdm-1536-61" {
        description
          "DWDM with 1536.61nm optics";
      }
      enum "ethernet-10gbase-dwdm-1535-82" {
        description
          "DWDM with 1535.82nm optics";
      }
      enum "ethernet-10gbase-dwdm-1535-04" {
        description
          "DWDM with 1535.04nm optics";
      }
      enum "ethernet-10gbase-dwdm-1534-25" {
        description
          "DWDM with 1534.25nm optics";
      }
      enum "ethernet-10gbase-dwdm-1533-47" {
        description
          "DWDM with 1533.47nm optics";
      }
      enum "ethernet-10gbase-dwdm-1532-68" {
        description
          "DWDM with 1532.68nm optics";
      }
      enum "ethernet-10gbase-dwdm-1531-90" {
        description
          "DWDM with 1531.90nm optics";
      }
      enum "ethernet-10gbase-dwdm-1531-12" {
        description
          "DWDM with 1531.12nm optics";
      }
      enum "ethernet-10gbase-dwdm-1530-33" {
        description
          "DWDM with 1530.33nm optics";
      }
      enum "ethernet-10gbase-dwdm-tunable" {
        description
          "DWDM with tunable optics";
      }
      enum "ethernet-40gbase-dwdm-1561-42" {
        description
          "DWDM with 1561.42nm optics";
      }
      enum "ethernet-40gbase-dwdm-1560-61" {
        description
          "DWDM with 1560.61nm optics";
      }
      enum "ethernet-40gbase-dwdm-1559-79" {
        description
          "DWDM with 1559.79nm optics";
      }
      enum "ethernet-40gbase-dwdm-1558-98" {
        description
          "DWDM with 1558.98nm optics";
      }
      enum "ethernet-40gbase-dwdm-1558-17" {
        description
          "DWDM with 1558.17nm optics";
      }
      enum "ethernet-40gbase-dwdm-1557-36" {
        description
          "DWDM with 1557.36nm optics";
      }
      enum "ethernet-40gbase-dwdm-1556-55" {
        description
          "DWDM with 1556.55nm optics";
      }
      enum "ethernet-40gbase-dwdm-1555-75" {
        description
          "DWDM with 1555.75nm optics";
      }
      enum "ethernet-40gbase-dwdm-1554-94" {
        description
          "DWDM with 1554.94nm optics";
      }
      enum "ethernet-40gbase-dwdm-1554-13" {
        description
          "DWDM with 1554.13nm optics";
      }
      enum "ethernet-40gbase-dwdm-1553-33" {
        description
          "DWDM with 1553.33nm optics";
      }
      enum "ethernet-40gbase-dwdm-1552-52" {
        description
          "DWDM with 1552.52nm optics";
      }
      enum "ethernet-40gbase-dwdm-1551-72" {
        description
          "DWDM with 1551.72nm optics";
      }
      enum "ethernet-40gbase-dwdm-1550-92" {
        description
          "DWDM with 1550.92nm optics";
      }
      enum "ethernet-40gbase-dwdm-1550-12" {
        description
          "DWDM with 1550.12nm optics";
      }
      enum "ethernet-40gbase-dwdm-1549-32" {
        description
          "DWDM with 1549.32nm optics";
      }
      enum "ethernet-40gbase-dwdm-1548-51" {
        description
          "DWDM with 1548.51nm optics";
      }
      enum "ethernet-40gbase-dwdm-1547-72" {
        description
          "DWDM with 1547.72nm optics";
      }
      enum "ethernet-40gbase-dwdm-1546-92" {
        description
          "DWDM with 1546.92nm optics";
      }
      enum "ethernet-40gbase-dwdm-1546-12" {
        description
          "DWDM with 1546.12nm optics";
      }
      enum "ethernet-40gbase-dwdm-1545-32" {
        description
          "DWDM with 1545.32nm optics";
      }
      enum "ethernet-40gbase-dwdm-1544-53" {
        description
          "DWDM with 1544.53nm optics";
      }
      enum "ethernet-40gbase-dwdm-1543-73" {
        description
          "DWDM with 1543.73nm optics";
      }
      enum "ethernet-40gbase-dwdm-1542-94" {
        description
          "DWDM with 1542.94nm optics";
      }
      enum "ethernet-40gbase-dwdm-1542-14" {
        description
          "DWDM with 1542.14nm optics";
      }
      enum "ethernet-40gbase-dwdm-1541-35" {
        description
          "DWDM with 1541.35nm optics";
      }
      enum "ethernet-40gbase-dwdm-1540-56" {
        description
          "DWDM with 1540.56nm optics";
      }
      enum "ethernet-40gbase-dwdm-1539-77" {
        description
          "DWDM with 1539.77nm optics";
      }
      enum "ethernet-40gbase-dwdm-1538-98" {
        description
          "DWDM with 1538.98nm optics";
      }
      enum "ethernet-40gbase-dwdm-1538-19" {
        description
          "DWDM with 1538.19nm optics";
      }
      enum "ethernet-40gbase-dwdm-1537-40" {
        description
          "DWDM with 1537.40nm optics";
      }
      enum "ethernet-40gbase-dwdm-1536-61" {
        description
          "DWDM with 1536.61nm optics";
      }
      enum "ethernet-40gbase-dwdm-1535-82" {
        description
          "DWDM with 1535.82nm optics";
      }
      enum "ethernet-40gbase-dwdm-1535-04" {
        description
          "DWDM with 1535.04nm optics";
      }
      enum "ethernet-40gbase-dwdm-1534-25" {
        description
          "DWDM with 1534.25nm optics";
      }
      enum "ethernet-40gbase-dwdm-1533-47" {
        description
          "DWDM with 1533.47nm optics";
      }
      enum "ethernet-40gbase-dwdm-1532-68" {
        description
          "DWDM with 1532.68nm optics";
      }
      enum "ethernet-40gbase-dwdm-1531-90" {
        description
          "DWDM with 1531.90nm optics";
      }
      enum "ethernet-40gbase-dwdm-1531-12" {
        description
          "DWDM with 1531.12nm optics";
      }
      enum "ethernet-40gbase-dwdm-1530-33" {
        description
          "DWDM with 1530.33nm optics";
      }
      enum "ethernet-40gbase-dwdm-tunable" {
        description
          "DWDM with tunable optics";
      }
      enum "ethernet-100gbase-dwdm-1561-42" {
        description
          "DWDM with 1561.42nm optics";
      }
      enum "ethernet-100gbase-dwdm-1560-61" {
        description
          "DWDM with 1560.61nm optics";
      }
      enum "ethernet-100gbase-dwdm-1559-79" {
        description
          "DWDM with 1559.79nm optics";
      }
      enum "ethernet-100gbase-dwdm-1558-98" {
        description
          "DWDM with 1558.98nm optics";
      }
      enum "ethernet-100gbase-dwdm-1558-17" {
        description
          "DWDM with 1558.17nm optics";
      }
      enum "ethernet-100gbase-dwdm-1557-36" {
        description
          "DWDM with 1557.36nm optics";
      }
      enum "ethernet-100gbase-dwdm-1556-55" {
        description
          "DWDM with 1556.55nm optics";
      }
      enum "ethernet-100gbase-dwdm-1555-75" {
        description
          "DWDM with 1555.75nm optics";
      }
      enum "ethernet-100gbase-dwdm-1554-94" {
        description
          "DWDM with 1554.94nm optics";
      }
      enum "ethernet-100gbase-dwdm-1554-13" {
        description
          "DWDM with 1554.13nm optics";
      }
      enum "ethernet-100gbase-dwdm-1553-33" {
        description
          "DWDM with 1553.33nm optics";
      }
      enum "ethernet-100gbase-dwdm-1552-52" {
        description
          "DWDM with 1552.52nm optics";
      }
      enum "ethernet-100gbase-dwdm-1551-72" {
        description
          "DWDM with 1551.72nm optics";
      }
      enum "ethernet-100gbase-dwdm-1550-92" {
        description
          "DWDM with 1550.92nm optics";
      }
      enum "ethernet-100gbase-dwdm-1550-12" {
        description
          "DWDM with 1550.12nm optics";
      }
      enum "ethernet-100gbase-dwdm-1549-32" {
        description
          "DWDM with 1549.32nm optics";
      }
      enum "ethernet-100gbase-dwdm-1548-51" {
        description
          "DWDM with 1548.51nm optics";
      }
      enum "ethernet-100gbase-dwdm-1547-72" {
        description
          "DWDM with 1547.72nm optics";
      }
      enum "ethernet-100gbase-dwdm-1546-92" {
        description
          "DWDM with 1546.92nm optics";
      }
      enum "ethernet-100gbase-dwdm-1546-12" {
        description
          "DWDM with 1546.12nm optics";
      }
      enum "ethernet-100gbase-dwdm-1545-32" {
        description
          "DWDM with 1545.32nm optics";
      }
      enum "ethernet-100gbase-dwdm-1544-53" {
        description
          "DWDM with 1544.53nm optics";
      }
      enum "ethernet-100gbase-dwdm-1543-73" {
        description
          "DWDM with 1543.73nm optics";
      }
      enum "ethernet-100gbase-dwdm-1542-94" {
        description
          "DWDM with 1542.94nm optics";
      }
      enum "ethernet-100gbase-dwdm-1542-14" {
        description
          "DWDM with 1542.14nm optics";
      }
      enum "ethernet-100gbase-dwdm-1541-35" {
        description
          "DWDM with 1541.35nm optics";
      }
      enum "ethernet-100gbase-dwdm-1540-56" {
        description
          "DWDM with 1540.56nm optics";
      }
      enum "ethernet-100gbase-dwdm-1539-77" {
        description
          "DWDM with 1539.77nm optics";
      }
      enum "ethernet-100gbase-dwdm-1538-98" {
        description
          "DWDM with 1538.98nm optics";
      }
      enum "ethernet-100gbase-dwdm-1538-19" {
        description
          "DWDM with 1538.19nm optics";
      }
      enum "ethernet-100gbase-dwdm-1537-40" {
        description
          "DWDM with 1537.40nm optics";
      }
      enum "ethernet-100gbase-dwdm-1536-61" {
        description
          "DWDM with 1536.61nm optics";
      }
      enum "ethernet-100gbase-dwdm-1535-82" {
        description
          "DWDM with 1535.82nm optics";
      }
      enum "ethernet-100gbase-dwdm-1535-04" {
        description
          "DWDM with 1535.04nm optics";
      }
      enum "ethernet-100gbase-dwdm-1534-25" {
        description
          "DWDM with 1534.25nm optics";
      }
      enum "ethernet-100gbase-dwdm-1533-47" {
        description
          "DWDM with 1533.47nm optics";
      }
      enum "ethernet-100gbase-dwdm-1532-68" {
        description
          "DWDM with 1532.68nm optics";
      }
      enum "ethernet-100gbase-dwdm-1531-90" {
        description
          "DWDM with 1531.90nm optics";
      }
      enum "ethernet-100gbase-dwdm-1531-12" {
        description
          "DWDM with 1531.12nm optics";
      }
      enum "ethernet-100gbase-dwdm-1530-33" {
        description
          "DWDM with 1530.33nm optics";
      }
      enum "ethernet-100gbase-dwdm-tunable" {
        description
          "DWDM with tunable optics";
      }
      enum "ethernet-40gbase-kr4" {
        description
          "4 lane copper (backplane)";
      }
      enum "ethernet-40gbase-cr4" {
        description
          "4 lane copper (very short reach)";
      }
      enum "ethernet-40gbase-sr4" {
        description
          "fiber over 4 lane optics (short reach)";
      }
      enum "ethernet-40gbase-fr" {
        description
          "serial fiber (2+ km)";
      }
      enum "ethernet-100gbase-cr10" {
        description
          "10 lane copper (very short reach)";
      }
      enum "ethernet-100gbase-sr10" {
        description
          "MMF fiber over 10 lane optics (short reach)";
      }
      enum "ethernet-40gbase-csr4" {
        description
          "fiber over 4 lane optics (extended short reach)";
      }
      enum "ethernet-10gbase-cwdm" {
        description
          "CWDM optics";
      }
      enum "ethernet-10gbase-cwdm-tunable" {
        description
          "CWDM with tunable optics";
      }
      enum "ethernet-10gbase-cwdm-1470" {
        description
          "CWDM with 1470nm optics";
      }
      enum "ethernet-10gbase-cwdm-1490" {
        description
          "CWDM with 1490nm optics";
      }
      enum "ethernet-10gbase-cwdm-1510" {
        description
          "CWDM with 1510nm optics";
      }
      enum "ethernet-10gbase-cwdm-1530" {
        description
          "CWDM with 1530nm optics";
      }
      enum "ethernet-10gbase-cwdm-1550" {
        description
          "CWDM with 1550nm optics";
      }
      enum "ethernet-10gbase-cwdm-1570" {
        description
          "CWDM with 1570nm optics";
      }
      enum "ethernet-10gbase-cwdm-1590" {
        description
          "CWDM with 1590nm optics";
      }
      enum "ethernet-10gbase-cwdm-1610" {
        description
          "CWDM with 1610nm optics";
      }
      enum "ethernet-40gbase-cwdm" {
        description
          "CWDM optics";
      }
      enum "ethernet-40gbase-cwdm-tunable" {
        description
          "CWDM with tunable optics";
      }
      enum "ethernet-40gbase-cwdm-1470" {
        description
          "CWDM with 1470nm optics";
      }
      enum "ethernet-40gbase-cwdm-1490" {
        description
          "CWDM with 1490nm optics";
      }
      enum "ethernet-40gbase-cwdm-1510" {
        description
          "CWDM with 1510nm optics";
      }
      enum "ethernet-40gbase-cwdm-1530" {
        description
          "CWDM with 1530nm optics";
      }
      enum "ethernet-40gbase-cwdm-1550" {
        description
          "CWDM with 1550nm optics";
      }
      enum "ethernet-40gbase-cwdm-1570" {
        description
          "CWDM with 1570nm optics";
      }
      enum "ethernet-40gbase-cwdm-1590" {
        description
          "CWDM with 1590nm optics";
      }
      enum "ethernet-40gbase-cwdm-1610" {
        description
          "CWDM with 1610nm optics";
      }
      enum "ethernet-100gbase-cwdm" {
        description
          "CWDM optics";
      }
      enum "ethernet-100gbase-cwdm-tunable" {
        description
          "CWDM with tunable optics";
      }
      enum "ethernet-100gbase-cwdm-1470" {
        description
          "CWDM with 1470nm optics";
      }
      enum "ethernet-100gbase-cwdm-1490" {
        description
          "CWDM with 1490nm optics";
      }
      enum "ethernet-100gbase-cwdm-1510" {
        description
          "CWDM with 1510nm optics";
      }
      enum "ethernet-100gbase-cwdm-1530" {
        description
          "CWDM with 1530nm optics";
      }
      enum "ethernet-100gbase-cwdm-1550" {
        description
          "CWDM with 1550nm optics";
      }
      enum "ethernet-100gbase-cwdm-1570" {
        description
          "CWDM with 1570nm optics";
      }
      enum "ethernet-100gbase-cwdm-1590" {
        description
          "CWDM with 1590nm optics";
      }
      enum "ethernet-100gbase-cwdm-1610" {
        description
          "CWDM with 1610nm optics";
      }
      enum "ethernet-40gbase-elpb" {
        description
          "Electrical loopback";
      }
      enum "ethernet-100gbase-elpb" {
        description
          "Electrical loopback";
      }
      enum "ethernet-100gbase-lr10" {
        description
          "Fiber over 10 lane optics (long reach)";
      }
      enum "ethernet-40gbase" {
        description
          "Four-pair Category 8 STP";
      }
      enum "ethernet-100gbase-kp4" {
        description
          "4 lane copper (backplane)";
      }
      enum "ethernet-100gbase-kr4" {
        description
          "Improved 4 lane copper (backplane)";
      }
      enum "ethernet-10gbase-lrm" {
        description
          "Multimode fiber with 1310nm optics (long reach)";
      }
      enum "ethernet-10gbase-cx4" {
        description
          "4 lane X copper";
      }
      enum "ethernet-10gbase" {
        description
          "Four-pair Category 6+ UTP";
      }
      enum "ethernet-10gbase-kx4" {
        description
          "4 lane X copper (backplane)";
      }
      enum "ethernet-10gbase-kr" {
        description
          "Copper (backplane)";
      }
      enum "ethernet-10gbase-pr" {
        description
          "Passive optical network";
      }
      enum "ethernet-100base-lx" {
        description
          "X fiber over 4 lane 1310nm optics";
      }
      enum "ethernet-100base-zx" {
        description
          "Single-mode fiber over 1550nm optics (Cisco)";
      }
      enum "ethernet-1000base-bx-d" {
        description
          "X fiber (D)";
      }
      enum "ethernet-1000base-bx-u" {
        description
          "X fiber (U)";
      }
      enum "ethernet-1000base-bx20-d" {
        description
          "X fiber (D, 20km)";
      }
      enum "ethernet-1000base-bx20-u" {
        description
          "X fiber (U, 20km)";
      }
      enum "ethernet-1000base-bx40-d" {
        description
          "X fiber (D, 40km)";
      }
      enum "ethernet-1000base-bx40-da" {
        description
          "X fiber (D, 40km)";
      }
      enum "ethernet-1000base-bx40-u" {
        description
          "X fiber (U, 40km)";
      }
      enum "ethernet-1000base-bx80-d" {
        description
          "X fiber (D, 80km)";
      }
      enum "ethernet-1000base-bx80-u" {
        description
          "X fiber (U, 80km)";
      }
      enum "ethernet-1000base-bx120-d" {
        description
          "X fiber (D, 120km)";
      }
      enum "ethernet-1000base-bx120-u" {
        description
          "X fiber (U, 120km)";
      }
      enum "ethernet-10gbase-bx-d" {
        description
          "X fiber (D)";
      }
      enum "ethernet-10gbase-bx-u" {
        description
          "X fiber (U)";
      }
      enum "ethernet-10gbase-bx10-d" {
        description
          "X fiber (D, 10km)";
      }
      enum "ethernet-10gbase-bx10-u" {
        description
          "X fiber (U, 10km)";
      }
      enum "ethernet-10gbase-bx20-d" {
        description
          "X fiber (D, 20km)";
      }
      enum "ethernet-10gbase-bx20-u" {
        description
          "X fiber (U, 20km)";
      }
      enum "ethernet-10gbase-bx40-d" {
        description
          "X fiber (D, 40km)";
      }
      enum "ethernet-10gbase-bx40-u" {
        description
          "X fiber (U, 40km)";
      }
      enum "ethernet-10gbase-bx80-d" {
        description
          "X fiber (D, 80km)";
      }
      enum "ethernet-10gbase-bx80-u" {
        description
          "X fiber (U, 80km)";
      }
      enum "ethernet-10gbase-bx120-d" {
        description
          "X fiber (D, 120km)";
      }
      enum "ethernet-10gbase-bx120-u" {
        description
          "X fiber (U, 120km)";
      }
      enum "ethernet-1000base-dr-lx" {
        description
          "X fiber over long-wl laser PMD, duplexity
           unknown, dual rate";
      }
      enum "ethernet-100gbase-er4l" {
        description
          "fiber over 4 lane optics (25km reach) (lite)";
      }
      enum "ethernet-100gbase-sr4" {
        description
          "fiber over 4 lane optics (short reach)";
      }
      enum "ethernet-40gbase-sr-bd" {
        description
          "Bi-directional fiber over 2 lane optics (short
           reach)";
      }
      enum "ethernet-25gbase-cr" {
        description
          "Twinaxial copper cabling";
      }
      enum "ethernet-25gbase-cr-s" {
        description
          "Twinaxial copper cabling (no RS-FEC)";
      }
      enum "ethernet-25gbase-kr" {
        description
          "One lane electrical backplane";
      }
      enum "ethernet-25gbase-kr-s" {
        description
          "One lane electrical backplane (no RS-FEC)";
      }
      enum "ethernet-25gbase-r" {
        description
          "One lane fiber";
      }
      enum "ethernet-25gbase-sr" {
        description
          "Multimode fiber";
      }
      enum "ethernet-25gbase-sl" {
        description
          "20/30m on OM3/4 MMF duplex fibre cable type
           (Short Link)";
      }
      enum "ethernet-25gbase-csr" {
        description
          "Multimode fiber";
      }
      enum "ethernet-25gbase-dwdm" {
        description
          "DWDM optics";
      }
      enum "ethernet-25gbase-dwdm-tunable" {
        description
          "DWDM with tunable optics";
      }
      enum "ethernet-25gbase-cwdm" {
        description
          "CWDM optics";
      }
      enum "ethernet-25gbase-cwdm-tunable" {
        description
          "CWDM with tunable optics";
      }
      enum "ethernet-100gbase-psm4" {
        description
          "4 parallel single mode fibers";
      }
      enum "ethernet-100gbase-er10" {
        description
          "Fiber over 10 lane optics (extended reach)";
      }
      enum "ethernet-100gbase-er10l" {
        description
          "Fiber over 10 lane optics (extended reach)
           (lite)";
      }
      enum "ethernet-100gbase-acc" {
        description
          "Active copper cable";
      }
      enum "ethernet-100gbase-aoc" {
        description
          "Active optical cable";
      }
      enum "ethernet-100gbase-cwdm4" {
        description
          "4 lane CWDM cable";
      }
      enum "ethernet-40gbase-psm4" {
        description
          "4 parallel single mode fibers";
      }
      enum "ethernet-100gbase-cr4" {
        description
          "4 lane copper (very short reach)";
      }
      enum "ethernet-100gbase-act-loop" {
        description
          "Active loopback";
      }
      enum "ethernet-100gbase-pas-loop" {
        description
          "Passive loopback";
      }
      enum "ethernet-50gbase-cr2" {
        description
          "2 lane copper (very short reach)";
      }
      enum "ethernet-50gbase-sr2" {
        description
          "fiber over 2 lane optics (short reach)";
      }
      enum "ethernet-50gbase-psm2" {
        description
          "2 parallel single mode fibers";
      }
      enum "ethernet-200gbase-cr4" {
        description
          "4 lanes Passive Copper";
      }
      enum "ethernet-400gbase-fr4" {
        description
          "Duplex SMF LC Connector 2km";
      }
      enum "ethernet-400gbase-dr4" {
        description
          "SMF with MPO-12 connector";
      }
      enum "ethernet-10gbase-cu1m" {
        description
          "Passive Twinax cable assembly 1m";
      }
      enum "ethernet-10gbase-cu1-5m" {
        description
          "Passive Twinax cable assembly 1.5m";
      }
      enum "ethernet-10gbase-cu2m" {
        description
          "Passive Twinax cable assembly 2m";
      }
      enum "ethernet-10gbase-cu2-5m" {
        description
          "Passive Twinax cable assembly 2.5m";
      }
      enum "ethernet-10gbase-cu3m" {
        description
          "Passive Twinax cable assembly 3m";
      }
      enum "ethernet-10gbase-cu5m" {
        description
          "Passive Twinax cable assembly 5m";
      }
      enum "ethernet-10gbase-acu7m" {
        description
          "Active Twinax cable assembly 7m";
      }
      enum "ethernet-10gbase-acu10m" {
        description
          "Active Twinax cable assembly 10m";
      }
      enum "ethernet-10gbase-aoc1m" {
        description
          "Active optical cable 1m";
      }
      enum "ethernet-10gbase-aoc2m" {
        description
          "Active optical cable 2m";
      }
      enum "ethernet-10gbase-aoc3m" {
        description
          "Active optical cable 3m";
      }
      enum "ethernet-10gbase-aoc5m" {
        description
          "Active optical cable 5m";
      }
      enum "ethernet-10gbase-aoc7m" {
        description
          "Active optical cable 7m";
      }
      enum "ethernet-10gbase-aoc10m" {
        description
          "Active optical cable 10m";
      }
      enum "ethernet-40gbase-aoc" {
        description
          "Active optical cable";
      }
      enum "ethernet-4x10g-base-lr" {
        description
          "fiber over 4 lane optics (long reach)";
      }
      enum "ethernet-40gbase-acu1m" {
        description
          "Active Twinax cable assembly 1m";
      }
      enum "ethernet-40gbase-acu3m" {
        description
          "Active Twinax cable assembly 3m";
      }
      enum "ethernet-40gbase-acu5m" {
        description
          "Active Twinax cable assembly 5m";
      }
      enum "ethernet-40gbase-acu7m" {
        description
          "Active Twinax cable assembly 7m";
      }
      enum "ethernet-40gbase-acu10m" {
        description
          "Active Twinax cable assembly 10m";
      }
      enum "ethernet-25gbase-cu1m" {
        description
          "Twinaxial copper cabling (1m)";
      }
      enum "ethernet-25gbase-cu2m" {
        description
          "Twinaxial copper cabling (2m)";
      }
      enum "ethernet-25gbase-cu3m" {
        description
          "Twinaxial copper cabling (3m)";
      }
      enum "ethernet-25gbase-cu4m" {
        description
          "Twinaxial copper cabling (4m)";
      }
      enum "ethernet-25gbase-cu5m" {
        description
          "Twinaxial copper cabling (5m)";
      }
      enum "ethernet-25gbase-cu1dot5m" {
        description
          "Twinaxial copper cabling (1.5m)";
      }
      enum "ethernet-25gbase-cu2dot5m" {
        description
          "Twinaxial copper cabling (2.5m)";
      }
      enum "ethernet-100gbase-sm-sr" {
        description
          "4 lane CWDM Lite cable";
      }
      enum "ethernet-25gbase-aoc1m" {
        description
          "Active optical cable 1m";
      }
      enum "ethernet-25gbase-aoc2m" {
        description
          "Active optical cable 2m";
      }
      enum "ethernet-25gbase-aoc3m" {
        description
          "Active optical cable 3m";
      }
      enum "ethernet-25gbase-aoc4m" {
        description
          "Active optical cable 4m";
      }
      enum "ethernet-25gbase-aoc5m" {
        description
          "Active optical cable 5m";
      }
      enum "ethernet-25gbase-aoc7m" {
        description
          "Active optical cable 7m";
      }
      enum "ethernet-25gbase-aoc10m" {
        description
          "Active optical cable 10m";
      }
      enum "ethernet-1000base-2bx-d" {
        description
          "2 channel X fibre (D)";
      }
      enum "ethernet-1000base-2bx-d-i" {
        description
          "2 channel X fibre (D/I)";
      }
      enum "ethernet-1000base-2bx-u" {
        description
          "2 channel X fibre (U)";
      }
      enum "ethernet-1000base-2bx-u-i" {
        description
          "2 channel X fibre (U/I)";
      }
      enum "ethernet-400gbase-cr8" {
        description
          "8 lane copper (very short reach)";
      }
      enum "ethernet-100gbase-sr-bd" {
        description
          "Bi-directional fiber over 2 lane optics (short
           reach)";
      }
      enum "ethernet-400gbase-lr8" {
        description
          "fiber over 8 lane optics (long reach)";
      }
      enum "ethernet-400gbase-aoc" {
        description
          "Active optical cable";
      }
      enum "ethernet-400gbase-acc" {
        description
          "Active copper cable";
      }
      enum "ethernet-400gbase-act-loop" {
        description
          "Active loopback";
      }
      enum "ethernet-400gbase-pas-loop" {
        description
          "Passive loopback";
      }
      enum "ethernet-8x-sfp50gbase-cu" {
        description
          "8x50G Copper cable";
      }
      enum "ethernet-2x100gbase-lr8-s" {
        description
          "2x100G over 8 lane optics (long reach)";
      }
      enum "ethernet-2x100gbase-sr4" {
        description
          "2x100G over 4 lane optics (short reach)";
      }
      enum "ethernet-2x100gbase-psm4" {
        description
          "2x100G over 4 parallel single mode fibers";
      }
      enum "ethernet-2x100gbase-cwdm4" {
        description
          "2x100G over 4 lane CWDM cable";
      }
      enum "ethernet-2x100gbase-lr4" {
        description
          "2x100G over 4 lane optics (long reach)";
      }
      enum "ethernet-100gbase-fr" {
        description
          "duplex single mode fiber (Far Reach/2 km)";
      }
      enum "ethernet-100gbase-dwdm2" {
        description
          "100G DWDM optics using 2 wavelengths on 1550nm
           DWDM grid with 80km reach";
      }
      enum "ethernet-100gbase-er4f" {
        description
          "fiber over 4 lane optics (40km reach)";
      }
      enum "ethernet-100gbase-er4l-s" {
        description
          "fiber over 4 lane optics (25km reach) (lite)";
      }
      enum "ethernet-100gbase-lr" {
        description
          "duplex single mode fiber (Long Reach/10 km)";
      }
      enum "ethernet-400gbase-aec" {
        description
          "Active electrical cable";
      }
      enum "ethernet-4x100gbase-fr" {
        description
          "Parallel SMF (Far Reach/2 km)";
      }
      enum "ethernet-400gbase-zr-s" {
        description
          "Duplex SMF LC Connector 80km";
      }
      enum "ethernet-400gbase-zr-plus-s" {
        description
          "Duplex SMF LC Connector 80km";
      }
      enum "ethernet-100gbase-dr-s" {
        description
          "Duplex SMF LC Connector 500m)";
      }
      enum "ethernet-400gbase-lr4" {
        description
          "Duplex SMF over 4 lane (long reach/10 km)";
      }
      enum "ethernet-25gbase-lr" {
        description
          "SFP28 Module for SMF";
      }
      enum "ethernet-25gbase-pas-loop" {
        description
          "Passive loopback";
      }
      enum "ethernet-50gbase-sr" {
        description
          "Multimode fiber";
      }
      enum "ethernet-50gbase-cu1m" {
        description
          "Twinaxial copper cabling (1m)";
      }
      enum "ethernet-50gbase-pas-loop" {
        description
          "Passive loopback";
      }
      enum "ethernet-25g-50g-sr-s" {
        description
          "Multimode fiber";
      }
      enum "ethernet-800gbase-cr8" {
        description
          "8 lane copper (very short reach)";
      }
      enum "ethernet-qsa" {
        description
          "No Media Type (Empty QSA)";
      }
      enum "ethernet-100gbase-erl" {
        description
          "duplex single mode fiber (Extended Reach 25km)";
      }
      enum "ethernet-50gbase-cu1-5m" {
        description
          "Twinaxial copper cabling (1.5m)";
      }
      enum "ethernet-50gbase-cu2m" {
        description
          "Twinaxial copper cabling (2m)";
      }
      enum "ethernet-50gbase-cu2-5m" {
        description
          "Twinaxial copper cabling (2.5m)";
      }
      enum "ethernet-50gbase-cu3m" {
        description
          "Twinaxial copper cabling (3m)";
      }
      enum "ethernet-50gbase-cu5m" {
        description
          "Twinaxial copper cabling (5m)";
      }
      enum "ethernet-4x100gbase-lr" {
        description
          "Parallel SMF (Long Reach/10 km)";
      }
      enum "ethernet-100gbase-zr-plus-s" {
        description
          "Duplex SMF LC Connector 80km";
      }
      enum "ethernet-2x400gbase-fr4" {
        description
          "Dual Duplex SMF CS 2km";
      }
      enum "ethernet-8x100gbase-dr" {
        description
          "SMF With Angled MPO-16 Connector 500m";
      }
      enum "ethernet-10gbase-pas-loop" {
        description
          "Passive loopback 10G ELB";
      }
      enum "ethernet-gebase-pas-loop" {
        description
          "Passive loopback 1GE ELB";
      }
      enum "ethernet-2x200gbase-cu" {
        description
          "2x200G over 8 lane passive copper";
      }
      enum "ethernet-800gbase-pas-loop" {
        description
          "Passive loopback for 800G ELB";
      }
      enum "ethernet-25gbase-er" {
        description
          "Duplex Single mode fibre (30/40km)";
      }
      enum "ethernet-400gbase-sr8" {
        description
          "MMF over 8 lane (short reach)";
      }
      enum "ethernet-qsa-28" {
        description
          "No Media Type (Empty QSA_28)";
      }
      enum "ethernet-200gbase-fr4" {
        description
          "Duplex single mode fiber (Far Reach/2km)";
      }
      enum "ethernet-8x100gbase-fr" {
        description
          "SMF With Angled MPO-16 Connector 500m";
      }
      enum "ethernet-800gbase-aec" {
        description
          "800G Active electrical cable";
      }
      enum "ethernet-100gbase-zr4s" {
        description
          "80Km duplex LC SMF";
      }
      enum "ethernet-1000base-lh" {
        description
          "H fiber over long-wl laser PMD, duplexity
           unknown";
      }
      enum "ethernet-1000base-lhhd" {
        description
          "H fiber over long-wl laser PMD, half duplex";
      }
      enum "ethernet-1000base-lhfd" {
        description
          "H fiber over long-wl laser PMD, full duplex";
      }
      enum "ethernet-25gbase-bx25-d" {
        description
          "X fiber (D, 10km)";
      }
      enum "ethernet-25gbase-bx25-u" {
        description
          "X fiber (U, 10km)";
      }
      enum "ethernet-2x400gbase-lr4" {
        description
          "Dual Duplex SMF CS 10km";
      }
      enum "ethernet-100gbase-zr-s" {
        description
          "Duplex SMF LC Connector 80km";
      }
      enum "ethernet-400gbase-bright-zr-plus-s" {
        description
          "400G BRIGHT ZRP Duplex SMF LC Connector 80km";
      }
      enum "ethernet-100gbase-sr-1-2" {
        description
          "Duplex SFF LC Connector 80km";
      }
      enum "ethernet-10gbase-t-x" {
        description
          "10GBASE SFP+ Copper lane";
      }
      enum "ethernet-25gbase-bx40-d" {
        description
          "X fiber (D, 40km)";
      }
      enum "ethernet-25gbase-bx40-u" {
        description
          "X fiber (U, 40km)";
      }
      enum "ethernet-400gbase-sr4-bd" {
        description
          "400G SR4-BD 100m on OM4 MMF";
      }
      enum "ethernet-25g-50gbase-bx40-d" {
        description
          "X fiber (D, 40km)";
      }
      enum "ethernet-25g-50gbase-bx40-u" {
        description
          "X fiber (U, 40km)";
      }
      enum "ethernet-25g-50gbase-er" {
        description
          "Duplex Single mode fibre (30/40km)";
      }
      enum "ethernet-100gbase-bx40-bd" {
        description
          "Duplex SMF LC Connector 40km";
      }
      enum "ethernet-400gbase-er1" {
        description
          "Duplex SMF LC Connector 40km";
      }
      enum "ethernet-25g-50gbase-lr-s" {
        description
          "25/50G Duplex SMF LC Connector 15km";
      }
      enum "ethernet-100gbase-bx20-bd" {
        description
          "Duplex SMF LC Connector 20km";
      }
      enum "ethernet-400gbase-ulh-s" {
        description
          "400G ULH Duplex SMF LC Connector 3000km";
      }
      enum "ethernet-25g-50gbase-sl" {
        description
          "Duplex Multimode Fiber LC Connector
           (25G/50G-SL)";
      }
      enum "ethernet-100gbase-qsfp28-zr" {
        description
          "100G ZR QSFP28 Digital Coherent Optics";
      }
      enum "ethernet-cfp2-dco" {
        description
          "CFP2 DCO Coherent Optics";
      }
      enum "ethernet-100gbase-cr2" {
        description
          "100G Passive Copper over 2 lanes";
      }
      enum "ethernet-4x100gbase-cr8" {
        description
          "4x100 Passive Copper Cable over 8 lanes";
      }
      enum "ethernet-800gbase-zr" {
        description
          "800G ZR Duplex SMF LC Connector";
      }
      enum "ethernet-800gbase-zrp" {
        description
          "800G ZRP Duplex SMF LC Connector";
      }
      enum "ethernet-800gbase-dr8" {
        description
          "800G DR8 Duplex SMF LC Connector";
      }
      enum "ethernet-base-max" {
        description
          "ethernet base max";
      }
    }
    description
      "Ethernet media types: IEEE 802.3/802.3ae clause
       30.5.1.1.2";
  }

  typedef Ethernet-port-enable {
    type enumeration {
      enum "disabled" {
        description
          "Port disabled, both directions";
      }
      enum "rx-enabled" {
        description
          "Port enabled rx direction only";
      }
      enum "tx-enabled" {
        description
          "Port enabled tx direction only";
      }
      enum "enabled" {
        description
          "Port enabled, both directions";
      }
    }
    description
      "Port admin state";
  }

  grouping ETHERNET-BERT-STATUS-TYPE {
    description
      "ETHERNET BERT STATUS TYPE";
    leaf bert-state-enabled {
      type uint8;
      description
        "State";
    }
    leaf data-availability {
      type Ethernet-bert-mask;
      description
        "Flag indicating available data";
    }
    leaf receive-count {
      type uint64;
      description
        "Receive count (if 0x1 set in flag)";
    }
    leaf transmit-count {
      type uint64;
      description
        "Transmit count (if 0x2 set in flag)";
    }
    leaf receive-errors {
      type uint64;
      description
        "Received errors (if 0x4 set in flag)";
    }
    leaf error-type {
      type Ethernet-bert-err-cnt;
      description
        "Bit, block or frame error";
    }
    leaf test-pattern {
      type Ethernet-bert-pattern;
      description
        "Bert Test pattern as per IEEE";
    }
    leaf device-under-test {
      type Ethernet-dev;
      description
        "Device being tested";
    }
    leaf interface-device {
      type Ethernet-dev-if;
      description
        "Interface being tested";
    }
  }

  grouping ETH-SHOWCTRL-BERT {
    description
      "Per port BERT test status information";
    container bert-status {
      description
        "Current test status";
      uses ETHERNET-BERT-STATUS-TYPE;
    }
    leaf time-left {
      type uint32;
      units "second";
      description
        "Remaining time for this test in seconds";
    }
    leaf port-bert-interval {
      type uint32;
      description
        "Port BERT interval";
    }
  }

  grouping ETHER-PFC-WD-DETAILS-V2 {
    description
      "Per port PFC wd stats";
    leaf priority-enabled-bitmap {
      type uint8;
      description
        "Bitmap to indicate the TC PFC is enabled";
    }
    list watchdog-event {
      max-elements "8";
      description
        "WD events";
      leaf entry {
        type uint64;
        description
          "WD events";
      }
    }
    list shutdown-event {
      max-elements "8";
      description
        "Shutdown Events";
      leaf entry {
        type uint64;
        description
          "Shutdown Events";
      }
    }
    list auto-restore-event {
      max-elements "8";
      description
        "Restore Events";
      leaf entry {
        type uint64;
        description
          "Restore Events";
      }
    }
    list auto-restore-and-stuck-event {
      max-elements "8";
      description
        "Restore And Stuck Events";
      leaf entry {
        type uint64;
        description
          "Restore And Stuck Events";
      }
    }
    list auto-restore-and-stuck-instantaneous-event {
      max-elements "8";
      description
        "Restore And Stuck instantaneous Events";
      leaf entry {
        type uint64;
        description
          "Restore And Stuck instantaneous Events";
      }
    }
    list total-dropped-packet {
      max-elements "8";
      description
        "Total dropped Packets";
      leaf entry {
        type uint64;
        description
          "Total dropped Packets";
      }
    }
    list dropped-packet {
      max-elements "8";
      description
        "Dropped Packets";
      leaf entry {
        type uint64;
        description
          "Dropped Packets";
      }
    }
  }

  grouping ETH-CTLR-PRBS-LANE-INFO {
    description
      "ETH CTLR PRBS LANE INFO";
    leaf lane-id {
      type uint16;
      description
        "Lane Identifier";
    }
    leaf signal-noise-ratio {
      type int32;
      description
        "Signal to Noise Ratio in units of 0.01dBm";
    }
    leaf max-signal-noise-ratio {
      type int32;
      description
        "Maximum Signal to Noise Ratio in units of 0
         .01dBm";
    }
    leaf total-bit {
      type uint64;
      description
        "Total Tx/Rx bits";
    }
    leaf error-count {
      type uint64;
      description
        "Error Count";
    }
    leaf bit-error-rate {
      type int64;
      description
        "Bit Error Rate on this lane in terms of 10^6";
    }
    leaf maximum-bit-error-rate {
      type int64;
      description
        "Maximum Bit Error Rate on this lane in terms of
         10^6";
    }
    leaf status {
      type Ether-prbs-status;
      description
        "Per Lane PRBS Status";
    }
    leaf lock-lost-count {
      type uint32;
      description
        "Lock Lost count";
    }
    leaf lock-found-count {
      type uint32;
      description
        "Lock Found count";
    }
    leaf lock-time {
      type uint64;
      units "second";
      description
        "prbs locked status time elapsed (in secs)";
    }
    leaf lock-lost-timestamp {
      type uint64;
      units "second";
      description
        "prbs lock lost timestamp in elapsed seconds
         since epoch";
    }
  }

  grouping ETH-CTLR-PRBS-INFO {
    description
      "ETH CTLR PRBS INFO";
    leaf mode {
      type Ether-prbs-mode;
      description
        "PRBS mode configured";
    }
    leaf pattern {
      type Ether-prbs-pattern;
      description
        "PRBS pattern configured";
    }
    leaf direction {
      type Ether-prbs-direction;
      description
        "PRBS direction configured";
    }
    leaf error-inject {
      type Ether-prbs-error-inject;
      description
        "PRBS Error inject type configured";
    }
    leaf framing {
      type Ether-prbs-framing;
      description
        "PRBS framing mode configured";
    }
    leaf swizzle {
      type Ether-prbs-swizzle;
      description
        "PRBS Swizzle configured";
    }
    leaf status {
      type Ether-prbs-status;
      description
        "PRBS Status";
    }
    leaf user-pattern {
      type uint64;
      description
        "PRBS user pattern configured";
    }
    leaf configured-time {
      type uint64;
      units "second";
      description
        "Configured time of PRBS in timestamp (in secs)";
    }
    leaf first-lock-time {
      type uint64;
      units "second";
      description
        "First lock established time elapsed (in secs)";
    }
    leaf lock-time {
      type uint64;
      units "second";
      description
        "prbs locked status time elapsed (in secs)";
    }
    leaf bit-errors {
      type uint64;
      description
        "Bit errors Count";
    }
    leaf lock-found-count {
      type uint32;
      description
        "Lock Found count";
    }
    leaf lock-lost-count {
      type uint32;
      description
        "Lock Lost count";
    }
    leaf result {
      type int32;
      description
        "Result is set to true when PRBS test passed with
         no bit errors, Otherwise as false";
    }
    leaf last-update-time {
      type uint64;
      description
        "PRBS stats updated timestamp (Epoch time)";
    }
    leaf fec-tail-index {
      type uint16;
      description
        "FEC Tail Index";
    }
    leaf lock-lost-timestamp {
      type uint64;
      units "second";
      description
        "prbs lock lost timestamp in elapsed seconds
         since epoch";
    }
    leaf-list fec-codeword {
      type uint64;
      description
        "FEC Codewords";
    }
    list lane {
      description
        "PRBS per lane statistics";
      uses ETH-CTLR-PRBS-LANE-INFO;
    }
  }

  grouping ETH-CTLR-TRANSPORT-INFO {
    description
      "ETH CTLR TRANSPORT INFO";
    leaf maintenance-mode-enabled {
      type boolean;
      description
        "Maintenance Mode - TRUE if enabled";
    }
    leaf ains-status {
      type Ether-ains-status;
      description
        "AINS Soak status";
    }
    leaf total-duration {
      type uint32;
      units "minute";
      description
        "Total duration (minutes) of AINS soak timer";
    }
    leaf remaining-duration {
      type uint32;
      units "second";
      description
        "Remaining duration (seconds) of AINS soak timer";
    }
  }

  grouping ETHER-MCAST-MAC-TYPE {
    description
      "Multicast MAC address";
    leaf mac-address {
      type Mac-addr;
      description
        "MAC address";
    }
    leaf mask {
      type Mac-addr;
      description
        "Mask for this MAC address";
    }
  }

  grouping ETH-CTRLR-MCAST-MAC-FILTER {
    description
      "ETH CTRLR MCAST MAC FILTER";
    leaf multicast-promiscuous {
      type boolean;
      description
        "Whether the port is in multicast promiscuous
         mode";
    }
    list multicast-mac-address {
      description
        "MAC addresses in the multicast ingress
         destination MAC filter";
      uses ETHER-MCAST-MAC-TYPE;
    }
  }

  grouping ETH-CTRLR-UCAST-MAC-FILTER {
    description
      "ETH CTRLR UCAST MAC FILTER";
    leaf-list unicast-mac-address {
      type Mac-addr;
      description
        "MAC addresses in the unicast ingress destination
         MAC filter";
    }
  }

  grouping ETH-CTRLR-MAC-INFO {
    description
      "ETH CTRLR MAC INFO";
    container unicast-mac-filters {
      description
        "Port unicast MAC filter information";
      uses ETH-CTRLR-UCAST-MAC-FILTER;
    }
    container multicast-mac-filters {
      description
        "Port multicast MAC filter information";
      uses ETH-CTRLR-MCAST-MAC-FILTER;
    }
    leaf mtu {
      type uint32;
      description
        "Port operational MTU";
    }
    leaf mru {
      type uint32;
      description
        "Port operational MRU";
    }
    leaf burned-in-mac-address {
      type Mac-addr;
      description
        "Port Burned-In MAC address";
    }
    leaf operational-mac-address {
      type Mac-addr;
      description
        "Port operational MAC address";
    }
  }

  grouping ETHER-PFC-WD-DETAILS-TYPE {
    description
      "ETHER PFC WD DETAILS TYPE";
    leaf watchdog-state {
      type string {
        length "0..8";
      }
      description
        "Watchdog State";
    }
    leaf watchdog-traffic-class-enable-mask {
      type uint8;
      description
        "WSTCMask";
    }
    list mode {
      max-elements "3";
      description
        "PFC Watchdog configured mode";
      leaf entry {
        type Ether-pfc-wd;
        description
          "PFC Watchdog configured mode";
      }
    }
    list interval {
      max-elements "3";
      description
        "PFC Watchdog Interval configured";
      leaf entry {
        type uint32;
        description
          "PFC Watchdog Interval configured";
      }
    }
    list shutdown-multiplier {
      max-elements "3";
      description
        "PFC Watchdog Shutdown Multiplier configured";
      leaf entry {
        type uint32;
        description
          "PFC Watchdog Shutdown Multiplier configured";
      }
    }
    list auto-restore-multiplier {
      max-elements "3";
      description
        "PFC Watchdog Auto Restore Multiplier configured";
      leaf entry {
        type uint32;
        description
          "PFC Watchdog Auto Restore Multiplier configured";
      }
    }
    list fixed-restore-multiplier {
      max-elements "3";
      description
        "PFC Watchdog Fixed Restore Multiplier configured";
      leaf entry {
        type uint32;
        description
          "PFC Watchdog Fixed Restore Multiplier
           configured";
      }
    }
    list qos-q-num {
      max-elements "8";
      description
        "Qos Q Number";
      leaf entry {
        type uint32;
        description
          "Qos Q Number";
      }
    }
    list watchdog-event {
      max-elements "8";
      description
        "WD events";
      leaf entry {
        type uint64;
        description
          "WD events";
      }
    }
    list shutdown-event {
      max-elements "8";
      description
        "Shutdown Events";
      leaf entry {
        type uint64;
        description
          "Shutdown Events";
      }
    }
    list auto-restore-event {
      max-elements "8";
      description
        "Restore Events";
      leaf entry {
        type uint64;
        description
          "Restore Events";
      }
    }
    list auto-restore-and-stuck-event {
      max-elements "8";
      description
        "Restore And Stuck Events";
      leaf entry {
        type uint64;
        description
          "Restore And Stuck Events";
      }
    }
    list auto-restore-and-stuck-instantaneous-event {
      max-elements "8";
      description
        "Restore And Stuck instatneous Events";
      leaf entry {
        type uint64;
        description
          "Restore And Stuck instatneous Events";
      }
    }
    list fixed-restore-event {
      max-elements "8";
      description
        "Restore Events";
      leaf entry {
        type uint64;
        description
          "Restore Events";
      }
    }
    list total-dropped-packet {
      max-elements "8";
      description
        "Total dropped Packets";
      leaf entry {
        type uint64;
        description
          "Total dropped Packets";
      }
    }
    list dropped-packet {
      max-elements "8";
      description
        "Dropped Packets";
      leaf entry {
        type uint64;
        description
          "Dropped Packets";
      }
    }
  }

  grouping ETHER-PFC-DETAILS-TYPE {
    description
      "ETHER PFC DETAILS TYPE";
    leaf priority-flowcontrol {
      type Ether-pfc;
      description
        "Port operational priority flow control";
    }
    leaf priority-enabled-bitmap {
      type uint8;
      description
        "Priority bitmap";
    }
    leaf total-rx-frames {
      type uint64;
      description
        "Total RX Frame counts";
    }
    leaf total-tx-frames {
      type uint64;
      description
        "Total TX Frame counts";
    }
    leaf total-rx-drop-data-frames {
      type uint64;
      description
        "Total RX Dropped Data Frames";
    }
    leaf per-tc-rx-drop-supported {
      type uint8;
      description
        "Indicates support for per TC RX drop Data frames";
    }
    leaf per-tc-tx-frames-not-supported {
      type uint8;
      description
        "Indicates support for per TC tx frames";
    }
    list rx-frame {
      max-elements "8";
      description
        "RX Frame counts";
      leaf entry {
        type uint64;
        description
          "RX Frame counts";
      }
    }
    list tx-frame {
      max-elements "8";
      description
        "TX Frame counts";
      leaf entry {
        type uint64;
        description
          "TX Frame counts";
      }
    }
    list rx-drop-data-frame {
      max-elements "8";
      description
        "RX Dropped Data Frames";
      leaf entry {
        type uint64;
        description
          "RX Dropped Data Frames";
      }
    }
  }

  grouping ETHER-OPD-SETTINGS {
    description
      "ETHER OPD SETTINGS";
    leaf received-optical-power-degrade-threshold-set {
      type boolean;
      description
        "Rx-OPD alarm threshold set?";
    }
    leaf received-optical-power-degrade-threshold {
      type int32;
      description
        "Rx-OPD alarm threshold value";
    }
  }

  grouping ETH-OPD-MONITORING {
    description
      "ETH OPD MONITORING";
    container settings {
      description
        "The OPD monitoring settings to be applied";
      uses ETHER-OPD-SETTINGS;
    }
    leaf supported {
      type boolean;
      description
        "Whether or not OPD monitoring is supported";
    }
  }

  grouping ETHER-BER-STATE {
    description
      "ETHER BER STATE";
    leaf sd-current-ber {
      type uint32;
      description
        "Current SD-BER";
    }
    leaf sf-current-ber {
      type uint32;
      description
        "Current SF-BER";
    }
  }

  grouping ETHER-BER-SETTINGS {
    description
      "ETHER BER SETTINGS";
    leaf signal-degrade-threshold {
      type uint32;
      description
        "BER threshold for signal to degrade";
    }
    leaf signal-degrade-alarm {
      type boolean;
      description
        "Report alarm to indicate signal degrade";
    }
    leaf signal-fail-threshold {
      type uint32;
      description
        "BER threshold for signal to fail";
    }
    leaf signal-fail-alarm {
      type boolean;
      description
        "Report alarm to indicate signal failure";
    }
    leaf signal-remote-fault {
      type boolean;
      description
        "Whether drivers should signal remote faults";
    }
  }

  grouping ETH-BER-MONITORING {
    description
      "ETH BER MONITORING";
    container settings {
      description
        "The BER monitoring settings to be applied";
      uses ETHER-BER-SETTINGS;
    }
    container state {
      description
        "The BER state";
      uses ETHER-BER-STATE;
    }
    leaf supported {
      type boolean;
      description
        "Whether or not BER monitoring is supported";
    }
  }

  grouping ETH-CTRLR-ERROR-COUNTERS {
    description
      "ETH CTRLR ERROR COUNTERS";
    leaf sync-header-errors {
      type uint64;
      description
        "Sync-header error count";
    }
    leaf pcsbip-errors {
      type uint64;
      description
        "PCS BIP error count";
    }
  }

  grouping ETH-CTRLR-ALARMS {
    description
      "ETH CTRLR ALARMS";
    leaf received-loss-of-signal-alarm {
      type Eth-ctrlr-alarm-state;
      description
        "Alarm state of Received Loss of Signal";
    }
    leaf pcs-loss-of-block-lock-alarm {
      type Eth-ctrlr-alarm-state;
      description
        "Alarm state of PCS Loss of Block Lock";
    }
    leaf local-fault-alarm {
      type Eth-ctrlr-alarm-state;
      description
        "Alarm state of Local Fault";
    }
    leaf remote-fault-alarm {
      type Eth-ctrlr-alarm-state;
      description
        "Alarm state of Remote Fault";
    }
    leaf sd-ber-alarm {
      type Eth-ctrlr-alarm-state;
      description
        "Alarm state of SD-BER";
    }
    leaf sf-ber-alarm {
      type Eth-ctrlr-alarm-state;
      description
        "Alarm state of SF-BER";
    }
    leaf loss-of-synchronization-data-alarm {
      type Eth-ctrlr-alarm-state;
      description
        "Alarm state of Loss of Synchronization Data
         Alarm";
    }
    leaf hi-ber-alarm {
      type Eth-ctrlr-alarm-state;
      description
        "Alarm state of Hi-BER";
    }
    leaf squelch-alarm {
      type Eth-ctrlr-alarm-state;
      description
        "Alarm state of Squelch";
    }
    leaf rx-opd-alarm {
      type Eth-ctrlr-alarm-state;
      description
        "Alarm state of Rx OPD Alarm";
    }
    leaf hi-ser-alarm {
      type Eth-ctrlr-alarm-state;
      description
        "Alarm state for Hi-SER";
    }
    leaf deg-ser-alarm {
      type Eth-ctrlr-alarm-state;
      description
        "Alarm state for degraded SER";
    }
    leaf local-deg-ser-alarm {
      type Eth-ctrlr-alarm-state;
      description
        "Alarm state for Local degrade SER";
    }
    leaf remote-deg-ser-alarm {
      type Eth-ctrlr-alarm-state;
      description
        "Alarm state for Remote degrade SER";
    }
  }

  grouping ETHER-AUTONEG-TYPE {
    description
      "Autonegotiation settings";
    leaf autoneg-enabled {
      type boolean;
      description
        "TRUE if autonegotiation is enabled";
    }
    leaf mask {
      type Ether-autoneg-mask;
      description
        "Validity mask: 0x1 speed, 0x2 duplex, 0x4
         flowcontrol, 0x8 fec";
    }
    leaf speed {
      type Ethernet-speed;
      description
        "Restricted speed (if relevant bit is set in
         mask)";
    }
    leaf duplex {
      type Ethernet-duplex;
      description
        "Restricted duplex (if relevant bit is set in
         mask)";
    }
    leaf flowcontrol {
      type Ether-flowcontrol;
      description
        "Restricted flowcontrol (if relevant bit is set
         in mask)";
    }
    leaf config-override {
      type boolean;
      description
        "If true, configuration overrides negotiated
         settings.  If false, negotiated settings in
         effect";
    }
    leaf fec {
      type Ethernet-fec;
      description
        "Restricted FEC (if revelevant bit is set in
         mask)";
    }
  }

  grouping ETH-CTRLR-L1-INFO {
    description
      "ETH CTRLR L1 INFO";
    container autoneg {
      description
        "Port autonegotiation configuration settings";
      uses ETHER-AUTONEG-TYPE;
    }
    container current-alarms {
      description
        "List of l1 Current alarms generated";
      uses ETH-CTRLR-ALARMS;
    }
    container previous-alarms {
      description
        "List of Previous alarms generated";
      uses ETH-CTRLR-ALARMS;
    }
    container error-counts {
      description
        "Statistics for detected errors";
      uses ETH-CTRLR-ERROR-COUNTERS;
    }
    container ber-monitoring {
      description
        "BER monitoring details";
      uses ETH-BER-MONITORING;
    }
    container opd-monitoring {
      description
        "OPD monitoring details";
      uses ETH-OPD-MONITORING;
    }
    container pfc-info {
      description
        "Priority flow control information";
      uses ETHER-PFC-DETAILS-TYPE;
    }
    container pfcwd-info {
      description
        "Priority flow control watchdog information";
      uses ETHER-PFC-WD-DETAILS-TYPE;
    }
    leaf link-state {
      type Ether-link-state;
      description
        "Link state information of ethernet port";
    }
    leaf led-state {
      type Ether-led-state;
      description
        "State of the LED";
    }
    leaf speed {
      type Ethernet-speed;
      description
        "Port operational speed";
    }
    leaf duplex {
      type Ethernet-duplex;
      description
        "Port operational duplexity";
    }
    leaf flowcontrol {
      type Ether-flowcontrol;
      description
        "Port operational flow control";
    }
    leaf ipg {
      type Ethernet-ipg;
      description
        "Port operational inter-packet-gap";
    }
    leaf laser-squelch-enabled {
      type boolean;
      description
        "Laser Squelch - TRUE if enabled";
    }
    leaf insert-idle-ingress-enabled {
      type boolean;
      description
        "Insert Idle Ingress - TRUE if enabled";
    }
    leaf insert-idle-egress-enabled {
      type boolean;
      description
        "Insert Idle Egress - TRUE if enabled";
    }
    leaf bandwidth-utilization {
      type uint32;
      units "percentage";
      description
        "Bandwidth utilization (hundredths of a percent)";
    }
    leaf bandwidth {
      type uint64;
      description
        "Port operational bandwidth";
    }
    leaf frame-preemption {
      type int32;
      description
        "Indicates whether Frame preemption is enabled";
    }
    leaf neighbor-mac-address {
      type Mac-addr;
      description
        "MAC addresses of the peer connection ";
    }
    leaf last-link-flap {
      type uint64;
      units "nanosecond";
      description
        "Last Link flap in elapsed nanoseconds since
         epoch";
    }
  }

  grouping ETHER-CTRL-STATS-PCS-VALIDITY-ST {
    description
      "ETHER CTRL STATS PCS VALIDITY ST";
    leaf validity-total-bip {
      type boolean;
      description
        "Flag indicating if Total BIP counter is valid";
    }
    leaf validity-total-frame-err {
      type boolean;
      description
        "Flag indicating if Total Frame Error counter is
         valid";
    }
    leaf validity-total-bad-sync-hdrs {
      type boolean;
      description
        "Flag indicating if Total Bad Sync Headers count
         is valid";
    }
  }

  grouping ETHER-CTRL-STATS-PCS-ST-TS {
    description
      "ETHER CTRL STATS PCS ST TS";
    leaf start-timestamp-total-bip {
      type uint64;
      units "millisecond";
      description
        "Start Timestamp for Total BIP counter (in msecs)";
    }
    leaf start-timestamp-total-frame-error {
      type uint64;
      units "millisecond";
      description
        "Start Timestamp for Total Frame error counter
         (in msecs)";
    }
    leaf start-timestamp-total-bad-sync-hdrs {
      type uint64;
      units "millisecond";
      description
        "Start Timestamp for Total Bad Sync Headers
         counter (in msecs)";
    }
  }

  grouping ETHER-PCS-DETAILS-TYPE {
    description
      "ETHER PCS DETAILS TYPE";
    container controller-stats-start-timestamp {
      description
        "Timestamp when PCS counters were created,last
         cleared or overrun(most recent event)";
      uses ETHER-CTRL-STATS-PCS-ST-TS;
    }
    container controller-stats-validity {
      description
        "Validity information for PCS counters, if PCS is
         supported";
      uses ETHER-CTRL-STATS-PCS-VALIDITY-ST;
    }
    leaf total-bip {
      type uint64;
      description
        "Total BIP errors for all lanes, if PCS is
         supported";
    }
    leaf total-frame-error {
      type uint64;
      description
        "Total Frame Errors for all lanes, if PCS is
         supported";
    }
    leaf total-bad-sync-hdrs {
      type uint64;
      description
        "Total Bad Sync Headers for all lanes, if PCS is
         supported";
    }
  }

  grouping EXTENDED-LOOPBACK-TYPE {
    description
      "EXTENDED LOOPBACK TYPE";
    leaf level {
      type uint32;
      description
        "Level";
    }
    leaf loopback {
      type Ethernet-loopback;
      description
        "Port operational loopback";
    }
  }

  grouping ETHER-FEC-BER-TYPE {
    description
      "ETHER FEC BER TYPE";
    leaf pre-fec-ber {
      type string;
      description
        "Bit Error Rate Before Forward Error Correction";
    }
    leaf post-fec-ber {
      type string;
      description
        "Bit Error Rate After Forward Error Correction";
    }
  }

  grouping ETHER-CTRL-STATS-FEC-VALIDITY-ST {
    description
      "ETHER CTRL STATS FEC VALIDITY ST";
    leaf validity-corrected-codeword-count {
      type boolean;
      description
        "Flag indicating if Corrected codeword count is
         valid";
    }
    leaf validity-uncorrected-codeword-count {
      type boolean;
      description
        "Flag indicating if Uncorrected codeword count is
         valid";
    }
  }

  grouping ETHER-CTRL-STATS-FEC-ST-TS {
    description
      "ETHER CTRL STATS FEC ST TS";
    leaf start-timestamp-corrected-codeword-count {
      type uint64;
      units "millisecond";
      description
        "Start Timestamp for Corrected codeword count (in
         msecs)";
    }
    leaf start-timestamp-uncorrected-codeword-count {
      type uint64;
      units "millisecond";
      description
        "Start Timestamp for Uncorrected codeword count
         (in msecs)";
    }
  }

  grouping ETHER-FEC-DETAILS-TYPE {
    description
      "ETHER FEC DETAILS TYPE";
    container controller-stats-start-timestamp {
      description
        "Timestamp when FEC stats were created,last
         cleared or overrun(most recent event)";
      uses ETHER-CTRL-STATS-FEC-ST-TS;
    }
    container controller-stats-validity {
      description
        "Validity information for FEC stats, if supported
         on platform";
      uses ETHER-CTRL-STATS-FEC-VALIDITY-ST;
    }
    leaf fec {
      type Ethernet-fec;
      description
        "Port operational FEC type";
    }
    leaf corrected-codeword-count {
      type uint64;
      description
        "Corrected codeword error count, if FEC is
         supported";
    }
    leaf uncorrected-codeword-count {
      type uint64;
      description
        "Uncorrected codeword error count, if FEC is
         supported";
    }
  }

  grouping ETH-CTRLR-PHY-DOM-ALARMS {
    description
      "ETH CTRLR PHY DOM ALARMS";
    leaf transceiver-temperature {
      type Ether-dom-alarm;
      description
        "Transceiver Optics Temperature Alarm State";
    }
    leaf transceiver-voltage {
      type Ether-dom-alarm;
      description
        "Transceiver Voltage Alarm State";
    }
    leaf transmit-laser-power {
      type Ether-dom-alarm;
      description
        "Transmit Laser Power Alarm State";
    }
    leaf received-laser-power {
      type Ether-dom-alarm;
      description
        "Received Optical Power Alarm State";
    }
    leaf laser-bias-current {
      type Ether-dom-alarm;
      description
        "Laser Bias Current Alarm State";
    }
  }

  grouping ETH-CTRLR-PHY-DOM-THRESHOLD-VALIDITY {
    description
      "ETH CTRLR PHY DOM THRESHOLD VALIDITY";
    leaf temperature-valid {
      type boolean;
      description
        "The temperature fields are valid";
    }
    leaf voltage-valid {
      type boolean;
      description
        "The voltage fields are valid";
    }
    leaf laser-bias-valid {
      type boolean;
      description
        "The laser bias fields are valid";
    }
    leaf transmit-power-valid {
      type boolean;
      description
        "The transmit power fields are valid";
    }
    leaf receive-power-valid {
      type boolean;
      description
        "The receive power fields are valid";
    }
  }

  grouping ETH-CTRLR-PHY-DOM-THRESHOLDS {
    description
      "ETH CTRLR PHY DOM THRESHOLDS";
    container field-validity {
      description
        "Indicates which of the DOM threshold fields are
         valid";
      uses ETH-CTRLR-PHY-DOM-THRESHOLD-VALIDITY;
    }
    leaf transceiver-temperature-alarm-high {
      type int32;
      description
        "Transceiver high temperature alarm threshold
         (mDegrees C)";
    }
    leaf transceiver-temperature-warning-high {
      type int32;
      description
        "Transceiver high temperature warning threshold
         (mDegrees C)";
    }
    leaf transceiver-temperature-warning-low {
      type int32;
      description
        "Transceiver low temperature warning threshold
         (mDegrees C)";
    }
    leaf transceiver-temperature-alarm-low {
      type int32;
      description
        "Transceiver low temperature alarm threshold
         (mDegrees C)";
    }
    leaf transceiver-voltage-alarm-high {
      type uint32;
      description
        "Transceiver high voltage alarm threshold (mV)";
    }
    leaf transceiver-voltage-warning-high {
      type uint32;
      description
        "Transceiver high voltage warning threshold (mV)";
    }
    leaf transceiver-voltage-warning-low {
      type uint32;
      description
        "Transceiver low voltage warning threshold (mV)";
    }
    leaf transceiver-voltage-alarm-low {
      type uint32;
      description
        "Transceiver low voltage alarm threshold (mV)";
    }
    leaf laser-bias-alarm-high {
      type uint32;
      description
        "Laser bias high alarm threshold (uA)";
    }
    leaf laser-bias-warning-high {
      type uint32;
      description
        "Laser bias high warning threshold (uA)";
    }
    leaf laser-bias-warning-low {
      type uint32;
      description
        "Laser bias low warning threshold (uA)";
    }
    leaf laser-bias-alarm-low {
      type uint32;
      description
        "Laser bias low alarm threshold (uA)";
    }
    leaf optical-transmit-power-alarm-high {
      type uint32;
      description
        "High optical transmit power alarm threshold (uW)";
    }
    leaf optical-transmit-power-warning-high {
      type uint32;
      description
        "High optical transmit power warning threshold
         (uW)";
    }
    leaf optical-transmit-power-warning-low {
      type uint32;
      description
        "Low optical transmit power warning threshold
         (uW)";
    }
    leaf optical-transmit-power-alarm-low {
      type uint32;
      description
        "Low optical transmit power alarm threshold (uW)";
    }
    leaf optical-receive-power-alarm-high {
      type uint32;
      description
        "High optical receive power alarm threshold (uW)";
    }
    leaf optical-receive-power-warning-high {
      type uint32;
      description
        "High optical receive power warning threshold
         (uW)";
    }
    leaf optical-receive-power-warning-low {
      type uint32;
      description
        "Low optical receive power warning threshold (uW)";
    }
    leaf optical-receive-power-alarm-low {
      type uint32;
      description
        "Low optical receive power alarm threshold (uW)";
    }
    leaf power-m-factor {
      type uint32;
      description
        "Power multipication factor for tx/rx
         alarm/warning";
    }
    leaf multipication-factor {
      type uint32;
      description
        "Multipication factor applicable for certain
         Platforms";
    }
  }

  grouping ETH-CTRLR-PHY-LANE-OPT-MON-VALIDITY {
    description
      "ETH CTRLR PHY LANE OPT MON VALIDITY";
    leaf wavelength-valid {
      type boolean;
      description
        "The wavelength 'per lane' field is valid";
    }
    leaf transmit-power-valid {
      type boolean;
      description
        "The transmit power 'per lane' field is valid";
    }
    leaf receive-power-valid {
      type boolean;
      description
        "The receive power 'per lane' field is valid";
    }
    leaf laser-bias-valid {
      type boolean;
      description
        "The laser bias 'per lane' field is valid";
    }
  }

  grouping ETH-CTRLR-PHY-DOM-LANE-ALARMS {
    description
      "ETH CTRLR PHY DOM LANE ALARMS";
    leaf transmit-laser-power {
      type Ether-dom-alarm;
      description
        "Transmit Laser Power Alarm";
    }
    leaf received-laser-power {
      type Ether-dom-alarm;
      description
        "Received Optical Power Alarm";
    }
    leaf laser-bias-current {
      type Ether-dom-alarm;
      description
        "Laser Bias Current Alarm";
    }
  }

  grouping ETH-CTRLR-PHY-LANE-OPT-MON {
    description
      "ETH CTRLR PHY LANE OPT MON";
    container dig-opt-mon-alarm {
      description
        "Digital Optical Monitoring alarms";
      uses ETH-CTRLR-PHY-DOM-LANE-ALARMS;
    }
    leaf center-wavelength {
      type uint32;
      description
        "Center Wavelength (nm*1000)";
    }
    leaf transmit-laser-power {
      type int32;
      description
        "Transmit Laser Power (dBm*1000)";
    }
    leaf received-laser-power {
      type int32;
      description
        "Received Optical Power (dBm*1000)";
    }
    leaf laser-bias-current {
      type uint32;
      description
        "Laser Bias Current (uAmps)";
    }
    leaf lane-id {
      type uint32;
      description
        "Numerical identifier for this lane";
    }
  }

  grouping ETHER-PHY-DETAILS-TYPE {
    description
      "ETHER PHY DETAILS TYPE";
    container lane-field-validity {
      description
        "Digital Optical Monitoring (per lane
         information) validity";
      uses ETH-CTRLR-PHY-LANE-OPT-MON-VALIDITY;
    }
    container dig-opt-mon-alarm-thresholds {
      description
        "Digital Optical Monitoring alarm thresholds";
      uses ETH-CTRLR-PHY-DOM-THRESHOLDS;
    }
    container dig-opt-mon-alarms {
      description
        "Digital Optical Monitoring alarms";
      uses ETH-CTRLR-PHY-DOM-ALARMS;
    }
    leaf vendor {
      type string;
      description
        "Name of the port optics manufacturer";
    }
    leaf vendor-part-number {
      type string;
      description
        "Part number for the port optics";
    }
    leaf vendor-serial-number {
      type string;
      description
        "Serial number for the port optics";
    }
    leaf transceiver-temperature {
      type int32;
      description
        "The temperature of the transceiver (mDegrees C)";
    }
    leaf transceiver-voltage {
      type int32;
      description
        "The input voltage to the transceiver (mV)";
    }
    leaf transceiver-tx-power {
      type int32;
      description
        "The transceiver transmit laser power (uW)";
    }
    leaf transceiver-rx-power {
      type int32;
      description
        "The transceiver receive optical power (uW)";
    }
    leaf transceiver-tx-bias {
      type int32;
      description
        "The laser bias of the transceiver (uA)";
    }
    leaf optics-wavelength {
      type uint32;
      description
        "Wavelength of the optics being used in nm * 1000";
    }
    leaf optics-type {
      type string;
      description
        "Optics module type";
    }
    leaf revision-number {
      type string;
      description
        "Module revision number";
    }
    list lane {
      description
        "Digital Optical Monitoring (per lane
         information)";
      uses ETH-CTRLR-PHY-LANE-OPT-MON;
    }
  }

  grouping ETH-CTRLR-PHY-INFO {
    description
      "ETH CTRLR PHY INFO";
    container phy-details {
      description
        "Details about the PHY";
      uses ETHER-PHY-DETAILS-TYPE;
    }
    container fec-details {
      description
        "Forward Error Correction information";
      uses ETHER-FEC-DETAILS-TYPE;
    }
    container fec-ber {
      description
        "Ethernet FEC BER values";
      uses ETHER-FEC-BER-TYPE;
    }
    container pcs-details {
      description
        "Physical Coding Sub-layer counter information";
      uses ETHER-PCS-DETAILS-TYPE;
    }
    leaf media-type {
      type Ethernet-media;
      description
        "Port media type";
    }
    leaf phy-present {
      type Ether-phy-present;
      description
        "Presence of PHY";
    }
    leaf loopback {
      type Ethernet-loopback;
      description
        "Port operational loopback";
    }
    leaf holdoff-time {
      type uint32;
      description
        "Ethernet port Holdoff Time";
    }
    list extended-loopback {
      description
        "Port operational extended loopback";
      uses EXTENDED-LOOPBACK-TYPE;
    }
  }

  grouping ETHERNET-CONTROLLER-DRIVER-BAG-V2-TYPE {
    description
      "Ethernet bag for driver state for the show
       controllers command";
    container phy-info {
      description
        "PHY information";
      uses ETH-CTRLR-PHY-INFO;
    }
    container layer1-info {
      description
        "Layer 1 information";
      uses ETH-CTRLR-L1-INFO;
    }
    container mac-info {
      description
        "MAC Layer information";
      uses ETH-CTRLR-MAC-INFO;
    }
    container transport-info {
      description
        "Transport state information";
      uses ETH-CTLR-TRANSPORT-INFO;
    }
    container prbs-info {
      description
        "Pseudo Random Binary Sequence test information";
      uses ETH-CTLR-PRBS-INFO;
    }
    leaf admin-state {
      type Ethernet-port-enable;
      description
        "Port Administrative State";
    }
    leaf oper-state-up {
      type boolean;
      description
        "Port Operational state - TRUE if up";
    }
  }

  grouping ETHER-PFC-DETAILS-V2 {
    description
      "Per port PFC stats";
    leaf priority-enabled-bitmap {
      type uint8;
      description
        "Bitmap to indicate the TC PFC is enabled";
    }
    leaf total-rx-frames {
      type uint64;
      description
        "Total Rx Frames";
    }
    leaf total-tx-frames {
      type uint64;
      description
        "Total Tx Frames";
    }
    leaf total-rx-drop-data-frames {
      type uint64;
      description
        "Total RxDrop Data Frames";
    }
    leaf per-tc-rx-drop-supported {
      type uint8;
      description
        "Indicates support for per TC RX drop Data frames";
    }
    leaf per-tc-tx-frames-not-supported {
      type uint8;
      description
        "Indicates support for per TC tx frames";
    }
    list rx-frame {
      max-elements "8";
      description
        "Rx Frames";
      leaf entry {
        type uint64;
        description
          "Rx Frames";
      }
    }
    list tx-frame {
      max-elements "8";
      description
        "Tx Frames";
      leaf entry {
        type uint64;
        description
          "Tx Frames";
      }
    }
    list rx-drop-data-frame {
      max-elements "8";
      description
        "Rx Drop Data Frames";
      leaf entry {
        type uint64;
        description
          "Rx Drop Data Frames";
      }
    }
  }

  grouping ETHER-CTRL-L2-VALIDITY-ST {
    description
      "ETHER CTRL L2 VALIDITY ST";
    leaf validity-received-total-bytes {
      type boolean;
      description
        "Validity of total octets of all frames recieved";
    }
    leaf validity-received-good-bytes {
      type boolean;
      description
        "Validity of total octets of all good frames
         recieved";
    }
    leaf validity-received-total-frames {
      type boolean;
      description
        "Validity of all frames, good or bad recieved";
    }
    leaf validity-received8021q-frames {
      type boolean;
      description
        "Validity of all 802.1Q frames recieved";
    }
    leaf validity-received-pause-frames {
      type boolean;
      description
        "Validity of all pause frames recieved";
    }
    leaf validity-received-unknown-opcodes {
      type boolean;
      description
        "Validity of unsupported MAC Control frames
         recieved";
    }
    leaf validity-received-total64-octet-frames {
      type boolean;
      description
        "Validity of all 64 Octet Frame Count recieved";
    }
    leaf validity-received-total-octet-frames-from65-to127 {
      type boolean;
      description
        "Validity of all 65-127 Octet Frame Count
         recieved";
    }
    leaf validity-received-total-octet-frames-from128-to255 {
      type boolean;
      description
        "Validity of all 128-255 Octet Frame Count
         recieved";
    }
    leaf validity-received-total-octet-frames-from256-to511 {
      type boolean;
      description
        "Validity of all 256-511 Octet Frame Count
         recieved";
    }
    leaf validity-received-total-octet-frames-from512-to1023 {
      type boolean;
      description
        "Validity of all 512-1023 Octet Frame Count
         recieved";
    }
    leaf validity-received-total-octet-frames-from1024-to1518 {
      type boolean;
      description
        "Validity of all 1024-1518 Octet Frame Count
         recieved";
    }
    leaf validity-received-total-octet-frames-from1519-to-max {
      type boolean;
      description
        "Validity of all > 1518 Octet Frame Count
         recieved";
    }
    leaf validity-received-good-frames {
      type boolean;
      description
        "Validity of number of well formed packets
         recieved";
    }
    leaf validity-received-unicast-frames {
      type boolean;
      description
        "Validity of number of unicast packets recieved";
    }
    leaf validity-received-multicast-frames {
      type boolean;
      description
        "Validity of number of multicast packets recieved";
    }
    leaf validity-received-broadcast-frames {
      type boolean;
      description
        "Validity of number of broadcast packets recieved";
    }
    leaf validity-number-of-buffer-overrun-packets-dropped {
      type boolean;
      description
        "Validity of input drops due to buffer overrun";
    }
    leaf validity-number-of-aborted-packets-dropped {
      type boolean;
      description
        "Validity of input drops due to packet abort";
    }
    leaf validity-numberof-invalid-vlan-id-packets-dropped {
      type boolean;
      description
        "Validity of input drops due to invalid VLAN id";
    }
    leaf validity-invalid-dest-mac-drop-packets {
      type boolean;
      description
        "Validity of input drops due to the destination
         MAC not matching";
    }
    leaf validity-invalid-encap-drop-packets {
      type boolean;
      description
        "Validity of input drops due to the encapsulation
         or ether type not matching";
    }
    leaf validity-number-of-miscellaneous-packets-dropped {
      type boolean;
      description
        "Validity of any other input drops not counted";
    }
    leaf validity-dropped-giant-packets-greaterthan-mru {
      type boolean;
      description
        "Validity of input Good frames > MRU, dropped";
    }
    leaf validity-dropped-ether-stats-undersize-pkts {
      type boolean;
      description
        "Validity of input Good frames < 64 Octet,
         dropped";
    }
    leaf validity-dropped-jabbers-packets-greaterthan-mru {
      type boolean;
      description
        "Validity of Bad input Frames > MRU, dropped";
    }
    leaf validity-dropped-ether-stats-fragments {
      type boolean;
      description
        "Validity of Bad input Frames < 64 Octet, dropped";
    }
    leaf validity-dropped-packets-with-crc-align-errors {
      type boolean;
      description
        "Validity of input Frames 64 - MRU with CRC error";
    }
    leaf validity-ether-stats-collisions {
      type boolean;
      description
        "Validity of all input collision events";
    }
    leaf validity-symbol-errors {
      type boolean;
      description
        "Validity of number of input symbol errors
         detected";
    }
    leaf validity-dropped-miscellaneous-error-packets {
      type boolean;
      description
        "Validity of Any other input errors not counted";
    }
    leaf validity-rfc2819-ether-stats-oversized-pkts {
      type boolean;
      description
        "Validity of input RFC2819
         etherStatsOversizedPkts";
    }
    leaf validity-rfc2819-ether-stats-jabbers {
      type boolean;
      description
        "Validity of input RFC2819 etherStatsJabbers";
    }
    leaf validity-rfc2819-ether-stats-crc-align-errors {
      type boolean;
      description
        "Validity of input RFC2819
         etherStatsCRCAlignErrors";
    }
    leaf validity-rfc3635dot3-stats-alignment-errors {
      type boolean;
      description
        "Validity of input RFC3635
         dot3StatsAlignmentErrors";
    }
    leaf validity-total-bytes-transmitted {
      type boolean;
      description
        "Validity of total octets of all frames sent";
    }
    leaf validity-total-good-bytes-transmitted {
      type boolean;
      description
        "Validity of total octets of all good frames sent";
    }
    leaf validity-total-frames-transmitted {
      type boolean;
      description
        "Validity of all frames, good or bad sent";
    }
    leaf validity-transmitted8021q-frames {
      type boolean;
      description
        "Validity of all 802.1Q frames sent";
    }
    leaf validity-transmitted-total-pause-frames {
      type boolean;
      description
        "Validity of all pause frames sent";
    }
    leaf validity-transmitted-total64-octet-frames {
      type boolean;
      description
        "Validity of all 64 Octet Frame Count sent";
    }
    leaf validity-transmitted-total-octet-frames-from65-to127 {
      type boolean;
      description
        "Validity of all 65-127 Octet Frame Count sent";
    }
    leaf validity-transmitted-total-octet-frames-from128-to255 {
      type boolean;
      description
        "Validity of all 128-255 Octet Frame Count sent";
    }
    leaf validity-transmitted-total-octet-frames-from256-to511 {
      type boolean;
      description
        "Validity of all 256-511 Octet Frame Count sent";
    }
    leaf validity-transmitted-total-octet-frames-from512-to1023 {
      type boolean;
      description
        "Validity of all 512-1023 Octet Frame Count sent";
    }
    leaf validity-transmitted-total-octet-frames-from1024-to1518 {
      type boolean;
      description
        "Validity of all 1024-1518 Octet Frame Count sent";
    }
    leaf validity-transmitted-total-octet-frames-from1518-to-max {
      type boolean;
      description
        "Validity of all > 1518 Octet Frame Count sent";
    }
    leaf validity-transmitted-good-frames {
      type boolean;
      description
        "Validity of number of well formed packets
         transmitted";
    }
    leaf validity-transmitted-unicast-frames {
      type boolean;
      description
        "Validity of number of unicast packets
         transmitted";
    }
    leaf validity-transmitted-multicast-frames {
      type boolean;
      description
        "Validity of number of multicast packets
         transmitted";
    }
    leaf validity-transmitted-broadcast-frames {
      type boolean;
      description
        "Validity of number of broadcast packets
         transmitted";
    }
    leaf validity-buffer-underrun-packet-drops {
      type boolean;
      description
        "Validity of output drops due to buffer underrun";
    }
    leaf validity-aborted-packet-drops {
      type boolean;
      description
        "Validity of output drops due to packet abort";
    }
    leaf validity-uncounted-dropped-frames {
      type boolean;
      description
        "Validity of any output drop not counted";
    }
    leaf validity-miscellaneous-output-errors {
      type boolean;
      description
        "Validity of any outputs error not counted";
    }
  }

  grouping ETHER-CTRL-L2-STATS-ST-TS {
    description
      "ETHER CTRL L2 STATS ST TS";
    leaf start-timestamp-received-total-bytes {
      type uint64;
      units "millisecond";
      description
        "Start Timestamp for Total octets of all frames
         recieved (in msecs)";
    }
    leaf start-timestamp-received-good-bytes {
      type uint64;
      units "millisecond";
      description
        "Start Timestamp for Total octets of all good
         frames recieved (in msecs)";
    }
    leaf start-timestamp-received-total-frames {
      type uint64;
      units "millisecond";
      description
        "Start Timestamp for All frames, good or bad
         recieved (in msecs)";
    }
    leaf start-timestamp-received8021q-frames {
      type uint64;
      units "millisecond";
      description
        "Start Timestamp for All 802.1Q frames recieved
         (in msecs)";
    }
    leaf start-timestamp-received-pause-frames {
      type uint64;
      units "millisecond";
      description
        "Start Timestamp for All pause frames recieved
         (in msecs)";
    }
    leaf start-timestamp-received-unknown-opcodes {
      type uint64;
      units "millisecond";
      description
        "Start Timestamp for Unsupported MAC Control
         frames recieved (in msecs)";
    }
    leaf start-timestamp-received-total64-octet-frames {
      type uint64;
      units "millisecond";
      description
        "Start Timestamp for All 64 Octet Frame Count
         recieved (in msecs)";
    }
    leaf start-timestamp-received-total-octet-frames-from65-to127 {
      type uint64;
      units "millisecond";
      description
        "Start Timestamp for All 65-127 Octet Frame Count
         recieved (in msecs)";
    }
    leaf start-timestamp-received-total-octet-frames-from128-to255 {
      type uint64;
      units "millisecond";
      description
        "Start Timestamp for All 128-255 Octet Frame
         Count recieved (in msecs)";
    }
    leaf start-timestamp-received-total-octet-frames-from256-to511 {
      type uint64;
      units "millisecond";
      description
        "Start Timestamp for All 256-511 Octet Frame
         Count recieved (in msecs)";
    }
    leaf start-timestamp-received-total-octet-frames-from512-to1023 {
      type uint64;
      units "millisecond";
      description
        "Start Timestamp for All 512-1023 Octet Frame
         Count recieved (in msecs)";
    }
    leaf start-timestamp-received-total-octet-frames-from1024-to1518 {
      type uint64;
      units "millisecond";
      description
        "Start Timestamp for All 1024-1518 Octet Frame
         Count recieved (in msecs)";
    }
    leaf start-timestamp-received-total-octet-frames-from1519-to-max {
      type uint64;
      units "millisecond";
      description
        "Start Timestamp for All > 1518 Octet Frame Count
         recieved (in msecs)";
    }
    leaf start-timestamp-received-good-frames {
      type uint64;
      units "millisecond";
      description
        "Start Timestamp for Number of well formed
         packets recieved (in msecs)";
    }
    leaf start-timestamp-received-unicast-frames {
      type uint64;
      units "millisecond";
      description
        "Start Timestamp for Number of unicast packets
         recieved (in msecs)";
    }
    leaf start-timestamp-received-multicast-frames {
      type uint64;
      units "millisecond";
      description
        "Start Timestamp for Number of multicast packets
         recieved (in msecs)";
    }
    leaf start-timestamp-received-broadcast-frames {
      type uint64;
      units "millisecond";
      description
        "Start Timestamp for Number of broadcast packets
         recieved (in msecs)";
    }
    leaf start-timestamp-number-of-buffer-overrun-packets-dropped {
      type uint64;
      units "millisecond";
      description
        "Start Timestamp for input Drops due to buffer
         overrun (in msecs)";
    }
    leaf start-timestamp-number-of-aborted-packets-dropped {
      type uint64;
      units "millisecond";
      description
        "Start Timestamp for input Drops due to packet
         abort (in msecs)";
    }
    leaf start-timestamp-numberof-invalid-vlan-id-packets-dropped {
      type uint64;
      units "millisecond";
      description
        "Start Timestamp for input Drops due to invalid
         VLAN id (in msecs)";
    }
    leaf start-timestamp-invalid-dest-mac-drop-packets {
      type uint64;
      units "millisecond";
      description
        "Start Timestamp for input Drops due to the
         destination MAC not matching (in msecs)";
    }
    leaf start-timestamp-invalid-encap-drop-packets {
      type uint64;
      units "millisecond";
      description
        "Start Timestamp for input Drops due to the
         encapsulation or ether type not matching (in
         msecs)";
    }
    leaf start-timestamp-number-of-miscellaneous-packets-dropped {
      type uint64;
      units "millisecond";
      description
        "Start Timestamp for Any other input drops not
         counted (in msecs)";
    }
    leaf start-timestamp-dropped-giant-packets-greaterthan-mru {
      type uint64;
      units "millisecond";
      description
        "Start Timestamp for input Good frames > MRU,
         dropped (in msecs)";
    }
    leaf start-timestamp-dropped-ether-stats-undersize-pkts {
      type uint64;
      units "millisecond";
      description
        "Start Timestamp for input Good frames < 64 Octet
         , dropped (in msecs)";
    }
    leaf start-timestamp-dropped-jabbers-packets-greaterthan-mru {
      type uint64;
      units "millisecond";
      description
        "Start Timestamp for Bad input Frames > MRU,
         dropped (in msecs)";
    }
    leaf start-timestamp-dropped-ether-stats-fragments {
      type uint64;
      units "millisecond";
      description
        "Start Timestamp for Bad input Frames < 64 Octet,
         dropped (in msecs)";
    }
    leaf start-timestamp-dropped-packets-with-crc-align-errors {
      type uint64;
      units "millisecond";
      description
        "Start Timestamp for input Frames 64 - MRU with
         CRC error (in msecs)";
    }
    leaf start-timestamp-ether-stats-collisions {
      type uint64;
      units "millisecond";
      description
        "Start Timestamp for all input collision events
         (in msecs)";
    }
    leaf start-timestamp-symbol-errors {
      type uint64;
      units "millisecond";
      description
        "Start Timestamp for Number of input symbol
         errors detected (in msecs)";
    }
    leaf start-timestamp-dropped-miscellaneous-error-packets {
      type uint64;
      units "millisecond";
      description
        "Start Timestamp for Any other input errors not
         counted (in msecs)";
    }
    leaf start-timestamp-rfc2819-ether-stats-oversized-pkts {
      type uint64;
      units "millisecond";
      description
        "Start Timestamp for input RFC2819
         etherStatsOversizedPkts (in msecs)";
    }
    leaf start-timestamp-rfc2819-ether-stats-jabbers {
      type uint64;
      units "millisecond";
      description
        "Start Timestamp for input RFC2819
         etherStatsJabbers (in msecs)";
    }
    leaf start-timestamp-rfc2819-ether-stats-crc-align-errors {
      type uint64;
      units "millisecond";
      description
        "Start Timestamp for input RFC2819
         etherStatsCRCAlignErrors (in msecs)";
    }
    leaf start-timestamp-rfc3635dot3-stats-alignment-errors {
      type uint64;
      units "millisecond";
      description
        "Start Timestamp for input RFC3635
         dot3StatsAlignmentErrors (in msecs)";
    }
    leaf start-timestamp-total-bytes-transmitted {
      type uint64;
      units "millisecond";
      description
        "Start Timestamp for Total octets of all frames
         sent (in msecs)";
    }
    leaf start-timestamp-total-good-bytes-transmitted {
      type uint64;
      units "millisecond";
      description
        "Start Timestamp for Total octets of all good
         frames sent (in msecs)";
    }
    leaf start-timestamp-total-frames-transmitted {
      type uint64;
      units "millisecond";
      description
        "Start Timestamp for All frames, good or bad sent
         (in msecs)";
    }
    leaf start-timestamp-transmitted8021q-frames {
      type uint64;
      units "millisecond";
      description
        "Start Timestamp for All 802.1Q frames sent (in
         msecs)";
    }
    leaf start-timestamp-transmitted-total-pause-frames {
      type uint64;
      units "millisecond";
      description
        "Start Timestamp for All pause frames sent (in
         msecs)";
    }
    leaf start-timestamp-transmitted-total64-octet-frames {
      type uint64;
      units "millisecond";
      description
        "Start Timestamp for All 64 Octet Frame Count
         sent (in msecs)";
    }
    leaf start-timestamp-transmitted-total-octet-frames-from65-to127 {
      type uint64;
      units "millisecond";
      description
        "Start Timestamp for All 65-127 Octet Frame Count
         sent (in msecs)";
    }
    leaf start-timestamp-transmitted-total-octet-frames-from128-to255 {
      type uint64;
      units "millisecond";
      description
        "Start Timestamp for All 128-255 Octet Frame
         Count sent (in msecs)";
    }
    leaf start-timestamp-transmitted-total-octet-frames-from256-to511 {
      type uint64;
      units "millisecond";
      description
        "Start Timestamp for All 256-511 Octet Frame
         Count sent (in msecs)";
    }
    leaf start-timestamp-transmitted-total-octet-frames-from512-to1023 {
      type uint64;
      units "millisecond";
      description
        "Start Timestamp for All 512-1023 Octet Frame
         Count sent (in msecs)";
    }
    leaf start-timestamp-transmitted-total-octet-frames-from1024-to1518 {
      type uint64;
      units "millisecond";
      description
        "Start Timestamp for All 1024-1518 Octet Frame
         Count sent (in msecs)";
    }
    leaf start-timestamp-transmitted-total-octet-frames-from1518-to-max {
      type uint64;
      units "millisecond";
      description
        "Start Timestamp for All > 1518 Octet Frame Count
         sent (in msecs)";
    }
    leaf start-timestamp-transmitted-good-frames {
      type uint64;
      units "millisecond";
      description
        "Start Timestamp for Number of well formed
         packets transmitted (in msecs)";
    }
    leaf start-timestamp-transmitted-unicast-frames {
      type uint64;
      units "millisecond";
      description
        "Start Timestamp for Number of unicast packets
         transmitted (in msecs)";
    }
    leaf start-timestamp-transmitted-multicast-frames {
      type uint64;
      units "millisecond";
      description
        "Start Timestamp for Number of multicast packets
         transmitted (in msecs)";
    }
    leaf start-timestamp-transmitted-broadcast-frames {
      type uint64;
      units "millisecond";
      description
        "Start Timestamp for Number of broadcast packets
         transmitted (in msecs)";
    }
    leaf start-timestamp-buffer-underrun-packet-drops {
      type uint64;
      units "millisecond";
      description
        "Start Timestamp for output drops due to buffer
         underrun (in msecs)";
    }
    leaf start-timestamp-aborted-packet-drops {
      type uint64;
      units "millisecond";
      description
        "Start Timestamp for output drops due to packet
         abort (in msecs)";
    }
    leaf start-timestamp-uncounted-dropped-frames {
      type uint64;
      units "millisecond";
      description
        "Start Timestamp for any output drop not counted
         (in msecs)";
    }
    leaf start-timestamp-miscellaneous-output-errors {
      type uint64;
      units "millisecond";
      description
        "Start Timestamp for any outputs error not
         counted (in msecs)";
    }
  }

  grouping ETHERNET-L2-CONTROLLER-STATS {
    description
      "Layer 2 Controller Stats";
    container controller-stats-start-timestamp {
      description
        "Timestamp when layer 2 controller stats were
         created,last cleared or overrun(most recent
         event)";
      uses ETHER-CTRL-L2-STATS-ST-TS;
    }
    container controller-stats-validity {
      description
        "Validity information for controller stats per
         counter for the port";
      uses ETHER-CTRL-L2-VALIDITY-ST;
    }
    leaf received-total-bytes {
      type uint64;
      description
        "Total octets of all frames";
    }
    leaf received-good-bytes {
      type uint64;
      description
        "Total octets of all good frames";
    }
    leaf received-total-frames {
      type uint64;
      description
        "All frames, good or bad";
    }
    leaf received8021q-frames {
      type uint64;
      description
        "All 802.1Q frames";
    }
    leaf received-pause-frames {
      type uint64;
      description
        "All pause frames";
    }
    leaf received-unknown-opcodes {
      type uint64;
      description
        "Unsupported MAC Control frames";
    }
    leaf received-total64-octet-frames {
      type uint64;
      description
        "All 64 Octet Frame Count";
    }
    leaf received-total-octet-frames-from65-to127 {
      type uint64;
      description
        "All 65-127 Octet Frame Count";
    }
    leaf received-total-octet-frames-from128-to255 {
      type uint64;
      description
        "All 128-255 Octet Frame Count";
    }
    leaf received-total-octet-frames-from256-to511 {
      type uint64;
      description
        "All 256-511 Octet Frame Count";
    }
    leaf received-total-octet-frames-from512-to1023 {
      type uint64;
      description
        "All 512-1023 Octet Frame Count";
    }
    leaf received-total-octet-frames-from1024-to1518 {
      type uint64;
      description
        "All 1024-1518 Octet Frame Count";
    }
    leaf received-total-octet-frames-from1519-to-max {
      type uint64;
      description
        "All > 1518 Octet Frame Count";
    }
    leaf received-good-frames {
      type uint64;
      description
        "Number of well formed packets received";
    }
    leaf received-unicast-frames {
      type uint64;
      description
        "Number of unicast packets received ";
    }
    leaf received-multicast-frames {
      type uint64;
      description
        "Number of multicast packets received";
    }
    leaf received-broadcast-frames {
      type uint64;
      description
        "Number of broadcast packets received";
    }
    leaf number-of-buffer-overrun-packets-dropped {
      type uint64;
      description
        "Drops due to buffer overrun";
    }
    leaf number-of-aborted-packets-dropped {
      type uint64;
      description
        "Drops due to packet abort";
    }
    leaf numberof-invalid-vlan-id-packets-dropped {
      type uint64;
      description
        "Drops due to invalid VLAN id";
    }
    leaf invalid-dest-mac-drop-packets {
      type uint64;
      description
        "Drops due to the destination MAC not matching";
    }
    leaf invalid-encap-drop-packets {
      type uint64;
      description
        "Drops due to the encapsulation or ether type not
         matching";
    }
    leaf number-of-miscellaneous-packets-dropped {
      type uint64;
      description
        "Any other drops not counted";
    }
    leaf dropped-giant-packets-greaterthan-mru {
      type uint64;
      description
        "Good frames > MRU, dropped";
    }
    leaf dropped-ether-stats-undersize-pkts {
      type uint64;
      description
        "Good frames < 64 Octet, dropped";
    }
    leaf dropped-jabbers-packets-greaterthan-mru {
      type uint64;
      description
        "Bad Frames > MRU, dropped";
    }
    leaf dropped-ether-stats-fragments {
      type uint64;
      description
        "Bad Frames < 64 Octet, dropped";
    }
    leaf dropped-packets-with-crc-align-errors {
      type uint64;
      description
        "Frames 64 - MRU with CRC error";
    }
    leaf ether-stats-collisions {
      type uint64;
      description
        "All collision events";
    }
    leaf symbol-errors {
      type uint64;
      description
        "Number of symbol errors detected";
    }
    leaf dropped-miscellaneous-error-packets {
      type uint64;
      description
        "Any other errors not counted";
    }
    leaf rfc2819-ether-stats-oversized-pkts {
      type uint64;
      description
        "RFC2819 etherStatsOversizedPkts";
    }
    leaf rfc2819-ether-stats-jabbers {
      type uint64;
      description
        "RFC2819 etherStatsJabbers";
    }
    leaf rfc2819-ether-stats-crc-align-errors {
      type uint64;
      description
        "RFC2819 etherStatsCRCAlignErrors";
    }
    leaf rfc3635dot3-stats-alignment-errors {
      type uint64;
      description
        "RFC3635 dot3StatsAlignmentErrors";
    }
    leaf total-bytes-transmitted {
      type uint64;
      description
        "Total octets of all frames";
    }
    leaf total-good-bytes-transmitted {
      type uint64;
      description
        "Total octets of all good frames";
    }
    leaf total-frames-transmitted {
      type uint64;
      description
        "All frames, good or bad";
    }
    leaf transmitted8021q-frames {
      type uint64;
      description
        "All 802.1Q frames";
    }
    leaf transmitted-total-pause-frames {
      type uint64;
      description
        "All pause frames";
    }
    leaf transmitted-total64-octet-frames {
      type uint64;
      description
        "All 64 Octet Frame Count";
    }
    leaf transmitted-total-octet-frames-from65-to127 {
      type uint64;
      description
        "All 65-127 Octet Frame Count";
    }
    leaf transmitted-total-octet-frames-from128-to255 {
      type uint64;
      description
        "All 128-255 Octet Frame Count";
    }
    leaf transmitted-total-octet-frames-from256-to511 {
      type uint64;
      description
        "All 256-511 Octet Frame Count";
    }
    leaf transmitted-total-octet-frames-from512-to1023 {
      type uint64;
      description
        "All 512-1023 Octet Frame Count";
    }
    leaf transmitted-total-octet-frames-from1024-to1518 {
      type uint64;
      description
        "All 1024-1518 Octet Frame Count";
    }
    leaf transmitted-total-octet-frames-from1518-to-max {
      type uint64;
      description
        "All > 1518 Octet Frame Count";
    }
    leaf transmitted-good-frames {
      type uint64;
      description
        "Number of well formed packets transmitted";
    }
    leaf transmitted-unicast-frames {
      type uint64;
      description
        "Number of unicast packets transmitted";
    }
    leaf transmitted-multicast-frames {
      type uint64;
      description
        "Number of multicast packets transmitted";
    }
    leaf transmitted-broadcast-frames {
      type uint64;
      description
        "Number of broadcast packets transmitted";
    }
    leaf buffer-underrun-packet-drops {
      type uint64;
      description
        "Drops due to buffer underrun";
    }
    leaf aborted-packet-drops {
      type uint64;
      description
        "Drops due to packet abort";
    }
    leaf uncounted-dropped-frames {
      type uint64;
      description
        "Any other drops not counted";
    }
    leaf miscellaneous-output-errors {
      type uint64;
      description
        "Any other errors not counted";
    }
  }
}
