submodule Cisco-IOS-XR-asr9k-qos-hal-np-res-oper-sub1 {
  belongs-to Cisco-IOS-XR-asr9k-qos-hal-np-res-oper {
    prefix Cisco-IOS-XR-asr9k-qos-hal-np-res-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR asr9k-qos-hal-np-res package operational data.
     
     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  grouping NPHAL-POLICE-PROFILE {
    description
      "Police Profile";
    leaf hw-count {
      type uint32;
      description
        "Resources Allocated in Hardware";
    }
    leaf sw-count {
      type uint32;
      description
        "Resources Allocated in Software";
    }
    leaf ref-count {
      type uint32;
      description
        "Reference Count";
    }
  }

  grouping NPHAL-PROFILE {
    description
      "Profile";
    container tm-counters {
      description
        "TMCounters";
      uses NPHAL-TM-COUNTERS;
    }
    leaf feature {
      type string;
      description
        "Feature";
    }
  }

  grouping NPHAL-GROUPS {
    description
      "Groups";
    container chunk-counters {
      description
        "Chunk Counters";
      uses NPHAL-CHUNK-COUNTERS;
    }
  }

  grouping NPHAL-ENTITIES {
    description
      "Entities";
    container chunk-counters {
      description
        "Chunk Counters";
      uses NPHAL-CHUNK-COUNTERS;
    }
  }

  grouping NPHAL-PER-TM-SUMMARY {
    description
      "Per TM Summary";
    container entities {
      description
        "Entities";
      uses NPHAL-ENTITIES;
    }
    container groups {
      description
        "Groups";
      uses NPHAL-GROUPS;
    }
    leaf tm {
      type uint32;
      description
        "TM ID";
    }
  }

  grouping NPHAL-TM-SUMMARY {
    description
      "TM Summary";
    container policers {
      description
        "Policers";
      uses NPHAL-POLICERS;
    }
    list per-tm-summary {
      description
        "Per TM Summary";
      uses NPHAL-PER-TM-SUMMARY;
    }
  }

  grouping NPHAL-NP-SUMMARY {
    description
      "NP Summary";
    container policy-instances {
      description
        "Policy Instances";
      uses NPHAL-POLICY-INSTANCES;
    }
    container tm-summary {
      description
        "TM Summary";
      uses NPHAL-TM-SUMMARY;
    }
    container wfq-profile {
      description
        "WFQ Profile";
      uses NPHAL-PROFILE;
    }
    container shape-profile {
      description
        "Shape Profile";
      uses NPHAL-PROFILE;
    }
    container wred-profile {
      description
        "WRED Profile";
      uses NPHAL-PROFILE;
    }
    container police-profile {
      description
        "Police Profile";
      uses NPHAL-POLICE-PROFILE;
    }
  }

  grouping NPHAL-POLICER-COUNTER {
    description
      "Policer Regular";
    leaf hw-count {
      type uint32;
      description
        "Resources Allocated in Hardware";
    }
    leaf sw-count {
      type uint32;
      description
        "Resources Allocated in Software";
    }
  }

  grouping NPHAL-POLICERS {
    description
      "Policers";
    container regular {
      description
        "Regular";
      uses NPHAL-POLICER-COUNTER;
    }
    container color-aware {
      description
        "Color Aware";
      uses NPHAL-POLICER-COUNTER;
    }
    container coupled-parent {
      description
        "Coupled Parent";
      uses NPHAL-POLICER-COUNTER;
    }
    container coupled-child {
      description
        "Coupled Child";
      uses NPHAL-POLICER-COUNTER;
    }
    container total {
      description
        "total";
      uses NPHAL-POLICER-COUNTER;
    }
  }

  grouping NPHAL-LEVEL-COUNTER {
    description
      "Level Counter";
    leaf level {
      type string;
      description
        "Level";
    }
    leaf hw-count {
      type uint32;
      description
        "Resources Allocated in Hardware";
    }
    leaf sw-count {
      type uint32;
      description
        "Resources Allocated in Software";
    }
    leaf ref-count {
      type uint32;
      description
        "Reference Count";
    }
  }

  grouping NPHAL-LEVEL-COUNTERS {
    description
      "Level Counters";
    list level-counter {
      description
        "Level Counter";
      uses NPHAL-LEVEL-COUNTER;
    }
  }

  grouping NPHAL-CHUNK-COUNTER {
    description
      "Chunk Counter";
    container level-counters {
      description
        "Level Counters";
      uses NPHAL-LEVEL-COUNTERS;
    }
    leaf chunk {
      type uint32;
      description
        "Chunk";
    }
  }

  grouping NPHAL-CHUNK-COUNTERS {
    description
      "Chunk Counters";
    list chunk-counter {
      description
        "Chunk Counter";
      uses NPHAL-CHUNK-COUNTER;
    }
  }

  grouping NPHAL-TM-COUNTER {
    description
      "TM Counter";
    container chunk-counters {
      description
        "Chunk Counters";
      uses NPHAL-CHUNK-COUNTERS;
    }
    leaf tm {
      type uint32;
      description
        "TM ID";
    }
  }

  grouping NPHAL-TM-COUNTERS {
    description
      "TM Counters";
    list tm-counter {
      description
        "TM Counter";
      uses NPHAL-TM-COUNTER;
    }
  }

  grouping NPHAL-POLICY-INSTANCES {
    description
      "Policy Instances";
    leaf ingress {
      type uint32;
      description
        "Ingress";
    }
    leaf egress {
      type uint32;
      description
        "Engress";
    }
    leaf total {
      type uint32;
      description
        "Total";
    }
  }

  grouping NPHAL-CLIENT-COUNTER {
    description
      "Client Counters";
    container policy-instances {
      description
        "Policy Instances";
      uses NPHAL-POLICY-INSTANCES;
    }
    container tm-counters {
      description
        "TM Counter";
      uses NPHAL-TM-COUNTERS;
    }
    container policers {
      description
        "policers";
      uses NPHAL-POLICERS;
    }
    leaf client {
      type string;
      description
        "Client Name";
    }
  }

  grouping NPHAL-CLIENT-COUNTERS {
    description
      "Client Counter";
    list client-counter {
      description
        "Client Counter";
      uses NPHAL-CLIENT-COUNTER;
    }
  }

  grouping NPHAL-RESOURCE-COUNTERS {
    description
      "Resource Counters";
    container client-counters {
      description
        "Client Counters";
      uses NPHAL-CLIENT-COUNTERS;
    }
    container np-summary {
      description
        "NP Summary";
      uses NPHAL-NP-SUMMARY;
    }
  }
}
