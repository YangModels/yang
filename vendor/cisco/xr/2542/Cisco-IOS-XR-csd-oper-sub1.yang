submodule Cisco-IOS-XR-csd-oper-sub1 {
  belongs-to Cisco-IOS-XR-csd-oper {
    prefix Cisco-IOS-XR-csd-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR csd package operational data.
     
     Copyright (c) 2013-2021 by Cisco Systems, Inc.
     All rights reserved.";

  revision 2021-07-23 {
    description
      "Removed the trusted_peers endpoint.";
    semver:module-version "1.0.0";
  }
  revision 2021-04-19 {
    description
      "Oper yang for CSD.";
  }
  revision 2019-04-05 {
    description
      "Establish semantic version baseline.";
  }
  revision 2015-11-09 {
    description
      "IOS XR 6.0 revision.";
  }

  typedef Tpm {
    type enumeration {
      enum "tpm-20" {
        description
          "tpm 20";
      }
      enum "tpm-12" {
        description
          "tpm 12";
      }
    }
    description
      "Tpm";
  }

  typedef String-array {
    type string;
    description
      "String array";
  }

  grouping ENCODED-ATT-RESULTS-DATA {
    description
      "ENCODED ATT RESULTS DATA";
    leaf encoded-att-results-data {
      type string;
      description
        "Attestation Results in CBOR-Encoded format";
    }
  }

  grouping PUB-KEY-GROUPING {
    description
      "PUB KEY GROUPING";
    leaf public-key-format {
      type string;
      description
        "Key Format Eg: DER, PEM";
    }
    leaf public-key {
      type string;
      description
        "Attester's public key";
    }
  }

  grouping PCRVALUE {
    description
      "PCRVALUE";
    leaf value {
      type string;
      description
        "PCR Value";
    }
  }

  grouping TPM12-INTERNALS {
    description
      "TPM1.2 Details";
    leaf timestamp {
      type string;
      description
        "The timestamp of the Verifier's appraisal";
    }
    leaf-list pcr-indice {
      type uint32;
      description
        "Indices of the desired PCRs";
    }
    list pcr-value {
      description
        "Values of desired PCRs";
      uses PCRVALUE;
    }
  }

  grouping TPM20-PCR-BANK-ENTRY {
    description
      "Information about one pcr bank";
    leaf hash-algorithm {
      type uint32;
      description
        "Hash algorithm used in numerical format as
         specified by TCG docs";
    }
    leaf-list pcr-indice {
      type uint32;
      description
        "Mentiones what PCRs are used to calculate the
         tpm2b digest";
    }
  }

  grouping TPM20-INTERNALS {
    description
      "Unmarshaled TPM2.0 Quote";
    leaf tpm2b-digest {
      type string;
      description
        "Hash/Digest of the string obtained by
         concatenating desired PCRs";
    }
    leaf clock {
      type uint64;
      description
        "Clock is a monotonically increasing counter that
         advances whenever power is applied to a TPM2. It
         is incremented every millisecond";
    }
    leaf reset-counter {
      type uint32;
      description
        "The counter increments on each TPM reset";
    }
    leaf restart-counter {
      type uint32;
      description
        "This counter shall increment by one for each TPM
         restart or resume";
    }
    leaf safe {
      type boolean;
      description
        "This parameter is set to YES when the value
         reported in Clock is guaranteed to be unique for
         the current owner";
    }
    list tpm20-pcr-bank {
      description
        "List of all PCR banks";
      uses TPM20-PCR-BANK-ENTRY;
    }
  }

  grouping TPM-DATA {
    description
      "TPM DATA";
    container tpm20-quote {
      when "../t = 'tpm-20'" {
        description
          "../t = 'TPM_20'";
      }
      description
        "tpm20 quote";
      uses TPM20-INTERNALS;
    }
    container tpm12-quote {
      when "../t = 'tpm-12'" {
        description
          "../t = 'TPM_12'";
      }
      description
        "tpm12 quote";
      uses TPM12-INTERNALS;
    }
    leaf t {
      type Tpm;
      description
        "t";
    }
  }

  grouping ATT-RESULTS-DATA {
    description
      "Unverified attestation results";
    container tpm-data {
      description
        "Based on tpm type, this data is evaluated";
      uses TPM-DATA;
    }
    container pubkey-grouping {
      description
        "Public Key Grouping";
      uses PUB-KEY-GROUPING;
    }
    leaf public-key-algorithm-type {
      type string;
      description
        "Public Key Algorithm type";
    }
    leaf verifier-sig-key-name {
      type string;
      description
        "A hint to identify the Verifier Key";
    }
    leaf verifier-key-algo-type {
      type string;
      description
        "Verifier Key Algorithm type";
    }
    leaf-list trustworthiness-vector {
      type String-array;
      description
        "Verifier evaluation of the Evidence";
    }
  }

  grouping MAC-PEER {
    description
      "MAC PEER";
    leaf peer-name {
      type string;
      description
        "Peer's name/MAC Address";
    }
    leaf-list trust-vector {
      type String-array;
      description
        "Trust vector for the peer";
    }
  }

  grouping CANARYSTAMP-INTERFACE {
    description
      "CANARYSTAMP INTERFACE";
    leaf if-name {
      type string;
      description
        "Interface Name";
    }
    list peers {
      description
        "List of all peers";
      uses MAC-PEER;
    }
  }

  grouping CANARYSTAMP-PEERS {
    description
      "CANARYSTAMP PEERS";
    list interface {
      description
        "Interface list";
      uses CANARYSTAMP-INTERFACE;
    }
  }
}
