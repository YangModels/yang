module Cisco-IOS-XR-controller-ots-cfg {
  namespace "http://cisco.com/ns/yang/Cisco-IOS-XR-controller-ots-cfg";
  prefix controller-ots-cfg;

  import cisco-semver {
    prefix semver;
  }
  import Cisco-IOS-XR-ifmgr-cfg {
    prefix a1;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR controller-ots package configuration.
     
     This YANG module augments the
       Cisco-IOS-XR-ifmgr-cfg
     module with configuration data.
     
     Copyright (c) 2013-2025 by Cisco Systems, Inc.
     All rights reserved.";

  revision 2025-05-14 {
    description
      "Updated ranges of raman-tx-power and raman-tx-power-disable";
    semver:module-version "1.0.0";
  }
  revision 2025-05-09 {
    description
      "Updated ranges of ots-rx-low-threshold, ots-tx-low-threshold, and changed the string of RxLowThreshold to TxLowThreshold";
  }
  revision 2025-01-28 {
    description
      "updated tone-pattern datatype from string to HexString";
  }
  revision 2024-05-15 {
    description
      "Updated config range for egress amplifier power";
  }
  revision 2024-04-06 {
    description
      "Changed data type for ots ToneRate";
  }
  revision 2024-03-15 {
    description
      "ots-otdr-rx-auto-excess-attenuation-threshold, ots-otdr-tx-auto-excess-attenuation-threshold configuration range change";
  }
  revision 2023-12-14 {
    description
      "ots-otdr-rx-auto-end-of-fiber-loss-threshold, ots-otdr-tx-auto-end-of-fiber-loss-threshold are added to configuration";
  }
  revision 2023-09-20 {
    description
      "ots-ingress-amplifier-gain, ots-egress-amplifier-gain leaf range enhanced";
  }
  revision 2023-08-25 {
    description
      "Added support for raman safety triggers";
  }
  revision 2023-08-14 {
    description
      "Added OTDR Excess Attenuation and OTDR Excess Optical Return Loss Threshold config support for OTS controllers";
  }
  revision 2023-05-23 {
    description
      "ots-rx-low-threshold, ots-tx-low-threshold and ots-ampli-control-mode leaves are added for ots";
  }
  revision 2023-01-18 {
    description
      "Leaves ots-ingress-amplifier-mode, ots-egress-amplifier-mode and ots-ingress-amplifier-power added. Increased range for ots-egress-amplifier-power.";
  }
  revision 2023-01-13 {
    description
      "Range increased for ots egress ampli gain.";
  }
  revision 2023-01-04 {
    description
      "leaf raman-safety-control-mode is removed from configuration";
  }
  revision 2022-12-28 {
    description
      "datatype is changed to signed int32 for ingress-ampli, egress-ampli, tx-voa-attn";
  }
  revision 2022-11-16 {
    description
      "Config for expected tone pattern below minimum length gets accepted on passive controllers,correction of the same";
  }
  revision 2022-10-17 {
    description
      "egress-ampli-power config support added";
  }
  revision 2022-08-22 {
    description
      "Removal of egress-ampli-br-high-th, egress-ampli-br and Ots-br-state";
  }
  revision 2022-08-22 {
    description
      "Removal of egress-ampli-br-high-th, egress-ampli-br and Ots-br-state";
  }
  revision 2022-06-15 {
    description
      "Range increased for ots ingress and egress ampli gain max value";
  }
  revision 2022-05-31 {
    description
      "ots-rx-low-threshold and ots-tx-low-threshold leaves are added for ots info container";
  }
  revision 2021-12-23 {
    description
      "Parameters egress_ampli_br_high_th_cfgd, egress_ampli_br_cfgd, raman_br_cfgd and raman_br_high_th_cfgd are removed from configuration";
  }
  revision 2021-11-30 {
    description
      "raman tx power disable parameter support added";
  }
  revision 2021-11-26 {
    description
      "excess reflection threshold parameter support added";
  }
  revision 2021-06-30 {
    description
      "Added OTS OTDR config parameters";
  }
  revision 2021-06-01 {
    description
      "Added OTS TX Voa Attenuation and changed range for Ingress and Egress Ampli Gain Params";
  }
  revision 2021-03-28 {
    description
      "egress-ampli-br-high-th-cfgd, egress-ampli-br-cfgd are added to configuration";
  }
  revision 2021-03-16 {
    description
      "Ingress/Egress Channel Attenuation config Params added for Ots Controller";
  }
  revision 2021-02-17 {
    description
      "Raman safety config Params added";
  }
  revision 2021-02-08 {
    description
      "Ingress/Egress safety config Params added";
  }
  revision 2020-09-02 {
    description
      "Raman Transmit Params added for Ots Controller";
  }
  revision 2020-08-21 {
    description
      "New Cfg Model Added for Ots Controller";
  }
  revision 2019-04-05 {
    description
      "Establish semantic version baseline.";
  }
  revision 2015-11-09 {
    description
      "IOS XR 6.0 revision.";
  }

  typedef Ots-ingress-egress-ampli-gain-range {
    type enumeration {
      enum "normal" {
        value 1;
        description
          "Normal Amplifier Gain Range";
      }
      enum "extended" {
        value 2;
        description
          "Extended Amplifier Gain Range";
      }
    }
    description
      "Ots ingress egress ampli gain range";
  }

  typedef Ots-ampli-working-mode {
    type enumeration {
      enum "power" {
        value 2;
        description
          "Amplifier working mode power";
      }
    }
    description
      "Ots ampli working mode";
  }

  typedef Ots-back-reflection-state {
    type enumeration {
      enum "disable" {
        value 0;
        description
          "Back Reflection State, Disable";
      }
      enum "enable" {
        value 1;
        description
          "Back Reflection State, Enable";
      }
    }
    description
      "Ots back reflection state";
  }

  typedef Ots-safety-control-mode {
    type enumeration {
      enum "auto" {
        value 1;
        description
          "Automatic Safety Control Mode";
      }
      enum "disabled" {
        value 2;
        description
          "Disable Safety Control Mode";
      }
    }
    description
      "Ots safety control mode";
  }

  typedef Scan-mode {
    type enumeration {
      enum "expert" {
        value 1;
        description
          "scan Expert";
      }
      enum "multi-region" {
        value 2;
        description
          "scan Multi-Region";
      }
    }
    description
      "Scan mode";
  }

  typedef Ots-ampli-control-mode {
    type enumeration {
      enum "automatic" {
        value 1;
        description
          "Automatic Amplifier Mode";
      }
      enum "manual" {
        value 2;
        description
          "Manual Amplifier Mode";
      }
      enum "powermode" {
        value 3;
        description
          "Power Amplifier Mode";
      }
    }
    description
      "Ots ampli control mode";
  }

  augment "/a1:interface-configurations/a1:interface-configuration" {
    description
      "This augment extends the configuration data of
       'Cisco-IOS-XR-ifmgr-cfg'";
    container ots {
      description
        "Ots controller configuration";
      container ingress-channel-slice-attns {
        description
          "Configure Ingress Channel Slice";
        list ingress-channel-slice-attn {
          key "ingress-channel-slice-attn";
          description
            "Configure Ingress Channel Slice Attenuation
             Value";
          leaf ingress-channel-slice-attn {
            type uint32 {
              range "1..1548";
            }
            description
              "Ingress Channel Slice Attenuation";
          }
          leaf ingress-channel-slice-attnvalue {
            type uint32 {
              range "0..250";
            }
            mandatory true;
            description
              "Ingress Channel Slice Attenuation Value";
          }
        }
      }
      container raman-tx-power-disables {
        description
          "Configure Raman Transmit Power Disable
           Parameter";
        list raman-tx-power-disable {
          key "raman-tx-power-disable-instance";
          description
            "Configure RamanTxPowerDisable Value";
          leaf raman-tx-power-disable-instance {
            type uint32 {
              range "1..7";
            }
            description
              "Raman Tx Power Disable Instance";
          }
        }
      }
      container raman-tx-powers {
        description
          "Configure Raman Transmit Power Parameter";
        list raman-tx-power {
          key "raman-tx-power-instance";
          description
            "Configure RamanTxPower Value";
          leaf raman-tx-power-instance {
            type uint32 {
              range "1..7";
            }
            description
              "Raman Tx Power Instance";
          }
          leaf raman-tx-power-value {
            type uint32 {
              range "100..39000";
            }
            mandatory true;
            description
              "Raman Tx Power value";
          }
        }
      }
      container ots-otdr {
        description
          "Configure OTDR parameters";
        container ots-otdr-rx {
          description
            "Configure OTDR RX parameters";
          container ots-otdr-rx-expert {
            description
              "Configure OTDR RX Expert parameters";
            leaf ots-otdr-rx-capture-start {
              type uint32 {
                range "0..10000000";
              }
              description
                "Select OTDR RX Capture Start <Value in cm>";
            }
            leaf ots-otdr-rx-scan-duration {
              type uint32 {
                range "0..180";
              }
              description
                "Select OTDR RX Scan Duration <Value in
                 seconds>";
            }
            leaf ots-otdr-rx-pulse-width {
              type uint32 {
                range "1..500000";
              }
              description
                "Select OTDR RX Pulse Width <Value in nano
                 seconds>";
            }
            leaf ots-otdr-rx-capture-end {
              type uint32 {
                range "0..15000000";
              }
              description
                "Select OTDR RX Capture End <Value in cm>";
            }
          }
          container ots-otdr-rx-auto {
            description
              "Configure OTDR RX Auto parameters";
            leaf ots-otdr-rx-excess-reflection-threshold {
              type int32 {
                range "-50..-10";
              }
              description
                "Select OTDR RX Excess Reflection Threshold
                 <Value in db>";
            }
            leaf ots-otdr-rx-end-of-fiber-threshold {
              type uint32 {
                range "5..990";
              }
              description
                "Configure OTDR Rx End of Fiber Loss
                 Threshold (Value in 0.1 dB)";
            }
            leaf ots-otdr-rx-splice-loss-threshold {
              type uint32 {
                range "200..5000";
              }
              description
                "Select OTDR RX Splice Loss Threshold (In
                 unit of 0.001 db)";
            }
            leaf ots-otdr-rx-excess-attenuation-threshold {
              type uint32 {
                range "5..990";
              }
              description
                "Configure OTDR Rx Excess Attenuation
                 Threshold (Value in 0.1 dB)";
            }
            leaf ots-otdr-rx-raman-setpoint {
              type uint32 {
                range "0..170";
              }
              description
                "Select OTDR RX Raman Setpoint <Value in 0.1
                 db>";
            }
            leaf ots-otdr-rx-excess-orl-threshold {
              type uint32 {
                range "100..600";
              }
              description
                "Configure OTDR Rx Excess Optical Return Loss
                 Threshold (Value in 0.1 dB)";
            }
            leaf ots-otdr-rx-reflectance-threshold {
              type int32 {
                range "-50..-10";
              }
              description
                "Select OTDR RX Reflectance Threshold <Value
                 in db>";
            }
          }
          leaf ots-otdr-rx-back-scattering {
            type int32 {
              range "-9000..-7000";
            }
            description
              "Select OTDR RX Back Scattering <Value in 0
               .01>";
          }
          leaf ots-otdr-rx-refractive-index {
            type uint32 {
              range "1000000..2000000";
            }
            description
              "Select OTDR TX Refractive Index <Value in 0
               .000001>";
          }
        }
        container ots-otdr-scan-mode {
          description
            "Configure OTDR Scan Mode";
          leaf ots-otdr-scan-mode-expert {
            type Scan-mode;
            description
              "Configure Otdr Scan Mode to MultiRegion or
               Expert";
          }
        }
        container ots-otdr-tx {
          description
            "Configure OTDR TX parameters";
          container ots-otdr-tx-expert {
            description
              "Configure OTDR TX Expert parameters";
            leaf ots-otdr-tx-capture-end {
              type uint32 {
                range "0..15000000";
              }
              description
                "Select OTDR TX Capture End <Value in cm>";
            }
            leaf ots-otdr-tx-scan-duration {
              type uint32 {
                range "0..180";
              }
              description
                "Select OTDR TX Scan Duration <Value in
                 seconds>";
            }
            leaf ots-otdr-tx-capture-start {
              type uint32 {
                range "0..10000000";
              }
              description
                "Select OTDR TX Capture Start <Value in cm>";
            }
            leaf ots-otdr-tx-pulse-width {
              type uint32 {
                range "1..500000";
              }
              description
                "Select OTDR TX Pulse Width <Value in nano
                 seconds>";
            }
          }
          container ots-otdr-tx-auto {
            description
              "Configure OTDR TX Auto parameters";
            leaf ots-otdr-tx-splice-loss-threshold {
              type uint32 {
                range "200..5000";
              }
              description
                "Select OTDR TX Splice Loss Threshold (In
                 unit of 0.001 db)";
            }
            leaf ots-otdr-tx-excess-reflection-threshold {
              type int32 {
                range "-50..-10";
              }
              description
                "Select OTDR TX Excess Reflection Threshold
                 <Value in db>";
            }
            leaf ots-otdr-tx-excess-attenuation-threshold {
              type uint32 {
                range "5..990";
              }
              description
                "Configure OTDR Tx Excess Attenuation
                 Threshold (Value in 0.1 dB)";
            }
            leaf ots-otdr-tx-raman-setpoint {
              type uint32 {
                range "0..170";
              }
              description
                "Select OTDR TX Raman Setpoint <Value in 0.1
                 db>";
            }
            leaf ots-otdr-tx-reflectance-threshold {
              type int32 {
                range "-50..-10";
              }
              description
                "Select OTDR TX Reflectance Threshold <Value
                 in db>";
            }
            leaf ots-otdr-tx-excess-orl-threshold {
              type uint32 {
                range "100..600";
              }
              description
                "Configure OTDR Tx Excess Optical Return Loss
                 Threshold (Value in 0.1 dB)";
            }
            leaf ots-otdr-tx-end-of-fiber-threshold {
              type uint32 {
                range "5..990";
              }
              description
                "Configure OTDR Tx End of Fiber Loss
                 Threshold (Value in 0.1 dB)";
            }
          }
          leaf ots-otdr-tx-refractive-index {
            type uint32 {
              range "1000000..2000000";
            }
            description
              "Select OTDR TX Refractive Index <Value in 0
               .000001>";
          }
          leaf ots-otdr-tx-back-scattering {
            type int32 {
              range "-9000..-7000";
            }
            description
              "Select OTDR TX Back Scattering <Value in 0
               .01>";
          }
        }
      }
      container egress-channel-slice-attns {
        description
          "Configure Egress Channel Slice";
        list egress-channel-slice-attn {
          key "egress-channel-slice-attn";
          description
            "Configure Egress Channel Slice Attenuation
             Value";
          leaf egress-channel-slice-attn {
            type uint32 {
              range "1..1548";
            }
            description
              "Egress Channel Slice Attenuation";
          }
          leaf egress-channel-slice-attnvalue {
            type uint32 {
              range "0..250";
            }
            mandatory true;
            description
              "Egress Channel Slice Attenuation Value";
          }
        }
      }
      leaf ots-ingress-amplifier-mode {
        type Ots-ampli-working-mode;
        description
          "Configure ingress amplifier working mode";
      }
      leaf ots-egress-safety-control-mode {
        type Ots-safety-control-mode;
        description
          "Configure Egress safety Control Mode";
      }
      leaf ots-raman-safety-als-osc-osnr-los {
        type empty;
        description
          "Raman Dual Safety Trigger includes OSC OSNR LOS";
      }
      leaf ots-ingress-amplifier-gain {
        type int32 {
          range "-30..400";
        }
        description
          "Select Amplifier Gain value(in units of 0.1dBm)";
      }
      leaf ots-tx-low-threshold {
        type int32 {
          range "-400..400";
        }
        description
          "configure Tx low threshold";
      }
      leaf ots-tone-pattern-expected {
        type string {
          length "8..64";
        }
        description
          "Enter HexString Values(Min Length 8 Bytes to
           Max Length 64 Bytes)";
      }
      leaf ots-egress-amplifier-back-reflection-high-threshold {
        type int32 {
          range "-500..300";
        }
        description
          "Select Egress Ampli Back Reflection High
           Threshold(in units of 0.1dBm)";
      }
      leaf ots-ingress-osri {
        type boolean;
        description
          "Configure Ingress Optical safety remote
           interlock (OSRI)";
      }
      leaf ots-ingress-amplifier-gain-degrade-high-threshold {
        type int32 {
          range "0..500";
        }
        description
          "Select Ingress Amplifier Gain Degrade High
           Threshold(in units of 0.1dBm)";
      }
      leaf ots-tx-voa-attenuation {
        type int32 {
          range "0..200";
        }
        description
          "Select TX Voa Attenuation Setpoint(in units of
           0.1dBm)";
      }
      leaf ots-raman-safety-als-osc-los {
        type empty;
        description
          "Raman Dual Safety Trigger includes Osc LOS";
      }
      leaf ots-egress-amplifier-power {
        type int32 {
          range "-50..250";
        }
        description
          "Select egress amplifier power value (in units
           of 0.1dBm)";
      }
      leaf ots-ingress-safety-control-mode {
        type Ots-safety-control-mode;
        description
          "Configure Ingress safety Control Mode";
      }
      leaf ots-ampli-control-mode {
        type Ots-ampli-control-mode;
        description
          "Configure amplifier working mode";
      }
      leaf ots-rx-low-threshold {
        type int32 {
          range "-470..400";
        }
        description
          "configure Rx low threshold";
      }
      leaf ots-tone-detect-oob {
        type empty;
        description
          "configure tone detect oob";
      }
      leaf ots-ingress-force-apr {
        type boolean;
        description
          "Configure Ingress Optical Force Automatic Power
           Reduction";
      }
      leaf ots-raman-force-apr {
        type boolean;
        description
          "Configure Raman Optical Force Automatic Power
           Reduction";
      }
      leaf ots-egress-amplifier-gain-degrade-low-threshold {
        type int32 {
          range "0..500";
        }
        description
          "Select Egress Amplifier Gain Degrade Low
           Threshold(in units of 0.1dBm)";
      }
      leaf ots-ingress-amplifier-gain-degrade-low-threshold {
        type int32 {
          range "0..500";
        }
        description
          "Select Ingress Amplifier Gain Degrade Low
           Threshold(in units of 0.1dBm)";
      }
      leaf ots-egress-amplifier-tilt {
        type int32 {
          range "-50..50";
        }
        description
          "Select Amplifier Tilt value(in units of 0.1dB)";
      }
      leaf ots-egress-amplifier-mode {
        type Ots-ampli-working-mode;
        description
          "Configure egress amplifier working mode";
      }
      leaf ots-tone-frequency {
        type string;
        description
          "Enter value between 191.175 THz and 196.175 THz
           GHz in steps of 100 MHz";
      }
      leaf ots-ingress-amplifier-power {
        type int32 {
          range "-90..250";
        }
        description
          "Select ingress amplifier power value (in units
           of 0.1dBm)";
      }
      leaf ots-egress-amplifier-gain {
        type int32 {
          range "-30..400";
        }
        description
          "Select Amplifier Gain value(in units of 0.1dBm)";
      }
      leaf ots-tone-pattern {
        type string {
          length "1..64";
        }
        description
          "Enter HexString Values(Min Length 1 Byte to Max
           Length 64 Bytes)";
      }
      leaf ots-raman-safety-als-dfb-los {
        type empty;
        description
          "Raman Dual Safety Trigger includes Dfb LOS";
      }
      leaf ots-egress-amplifier-back-reflection {
        type Ots-back-reflection-state;
        description
          "Configure Optical Egress Ampli Back Reflection
           as Enable or Disable";
      }
      leaf ots-egress-amplifier-gain-degrade-high-threshold {
        type int32 {
          range "0..500";
        }
        description
          "Select Egress Amplifier Gain Degrade High
           Threshold(in units of 0.1dBm)";
      }
      leaf ots-raman-osri {
        type boolean;
        description
          "Configure Optical safety remote interlock
           (OSRI)";
      }
      leaf ots-egress-osri {
        type boolean;
        description
          "Configure Egress Optical safety remote
           interlock (OSRI)";
      }
      leaf ots-egress-amplifier-gain-range {
        type Ots-ingress-egress-ampli-gain-range;
        description
          "Configure EGRESS AMPLIFIER GAIN Range";
      }
      leaf ots-ingress-amplifier-gain-range {
        type Ots-ingress-egress-ampli-gain-range;
        description
          "Configure INGRESS AMPLIFIER GAIN Range";
      }
      leaf ots-ingress-amplifier-tilt {
        type int32 {
          range "-50..50";
        }
        description
          "Select Amplifier Tilt value(in units of 0.1dB)";
      }
      leaf ots-tone-rate {
        type int32 {
          range "2..25";
        }
        description
          "Configure Tone Rate";
      }
      leaf ots-egress-force-apr {
        type boolean;
        description
          "Configure Egress Optical Force Automatic Power
           Reduction";
      }
    }
  }
}
