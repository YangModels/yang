module Cisco-IOS-XR-um-install-cfg {
  namespace "http://cisco.com/ns/yang/Cisco-IOS-XR-um-install-cfg";
  prefix um-install-cfg;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR install package configuration.
     
     This YANG module augments the
     modules with configuration data.
     
     Copyright (c) 2021-2025 by Cisco Systems, Inc., and/or its affiliates.
     All rights reserved.";

  revision 2023-07-27 {
    description
      "Added 'enable' leaf to fingerprints config
       2022-07-14
         Added support for fingerprints frequency never
       2022-03-10
         Added configuration for RPM fingerprinting
       2022-01-19
         Updated length of url and description nodes";
    semver:module-version "2.0.0";
  }
  revision 2021-02-04 {
    description
      "Initial release";
    semver:module-version "1.0.0";
  }

  feature is-lnt {
    description
      "Enabled for LNT only";
  }

  container install {
    description
      "Install configuration";
    container repositories {
      if-feature "is-lnt";
      description
        "Per repository configuration";
      list repository {
        must "url or description";
        key "repository-name";
        description
          "Per repository configuration";
        leaf repository-name {
          type string {
            length "1..80" {
              description
                "Repository ID (up to 80 characters)";
            }
          }
          description
            "Per repository configuration";
        }
        leaf url {
          type string {
            length "1..900" {
              description
                "ftp://<server>[;<vrf>]/<full_path_to_repo>   -> FTP repository,
                 http://<server>[;<vrf>]/<full_path_to_repo>  -> HTTP repository,
                 https://<server>[;<vrf>]/<full_path_to_repo> -> HTTPS repository,
                 file:///<full_path_to_repo>                  -> Local File repository
                 or directory - this must be a subdirectory of one of
                 '/var/xr/disk1/', '/harddisk:/', or '/misc/disk1/'";
            }
          }
          description
            "Repository URL - path to local repository or directory or ftp, http,
             or https path to remote repository, optionally containing the name of
             a VRF for the repository.";
        }
        leaf description {
          type string {
            length "1..900" {
              description
                "Repository description";
            }
          }
          description
            "Description of this repository";
        }
      }
    }
    container fingerprints {
      presence "Indicates a fingerprints node is configured.";
      description
        "RPM fingerprinting configuration";
      leaf frequency {
        if-feature "is-lnt";
        type uint32 {
          range "1..12" {
            description
              "Frequency of fingerprint generation in hours";
          }
        }
        description
          "Configure RPM fingerprint generation frequency";
      }
    }
  }
}
