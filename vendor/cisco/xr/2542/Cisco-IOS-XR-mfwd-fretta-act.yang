module Cisco-IOS-XR-mfwd-fretta-act {
  namespace "http://cisco.com/ns/yang/Cisco-IOS-XR-mfwd-fretta-act";
  prefix mfwd-fretta-act;

  import ietf-inet-types {
    prefix inet;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR fretta multicast package action data to clear stats.
     
     Copyright (c) 2022-2023 by Cisco Systems, Inc.
     All rights reserved.";

  revision 2023-02-15 {
    description
      "Initial revision.";
    reference "1.0.0";
    semver:module-version "1.0.0";
  }

  typedef StatsDirection {
    type enumeration {
      enum "Both" {
        value 0;
        description
          "Ingress and Egress directions";
      }
      enum "Ingress" {
        value 1;
        description
          "Ingress direction";
      }
      enum "Egress" {
        value 2;
        description
          "Egress direction";
      }
    }
    description
      "Direction of route statistics to clear (Both, Ingress, or Egress)";
  }

  rpc clear-mfib-hardware-route-statistics-location {
    description
      "Clear the hardware counters for the multicast routes at the given location";
    input {
      leaf statistics-direction {
        type StatsDirection;
        description
          "Direction of statistics to clear; Both, Ingress, or Egress";
      }
      leaf source-address {
        type inet:ip-address-no-zone;
        description
          "Source Address";
      }
      leaf group-address {
        type inet:ip-prefix;
        description
          "Group Address/Prefix Length";
      }
      leaf node-location {
        type string;
        mandatory true;
        description
          "Node location";
      }
    }
  }
}
