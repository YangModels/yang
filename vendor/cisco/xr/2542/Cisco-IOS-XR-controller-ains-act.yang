module Cisco-IOS-XR-controller-ains-act {
  namespace "http://cisco.com/ns/yang/Cisco-IOS-XR-controller-ains-act";
  prefix controller-ains-act;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR Controller AINS configuration.
     
     Copyright (c) 2018-2019, 2022 by Cisco Systems, Inc.
     All rights reserved.";

  revision 2019-10-01 {
    description
      "Made changes to be RFC6087 compliant";
    semver:module-version "1.0.1";
  }
  revision 2019-04-05 {
    description
      "Establish semantic version baseline.";
    semver:module-version "1.0.0";
  }
  revision 2018-01-09 {
    description
      "IOS XR 6.5.1 revision.";
  }

  rpc controller-ains-soak {
    description
      "Execute ains soak configuration operations";
    input {
      leaf controller {
        type string;
        description
          "Controller name in R/S/I/P format";
      }
      leaf hours {
        type uint32 {
          range "0..48";
        }
        description
          "Hours in range of 0-48";
      }
      leaf minutes {
        type uint32 {
          range "0..59";
        }
        description
          "Minutes in range of 0-59";
      }
    }
  }
}
