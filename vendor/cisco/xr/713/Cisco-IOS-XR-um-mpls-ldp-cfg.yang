module Cisco-IOS-XR-um-mpls-ldp-cfg {
  namespace "http://cisco.com/ns/yang/Cisco-IOS-XR-um-mpls-ldp-cfg";
  prefix um-mpls-ldp-cfg;

  import cisco-semver {
    prefix semver;
  }
  import Cisco-IOS-XR-types {
    prefix xr;
  }
  import ietf-inet-types {
    prefix inet;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR mpls-ldp package configuration.
     
     This YANG module augments the
     modules with configuration data.
     
     Copyright (c) 2019-2020 by Cisco Systems, Inc.
     All rights reserved.";

  revision 2019-12-10 {
    description
      "Corrected must statement definition for password/encrypted,disable";
  }
  revision 2019-10-10 {
    description
      "Moved trap augments into Cisco-IOS-XR-um-traps-mpls-ldp-cfg.";
  }
  revision 2019-09-25 {
    description
      "Changed the list node name access-list to access-lists.";
    semver:module-version "2.0.0";
  }
  revision 2019-06-10 {
    description
      "Establish semantic version baseline.";
  }
  revision 2019-03-30 {
    description
      "Initial version";
  }

  container mpls {
    description
      "Global MPLS configuration subcommands";
    container ldp {
      presence "Indicates a ldp node is configured.";
      description
        "Label Distribution Protocol";
      container mldp {
        presence "Indicates a mldp node is configured.";
        description
          "Configure mLDP parameters";
        container logging {
          description
            "MLDP logging commands";
          container notifications {
            presence "Indicates a notifications node is configured.";
            description
              "MLDP logging notifications";
          }
          container internal {
            presence "Indicates a internal node is configured.";
            description
              "MLDP logging internal";
          }
        }
        container vrfs {
          description
            "Configure VRF parameters";
          list vrf {
            key "vrf-name";
            description
              "Configure VRF parameters";
            leaf vrf-name {
              type xr:Cisco-ios-xr-string {
                length "1..1024" {
                  description
                    "VRF name";
                }
              }
              description
                "Configure VRF parameters";
            }
            container address-families {
              description
                "Configure Address Family and its parameters";
              list address-family {
                key "af-name";
                description
                  "Configure Address Family and its parameters";
                leaf af-name {
                  type enumeration {
                    enum "ipv4" {
                      value 4;
                      description
                        "IPv4";
                    }
                  }
                  description
                    "Configure Address Family and its parameters";
                }
                container statics {
                  description
                    "Static mLDP LSP";
                  list static {
                    key "lsp-address";
                    description
                      "Staic mLDP LSP";
                    leaf lsp-address {
                      type inet:ipv4-address-no-zone;
                      description
                        "LSP address";
                    }
                    leaf p2mp {
                      type uint32 {
                        range "1..1000" {
                          description
                            "Number of LSPs";
                        }
                      }
                      description
                        "P2MP LSP";
                    }
                    leaf mp2mp {
                      type uint32 {
                        range "1..1000" {
                          description
                            "Number of LSPs";
                        }
                      }
                      description
                        "MP2MP LSP";
                    }
                  }
                }
                container make-before-break {
                  description
                    "Make Before Break";
                  container delay {
                    presence "Indicates a delay node is configured.";
                    description
                      "MBB delay";
                    leaf forwarding-delay {
                      type uint32 {
                        range "0..600" {
                          description
                            "Forwarding delay in seconds";
                        }
                      }
                      mandatory true;
                      description
                        "MBB delay";
                    }
                    leaf delete-delay {
                      type uint32 {
                        range "0..60" {
                          description
                            "Delete delay in seconds";
                        }
                      }
                      default "0";
                      description
                        "Delete delay in seconds";
                    }
                  }
                  leaf route-policy {
                    type xr:Route-policy-name;
                    description
                      "Route policy";
                  }
                }
                container mofrr {
                  presence "Indicates a mofrr node is configured.";
                  description
                    "MLDP MoFRR support";
                  leaf route-policy {
                    type xr:Route-policy-name;
                    description
                      "Route policy";
                  }
                }
                container neighbors {
                  description
                    "MLDP neighbor commands";
                  container in {
                    description
                      "Inbound route policy";
                    leaf route-policy {
                      type xr:Route-policy-name;
                      description
                        "Route policy";
                    }
                  }
                  container out {
                    description
                      "Inbound route policy";
                    leaf route-policy {
                      type xr:Route-policy-name;
                      description
                        "Route policy";
                    }
                  }
                  list neighbor {
                    must "in or out or (in and out)";
                    key "neighbor-address";
                    description
                      "MLDP neighbor commands";
                    leaf neighbor-address {
                      type inet:ipv4-address-no-zone;
                      description
                        "configure this node";
                    }
                    container in {
                      description
                        "Inbound route policy";
                      leaf route-policy {
                        type xr:Route-policy-name;
                        description
                          "Route policy";
                      }
                    }
                    container out {
                      description
                        "Inbound route policy";
                      leaf route-policy {
                        type xr:Route-policy-name;
                        description
                          "Route policy";
                      }
                    }
                  }
                }
                container forwarding {
                  description
                    "Forwarding commands";
                  container recursive {
                    presence "Indicates a recursive node is configured.";
                    description
                      "Enable recursive forwarding";
                    leaf route-policy {
                      type xr:Route-policy-name;
                      description
                        "Route policy";
                    }
                  }
                }
                container rib {
                  description
                    "RIB commands";
                  container unicast-always {
                    presence "Indicates a unicast-always node is configured.";
                    description
                      "Always use unicast table for root lookup";
                  }
                }
              }
            }
          }
        }
        container address-families {
          description
            "Configure Address Family and its parameters";
          list address-family {
            key "af-name";
            description
              "Configure Address Family and its parameters";
            leaf af-name {
              type enumeration {
                enum "ipv4" {
                  value 4;
                  description
                    "IPv4";
                }
              }
              description
                "Configure Address Family and its parameters";
            }
            container statics {
              description
                "Static mLDP LSP";
              list static {
                key "lsp-address";
                description
                  "Static mLDP LSP";
                leaf lsp-address {
                  type inet:ipv4-address-no-zone;
                  description
                    "LSP address";
                }
                leaf p2mp {
                  type uint32 {
                    range "1..1000" {
                      description
                        "Number of LSPs";
                    }
                  }
                  description
                    "P2MP LSP";
                }
                leaf mp2mp {
                  type uint32 {
                    range "1..1000" {
                      description
                        "Number of LSPs";
                    }
                  }
                  description
                    "MP2MP LSP";
                }
              }
            }
            container make-before-break {
              description
                "Make Before Break";
              container delay {
                presence "Indicates a delay node is configured.";
                description
                  "MBB delay";
                leaf forwarding-delay {
                  type uint32 {
                    range "0..600" {
                      description
                        "Forwarding delay in seconds";
                    }
                  }
                  mandatory true;
                  description
                    "MBB delay";
                }
                leaf delete-delay {
                  type uint32 {
                    range "0..60" {
                      description
                        "Delete delay in seconds";
                    }
                  }
                  default "0";
                  description
                    "Delete delay in seconds";
                }
              }
              leaf route-policy {
                type xr:Route-policy-name;
                description
                  "Route policy";
              }
            }
            container carrier-supporting-carrier {
              presence "Indicates a carrier-supporting-carrier node is configured.";
              description
                "MLDP CSC support";
            }
            container mofrr {
              presence "Indicates a mofrr node is configured.";
              description
                "MLDP MoFRR support";
              leaf route-policy {
                type xr:Route-policy-name;
                description
                  "Route policy";
              }
            }
            container recursive-fec {
              presence "Indicates a recursive-fec node is configured.";
              description
                "MLDP Recursive FEC support";
              leaf route-policy {
                type xr:Route-policy-name;
                description
                  "Route policy";
              }
            }
            container neighbors {
              description
                "MLDP neighbor commands";
              container in {
                description
                  "Inbound route policy";
                leaf route-policy {
                  type xr:Route-policy-name;
                  description
                    "Route policy";
                }
              }
              container out {
                description
                  "Inbound route policy";
                leaf route-policy {
                  type xr:Route-policy-name;
                  description
                    "Route policy";
                }
              }
              list neighbor {
                must "in or out or (in and out)";
                key "neighbor-address";
                description
                  "configure this node";
                leaf neighbor-address {
                  type inet:ipv4-address-no-zone;
                  description
                    "configure this node";
                }
                container in {
                  description
                    "Inbound route policy";
                  leaf route-policy {
                    type xr:Route-policy-name;
                    description
                      "Route policy";
                  }
                }
                container out {
                  description
                    "Inbound route policy";
                  leaf route-policy {
                    type xr:Route-policy-name;
                    description
                      "Route policy";
                  }
                }
              }
            }
            container forwarding {
              description
                "Forwarding commands";
              container recursive {
                presence "Indicates a recursive node is configured.";
                description
                  "Enable recursive forwarding";
                leaf route-policy {
                  type xr:Route-policy-name;
                  description
                    "Route policy";
                }
              }
            }
            container rib {
              description
                "RIB commands";
              container unicast-always {
                presence "Indicates a unicast-always node is configured.";
                description
                  "Always use unicast table for root lookup";
              }
            }
          }
        }
      }
      container vrfs {
        description
          "Configure VRF parameters";
        list vrf {
          key "vrf-name";
          description
            "Configure VRF parameters";
          leaf vrf-name {
            type xr:Cisco-ios-xr-string {
              length "1..1024" {
                description
                  "VRF name";
              }
            }
            description
              "Configure VRF parameters";
          }
          leaf router-id {
            type inet:ipv4-address-no-zone;
            description
              "Configure router Id";
          }
          container session {
            description
              "Configure session parameters";
            container downstream-on-demand {
              description
                "Downstream on demand label advertisment mode";
              leaf with {
                type string {
                  length "1..1024" {
                    description
                      "IPv4 access-list (specify peer LSR Ids)";
                  }
                }
                description
                  "Access list of LDP Peers";
              }
            }
          }
          container graceful-restart {
            description
              "Configure graceful restart feature";
            container helper-peer {
              description
                "Configure parameters related to GR peer(s) operating in helper mode";
              container maintain-on-local-reset {
                description
                  "Maintain the state of a GR peer upon a local reset";
                leaf for {
                  type string {
                    length "1..32" {
                      description
                        "IPv4 access-list (specify peer LSR Ids)";
                    }
                  }
                  description
                    "Access list of LDP Peers";
                }
              }
            }
          }
          container neighbors {
            description
              "Configure neighbor parameters";
            container password {
              description
                "Configure password for MD5 authentication for all neighbors";
              leaf encrypted {
                type xr:Proprietary-password;
                description
                  "Specifies an ENCRYPTED password will follow";
              }
            }
            list neighbor {
              key "neighbor-address label-space-id";
              description
                "neighbor";
              leaf neighbor-address {
                type inet:ipv4-address-no-zone;
                description
                  "configure this node";
              }
              leaf label-space-id {
                type uint32 {
                  range "0" {
                    description
                      "Label Space Id of neighbor";
                  }
                }
                description
                  "Label Space Id of neighbor";
              }
              container password {
                description
                  "Configure password for MD5 authentication";
                leaf encrypted {
                  type xr:Proprietary-password;
                  must "not(../disable)";
                  description
                    "Specifies an ENCRYPTED password will follow";
                }
                container disable {
                  must "not(../encrypted)";
                  presence "Indicates a disable node is configured.";
                  description
                    "Disables the global password from this neighbor";
                }
              }
            }
          }
          container address-family {
            description
              "Configure Address Family and its parameters";
            container ipv4 {
              presence "Indicates a ipv4 node is configured.";
              description
                "IPv4";
              container discovery {
                description
                  "Configure discovery parameters";
                container transport-address {
                  presence "Indicates a transport-address node is configured.";
                  description
                    "Specify transport address for TCP connection";
                  leaf ip-address {
                    type inet:ipv4-address-no-zone;
                    mandatory true;
                    description
                      "IP address to be used as transport address";
                  }
                }
              }
              container label {
                description
                  "Configure label control and policies";
                container local {
                  description
                    "Configure local label control and policies";
                  container allocate {
                    description
                      "Configure label allocation control";
                    container for {
                      description
                        "Limit label allocation to a set of prefixes";
                      leaf ip-access-list {
                        type string {
                          length "1..1024" {
                            description
                              "IP access-list";
                          }
                        }
                        must "not(../host-routes)";
                        description
                          "IP access-list";
                      }
                      container host-routes {
                        must "not(../ip-access-list)";
                        presence "Indicates a host-routes node is configured.";
                        description
                          "Allocate label for host routes only";
                      }
                    }
                  }
                  container default-route {
                    presence "Indicates a default-route node is configured.";
                    description
                      "Enable MPLS forwarding for default route";
                  }
                  container implicit-null-override {
                    description
                      "Configure use of implicit-null local label for non-egress prefixes";
                    leaf for {
                      type string {
                        length "1..32" {
                          description
                            "IP access-list";
                        }
                      }
                      description
                        "Limit implicit-null label use to a set of prefixes";
                    }
                  }
                  container advertise {
                    description
                      "Configure outbound label advertisement control";
                    container explicit-null {
                      must "not(for and to)";
                      presence "Indicates a explicit-null node is configured.";
                      description
                        "Configure explicit-null advertisement";
                      container for {
                        presence "Indicates a for node is configured.";
                        description
                          "IP Access-list specifying controls on destination prefixes";
                        leaf access-list {
                          type string {
                            length "1..1024" {
                              description
                                "IP access-list";
                            }
                          }
                          mandatory true;
                          description
                            "IP Access-list specifying controls on destination prefixes";
                        }
                        container to {
                          presence "Indicates a to node is configured.";
                          description
                            "IP Access-list specifying controls on LDP Peers";
                          leaf access-list {
                            type string {
                              length "1..1024" {
                                description
                                  "IPv4 access-list (specify peer LSR Ids)";
                              }
                            }
                            mandatory true;
                            description
                              "IP Access-list specifying controls on LDP Peers";
                          }
                        }
                      }
                      container to {
                        presence "Indicates a to node is configured.";
                        description
                          "IP Access-list specifying controls on LDP Peers";
                        leaf access-list {
                          type string {
                            length "1..1024" {
                              description
                                "IPv4 access-list (specify peer LSR Ids)";
                            }
                          }
                          mandatory true;
                          description
                            "IP Access-list specifying controls on LDP Peers";
                        }
                      }
                    }
                    container to {
                      description
                        "Peer centric outbound label filtering";
                      list neighbor {
                        key "neighbor-address label-space-id";
                        description
                          "neighbor";
                        leaf neighbor-address {
                          type inet:ipv4-address-no-zone;
                          description
                            "neighbor address";
                        }
                        leaf label-space-id {
                          type uint32 {
                            range "0" {
                              description
                                "Label Space Id of neighbor";
                            }
                          }
                          description
                            "Label Space Id of neighbor";
                        }
                        leaf for {
                          type string {
                            length "1..32" {
                              description
                                "IP access-list";
                            }
                          }
                          mandatory true;
                          description
                            "IP access-list for prefixes to be sent";
                        }
                      }
                    }
                    container interfaces {
                      description
                        "Advertise interface host address";
                      list interface {
                        key "interface-name";
                        description
                          "Advertise interface host address";
                        leaf interface-name {
                          type xr:Interface-name;
                          description
                            "Advertise interface host address";
                        }
                      }
                    }
                    container disable {
                      presence "Indicates a disable node is configured.";
                      description
                        "Disable label advertisement to all peers for all prefixes";
                    }
                  }
                }
                container remote {
                  description
                    "Configure remote/peer label control and policies";
                  container accept {
                    description
                      "Configure inbound label acceptance control";
                    container from {
                      description
                        "Neighbor from whom to accept label advertisement";
                      list neighbor {
                        key "neighbor-address label-space-id";
                        description
                          "Neighbor from whom to accept label advertisement";
                        leaf neighbor-address {
                          type inet:ipv4-address-no-zone;
                          description
                            "Neighbor from whom to accept label advertisement";
                        }
                        leaf label-space-id {
                          type uint32 {
                            range "0" {
                              description
                                "Label Space Id of neighbor";
                            }
                          }
                          description
                            "Label Space Id of neighbor";
                        }
                        leaf for {
                          type string {
                            length "1..32" {
                              description
                                "IP access-list";
                            }
                          }
                          description
                            "IP access-list for destination prefixes";
                        }
                      }
                    }
                  }
                }
              }
            }
          }
          container interfaces {
            description
              "Enable LDP on an interface and enter interface submode";
            list interface {
              key "interface-name";
              description
                "Enable LDP on an interface and enter interface submode";
              leaf interface-name {
                type xr:Interface-name;
                description
                  "Enable LDP on an interface and enter interface submode";
              }
              container address-family {
                description
                  "Configure Address Family and its parameters";
                container ipv4 {
                  presence "Indicates a ipv4 node is configured.";
                  description
                    "IPv4";
                  container discovery {
                    description
                      "Configure discovery parameters";
                    container transport-address {
                      must "(interface and not(ip-address)) or (ip-address and not(interface))";
                      presence "Indicates a transport-address node is configured.";
                      description
                        "Specify interface LDP transport address";
                      container interface {
                        presence "Indicates a interface node is configured.";
                        description
                          "Use this interface address as transport address";
                      }
                      leaf ip-address {
                        type inet:ipv4-address-no-zone;
                        description
                          "IP address to be used as transport address";
                      }
                    }
                  }
                }
              }
            }
          }
        }
      }
      container ltrace-buffer {
        description
          "Configure ltrace buffer file";
        leaf multiplier {
          type uint32 {
            range "1..5" {
              description
                "Multiplier factor";
            }
          }
          description
            "Ltrace buffer file size multiplier";
        }
      }
      container default-vrf {
        description
          "Control default VRF behaviour";
        container implicit-ipv4 {
          description
            "Control Implicit enabling of IPv4 address family behavior";
          container disable {
            presence "Indicates a disable node is configured.";
            description
              "Disable the implicit enabling for IPv4 address family ";
          }
        }
      }
      container session {
        description
          "Configure session parameters";
        container backoff {
          presence "Indicates a backoff node is configured.";
          description
            "Configure session backoff parameters";
          leaf backoff-time {
            type uint32 {
              range "5..2147483" {
                description
                  "Initial session backoff time (seconds)";
              }
            }
            mandatory true;
            description
              "Configure session backoff parameters";
          }
          leaf maximum-session-backoff-time {
            type uint32 {
              range "5..2147483" {
                description
                  "Maximum session backoff time (seconds)";
              }
            }
            mandatory true;
            description
              "Maximum session backoff time (seconds)";
          }
        }
        leaf holdtime {
          type uint32 {
            range "15..65535" {
              description
                "Time (seconds)";
            }
          }
          description
            "Configure session holdtime";
        }
        container downstream-on-demand {
          description
            "Downstream on demand label advertisment mode";
          leaf with {
            type string {
              length "1..1024" {
                description
                  "IPv4 access-list (specify peer LSR Ids)";
              }
            }
            description
              "Access list of LDP Peers";
          }
        }
        container protection {
          presence "Indicates a protection node is configured.";
          description
            "Configure session protection parameters";
          container for {
            must "not(../duration)";
            presence "Indicates a for node is configured.";
            description
              "IP Access list to specify LDP Peers";
            leaf for-access-list {
              type string {
                length "1..1024" {
                  description
                    "IPv4 access-list (specify peer LSR Ids)";
                }
              }
              mandatory true;
              description
                "IP Access list to specify LDP Peers";
            }
            container duration {
              description
                "Session protection duration after loss of link discovery";
              leaf holdup-time {
                type uint32 {
                  range "30..2147483" {
                    description
                      "Holdup time in seconds";
                  }
                }
                must "not(../infinite)";
                description
                  "Holdup time in seconds";
              }
              container infinite {
                must "not(../holdup-time)";
                presence "Indicates a infinite node is configured.";
                description
                  "Protect session forever after loss of link discovery";
              }
            }
          }
          container duration {
            must "not(../for) and (holdup-time or infinite)";
            presence "Indicates a duration node is configured.";
            description
              "Session protection duration after loss of link discovery";
            leaf holdup-time {
              type uint32 {
                range "30..2147483" {
                  description
                    "Holdup time in seconds";
                }
              }
              must "not(../infinite)";
              description
                "Holdup time in seconds";
            }
            container infinite {
              must "not(../holdup-time)";
              presence "Indicates a infinite node is configured.";
              description
                "Protect session forever after loss of link discovery";
            }
          }
        }
      }
      container nsr {
        presence "Indicates a nsr node is configured.";
        description
          "Configure Non-Stop Routing";
      }
      container entropy-label {
        presence "Indicates a entropy-label node is configured.";
        description
          "Configure Entropy Label";
      }
      container signalling {
        description
          "Configure signalling parameters";
        leaf dscp {
          type uint32 {
            range "0..63" {
              description
                "Differentiated Services Code Point (DSCP)";
            }
          }
          description
            "Set DSCP for LDP control packets";
        }
      }
      container graceful-restart {
        presence "Indicates a graceful-restart node is configured.";
        description
          "Configure graceful restart feature";
      }
      leaf graceful-restart-reconnect-timeout {
        type uint32 {
          range "60..1800" {
            description
              "Time (seconds)";
          }
        }
        description
          "Session Reconnect timeout";
      }
      leaf graceful-restart-forwarding-state-holdtime {
        type uint32 {
          range "60..1800" {
            description
              "Time (seconds)";
          }
        }
        description
          "Forwarding State holdtime for a restarting LSR";
      }
      container graceful-restart-helper-peer {
        description
          "Configure parameters related to GR peer(s) operating in helper mode";
        container maintain-on-local-reset {
          presence "Indicates a maintain-on-local-reset node is configured.";
          description
            "Maintain the state of a GR peer upon a local reset";
          leaf for {
            type string {
              length "1..32" {
                description
                  "IPv4 access-list (specify peer LSR Ids)";
              }
            }
            mandatory true;
            description
              "Access list of LDP Peers";
          }
        }
      }
      container igp {
        description
          "Configure igp parameters";
        container sync {
          description
            "Configure LDP-IGP synchronization parameters";
          container delay {
            description
              "Configure sync up delay after session up";
            leaf on-session-up {
              type uint32 {
                range "5..300" {
                  description
                    "Interface sync-up delay (seconds)";
                }
              }
              description
                "Interface sync-up delay after session up";
            }
            leaf on-proc-restart {
              type uint32 {
                range "60..600" {
                  description
                    "Global sync-up delay (seconds)";
                }
              }
              description
                "Global sync up delay to be used after process restart";
            }
          }
        }
      }
      leaf router-id {
        type inet:ipv4-address-no-zone;
        description
          "Configure router Id";
      }
      container capabilities {
        description
          "Configure LDP Capabilities";
        container cisco {
          description
            "Cisco capabilities options";
          container ios-xr {
            description
              "Cisco IOS-XR capabilities options";
            container disable {
              presence "Indicates a disable node is configured.";
              description
                "Disable Cisco IOS-XR capability";
            }
          }
        }
        container sac {
          presence "Indicates a sac node is configured.";
          description
            "Source Announcement Control";
          container ipv4-disable {
            presence "Indicates a ipv4-disable node is configured.";
            description
              "Disable exchanging IPv4 prefix label bindings";
          }
          container ipv6-disable {
            presence "Indicates a ipv6-disable node is configured.";
            description
              "Disable exchanging IPv6 prefix label bindings";
          }
          container fec128-disable {
            presence "Indicates a fec128-disable node is configured.";
            description
              "Disable exchanging PW FEC128 label bindings";
          }
          container fec129-disable {
            presence "Indicates a fec129-disable node is configured.";
            description
              "Disable exchanging PW FEC129 label bindings";
          }
        }
      }
      container log {
        description
          "Configure logging of LDP events";
        container hello-adjacency {
          presence "Indicates a hello-adjacency node is configured.";
          description
            "Hello adjacency events";
        }
        container neighbor {
          presence "Indicates a neighbor node is configured.";
          description
            "Neighbor events";
        }
        container nsr {
          presence "Indicates a nsr node is configured.";
          description
            "NSR synchronization events";
        }
        container graceful-restart {
          presence "Indicates a graceful-restart node is configured.";
          description
            "Graceful Restart events";
        }
        container session-protection {
          presence "Indicates a session-protection node is configured.";
          description
            "Session Protection events";
        }
      }
      container discovery {
        description
          "Configure discovery parameters";
        container hello {
          description
            "LDP Link Hellos";
          leaf holdtime {
            type uint32 {
              range "1..65535" {
                description
                  "Time (seconds) - 65535 implies infinite";
              }
            }
            description
              "Hello holdtime";
          }
          leaf interval {
            type uint32 {
              range "1..65535" {
                description
                  "Time (seconds)";
              }
            }
            description
              "Hello interval";
          }
        }
        container targeted-hello {
          description
            "LDP Targeted Hellos";
          leaf holdtime {
            type uint32 {
              range "1..65535" {
                description
                  "Time (seconds) - 65535 implies infinite";
              }
            }
            description
              "Targeted hello holdtime";
          }
          leaf interval {
            type uint32 {
              range "1..65535" {
                description
                  "Time (seconds)";
              }
            }
            description
              "Targeted Hello interval";
          }
        }
        container instance-tlv {
          description
            "Control support for Neighbor instance TLV in Hello messages";
          container disable {
            presence "Indicates a disable node is configured.";
            description
              "Disable transmit and receive processing for TLV";
          }
        }
        container ds-tlv {
          description
            "Control Dual Stack TLV sending";
          container disable {
            presence "Indicates a disable node is configured.";
            description
              "Disable transmit and receive processing for TLV";
          }
        }
        container quick-start {
          description
            "Control quick discovery and initial burst of hello";
          container disable {
            presence "Indicates a disable node is configured.";
            description
              "Disable quick discovery";
          }
        }
      }
      container neighbor {
        description
          "Configure neighbor parameters";
        container dual-stack {
          description
            "Configure dual stack ipv4/ipv6 neighbor parameters";
          container transport-connection {
            description
              "Configure TCP transport parameters for neighbors";
            container prefer {
              description
                "Configure prefered address family for TCP transport connection with neighbors";
              container ipv4 {
                presence "Indicates a ipv4 node is configured.";
                description
                  "IPv4";
              }
            }
            leaf max-wait {
              type uint32 {
                range "0..60" {
                  description
                    "Wait time in seconds (0 indicates no preference)";
                }
              }
              description
                "Maximum wait for prefered transport connection establishment";
            }
          }
          container tlv-compliance {
            presence "Indicates a tlv-compliance node is configured.";
            description
              "Configure dual-stack tlv compliance checks";
          }
        }
        container password {
          description
            "Configure password for MD5 authentication for all neighbors";
          leaf encrypted {
            type xr:Proprietary-password;
            description
              "Specifies an ENCRYPTED password will follow";
          }
        }
        container neighbors {
          description
            "neighbor";
          list neighbor {
            key "neighbor-address label-space-id";
            description
              "configure this node";
            leaf neighbor-address {
              type inet:ipv4-address-no-zone;
              description
                "configure this node";
            }
            leaf label-space-id {
              type uint32 {
                range "0" {
                  description
                    "Label Space Id of neighbor";
                }
              }
              description
                "Label Space Id of neighbor";
            }
            container password {
              description
                "Configure password for MD5 authentication";
              leaf encrypted {
                type xr:Proprietary-password;
                must " not(../disable)";
                description
                  "Specifies an ENCRYPTED password will follow";
              }
              container disable {
                must " not(../encrypted)";
                presence "Indicates a disable node is configured.";
                description
                  "Disables the global password from this neighbor";
              }
            }
          }
        }
      }
      container address-families {
        description
          "Configure Address Family and its parameters";
        list address-family {
          key "af-name";
          description
            "Configure Address Family and its parameters";
          leaf af-name {
            type enumeration {
              enum "ipv4" {
                value 4;
                description
                  "IPv4";
              }
              enum "ipv6" {
                value 6;
                description
                  "IPv6";
              }
            }
            description
              "Configure Address Family and its parameters";
          }
          container discovery {
            description
              "Configure discovery parameters";
            container transport-address {
              presence "Indicates a transport-address node is configured.";
              description
                "Specify transport address for TCP connection";
              leaf ip-address {
                type inet:ip-address-no-zone;
                mandatory true;
                description
                  "IP address to be used as transport address";
              }
            }
            container targeted-hello {
              description
                "LDP Targeted Hellos";
              container accept {
                presence "Indicates a accept node is configured.";
                description
                  "Accept and respond to targeted hellos";
                leaf from {
                  type string {
                    length "1..1024" {
                      description
                        "access-list";
                    }
                  }
                  description
                    "IP Access list to specify acceptable targeted hello sources";
                }
              }
            }
          }
          container neighbor {
            description
              "Configure neighbor parameters";
            container addresses {
              description
                "IP address of neighbor";
              list address {
                key "neighbor-address";
                description
                  "IP address of neighbor";
                leaf neighbor-address {
                  type inet:ip-address-no-zone;
                  description
                    "IP address of neighbor";
                }
                container targeted {
                  presence "Indicates a targeted node is configured.";
                  description
                    "Establish targeted session";
                }
              }
            }
            container sr-policies {
              description
                "Configure Segment Routing policy parameters";
              list sr-policy {
                key "policy-name";
                description
                  "Segment Routing policy name";
                leaf policy-name {
                  type string {
                    length "1..59" {
                      description
                        "Segment Routing policy name";
                    }
                  }
                  description
                    "Segment Routing policy name";
                }
                container targeted {
                  presence "Indicates a targeted node is configured.";
                  description
                    "Establish targeted session";
                }
              }
            }
          }
          container traffic-eng {
            description
              "Configure LDP parameters for MPLS Traffic-Engineering (TE)";
            container auto-tunnel {
              description
                "Configure LDP TE auto-tunnel related parameters";
              container mesh {
                description
                  "Configure TE auto-tunnel mesh groups";
                container groups {
                  description
                    "Configure an auto-tunnel mesh group of interfaces in LDP";
                  list group {
                    key "group-id";
                    description
                      "Configure an auto-tunnel mesh group of interfaces in LDP";
                    leaf group-id {
                      type uint32 {
                        range "0..4294967295" {
                          description
                            "The TE mesh group ID on which to enable LDP";
                        }
                      }
                      description
                        "Configure an auto-tunnel mesh group of interfaces in LDP";
                    }
                  }
                  container all {
                    presence "Indicates a all node is configured.";
                    description
                      "Enable LDP on all TE meshgroup interfaces";
                  }
                }
              }
            }
          }
          container redistribute {
            description
              "Redistribute routes from routing protocols";
            container bgp {
              description
                "Redistribute routes from BGP protocol";
              leaf as {
                type xr:Bgp-as-number;
                description
                  "bgp as-number";
              }
              leaf advertise-to {
                type string {
                  length "1..1024" {
                    description
                      "IPv4 access-list (specify peer LSR Ids)";
                  }
                }
                description
                  "IP access list specifying LDP peers to advertise";
              }
            }
          }
          container label {
            description
              "Configure label control and policies";
            container local {
              description
                "Configure local label control and policies";
              container allocate {
                description
                  "Configure label allocation control";
                container for {
                  description
                    "Limit label allocation to a set of prefixes";
                  leaf access-list {
                    type string {
                      length "1..1024" {
                        description
                          "IP access-list";
                      }
                    }
                    must "not(../host-routes)";
                    description
                      "IP access-list";
                  }
                  container host-routes {
                    must "not(../access-list)";
                    presence "Indicates a host-routes node is configured.";
                    description
                      "Allocate label for host routes only";
                  }
                }
              }
              container default-route {
                presence "Indicates a default-route node is configured.";
                description
                  "Enable MPLS forwarding for default route";
              }
              container implicit-null-override {
                description
                  "Configure use of implicit-null local label for non-egress prefixes";
                leaf for {
                  type string {
                    length "1..32" {
                      description
                        "IP access-list";
                    }
                  }
                  description
                    "Limit implicit-null label use to a set of prefixes";
                }
              }
              container advertise {
                description
                  "Configure outbound label advertisement control";
                container explicit-null {
                  must "not(for and to)";
                  presence "Indicates a explicit-null node is configured.";
                  description
                    "Configure explicit-null advertisement";
                  container for {
                    presence "Indicates a for node is configured.";
                    description
                      "IP Access-list specifying controls on destination prefixes";
                    leaf access-list {
                      type string {
                        length "1..1024" {
                          description
                            "IP access-list";
                        }
                      }
                      mandatory true;
                      description
                        "IP Access-list specifying controls on destination prefixes";
                    }
                    container to {
                      presence "Indicates a to node is configured.";
                      description
                        "IP Access-list specifying controls on LDP Peers";
                      leaf access-list {
                        type string {
                          length "1..1024" {
                            description
                              "IPv4 access-list (specify peer LSR Ids)";
                          }
                        }
                        mandatory true;
                        description
                          "IP Access-list specifying controls on LDP Peers";
                      }
                    }
                  }
                  container to {
                    presence "Indicates a to node is configured.";
                    description
                      "IP Access-list specifying controls on LDP Peers";
                    leaf access-list {
                      type string {
                        length "1..1024" {
                          description
                            "IPv4 access-list (specify peer LSR Ids)";
                        }
                      }
                      mandatory true;
                      description
                        "IP Access-list specifying controls on LDP Peers";
                    }
                  }
                }
                container to {
                  description
                    "Peer centric outbound label filtering";
                  list neighbor {
                    key "neighbor-address label-space-id";
                    description
                      "neighbor";
                    leaf neighbor-address {
                      type inet:ipv4-address-no-zone;
                      description
                        "neighbor address";
                    }
                    leaf label-space-id {
                      type uint32 {
                        range "0" {
                          description
                            "Label Space Id of neighbor";
                        }
                      }
                      description
                        "Label Space Id of neighbor";
                    }
                    leaf for {
                      type string {
                        length "1..32" {
                          description
                            "IP access-list";
                        }
                      }
                      mandatory true;
                      description
                        "IP access-list for prefixes to be sent";
                    }
                  }
                }
                container interfaces {
                  description
                    "Advertise interface host address";
                  list interface {
                    key "interface-name";
                    description
                      "Advertise interface host address";
                    leaf interface-name {
                      type xr:Interface-name;
                      description
                        "Advertise interface host address";
                    }
                  }
                }
                container disable {
                  presence "Indicates a disable node is configured.";
                  description
                    "Disable label advertisement to all peers for all prefixes";
                }
                container for {
                  description
                    "Prefix centric outbound label filtering";
                  list access-lists {
                    key "access-list-name";
                    description
                      "Prefix centric outbound label filtering";
                    leaf access-list-name {
                      type xr:Cisco-ios-xr-string {
                        length "1..1024" {
                          description
                            "IP access-list";
                        }
                      }
                      description
                        "Prefix centric outbound label filtering";
                    }
                    leaf to {
                      type string {
                        length "1..1024" {
                          description
                            "IP access-list";
                        }
                      }
                      description
                        "IP access-list for LDP peers";
                    }
                  }
                }
              }
            }
            container remote {
              description
                "Configure remote/peer label control and policies";
              container accept {
                description
                  "Configure inbound label acceptance control";
                container from {
                  description
                    "Neighbor from whom to accept label advertisement";
                  list neighbor {
                    key "neighbor-address label-space-id";
                    description
                      "Neighbor from whom to accept label advertisement";
                    leaf neighbor-address {
                      type inet:ipv4-address-no-zone;
                      description
                        "Neighbor from whom to accept label advertisement";
                    }
                    leaf label-space-id {
                      type uint32 {
                        range "0" {
                          description
                            "Label Space Id of neighbor";
                        }
                      }
                      description
                        "Label Space Id of neighbor";
                    }
                    leaf for {
                      type string {
                        length "1..32" {
                          description
                            "IP access-list";
                        }
                      }
                      description
                        "IP access-list for destination prefixes";
                    }
                  }
                }
              }
            }
          }
        }
      }
      container interfaces {
        description
          "Enable LDP on an interface and enter interface submode";
        list interface {
          key "interface-name";
          description
            "Enable LDP on an interface and enter interface submode";
          leaf interface-name {
            type xr:Interface-name;
            description
              "Enable LDP on an interface and enter interface submode";
          }
          container discovery {
            description
              "Configure discovery parameters";
            container hello {
              description
                "LDP Link Hellos";
              leaf holdtime {
                type uint32 {
                  range "1..65535" {
                    description
                      "Time (seconds) - 65535 implies infinite";
                  }
                }
                description
                  "Hello holdtime";
              }
              leaf interval {
                type uint32 {
                  range "1..65535" {
                    description
                      "Time (seconds)";
                  }
                }
                description
                  "Hello interval";
              }
              leaf dual-stack-tlv {
                type enumeration {
                  enum "ipv4" {
                    value 4;
                    description
                      "IPv4";
                  }
                  enum "ipv6" {
                    value 6;
                    description
                      "IPv6";
                  }
                }
                description
                  "Change AF preference in Dual Stack TLV";
              }
            }
            container quick-start {
              description
                "Control quick discovery and initial burst of hello";
              container disable {
                presence "Indicates a disable node is configured.";
                description
                  "Disable quick discovery";
              }
            }
          }
          container igp {
            description
              "Configure igp parameters";
            container sync {
              description
                "Configure LDP-IGP synchronization parameters";
              container delay {
                description
                  "Configure sync up delay";
                container on-session-up {
                  description
                    "Interface sync-up delay after session up";
                  leaf interface-sync-up-delay {
                    type uint32 {
                      range "5..300" {
                        description
                          "Interface sync-up delay (seconds)";
                      }
                    }
                    must "not(../disable)";
                    description
                      "Interface sync-up delay (seconds)";
                  }
                  container disable {
                    must "not(../interface-sync-up-delay)";
                    presence "Indicates a disable node is configured.";
                    description
                      "Disable";
                  }
                }
              }
            }
          }
          container address-families {
            description
              "Configure Address Family and its parameters";
            list address-family {
              key "af-name";
              description
                "Configure Address Family and its parameters";
              leaf af-name {
                type enumeration {
                  enum "ipv4" {
                    value 4;
                    description
                      "IPv4";
                  }
                  enum "ipv6" {
                    value 6;
                    description
                      "IPv6";
                  }
                }
                description
                  "Configure Address Family and its parameters";
              }
              container discovery {
                description
                  "Configure discovery parameters";
                container transport-address {
                  must "(interface and not(ip-address)) or (ip-address and not(interface))";
                  presence "Indicates a transport-address node is configured.";
                  description
                    "Specify interface LDP transport address";
                  container interface {
                    presence "Indicates a interface node is configured.";
                    description
                      "Use this interface address as transport address";
                  }
                  leaf ip-address {
                    type inet:ip-address-no-zone;
                    description
                      "IP address to be used as transport address";
                  }
                }
              }
              container igp {
                description
                  "Configure igp parameters";
                container auto-config {
                  description
                    "Auto-configuration";
                  container disable {
                    presence "Indicates a disable node is configured.";
                    description
                      "Disable";
                  }
                }
              }
              container mldp {
                description
                  "Configure mLDP parameters";
                container disable {
                  presence "Indicates a disable node is configured.";
                  description
                    "Disable mLDP on LDP enabled interface";
                }
              }
            }
          }
        }
      }
    }
  }
}
