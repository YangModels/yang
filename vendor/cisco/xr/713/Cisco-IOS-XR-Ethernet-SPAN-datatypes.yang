module Cisco-IOS-XR-Ethernet-SPAN-datatypes {
  namespace "http://cisco.com/ns/yang/Cisco-IOS-XR-Ethernet-SPAN-datatypes";
  prefix ethernet-span-datatypes;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of generally useful
     derived YANG data types.
     
     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  typedef Span-session-name {
    type string {
      length "1..79";
    }
    description
      "Span session name";
  }

  typedef Span-session-class {
    type enumeration {
      enum "ethernet" {
        value 0;
        description
          "Mirror Ethernet packets";
      }
      enum "ipv4" {
        value 1;
        description
          "Mirror IPv4 packets";
      }
      enum "ipv6" {
        value 2;
        description
          "Mirror IPv6 packets";
      }
      enum "mpls-ipv4" {
        value 3;
        description
          "Mirror MPLS-encapsulated IPv4 packets";
      }
      enum "mpls-ipv6" {
        value 4;
        description
          "Mirror MPLS-encapsulated IPv6 packets";
      }
    }
    description
      "Span session class";
  }

  typedef Span-acl-name {
    type string {
      length "1..80";
    }
    description
      "Span acl name";
  }

  typedef Span-session-id {
    type uint32;
    description
      "Span session id";
  }

  typedef Span-session-class-old {
    type enumeration {
      enum "true" {
        value 0;
        description
          "Mirror Ethernet packets";
      }
    }
    description
      "Span session class old";
  }
}
