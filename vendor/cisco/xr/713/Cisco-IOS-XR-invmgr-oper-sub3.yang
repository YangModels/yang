submodule Cisco-IOS-XR-invmgr-oper-sub3 {
  belongs-to Cisco-IOS-XR-invmgr-oper {
    prefix Cisco-IOS-XR-invmgr-oper;
  }

  import ietf-yang-types {
    prefix yang;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR invmgr package operational data.
     
     Copyright (c) 2013-2020 by Cisco Systems, Inc.
     All rights reserved.";

  revision 2020-05-08 {
    description
      "Deprecated Inventory:Rack container.
       2020-03-30
         Changed threshold-value type to int32.";
    semver:module-version "2.0.0";
  }
  revision 2019-04-05 {
    description
      "Establish semantic version baseline.";
    semver:module-version "1.0.0";
  }
  revision 2019-03-21 {
    description
      "Resolved string constraints issue.";
  }
  revision 2018-08-03 {
    description
      "Added slot-info and parent-info bags.";
  }
  revision 2018-04-19 {
    description
      "Added additional bags";
  }
  revision 2017-09-07 {
    description
      "Fixed type translation error.";
  }
  revision 2017-05-01 {
    description
      "Fixing backward compatibility error in module.";
  }
  revision 2015-11-09 {
    description
      "IOS XR 6.0 revision.";
  }

  grouping RMA-DETAIL {
    description
      "EEPROM RMA data content";
    leaf test-history {
      type string {
        length "0..255";
      }
      description
        "RMA detail Test history innformation";
    }
    leaf rma-number {
      type string {
        length "0..255";
      }
      description
        "RMA tracking number format is N-N-N";
    }
    leaf rma-history {
      type string {
        length "0..255";
      }
      description
        "RMA history infromation";
    }
  }

  grouping DIAG-EEPROM {
    description
      "Diag EEPROM data content";
    container rma {
      description
        "Description of Entity RMA Data";
      uses RMA-DETAIL;
    }
    leaf description {
      type string {
        length "0..255";
      }
      description
        "A textual description of physical entity";
    }
    leaf idprom-format-rev {
      type string {
        length "0..255";
      }
      description
        "Description of Entity IDPROM Format Revision";
    }
    leaf controller-family {
      type string {
        length "0..255";
      }
      description
        "Description of Entity Controller family";
    }
    leaf controller-type {
      type string {
        length "0..255";
      }
      description
        "Description of Entity Controller type";
    }
    leaf vid {
      type string {
        length "0..255";
      }
      description
        "Description of Entity Version ID";
    }
    leaf hwid {
      type string {
        length "0..255";
      }
      description
        "Description of Entity Hardware Revision";
    }
    leaf pid {
      type string {
        length "0..255";
      }
      description
        "Description of Entity Product ID";
    }
    leaf udi-description {
      type string {
        length "0..255";
      }
      description
        "Description of Entity UDI";
    }
    leaf udi-name {
      type string {
        length "0..255";
      }
      description
        "Description of Entity UDI name";
    }
    leaf clei {
      type string {
        length "0..255";
      }
      description
        "Common Language Equipment Identifier (CLEI) code";
    }
    leaf eci {
      type string {
        length "0..255";
      }
      description
        "Equipment Catalog Item (ECI) number";
    }
    leaf top-assem-part-num {
      type string {
        length "0..255";
      }
      description
        "Description of Top assembly part number";
    }
    leaf top-assem-vid {
      type string {
        length "0..255";
      }
      description
        "Description of Top assembly revision number";
    }
    leaf pca-num {
      type string {
        length "0..255";
      }
      description
        "Description of Entity PCA number";
    }
    leaf pcavid {
      type string {
        length "0..255";
      }
      description
        "Description of Entity PCA revision ID";
    }
    leaf chassis-sid {
      type string {
        length "0..255";
      }
      description
        "Description of Entity Chassis serial number";
    }
    leaf dev-num1 {
      type string {
        length "0..255";
      }
      description
        "Deviation Number # 1";
    }
    leaf dev-num2 {
      type string {
        length "0..255";
      }
      description
        "Deviation Number # 2";
    }
    leaf dev-num3 {
      type string {
        length "0..255";
      }
      description
        "Deviation Number # 3";
    }
    leaf dev-num4 {
      type string {
        length "0..255";
      }
      description
        "Deviation Number # 4";
    }
    leaf dev-num5 {
      type string {
        length "0..255";
      }
      description
        "Deviation Number # 5";
    }
    leaf dev-num6 {
      type string {
        length "0..255";
      }
      description
        "Deviation Number # 6";
    }
    leaf dev-num7 {
      type string {
        length "0..255";
      }
      description
        "Deviation Number # 7";
    }
    leaf manu-test-data {
      type string {
        length "0..255";
      }
      description
        "Manufacturing Test Data";
    }
    leaf asset-id {
      type string {
        length "0..255";
      }
      description
        "Description of Entity Asset ID";
    }
    leaf asset-alias {
      type string {
        length "0..255";
      }
      description
        "Description of Entity Asset Alias";
    }
    leaf base-mac-address1 {
      type string {
        length "0..255";
      }
      description
        "Base Mac Address #1";
    }
    leaf mac-add-blk-size1 {
      type string {
        length "0..255";
      }
      description
        "Mac Address Block Size #1";
    }
    leaf base-mac-address2 {
      type string {
        length "0..255";
      }
      description
        "Base Mac Address #2";
    }
    leaf mac-add-blk-size2 {
      type string {
        length "0..255";
      }
      description
        "Mac Address Block Size #2";
    }
    leaf base-mac-address3 {
      type string {
        length "0..255";
      }
      description
        "Base Mac Address #3";
    }
    leaf mac-add-blk-size3 {
      type string {
        length "0..255";
      }
      description
        "Mac Address Block Size #3";
    }
    leaf base-mac-address4 {
      type string {
        length "0..255";
      }
      description
        "Base Mac Address #4";
    }
    leaf mac-add-blk-size4 {
      type string {
        length "0..255";
      }
      description
        "Mac Address Block Size #4";
    }
    leaf pcb-serial-num {
      type string {
        length "0..255";
      }
      description
        "Description of Entity PCB Serial Number";
    }
    leaf power-supply-type {
      type string {
        length "0..255";
      }
      description
        "Description of Entity Power Supply Type";
    }
    leaf power-consumption {
      type string {
        length "0..255";
      }
      description
        "Description of Entity Power Consumption";
    }
    leaf block-signature {
      type string {
        length "0..255";
      }
      description
        "Description of Entity Block Signature";
    }
    leaf block-version {
      type string {
        length "0..255";
      }
      description
        "Description of Entity Block Version";
    }
    leaf block-length {
      type string {
        length "0..255";
      }
      description
        "Description of Entity Block Length";
    }
    leaf block-checksum {
      type string {
        length "0..255";
      }
      description
        "Description of Entity Block Checksum";
    }
    leaf eeprom-size {
      type string {
        length "0..255";
      }
      description
        "Description of Entity EEPROM Size";
    }
    leaf block-count {
      type string {
        length "0..255";
      }
      description
        "Description of Entity Block Count";
    }
    leaf fru-major-type {
      type string {
        length "0..255";
      }
      description
        "Description of Entity FRU Major Type";
    }
    leaf fru-minor-type {
      type string {
        length "0..255";
      }
      description
        "Description of Entity FRU Minor Type";
    }
    leaf oem-string {
      type string {
        length "0..255";
      }
      description
        "Description of Entity OEM String";
    }
    leaf product-id {
      type string {
        length "0..255";
      }
      description
        "Description of Entity Product ID";
    }
    leaf serial-number {
      type string {
        length "0..255";
      }
      description
        "Description of Entity Serial Number";
    }
    leaf part-number {
      type string {
        length "0..255";
      }
      description
        "Description of Entity Part Number";
    }
    leaf part-revision {
      type string {
        length "0..255";
      }
      description
        "Description of Entity Part Revision";
    }
    leaf mfg-deviation {
      type string {
        length "0..255";
      }
      description
        "Description of Entity MFG Deviation";
    }
    leaf hw-version {
      type string {
        length "0..255";
      }
      description
        "Description of Entity Hardware Version";
    }
    leaf mfg-bits {
      type string {
        length "0..255";
      }
      description
        "Description of Entity MFG Bits";
    }
    leaf engineer-use {
      type string {
        length "0..255";
      }
      description
        "Description of Entity Engineer Use";
    }
    leaf snmpoid {
      type string {
        length "0..255";
      }
      description
        "Description of Entity SNMP OID";
    }
    leaf rma-code {
      type string {
        length "0..255";
      }
      description
        "Description of Entity RMA Code";
    }
    leaf eci-alpha-number {
      type string {
        length "0..255";
      }
      description
        "AlphaNumeric Equipment Catalog Item (ECI) number";
    }
  }

  grouping INVMGR-EEPROM-OPAQUE-DATA {
    description
      "invmgr eeprom opaque data";
    container eeprom {
      description
        "EEPROM data not from hex data";
      uses DIAG-EEPROM;
    }
    leaf inv-card-type {
      type uint8;
      description
        "Inventory card type";
    }
    leaf opaque-data {
      type yang:hex-string;
      description
        "EEPROM hex data";
    }
    leaf opaque-data-size {
      type uint32;
      description
        "size of the EEPROM hex data";
    }
    leaf has-eeprom {
      type uint32;
      description
        "use eeprom instead of opaque data";
    }
    leaf has-eeprom-format {
      type uint32;
      description
        "Format of the eeprom present";
    }
    leaf eeprom-format {
      type uint32;
      description
        "Format of the eeprom";
    }
    leaf name {
      type string {
        length "0..255";
      }
      description
        "Name of the physical entity";
    }
    leaf description {
      type string {
        length "0..255";
      }
      description
        "A textual description of physical entity";
    }
    leaf form-factor {
      type uint32;
      description
        "Optics form factor";
    }
    leaf connector-type {
      type uint32;
      description
        "Describes the Entity Connector type";
    }
    leaf otn-application-code {
      type uint32;
      description
        "Describes the Entity Otn Application Code";
    }
    leaf sonet-application-code {
      type uint32;
      description
        "Describes the Entity Sonet Application Code";
    }
    leaf ethernet-compliance-code {
      type uint32;
      description
        "Describes the Entity Ethernet Compliance Code";
    }
    leaf date-string {
      type string {
        length "0..255";
      }
      description
        "Describes the Entity Date string in IDPROM";
    }
    leaf vendor-revision {
      type string {
        length "0..255";
      }
      description
        "Vendor rev string in IDPROM";
    }
  }

  grouping NODEID-INFO {
    description
      "Node ID Information";
    leaf node-id {
      type uint32;
      description
        "Node Id Tuple";
    }
  }

  grouping VM-NODEID-INFO {
    description
      "VM Node ID Information";
    leaf vm-node-id {
      type uint32;
      description
        "VM Node Id Tuple";
    }
  }

  grouping SUBENTITY-INFO {
    description
      "Subentity Information";
    leaf subentity-name {
      type string {
        length "0..255";
      }
      description
        "Describe the Subentity Name";
    }
  }

  grouping INV-PARENT-INFO {
    description
      "Bag to indicate the name of the parent entity";
    leaf name {
      type string {
        length "0..255";
      }
      description
        "Parent entity name";
    }
  }
}
