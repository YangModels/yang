module Cisco-IOS-XR-infra-dumper-exception-oper {
  namespace "http://cisco.com/ns/yang/Cisco-IOS-XR-infra-dumper-exception-oper";
  prefix infra-dumper-exception-oper;

  import cisco-semver {
    prefix semver;
  }
  include Cisco-IOS-XR-infra-dumper-exception-oper-sub1 {
    revision-date 2019-04-05;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR infra-dumper-exception package operational data.
     
     This module contains definitions
     for the following management objects:
       exception: Show all exception dump configuration
     
     Copyright (c) 2013-2019 by Cisco Systems, Inc.
     All rights reserved.";

  revision 2019-04-05 {
    description
      "Establish semantic version baseline.";
    semver:module-version "1.0.0";
  }
  revision 2017-05-05 {
    description
      "Fix comp-mdata.pl for adding sub1 yang file to /pkg/yang";
  }
  revision 2015-11-09 {
    description
      "IOS XR 6.0 revision.";
  }

  container exception {
    config false;
    description
      "Show all exception dump configuration";
    container enter {
      description
        "exception bag";
      uses DUMPER-EXCEPTION-CONFIG-XML;
    }
  }
}
