module Cisco-IOS-XR-asr9k-xbar-oper {
  namespace "http://cisco.com/ns/yang/Cisco-IOS-XR-asr9k-xbar-oper";
  prefix asr9k-xbar-oper;

  import Cisco-IOS-XR-types {
    prefix xr;
  }
  import cisco-semver {
    prefix semver;
  }
  include Cisco-IOS-XR-asr9k-xbar-oper-sub4 {
    revision-date 2019-04-05;
  }
  include Cisco-IOS-XR-asr9k-xbar-oper-sub3 {
    revision-date 2019-04-05;
  }
  include Cisco-IOS-XR-asr9k-xbar-oper-sub2 {
    revision-date 2019-04-05;
  }
  include Cisco-IOS-XR-asr9k-xbar-oper-sub1 {
    revision-date 2019-04-05;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR asr9k-xbar package operational data.
     
     This module contains definitions
     for the following management objects:
       cross-bar-stats: Crossbar stats operational data
     
     Copyright (c) 2013-2019 by Cisco Systems, Inc.
     All rights reserved.";

  revision 2019-04-05 {
    description
      "Establish semantic version baseline.";
    semver:module-version "1.1.0";
  }
  revision 2015-11-09 {
    description
      "IOS XR 6.0 revision.";
  }

  container cross-bar-stats {
    config false;
    description
      "Crossbar stats operational data";
    container nodes {
      description
        "Table of Nodes";
      list node {
        key "node-name";
        description
          "Information about a particular node";
        container cross-bar-table {
          description
            "Table of stats information";
          container bandwidth-utils-stats {
            description
              "Table of packet stats for Bandwidth Utils";
            list bandwidth-utils-stat {
              key "asic-id";
              description
                "Stats information for Bandwidth Utils
                 Counter";
              leaf asic-id {
                type xr:Cisco-ios-xr-string;
                description
                  "Asic ID";
              }
              uses XBAR-EDM-BANDWIDTH-UTILS;
            }
          }
          container skb-stats {
            description
              "Table of packet stats for SKB";
            list skb-stat {
              description
                "Stats information for a particular asic type
                 and port";
              leaf asic-id {
                type xr:Cisco-ios-xr-string;
                description
                  "Asic ID";
              }
              leaf port {
                type xr:Cisco-ios-xr-string;
                description
                  "Port";
              }
              uses XBAR-EDM-SKB-PORT-STATS;
            }
          }
          container pkt-stats {
            description
              "Table of packet stats";
            list pkt-stat {
              description
                "Stats information for a particular asic type
                 and port";
              leaf asic-id {
                type xr:Cisco-ios-xr-string;
                description
                  "Asic ID";
              }
              leaf port {
                type xr:Cisco-ios-xr-string;
                description
                  "Port";
              }
              uses XBAR-XML-EDM-PORT-STATS;
            }
          }
          container sm15-stats {
            description
              "Table of packet stats for SM15";
            list sm15-stat {
              description
                "Stats information for a particular asic type
                 and port";
              leaf asic-id {
                type xr:Cisco-ios-xr-string;
                description
                  "Asic ID";
              }
              leaf port {
                type xr:Cisco-ios-xr-string;
                description
                  "Port";
              }
              uses XBAR-EDM-SM15-PORT-STATS;
            }
          }
        }
        leaf node-name {
          type xr:Node-id;
          description
            "Node name";
        }
      }
    }
  }
}
