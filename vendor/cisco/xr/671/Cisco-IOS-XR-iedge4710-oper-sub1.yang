submodule Cisco-IOS-XR-iedge4710-oper-sub1 {
  belongs-to Cisco-IOS-XR-iedge4710-oper {
    prefix Cisco-IOS-XR-iedge4710-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR iedge4710 package operational data.
     
     Copyright (c) 2013-2019 by Cisco Systems, Inc.
     All rights reserved.";

  revision 2019-04-05 {
    description
      "Establish semantic version baseline.";
    semver:module-version "1.0.1";
  }
  revision 2018-09-20 {
    description
      "Fixed yang gaps.";
  }
  revision 2015-11-09 {
    description
      "IOS XR 6.0 revision.";
  }

  grouping ISLM-SUMMARY-DATA {
    description
      "ISLM SUMMARY DATA";
    leaf session-limit {
      type uint32;
      description
        "configured session limit";
    }
    leaf session-threshold {
      type uint32;
      description
        "configured session threshold";
    }
    leaf session-license-count {
      type uint32;
      description
        "number of license";
    }
    leaf session-count {
      type uint32;
      description
        "number of sessions";
    }
  }
}
