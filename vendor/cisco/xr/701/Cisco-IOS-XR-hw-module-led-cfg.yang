module Cisco-IOS-XR-hw-module-led-cfg {
  namespace "http://cisco.com/ns/yang/Cisco-IOS-XR-hw-module-led-cfg";
  prefix hw-module-led-cfg;

  import cisco-semver {
    prefix semver;
  }
  import Cisco-IOS-XR-hw-module-cfg {
    prefix a1;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR hw-module-led package configuration.
     
     This YANG module augments the
       Cisco-IOS-XR-hw-module-cfg
     module with configuration data.
     
     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  augment "/a1:hw-module" {
    description
      "This augment extends the configuration data of
       'Cisco-IOS-XR-hw-module-cfg'";
    container attention-led {
      description
        "Enable attention LED (Blue)";
      container locations {
        description
          "Location of HW module";
        list location {
          key "location";
          description
            "Location of HW module";
          leaf location {
            type string;
            description
              "Location String";
          }
        }
      }
    }
  }
}
