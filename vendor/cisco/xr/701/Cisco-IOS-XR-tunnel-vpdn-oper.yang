module Cisco-IOS-XR-tunnel-vpdn-oper {
  namespace "http://cisco.com/ns/yang/Cisco-IOS-XR-tunnel-vpdn-oper";
  prefix tunnel-vpdn-oper;

  import ietf-inet-types {
    prefix inet;
  }
  import Cisco-IOS-XR-types {
    prefix xr;
  }
  import cisco-semver {
    prefix semver;
  }
  include Cisco-IOS-XR-tunnel-vpdn-oper-sub1 {
    revision-date 2019-04-05;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR tunnel-vpdn package operational data.
     
     This module contains definitions
     for the following management objects:
       vpdn: VPDN operational data
     
     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  container vpdn {
    config false;
    description
      "VPDN operational data";
    container nodes {
      description
        "List of nodes for which subscriber data is
         collected";
      list node {
        key "node-name";
        description
          "Subscriber data for a particular node";
        container sessions {
          description
            "VPDN session list";
          list session {
            key "session-label";
            description
              " VPDN session information";
            leaf session-label {
              type xr:Hex-integer;
              description
                "Session label";
            }
            uses VPDN-EDM-SHOW-SESSION-DET;
          }
        }
        container tunnel-destinations {
          description
            "VPDN tunnel Destinations";
          list tunnel-destination {
            description
              "VPDN tunnel destination information";
            leaf vrf-name {
              type xr:Cisco-ios-xr-string;
              description
                "VRF name";
            }
            leaf address {
              type inet:ipv4-address-no-zone;
              description
                "IP address";
            }
            uses VPDN-LSG-NODE;
          }
        }
        container vpdn-mirroring {
          description
            "VPDN Mirroring Statistics";
          uses VPDN-MIRRORING-STATS;
        }
        container vpdn-redundancy {
          description
            "Show VPDN Redundancy information";
          uses VPDN-REDUNDANCY;
        }
        container history-failures {
          description
            "VPDN history failure list";
          list history-failure {
            description
              "VPDN history failure information";
            leaf username {
              type string;
              description
                "Username";
            }
            leaf remote-name {
              type xr:Cisco-ios-xr-string;
              description
                "Remote name";
            }
            uses VPDN-HISTORY-ENTRY;
          }
        }
        leaf node-name {
          type xr:Node-id;
          description
            "Node name";
        }
      }
    }
  }
}
