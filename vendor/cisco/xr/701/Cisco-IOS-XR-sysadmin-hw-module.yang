module Cisco-IOS-XR-sysadmin-hw-module {
  namespace "http://www.cisco.com/ns/yang/Cisco-IOS-XR-sysadmin-hw-module";
  prefix calvados_hw_module;

  import Cisco-IOS-XR-sysadmin-sm-hw-mod {
    prefix shelf_mgr;
  }
  import Cisco-IOS-XR-sysadmin-led-mgr-ui {
    prefix led_mgr;
  }
  import Cisco-IOS-XR-sysadmin-fpd-infra-cli-shhwfpd {
    prefix shhwfpd;
  }
  import Cisco-IOS-XR-sysadmin-obfl-conf {
    prefix obflconf;
  }
  import cisco-semver {
    prefix semver;
  }

  organization
    "Cisco Systems Inc.";
  contact
    "Cisco Systems, Inc.
     Customer Service
     
     Postal: 170 West Tasman Drive
     San Jose, CA 95134
     
     Tel: +1 800 553-NETS
     
     E-mail: cs-yang@cisco.com";
  description
    "This module contains a collection of YANG
     definitions for Cisco IOS-XR SysAdmin configuration.
     
     This module defines the top level container for
     all 'hw-module' commands for Sysadmin.
     
     Copyright (c) 2012-2019 by Cisco Systems, Inc.
     All rights reserved.";

  revision 2019-04-15 {
    description
      "Establish semantic version baseline.";
    semver:module-version "1.0.0";
  }
  revision 2017-01-31 {
    description
      "Changed the namespace and module name";
  }
  revision 2012-07-03 {
    description
      "Created initial 'hw-module' refactorization";
  }

  container hw-module {
    container config {
      config true;
      uses shelf_mgr:hw-module-config-group;
      uses led_mgr:hw-module-config-group;
      uses obflconf:hw-module-config-group;
    }
    container oper {
      config false;
      list location {
        key "location";
        leaf location {
          type string;
        }
        container actions {
          uses shelf_mgr:hw-module-action-group;
        }
        container show;
      }
    }
    uses shhwfpd:hw-module-oper-group;
  }
}
