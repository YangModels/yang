submodule Cisco-IOS-XR-sse-span-oper-sub1 {
  belongs-to Cisco-IOS-XR-sse-span-oper {
    prefix Cisco-IOS-XR-sse-span-oper;
  }

  import ietf-yang-types {
    prefix yang;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR sse-span package operational data.
     
     Copyright (c) 2013-2019 by Cisco Systems, Inc.
     All rights reserved.";

  revision 2019-04-05 {
    description
      "Establish semantic version baseline.";
    semver:module-version "1.0.0";
  }
  revision 2017-09-07 {
    description
      "Fixed type translation error.";
  }
  revision 2015-11-09 {
    description
      "IOS XR 6.0 revision.";
  }

  grouping SSE-SPAN-EA-SDT-BAG {
    description
      "SPAN Session Information";
    leaf valid {
      type uint8;
      description
        "marks validity of entry";
    }
    leaf id {
      type uint32;
      description
        "Numerical ID assigned to session";
    }
    leaf state {
      type uint32;
      description
        "session state";
    }
    leaf class {
      type uint32;
      description
        "session Class gre,ipv4,ipv6";
    }
    leaf ifhandle {
      type uint32;
      description
        "ifhandle of interface";
    }
    leaf mode {
      type uint32;
      description
        "Tunnel mode";
    }
    leaf ip-type {
      type uint32;
      description
        "IP type v4 or v6 ";
    }
    leaf vrf-id {
      type uint32;
      description
        "Vrf Id";
    }
    leaf tos-bit {
      type uint32;
      description
        "type of service";
    }
    leaf tos-bit-copied {
      type uint32;
      description
        "type of service copied";
    }
    leaf ttl {
      type uint32;
      description
        "TTL";
    }
    leaf dfbit {
      type uint32;
      description
        "DF bit";
    }
    leaf-list src-ip {
      type uint32;
      max-elements "4";
      description
        "src ip v4 or v6";
    }
    leaf-list dst-ip {
      type uint32;
      max-elements "4";
      description
        "dst ip v4 or v6";
    }
    leaf-list sdt-hw-data {
      type uint32;
      max-elements "20";
      description
        "16x5npu=80 bytes of hw sdt entry";
    }
  }

  grouping SSE-SPAN-EA-UDF-BAG {
    description
      "UDF Information";
    leaf-list udf-hdr {
      type uint32;
      max-elements "8";
      description
        "udf header";
    }
    leaf-list udf-type {
      type uint32;
      max-elements "8";
      description
        "udf type";
    }
    leaf-list udf-len {
      type uint32;
      max-elements "8";
      description
        "udf len";
    }
    leaf-list udf-value {
      type uint32;
      max-elements "8";
      description
        "udf value";
    }
    leaf-list udf-hw-data {
      type uint32;
      max-elements "20";
      description
        "16x5npu=80 bytes of hw udf entry";
    }
  }

  grouping SSE-SPAN-EA-SFT-BAG {
    description
      "SPAN Session SFT Information";
    leaf src-ifh {
      type uint32;
      description
        "source IFH";
    }
    leaf intf-name-xr {
      type yang:hex-string;
      description
        "interface name";
    }
    leaf v4-acl-flag {
      type uint32;
      description
        "ipv4 acl flag";
    }
    leaf v6-acl-flag {
      type uint32;
      description
        "ipv6 acl flag";
    }
    leaf gre-acl-flag {
      type uint32;
      description
        "gre acl flag";
    }
    leaf v4state {
      type uint32;
      description
        "ipv4 state";
    }
    leaf v6state {
      type uint32;
      description
        "ipv6 state";
    }
    leaf gre-state {
      type uint32;
      description
        "gre state";
    }
    leaf v4sessid {
      type uint32;
      description
        "ipv4 session Id";
    }
    leaf v6sessid {
      type uint32;
      description
        "ipv6 session Id";
    }
    leaf gre-sessid {
      type uint32;
      description
        "gre session Id";
    }
    leaf v4dst-type {
      type uint32;
      description
        "ipv4 dst type";
    }
    leaf v6dst-type {
      type uint32;
      description
        "ipv6 dst type";
    }
    leaf gredst-type {
      type uint32;
      description
        "gre dst type";
    }
    leaf v4statsptr {
      type uint32;
      description
        "v4 stats ptr";
    }
    leaf v6statsptr {
      type uint32;
      description
        "v6 stats ptr";
    }
    leaf grev4statsptr {
      type uint32;
      description
        "mpls ipv4 stats ptr";
    }
    leaf grev6statsptr {
      type uint32;
      description
        "mpls ipv6 stats ptr";
    }
    leaf mplsv4stats {
      type uint32;
      description
        "mpls ipv4 pkts";
    }
    leaf mplsv6pkts {
      type uint32;
      description
        "mpls ipv6 pkts";
    }
    leaf np-umask {
      type uint32;
      description
        "npu mask";
    }
    leaf-list uidb {
      type uint32;
      max-elements "5";
      description
        "uidb array ";
    }
    leaf-list sft-hw-data {
      type uint32;
      max-elements "20";
      description
        "16x5npu=80 bytes of hw sft entry";
    }
  }
}
