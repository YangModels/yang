module Cisco-IOS-XR-ip-static-ipv6-oper {
  namespace "http://cisco.com/ns/yang/Cisco-IOS-XR-ip-static-ipv6-oper";
  prefix ip-static-ipv6-oper;

  import Cisco-IOS-XR-types {
    prefix xr;
  }
  import cisco-semver {
    prefix semver;
  }
  include Cisco-IOS-XR-ip-static-ipv6-oper-sub1 {
    revision-date 2019-04-05;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ip-static-ipv6 package operational data.
     
     This module contains definitions
     for the following management objects:
       ipv6-local: Local Routing Information
       ipv6-static: Static Routing Information
       ipv6-connected: connected Routing Information
     
     Copyright (c) 2013-2019 by Cisco Systems, Inc.
     All rights reserved.";

  revision 2019-04-05 {
    description
      "Establish semantic version baseline.";
    semver:module-version "1.0.0";
  }
  revision 2019-01-03 {
    description
      "Added oper ipv6 support";
  }
  revision 2015-11-09 {
    description
      "IOS XR 6.0 revision.";
  }

  typedef Afiipv6 {
    type enumeration {
      enum "ipv4" {
        value 1;
        description
          "ipv4 addressfamily";
      }
      enum "ipv6" {
        value 2;
        description
          "ipv6 addressfamily";
      }
    }
    description
      "Afiipv6";
  }

  typedef Safiipv6 {
    type enumeration {
      enum "unicast" {
        value 1;
        description
          "unicat type";
      }
      enum "multicast" {
        value 2;
        description
          "multicast type";
      }
    }
    description
      "Safiipv6";
  }

  grouping TOPO-VRF-TABLE {
    description
      "Common node of ipv6-static, ipv6-local,
       ipv6-connected";
    container topo-vrfs {
      description
        "vrf list for Topology";
      list topo-vrf {
        key "vrf-name";
        description
          "vrf name";
        leaf vrf-name {
          type xr:Cisco-ios-xr-string;
          description
            "The name of thei vrf";
        }
        list topo-table {
          key "table-name";
          description
            "Topology table name";
          leaf table-name {
            type xr:Cisco-ios-xr-string;
            description
              "The name of the atble";
          }
          list topo-afi {
            key "afi";
            description
              "Topology address family type";
            leaf afi {
              type Afiipv6;
              description
                "IPv6 AFI";
            }
            list topo-safi {
              key "safi";
              description
                "Topology SAFI type";
              container destinations {
                description
                  "route info";
                list destination {
                  description
                    "Destinatioin address and prefix length";
                  leaf prefix {
                    type xr:Cisco-ios-xr-string;
                    description
                      "IP Prefix";
                  }
                  leaf prefix-length {
                    type xr:Hex-integer;
                    description
                      "IPv6 Prefix length";
                  }
                  uses IPV6-STATIC-ROUTE-BD;
                }
              }
              leaf safi {
                type Safiipv6;
                description
                  "IPv6 SAFI";
              }
            }
          }
        }
      }
    }
  }

  grouping NHVRF-TABLE {
    description
      "Common node of ipv6-static, ipv6-local,
       ipv6-connected";
    container nhvrfs {
      description
        "next-hop's vrf list";
      list nhvrf {
        key "vrf-name";
        description
          "vrf name";
        leaf vrf-name {
          type xr:Cisco-ios-xr-string;
          description
            "The name of thei vrf";
        }
        list nh-table {
          key "table-name";
          description
            "next-hop table name";
          leaf table-name {
            type xr:Cisco-ios-xr-string;
            description
              "The name of the atble";
          }
          list nhafi {
            key "afi";
            description
              "next-hop address family type";
            leaf afi {
              type Afiipv6;
              description
                "IPv6 AFI";
            }
            list nhsafi {
              key "safi";
              description
                "next-hop safi(unicat|multicast) type";
              container nh-addresses {
                description
                  "next-hop Database";
                list nh-address {
                  key "next-hop-addr";
                  description
                    "next hop address to display";
                  leaf next-hop-addr {
                    type xr:Cisco-ios-xr-string;
                    description
                      "next hop address";
                  }
                  uses IPV6-STATIC-NHDB-BD;
                }
              }
              leaf safi {
                type Safiipv6;
                description
                  "IPv6 SAFI";
              }
            }
          }
        }
      }
    }
  }

  grouping TABLE {
    description
      "Common node of ipv6-static, ipv6-local,
       ipv6-connected";
    container table-ids {
      description
        "list of Tables";
      list table-id {
        key "table-id";
        description
          "Table ID to display";
        leaf table-id {
          type xr:Hex-integer;
          description
            "Table ID";
        }
        uses IP-STATIC-TDB-BD;
      }
    }
  }

  grouping TABLE-EVENTS {
    description
      "Common node of ipv6-static, ipv6-local,
       ipv6-connected";
    container table-events-ids {
      description
        "list of Tables";
      list table-events-id {
        key "table-id";
        description
          "Table ID to display events info";
        leaf table-id {
          type xr:Hex-integer;
          description
            "Table ID";
        }
        uses EVT-HIST-INFO;
      }
    }
  }

  grouping IPV6-IF-DB {
    description
      "Common node of ipv6-static, ipv6-local,
       ipv6-connected";
    container ipv6vrfs {
      description
        "ipv6 interface database";
      list ipv6vrf {
        key "vrf-name";
        description
          "vrf name";
        leaf vrf-name {
          type xr:Cisco-ios-xr-string;
          description
            "The name of the";
        }
        list ipv6-table {
          key "table-name";
          description
            "table name";
          leaf table-name {
            type xr:Cisco-ios-xr-string;
            description
              "The name of the";
          }
          list ipv6afi {
            key "afi";
            description
              "address family type";
            leaf afi {
              type Afiipv6;
              description
                "IPv6 AFI";
            }
            list ipv6safi {
              key "safi";
              description
                "unicast|multicast";
              leaf safi {
                type Safiipv6;
                description
                  "IPv6 SAFI";
              }
              list ipv6-interface {
                key "interface-name";
                description
                  "Interface to display";
                leaf interface-name {
                  type xr:Interface-name;
                  description
                    "Interface name";
                }
                uses IPV6-STATIC-IDB-BD;
              }
            }
          }
        }
      }
    }
  }

  container ipv6-local {
    config false;
    description
      "Local Routing Information";
    uses NHVRF-TABLE;
    uses TABLE-EVENTS;
    uses TOPO-VRF-TABLE;
    uses IPV6-IF-DB;
    uses TABLE;
  }
  container ipv6-static {
    config false;
    description
      "Static Routing Information";
    uses NHVRF-TABLE;
    uses TABLE-EVENTS;
    uses TOPO-VRF-TABLE;
    uses IPV6-IF-DB;
    uses TABLE;
  }
  container ipv6-connected {
    config false;
    description
      "connected Routing Information";
    uses NHVRF-TABLE;
    uses TABLE-EVENTS;
    uses TOPO-VRF-TABLE;
    uses IPV6-IF-DB;
    uses TABLE;
  }
}
