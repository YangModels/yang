module Cisco-IOS-XR-ping-act {
  namespace "http://cisco.com/ns/yang/Cisco-IOS-XR-ping-act";
  prefix ping-act;

  import cisco-semver {
    prefix semver;
  }
  include Cisco-IOS-XR-ipv4-ping-act;
  include Cisco-IOS-XR-ipv6-ping-act;

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ping action package configuration.
     
     Copyright (c) 2016-2019 by Cisco Systems, Inc.
     All rights reserved.";

  revision 2019-04-05 {
    description
      "Establish semantic version baseline.";
    semver:module-version "1.0.0";
  }
  revision 2018-10-01 {
    description
      "IOS XR 6.2.1 revision.";
  }

  rpc ping {
    description
      "Send echo messages";
    input {
      container destination {
        presence "ping input";
        uses PING-OPTIONS;
        uses IPV4-SPECIFIC-OPTIONS;
        uses IPV6-SPECIFIC-OPTIONS;
      }
      list ipv4 {
        key "destination";
        uses IPV4-PING-INPUT;
      }
      container ipv6 {
        presence "ipv6 ping input";
        uses IPV6-PING-INPUT;
      }
    }
    output {
      container ping-response {
        list ipv4 {
          key "destination";
          uses IPV4-PING-OUTPUT;
        }
        container ipv6 {
          presence "ipv6 ping output";
          uses IPV6-PING-OUTPUT;
        }
      }
    }
  }
}
