module Cisco-IOS-XR-shellutil-cfg {
  namespace "http://cisco.com/ns/yang/Cisco-IOS-XR-shellutil-cfg";
  prefix shellutil-cfg;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR shellutil package configuration.
     
     This module contains definitions
     for the following management objects:
       host-names: Container Schema for hostname configuration
     
     Copyright (c) 2013-2019 by Cisco Systems, Inc.
     All rights reserved.";

  revision 2019-04-05 {
    description
      "Establish semantic version baseline.";
    semver:module-version "1.0.0";
  }
  revision 2015-10-12 {
    description
      "Descriptions updated.";
  }
  revision 2015-01-07 {
    description
      "IOS XR 5.3.1 revision.";
  }

  container host-names {
    description
      "Container Schema for hostname configuration";
    leaf host-name {
      type string;
      description
        "Configure system's hostname";
    }
  }
}
