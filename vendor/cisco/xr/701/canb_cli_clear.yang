module canb_cli_clear {
  namespace "http://cisco.com/calvados/canb_cli_clear";
  prefix canb_clear;

  import tailf-common {
    prefix tailf;
  }

  organization
    "Cisco Systems Inc.";
  contact
    "Cisco Systems, Inc.
     Customer Service
     
     Postal: 170 West Tasman Drive
     San Jose, CA 95134
     
     Tel: +1 800 553-NETS
     
     E-mail: cs-yang@cisco.com";
  description
    "This module is for clearing OIR counters.
     
     Copyright (c) 2012-2019 by Cisco Systems, Inc.
     All rights reserved.";

  revision 2016-05-24 {
    description
      "Initial revision.";
  }

  grouping canb-clear-grp {
    container plugin {
      config false;
      container slot {
        config false;
        list location {
          key "location";
          config false;
          leaf location {
            type string;
          }
          tailf:action "counts" {
            output {
              leaf canb_clear_plugin_result {
                type string;
                mandatory true;
              }
            }
          }
        }
      }
    }
  }
}
