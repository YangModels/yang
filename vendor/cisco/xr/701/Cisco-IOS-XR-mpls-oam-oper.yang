module Cisco-IOS-XR-mpls-oam-oper {
  namespace "http://cisco.com/ns/yang/Cisco-IOS-XR-mpls-oam-oper";
  prefix mpls-oam-oper;

  import ietf-inet-types {
    prefix inet;
  }
  import Cisco-IOS-XR-types {
    prefix xr;
  }
  import cisco-semver {
    prefix semver;
  }
  include Cisco-IOS-XR-mpls-oam-oper-sub2 {
    revision-date 2019-04-05;
  }
  include Cisco-IOS-XR-mpls-oam-oper-sub1 {
    revision-date 2019-04-05;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR mpls-oam package operational data.
     
     This module contains definitions
     for the following management objects:
       mpls-oam: MPLS OAM operational data
     
     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  container mpls-oam {
    config false;
    description
      "MPLS OAM operational data";
    container interface {
      description
        "MPLS OAM interface operational data";
      container briefs {
        description
          "MPLS OAM interface detail data";
        list brief {
          key "interface-name";
          description
            "MPLS OAM interface operational data";
          leaf interface-name {
            type xr:Interface-name;
            description
              "Interface name";
          }
          uses LSPV-INTERFACE-INFO-BRIEF;
        }
      }
      container details {
        description
          "MPLS OAM interface detail data";
        list detail {
          key "interface-name";
          description
            "MPLS OAM interface operational data";
          leaf interface-name {
            type xr:Interface-name;
            description
              "Interface name";
          }
          uses LSPV-INTERFACE-INFO;
        }
      }
    }
    container packet {
      description
        "LSPV packet counters operational data";
      uses LSPV-PACKET-STATISTICS;
    }
    container global {
      description
        "LSPV global counters operational data";
      uses LSPV-GLOBAL-TYPE;
    }
    container dpm {
      description
        "MPLS OAM DPM operational data";
      container adjacency-summary {
        description
          "LSPV DPM adjacency summary operational data";
        uses LSPV-DPM-ADJ-DB-SUMMARY;
      }
      container prefixes {
        description
          "MPLS OAM DPM prefix operational data";
        list prefix {
          key "prefix";
          description
            "MPLS OAM DPM prefix operational data";
          leaf prefix {
            type inet:ip-prefix;
            description
              "The IP Prefix";
          }
          uses LSPV-DPM-PFX;
        }
      }
      container counters {
        description
          "LSPV DPM counters operational data";
        uses LSPV-DPM-COUNTERS;
      }
      container prefix-faults {
        description
          "MPLS OAM DPM prefix fault operational data";
        list prefix-fault {
          description
            "MPLS OAM DPM prefix fault operational data";
          leaf prefix {
            type inet:ip-prefix;
            description
              "The IP Prefix";
          }
          leaf downstream-address {
            type inet:ip-address-no-zone;
            description
              "Downstream IP Address";
          }
          leaf upstream-address {
            type inet:ip-address-no-zone;
            description
              "Upstream IP Address";
          }
          uses LSPV-DPM-FAULT;
        }
      }
      container adjacency-summary-last {
        description
          "LSPV last DPM run adjacency summary operational
           data";
        uses LSPV-DPM-ADJ-DB-SUMMARY;
      }
      container summary {
        description
          "LSPV DPM summary operational data";
        uses LSPV-DPM-SUMMARY;
      }
      container adjacency-faults {
        description
          "MPLS OAM DPM adjacency operational data";
        list adjacency-fault {
          description
            "MPLS OAM DPM adjcency fault operational data";
          leaf interface-name {
            type xr:Interface-name;
            description
              "Interface name";
          }
          leaf local-label-id {
            type uint32 {
              range "16..1048575";
            }
            description
              "Local Label";
          }
          uses LSPV-DPM-ADJ-FAULT;
        }
      }
      container adjacencies {
        description
          "MPLS OAM DPM adjacency operational data";
        list adjacency {
          key "interface-name";
          description
            "MPLS OAM DPM adjcency operational data";
          leaf interface-name {
            type xr:Interface-name;
            description
              "Interface name";
          }
          uses LSPV-DPM-ADJ;
        }
      }
      container prefix-summary {
        description
          "LSPV DPM prefix summary operational data";
        uses LSPV-DPM-PFX-DB-SUMMARY;
      }
      container prefix-summary-last {
        description
          "LSPV last DPM run prefix summary operational
           data";
        uses LSPV-DPM-PFX-DB-SUMMARY;
      }
      container summary-last {
        description
          "LSPV last DPM run summary operational data";
        uses LSPV-DPM-SUMMARY;
      }
    }
  }
}
