module Cisco-IOS-XR-sysadmin-controllers-asr9k {
  namespace "http://www.cisco.com/ns/yang/Cisco-IOS-XR-sysadmin-controllers-ASR9K";
  prefix calvados_controllers_asr9k;

  import Cisco-IOS-XR-sysadmin-ethsw-esdma-cli-asr9k {
    prefix esdma;
  }
  import cisco-semver {
    prefix semver;
  }

  organization
    "Cisco Systems Inc.";
  contact
    "Cisco Systems, Inc.
     Customer Service
     
     Postal: 170 West Tasman Drive
     San Jose, CA 95134
     
     Tel: +1 800 553-NETS
     
     E-mail: cs-yang@cisco.com";
  description
    "This module contains a collection of YANG
     definitions for Cisco IOS-XR SysAdmin configuration.
     
     This module defines the top level container for
     all hardware devices managed in Sysadmin.
     
     Copyright (c) 2011-2019 by Cisco Systems, Inc.
     All rights reserved.";

  revision 2019-04-15 {
    description
      "Establish semantic version baseline.";
    semver:module-version "1.0.0";
  }
  revision 2017-11-10 {
    description
      "Changed the namespace for ASR9K platform";
  }
  revision 2017-01-31 {
    description
      "Changed the namespace and module name";
  }
  revision 2015-02-23 {
    description
      "Initial Revision";
  }

  container controller {
    container switch {
      uses esdma:switch;
    }
  }
}
