module Cisco-IOS-XR-cli-diff-act {
  namespace "http://cisco.com/ns/yang/Cisco-IOS-XR-cli-diff-act";
  prefix cli-diff-act;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR CLI package configuration.
     
     Copyright (c) 2019 by Cisco Systems, Inc.
     All rights reserved.";

  revision 2019-04-15 {
    description
      "Initial draft";
    semver:module-version "1.0.0";
  }

  rpc get-cli-config-diff {
    description
      "Return CLI config command changeset";
    output {
      leaf response {
        type string;
        description
          "The diff output of CLI config being changed";
      }
    }
  }
}
