module Cisco-IOS-XR-shelfmgr-act {
  namespace "http://cisco.com/ns/yang/Cisco-IOS-XR-shelfmgr-act";
  prefix shelfmgr-act;

  import Cisco-IOS-XR-types {
    prefix csc;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR action package configuration.
     
     Copyright (c) 2017-2019 by Cisco Systems, Inc.
     All rights reserved.";

  revision 2019-04-05 {
    description
      "Establish semantic version baseline.";
    semver:module-version "1.0.0";
  }
  revision 2018-01-31 {
    description
      "IOS XR 6.3.1 revision.";
  }

  typedef location-name {
    type string {
      length "1..64";
    }
  }

  typedef reboot-method {
    type enumeration {
      enum "unknown";
      enum "cold";
      enum "powerdown";
      enum "halt";
      enum "warm";
      enum "nsf";
      enum "reset";
      enum "powerup";
    }
    description
      "Reboot action type";
  }

  typedef boot-media {
    type enumeration {
      enum "network";
      enum "usb";
    }
    description
      "Boot media Type";
  }

  rpc reboot-request {
    description
      "Boot, reboot, or shutdown the specified entity";
    input {
      leaf method {
        type reboot-method;
        mandatory true;
        description
          "Reboot operation type";
      }
      leaf delay {
        type uint32;
        mandatory false;
        description
          "Delay in nanoseconds before issuing command";
      }
      leaf message {
        type string;
        mandatory false;
        description
          "Informational reason for the operation";
      }
      leaf location {
        type location-name;
        mandatory false;
        description
          "Fully qualified location specification";
      }
      leaf force {
        type boolean;
        mandatory false;
        description
          "Do not wait for software to shutdown gracefully";
      }
      leaf bootmedia {
        type boot-media;
        mandatory false;
        description
          "Bootmedia type";
      }
    }
    csc:xr-task "spi-shelfmgr";
  }
  rpc reboot-status-request {
    description
      "Retrieves the latest boot status of the specified entity";
    input {
      leaf location {
        type location-name;
        mandatory true;
        description
          "Fully qualified location specification";
      }
    }
    output {
      container reboot-status-response {
        description
          "Latest boot status of the target";
        csc:xr-task "spi-shelfmgr";
        leaf active {
          type boolean;
          description
            "Set to true if reboot is active";
        }
        leaf wait {
          type uint64;
          description
            "Time left until reboot";
        }
        leaf when {
          type uint64;
          description
            "Time to reboot in nanoseconds since the epoch";
        }
        leaf reason {
          type string;
          description
            "Reason for reboot";
        }
        leaf count {
          type uint32;
          description
            "Number of reboots since active";
        }
      }
    }
    csc:xr-task "spi-shelfmgr";
  }
}
