module Cisco-IOS-XR-sysadmin-ethsw-esdma-debug {
  namespace "http://www.cisco.com/ns/yang/Cisco-IOS-XR-sysadmin-ethsw-esdma-debug";
  prefix esdma_debug;

  import Cisco-IOS-XR-sysadmin-ethsw-esdma-types {
    prefix esdma_types;
  }
  import cisco-semver {
    prefix semver;
  }

  organization
    "Cisco Systems Inc.";
  contact
    "Cisco Systems, Inc.
     Customer Service
     
     Postal: 170 West Tasman Drive
     San Jose, CA 95134
     
     Tel: +1 800 553-NETS
     
     E-mail: cs-yang@cisco.com";
  description
    "This module contains the YANG definitions
     for the hidden Cisco IOS-XR SysAdmin
     'show controller switch debug counters' command.
     
     Copyright (c) 2011-2019 by Cisco Systems, Inc.
     All rights reserved.";

  revision 2019-04-15 {
    description
      "Establish semantic version baseline.";
    semver:module-version "1.0.0";
  }
  revision 2017-05-01 {
    description
      "Namespace change to comply with Cisco guidelines on namespace";
  }
  revision 2016-10-12 {
    description
      "Unhide commands and configs. Moved to advanced-grp";
  }
  revision 2016-07-06 {
    description
      "Initial revision with content extracted from esdma_cli.yang.";
  }

  grouping switch-debug-data {
    container debug {
      container counters {
        list location {
          key "rack card switch-id";
          leaf rack {
            type esdma_types:esdma-rack-num-enum;
          }
          leaf card {
            type esdma_types:esdma-cpu;
          }
          leaf switch-id {
            type esdma_types:esdma-switch-type-enum;
          }
          container counters {
            leaf phy-polling-enabled {
              type boolean;
            }
            leaf tx-thread-wdog-cnt {
              type uint64;
            }
            leaf rx-thread-wdog-cnt {
              type uint64;
            }
            leaf task-lock-longest-wait-time {
              type uint64;
            }
            leaf task-lock-longest-wait-event {
              type uint32;
            }
            leaf task-lock-longest-held-time {
              type uint64;
            }
            leaf task-lock-longest-held-event {
              type uint32;
            }
            leaf task-unlock-longest-wait-time {
              type uint64;
            }
            leaf task-unlock-longest-wait-event {
              type uint32;
            }
            leaf dma-max-rx-dequeued-per-int {
              type uint64;
            }
            leaf dma-rx-packets-dequeued {
              type uint64;
            }
            leaf dma-rx-packet-dequeue-errors {
              type uint64;
            }
            leaf dma-tx-packets-queued {
              type uint64;
            }
            leaf dma-tx-packets-completed {
              type uint64;
            }
            leaf dma-tx-packet-no-msg-errors {
              type uint64;
            }
            leaf dma-tx-packet-msg-too-big-errors {
              type uint64;
            }
            leaf dma-tx-packet-no-buffer-errors {
              type uint64;
            }
            leaf dma-tx-packet-queue-errors {
              type uint64;
            }
            leaf dma-tx-packet-completion-errors {
              type uint64;
            }
            leaf dma-max-tx-freed-per-int {
              type uint64;
            }
            leaf dma-tx-buf-alloc-count {
              type uint64;
            }
            leaf dma-tx-buf-free-count {
              type uint64;
            }
            list switch-core {
              key "core";
              leaf core {
                type uint8;
              }
              leaf msi-count {
                type uint64;
              }
              leaf aer-count {
                type uint64;
              }
              leaf hp-count {
                type uint64;
              }
              leaf wdog-count {
                type uint64;
              }
              leaf core-task-lock-longest-wait-time {
                type uint64;
              }
              leaf core-task-lock-longest-held-time {
                type uint64;
              }
              leaf core-task-unlock-longest-wait-time {
                type uint64;
              }
            }
          }
        }
      }
    }
  }

  grouping switch-debug-group {
    container switch-debug-cont {
      uses switch-debug-data;
    }
  }
}
