module Cisco-IOS-XR-ipv4-ma-subscriber-cfg {
  namespace "http://cisco.com/ns/yang/Cisco-IOS-XR-ipv4-ma-subscriber-cfg";
  prefix ipv4-ma-subscriber-cfg;

  import cisco-semver {
    prefix semver;
  }
  import Cisco-IOS-XR-subscriber-infra-tmplmgr-cfg {
    prefix a1;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ipv4-ma-subscriber package configuration.
     
     This YANG module augments the
       Cisco-IOS-XR-subscriber-infra-tmplmgr-cfg
     module with configuration data.
     
     Copyright (c) 2013-2019 by Cisco Systems, Inc.
     All rights reserved.";

  revision 2019-04-05 {
    description
      "Establish semantic version baseline.";
    semver:module-version "1.0.0";
  }
  revision 2015-07-30 {
    description
      "Descriptions updated.";
  }
  revision 2015-01-07 {
    description
      "IOS XR 5.3.1 revision.";
  }

  grouping IPV4-NETWORK {
    description
      "Common node of ip-subscriber, ppp,
       subscriber-service";
    container ipv4-network {
      description
        "Interface IPv4 Network configuration data";
      leaf unnumbered {
        type string;
        description
          "Enable IP processing without an explicit
           address";
      }
      leaf mtu {
        type uint32 {
          range "68..65535";
        }
        units "byte";
        description
          "The IP Maximum Transmission Unit";
      }
      leaf unreachables {
        type boolean;
        default "false";
        description
          "TRUE if enabled, FALSE if disabled";
      }
      leaf rpf {
        type boolean;
        default "true";
        description
          "TRUE if enabled, FALSE if disabled";
      }
    }
  }

  augment "/a1:dynamic-template/a1:subscriber-services/a1:subscriber-service" {
    description
      "This augment extends the configuration data of
       'Cisco-IOS-XR-subscriber-infra-tmplmgr-cfg'";
    uses IPV4-NETWORK;
  }
  augment "/a1:dynamic-template/a1:ppps/a1:ppp" {
    description
      "This augment extends the configuration data of
       'Cisco-IOS-XR-subscriber-infra-tmplmgr-cfg'";
    uses IPV4-NETWORK;
  }
  augment "/a1:dynamic-template/a1:ip-subscribers/a1:ip-subscriber" {
    description
      "This augment extends the configuration data of
       'Cisco-IOS-XR-subscriber-infra-tmplmgr-cfg'";
    uses IPV4-NETWORK;
  }
}
