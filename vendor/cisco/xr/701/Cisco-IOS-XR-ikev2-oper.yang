module Cisco-IOS-XR-ikev2-oper {
  namespace "http://cisco.com/ns/yang/Cisco-IOS-XR-ikev2-oper";
  prefix ikev2-oper;

  import ietf-inet-types {
    prefix inet;
  }
  import Cisco-IOS-XR-types {
    prefix xr;
  }
  import cisco-semver {
    prefix semver;
  }
  include Cisco-IOS-XR-ikev2-oper-sub1 {
    revision-date 2019-04-05;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ikev2 package operational data.
     
     This module contains definitions
     for the following management objects:
       ikev2: IKEv2 operational data
     
     Copyright (c) 2013-2019 by Cisco Systems, Inc.
     All rights reserved.";

  revision 2019-04-05 {
    description
      "Establish semantic version baseline.";
    semver:module-version "1.0.0";
  }
  revision 2018-12-20 {
    description
      "Operational Yang Support";
  }
  revision 2015-11-09 {
    description
      "IOS XR 6.0 revision.";
  }

  grouping IP {
    description
      "Common node of local-v4, remote-v4";
    list ip {
      key "address";
      description
        "IKEv2 SA data based on address";
      leaf address {
        type inet:ipv4-address-no-zone;
        description
          "Address";
      }
      uses IKEV2-EDM-SA-DB;
    }
  }

  container ikev2 {
    config false;
    description
      "IKEv2 operational data";
    container nodes {
      description
        "Per node IKEv2 operational data";
      list node {
        key "node-name";
        description
          "IKEv2 operational data for a particular node";
        container session-ids {
          description
            "IKEv2 Session data";
          list session-id {
            key "id";
            description
              "IKEv2 Session data";
            leaf id {
              type uint32 {
                range "1..65535";
              }
              description
                "Session Id";
            }
            uses IKEV2-EDM-SESSION;
          }
        }
        container stats {
          description
            "IKEv2 Stats data";
          uses IKEV2-EDM-STATS;
        }
        container sa {
          description
            "IKEv2 SA data";
          container local-v4 {
            description
              "IKEv2 SA lookup on local IP";
            uses IP;
          }
          container remote-v4 {
            description
              "IKEv2 SA lookup on remote IP";
            uses IP;
          }
          container all {
            description
              "IKEv2 SA all data";
            uses IKEV2-EDM-SA-DB;
          }
        }
        container summary {
          description
            "IKEv2 Summary data";
          uses IKEV2-EDM-SUMMARY;
        }
        container policies {
          description
            "IKEv2 policies on this node";
          list policy {
            key "name";
            description
              "IKEv2 policy data";
            leaf name {
              type xr:Cisco-ios-xr-string {
                length "1..32";
              }
              description
                "Name of the IKEv2 policy";
            }
            uses IKEV2-EDM-POLICY;
          }
        }
        container proposals {
          description
            "IKEv2 proposals on this node";
          list proposal {
            key "name";
            description
              "IKEv2 proposal data";
            leaf name {
              type xr:Cisco-ios-xr-string {
                length "1..32";
              }
              description
                "Name of the IKEv2 proposal";
            }
            uses IKEV2-EDM-PROPOSAL;
          }
        }
        container profiles {
          description
            "IKEv2 profiles on this node";
          list profile {
            key "name";
            description
              "IKEv2 profile data";
            leaf name {
              type xr:Cisco-ios-xr-string {
                length "1..32";
              }
              description
                "Name of the IKEv2 profile";
            }
            uses IKEV2-EDM-PROFILE;
          }
        }
        leaf node-name {
          type xr:Node-id;
          description
            "The identifier for the node";
        }
      }
    }
  }
}
