module Cisco-IOS-XR-ipv6-new-dhcpv6d-subscriber-cfg {
  namespace "http://cisco.com/ns/yang/Cisco-IOS-XR-ipv6-new-dhcpv6d-subscriber-cfg";
  prefix ipv6-new-dhcpv6d-subscriber-cfg;

  import ietf-inet-types {
    prefix inet;
  }
  import Cisco-IOS-XR-types {
    prefix xr;
  }
  import cisco-semver {
    prefix semver;
  }
  import Cisco-IOS-XR-subscriber-infra-tmplmgr-cfg {
    prefix a1;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ipv6-new-dhcpv6d-subscriber package configuration.
     
     This YANG module augments the
       Cisco-IOS-XR-subscriber-infra-tmplmgr-cfg
     module with configuration data.
     
     Copyright (c) 2013-2019 by Cisco Systems, Inc.
     All rights reserved.";

  revision 2019-04-05 {
    description
      "Establish semantic version baseline.";
    semver:module-version "1.0.0";
  }
  revision 2017-09-30 {
    description
      "Ensure propagation of MDA mandatory state to YANG model.";
  }
  revision 2015-11-09 {
    description
      "IOS XR 6.0 revision.";
  }

  grouping DHCPV6 {
    description
      "Common node of ip-subscriber, ppp";
    container dhcpv6 {
      description
        "Interface dhcpv6 configuration data";
      container delegated-prefix {
        presence "Indicates a delegated-prefix node is configured.";
        description
          "The prefix to be used for Prefix Delegation";
        leaf prefix {
          type inet:ipv6-address-no-zone;
          mandatory true;
          description
            "IPv6 Prefix";
        }
        leaf prefix-length {
          type xr:Ipv6-prefix-length;
          mandatory true;
          description
            "PD Prefix Length";
        }
      }
      leaf dns-ipv6address {
        type inet:ipv6-address-no-zone;
        description
          "Dns IPv6 Address";
      }
      leaf mode-class {
        type string;
        description
          "Select proxy/server profile based on mode class
           name";
      }
      leaf dhcpv6-iplease {
        type string;
        description
          "Cisco VSA to configure any dhcpv6 ip lease per
           subscriber";
      }
      leaf dhcpv6-option {
        type string;
        description
          "Cisco VSA to configure any dhcpv6 option per
           subscriber";
      }
      leaf address-pool {
        type string;
        description
          "The pool to be used for Address assignment";
      }
      leaf delegated-prefix-pool {
        type string;
        description
          "The pool to be used for Prefix Delegation";
      }
      leaf class {
        type string;
        description
          "The class to be used for proxy/server profile";
      }
      leaf stateful-address {
        type inet:ipv6-address-no-zone;
        description
          "Stateful IPv6 Address";
      }
    }
  }

  augment "/a1:dynamic-template/a1:ppps/a1:ppp" {
    description
      "This augment extends the configuration data of
       'Cisco-IOS-XR-subscriber-infra-tmplmgr-cfg'";
    uses DHCPV6;
  }
  augment "/a1:dynamic-template/a1:ip-subscribers/a1:ip-subscriber" {
    description
      "This augment extends the configuration data of
       'Cisco-IOS-XR-subscriber-infra-tmplmgr-cfg'";
    uses DHCPV6;
  }
}
