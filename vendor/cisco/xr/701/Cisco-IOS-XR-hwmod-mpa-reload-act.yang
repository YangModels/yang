module Cisco-IOS-XR-hwmod-mpa-reload-act {
  namespace "http://cisco.com/ns/yang/Cisco-IOS-XR-hwmod-mpa-reload-act";
  prefix hwmod-mpa-reload-act;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR MPA reload action package configuration.
     
     Copyright (c) 2016-2019 by Cisco Systems, Inc.
     All rights reserved.";

  revision 2019-04-05 {
    description
      "Establish semantic version baseline.";
    semver:module-version "1.0.0";
  }
  revision 2016-06-30 {
    description
      "IOS XR 6.2.1 revision.";
  }

  rpc hw-module-subslot {
    description
      "Execute subslot h/w module operations";
    input {
      leaf subslot {
        type string;
        description
          "Fully qualified location specification";
      }
      leaf reload {
        type empty;
        description
          "Cycle subslot h/w reset";
      }
    }
  }
}
