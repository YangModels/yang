module SNMP-VIEW-BASED-ACM-MIB {
  namespace "http://tail-f.com/ns/mibs/SNMP-VIEW-BASED-ACM-MIB/200210160000Z";
  prefix SNMP_VIEW_BASED_ACM_MIB;

  import ietf-yang-types {
    prefix yang;
  }
  import tailf-common {
    prefix tailf;
  }
  import SNMPv2-TC {
    prefix SNMPv2_TC;
  }
  import SNMP-FRAMEWORK-MIB {
    prefix SNMP_FRAMEWORK_MIB;
  }

  revision 2002-10-16 {
    description
      "";
  }

  typedef vacmContextNameType {
    type string {
      length "min .. 32";
    }
  }

  typedef vacmSecurityModelType {
    type int32 {
      range "1 .. 2147483647";
    }
  }

  typedef vacmSecurityNameType {
    type string {
      length "1 .. 32";
    }
  }

  typedef vacmGroupNameType {
    type string {
      length "1 .. 32";
    }
  }

  typedef vacmAccessContextPrefixType {
    type string {
      length "min .. 32";
    }
  }

  typedef vacmAccessContextMatchType {
    type enumeration {
      enum "exact" {
        value 1;
      }
      enum "prefix" {
        value 2;
      }
    }
  }

  typedef vacmAccessReadViewNameType {
    type string {
      length "min .. 32";
    }
  }

  typedef vacmAccessWriteViewNameType {
    type string {
      length "min .. 32";
    }
  }

  typedef vacmAccessNotifyViewNameType {
    type string {
      length "min .. 32";
    }
  }

  typedef vacmViewTreeFamilyViewNameType {
    type string {
      length "1 .. 32";
    }
  }

  typedef vacmViewTreeFamilyMaskType {
    type tailf:hex-list {
      pattern "(((([0-9A-Fa-f]{2}):){0,15}([0-9A-Fa-f]{2}))){0,1}";
      tailf:value-length "0 .. 16";
    }
  }

  typedef vacmViewTreeFamilyTypeType {
    type enumeration {
      enum "included" {
        value 1;
      }
      enum "excluded" {
        value 2;
      }
    }
  }
  tailf:id "";
  tailf:snmp-mib-module-name "SNMP-VIEW-BASED-ACM-MIB";

  container SNMP-VIEW-BASED-ACM-MIB {
    container vacmSecurityToGroupTable {
      list vacmSecurityToGroupEntry {
        key "vacmSecurityModel vacmSecurityName";
        tailf:sort-order "snmp";
        tailf:snmp-oid "1.3.6.1.6.3.16.1.2";
        leaf vacmSecurityModel {
          type vacmSecurityModelType;
          tailf:snmp-oid "1.3.6.1.6.3.16.1.2.1.1";
        }
        leaf vacmSecurityName {
          type vacmSecurityNameType;
          tailf:snmp-oid "1.3.6.1.6.3.16.1.2.1.2";
        }
        leaf vacmGroupName {
          type vacmGroupNameType;
          mandatory true;
          tailf:snmp-oid "1.3.6.1.6.3.16.1.2.1.3";
        }
        leaf vacmSecurityToGroupStorageType {
          type SNMPv2_TC:StorageType;
          default "nonVolatile";
          tailf:snmp-oid "1.3.6.1.6.3.16.1.2.1.4";
        }
      }
    }
    container vacmAccessTable {
      list vacmAccessEntry {
        key "vacmGroupName vacmAccessContextPrefix vacmAccessSecurityModel vacmAccessSecurityLevel";
        tailf:sort-order "snmp";
        tailf:snmp-oid "1.3.6.1.6.3.16.1.4";
        leaf vacmGroupName {
          type vacmGroupNameType;
          tailf:snmp-oid "1.3.6.1.6.3.16.1.2.1.3";
        }
        leaf vacmAccessContextPrefix {
          type vacmAccessContextPrefixType;
          tailf:snmp-oid "1.3.6.1.6.3.16.1.4.1.1";
        }
        leaf vacmAccessSecurityModel {
          type SNMP_FRAMEWORK_MIB:SnmpSecurityModel;
          tailf:snmp-oid "1.3.6.1.6.3.16.1.4.1.2";
        }
        leaf vacmAccessSecurityLevel {
          type SNMP_FRAMEWORK_MIB:SnmpSecurityLevel;
          tailf:snmp-oid "1.3.6.1.6.3.16.1.4.1.3";
        }
        leaf vacmAccessContextMatch {
          type vacmAccessContextMatchType;
          default "exact";
          tailf:snmp-oid "1.3.6.1.6.3.16.1.4.1.4";
        }
        leaf vacmAccessReadViewName {
          type vacmAccessReadViewNameType;
          tailf:snmp-oid "1.3.6.1.6.3.16.1.4.1.5";
        }
        leaf vacmAccessWriteViewName {
          type vacmAccessWriteViewNameType;
          tailf:snmp-oid "1.3.6.1.6.3.16.1.4.1.6";
        }
        leaf vacmAccessNotifyViewName {
          type vacmAccessNotifyViewNameType;
          tailf:snmp-oid "1.3.6.1.6.3.16.1.4.1.7";
        }
        leaf vacmAccessStorageType {
          type SNMPv2_TC:StorageType;
          default "nonVolatile";
          tailf:snmp-oid "1.3.6.1.6.3.16.1.4.1.8";
        }
      }
    }
    container vacmViewTreeFamilyTable {
      list vacmViewTreeFamilyEntry {
        key "vacmViewTreeFamilyViewName vacmViewTreeFamilySubtree";
        tailf:sort-order "snmp";
        tailf:snmp-oid "1.3.6.1.6.3.16.1.5.2";
        leaf vacmViewTreeFamilyViewName {
          type vacmViewTreeFamilyViewNameType;
          tailf:snmp-oid "1.3.6.1.6.3.16.1.5.2.1.1";
        }
        leaf vacmViewTreeFamilySubtree {
          type yang:object-identifier;
          tailf:snmp-oid "1.3.6.1.6.3.16.1.5.2.1.2";
        }
        leaf vacmViewTreeFamilyMask {
          type vacmViewTreeFamilyMaskType;
          tailf:snmp-oid "1.3.6.1.6.3.16.1.5.2.1.3";
        }
        leaf vacmViewTreeFamilyType {
          type vacmViewTreeFamilyTypeType;
          default "included";
          tailf:snmp-oid "1.3.6.1.6.3.16.1.5.2.1.4";
        }
        leaf vacmViewTreeFamilyStorageType {
          type SNMPv2_TC:StorageType;
          default "nonVolatile";
          tailf:snmp-oid "1.3.6.1.6.3.16.1.5.2.1.5";
        }
      }
    }
  }
}
