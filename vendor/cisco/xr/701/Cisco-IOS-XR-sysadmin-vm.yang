module Cisco-IOS-XR-sysadmin-vm {
  namespace "http://www.cisco.com/ns/yang/Cisco-IOS-XR-sysadmin-vm";
  prefix vm;

  import tailf-common {
    prefix tailf;
  }
  import cisco-semver {
    prefix semver;
  }

  organization
    "Cisco Systems Inc.";
  contact
    "Cisco Systems, Inc.
     Customer Service
     
     Postal: 170 West Tasman Drive
     San Jose, CA 95134
     
     Tel: +1 800 553-NETS
     
     E-mail: cs-yang@cisco.com";
  description
    "This module contains the YANG definitions
     for the Cisco IOS-XR SysAdmin
     'vm profile|cpu|memory' commands.
     
     Copyright(c) 2018 by Cisco Systems, Inc.
     All rights reserved.
     
     Copyright (c) 2012-2019 by Cisco Systems, Inc.
     All rights reserved.";

  revision 2019-04-15 {
    description
      "Establish semantic version baseline.";
    semver:module-version "1.0.0";
  }
  revision 2018-11-20 {
    description
      "CSCvn05746, force hw-profile to be vrr";
  }
  revision 2018-06-20 {
    description
      "Initial revision";
  }

  typedef cp-dp-cores {
    type string {
      pattern "0(-[0-9]+)?/[0-9]+(-[0-9]+)?";
    }
    description
      "assign cpu cores to control/data plane";
  }

  container vm {
    config true;
    tailf:action "reload" {
      description
        "reload system to use new hareware profile configuration";
      input;
      output {
        leaf response {
          type string;
        }
      }
    }
    tailf:action "console" {
      description
        "switch xr console to vga/serial";
      input {
        leaf vga_serial {
          type enumeration {
            enum "vga";
            enum "serial";
          }
        }
      }
      output {
        leaf response {
          type string;
        }
      }
    }
    container config {
      choice cpu_mem-profile {
        mandatory true;
        case choose-profile {
          container hw-profile {
            leaf profile {
              type enumeration {
                enum "vrr";
              }
              description
                "xrv9k profile vpe|vrr";
            }
          }
        }
        case choose-cpu_mem {
          container memory {
            leaf admin {
              type uint32;
              description
                "admin container memory in GB";
            }
            leaf rp {
              type uint32;
              description
                "rp container memory in GB";
            }
            leaf lc {
              type uint32;
              description
                "lc container memory in GB";
            }
          }
          container cpu {
            leaf assign {
              type cp-dp-cores;
              description
                "assign cpu cores to control/data plane";
            }
          }
        }
      }
    }
  }
}
