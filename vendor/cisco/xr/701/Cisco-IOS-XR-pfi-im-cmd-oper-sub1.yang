submodule Cisco-IOS-XR-pfi-im-cmd-oper-sub1 {
  belongs-to Cisco-IOS-XR-pfi-im-cmd-oper {
    prefix Cisco-IOS-XR-pfi-im-cmd-oper;
  }

  import ietf-inet-types {
    prefix inet;
  }
  import ietf-yang-types {
    prefix yang;
  }
  import Cisco-IOS-XR-types {
    prefix xr;
  }
  import cisco-semver {
    prefix semver;
  }
  include Cisco-IOS-XR-pfi-im-cmd-oper-sub2 {
    revision-date 2019-04-05;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR pfi-im-cmd package operational data.
     
     Copyright (c) 2013-2019 by Cisco Systems, Inc.
     All rights reserved.";

  revision 2019-04-05 {
    description
      "Establish semantic version baseline.";
    semver:module-version "1.0.0";
  }
  revision 2017-06-26 {
    description
      "Change identifiers to be more readable.";
  }
  revision 2017-05-01 {
    description
      "Fixing backward compatibility error in module.";
  }
  revision 2016-12-18 {
    description
      "Description updated.";
  }
  revision 2015-11-09 {
    description
      "IOS XR 6.0 revision.";
  }

  typedef Stats-counter {
    type enumeration {
      enum "stats-counter-rate" {
        value 0;
        description
          "stats counter rate";
      }
      enum "stats-counter-uint32" {
        value 1;
        description
          "stats counter uint32";
      }
      enum "stats-counter-uint64" {
        value 2;
        description
          "stats counter uint64";
      }
      enum "stats-counter-generic" {
        value 3;
        description
          "stats counter generic";
      }
      enum "stats-counter-proto" {
        value 4;
        description
          "stats counter proto";
      }
      enum "stats-counter-srp" {
        value 5;
        description
          "stats counter srp";
      }
      enum "stats-counter-ipv4-prec" {
        value 6;
        description
          "stats counter ipv4 prec";
      }
      enum "stats-counter-ipv4-dscp" {
        value 7;
        description
          "stats counter ipv4 dscp";
      }
      enum "stats-counter-mpls-exp" {
        value 8;
        description
          "stats counter mpls exp";
      }
      enum "stats-counter-ipv4-bgp-pa" {
        value 9;
        description
          "stats counter ipv4 bgp pa";
      }
      enum "stats-counter-src-bgp-pa" {
        value 10;
        description
          "stats counter src bgp pa";
      }
      enum "stats-counter-basic" {
        value 11;
        description
          "stats counter basic";
      }
      enum "stats-counter-comp-generic" {
        value 12;
        description
          "stats counter comp generic";
      }
      enum "stats-counter-comp-proto" {
        value 13;
        description
          "stats counter comp proto";
      }
      enum "stats-counter-comp-basic" {
        value 14;
        description
          "stats counter comp basic";
      }
      enum "stats-counter-accounting" {
        value 15;
        description
          "stats counter accounting";
      }
      enum "stats-counter-comp-accounting" {
        value 16;
        description
          "stats counter comp accounting";
      }
      enum "stats-counter-flow" {
        value 17;
        description
          "stats counter flow";
      }
      enum "stats-counter-comp-flow" {
        value 18;
        description
          "stats counter comp flow";
      }
    }
    description
      "Stats counter";
  }

  typedef Stats-type-contents {
    type enumeration {
      enum "stats-type-single" {
        value 100;
        description
          "stats type single";
      }
      enum "stats-type-variable" {
        value 101;
        description
          "stats type variable";
      }
    }
    description
      "Stats type contents";
  }

  typedef Stats-id {
    type enumeration {
      enum "stats-id-type-unknown" {
        value 0;
        description
          "stats id type unknown";
      }
      enum "stats-id-type-min" {
        value 1;
        description
          "stats id type min";
      }
      enum "stats-id-type-spare" {
        value 2;
        description
          "stats id type spare";
      }
      enum "stats-id-type-node" {
        value 3;
        description
          "stats id type node";
      }
      enum "stats-id-type-other" {
        value 4;
        description
          "stats id type other";
      }
      enum "stats-id-type-feature" {
        value 5;
        description
          "stats id type feature";
      }
      enum "stats-id-type-max" {
        value 6;
        description
          "stats id type max";
      }
    }
    description
      "Stats id";
  }

  typedef Stats-type-val {
    type uint32;
    description
      "Stats type val";
  }

  typedef Im-cmd-stats-enum {
    type enumeration {
      enum "full" {
        value 1;
        description
          "full";
      }
      enum "basic" {
        value 2;
        description
          "basic";
      }
    }
    description
      "List of different interface stats structures";
  }

  typedef Gcc-sec-state {
    type enumeration {
      enum "normal" {
        value 0;
        description
          "Normal";
      }
      enum "maintenance" {
        value 1;
        description
          "Maintenance";
      }
      enum "ais" {
        value 2;
        description
          "Automatic In Service";
      }
    }
    description
      "Gcc sec state";
  }

  typedef Gcc-der-state {
    type enumeration {
      enum "in-service" {
        value 0;
        description
          "In Service";
      }
      enum "out-of-service" {
        value 1;
        description
          "Out Of Service";
      }
      enum "maintenance" {
        value 2;
        description
          "Maintenance";
      }
      enum "ais" {
        value 3;
        description
          "Automatic In Service";
      }
    }
    description
      "Gcc der state";
  }

  typedef Tunnel-key-state {
    type enumeration {
      enum "absent" {
        value 0;
        description
          "Tunnel GRE Key is not present";
      }
      enum "present" {
        value 1;
        description
          "Tunnel GRE Key is present";
      }
    }
    description
      "Tunnel key state";
  }

  typedef Tunnel-ka-df-state {
    type enumeration {
      enum "disable" {
        value 0;
        description
          "Tunnel GRE KA State is Disabled";
      }
      enum "enable" {
        value 1;
        description
          "Tunnel GRE KA State is Enabled";
      }
    }
    description
      "Tunnel ka df state";
  }

  typedef Tunl-ip-mode-dir {
    type enumeration {
      enum "tunl-ip-mode-dir-none" {
        description
          "tunl ip mode dir none";
      }
      enum "tunl-ip-mode-dir-decap" {
        description
          "tunl ip mode dir decap";
      }
      enum "tunl-ip-mode-dir-encap" {
        description
          "tunl ip mode dir encap";
      }
      enum "tunl-ip-mode-dir-max" {
        description
          "tunl ip mode dir max";
      }
    }
    description
      "Tunl ip mode dir";
  }

  typedef Tunnel-gre-mode {
    type enumeration {
      enum "unknown" {
        value 0;
        description
          "Tunnel GRE mode is Unknown";
      }
      enum "gr-eo-ipv4" {
        value 1;
        description
          "Tunnel GRE Mode is IPv4";
      }
      enum "gr-eo-ipv6" {
        value 2;
        description
          "Tunnel GRE Mode is IPv6";
      }
      enum "mgr-eo-ipv4" {
        value 3;
        description
          "Tunnel MGRE Mode is IPv4";
      }
      enum "mgr-eo-ipv6" {
        value 4;
        description
          "Tunnel MGRE Mode is IPv6";
      }
      enum "ipv4" {
        value 5;
        description
          "Tunnel Mode is IPv4";
      }
      enum "ipv6" {
        value 6;
        description
          "Tunnel Mode is IPv6";
      }
    }
    description
      "Tunnel gre mode";
  }

  typedef Tunl-pfi-in6-addr {
    type inet:ipv6-address;
    description
      "Tunl pfi in6 addr";
  }

  typedef Tunl-pfi-in-addr {
    type inet:ipv4-address;
    description
      "Tunl pfi in addr";
  }

  typedef Tunl-pfi-af-id {
    type enumeration {
      enum "tunl-pfi-af-id-none" {
        value 0;
        description
          "Unspecified AFI";
      }
      enum "tunl-pfi-af-id-ipv4" {
        value 2;
        description
          "IPv4 AFI";
      }
      enum "tunl-pfi-af-id-ipv6" {
        value 10;
        description
          "IPv6 AFI";
      }
    }
    description
      "Tunl pfi af id";
  }

  typedef Sonet-aps-et {
    type enumeration {
      enum "not-configured" {
        value 0;
        description
          "APS not configured on port";
      }
      enum "working-active" {
        value 1;
        description
          "Working port is up ";
      }
      enum "protect-active" {
        value 2;
        description
          "Protect port is up  ";
      }
      enum "working-inactive" {
        value 3;
        description
          "Working port is down ";
      }
      enum "protect-inactive" {
        value 4;
        description
          "Protect port is down  ";
      }
    }
    description
      "APS states";
  }

  typedef Bmd-member-type-enum {
    type enumeration {
      enum "bmd-mbr-local" {
        value 0;
        description
          "Member has been configured on the local device";
      }
      enum "bmd-mbr-foreign" {
        value 1;
        description
          "Member has been configured on an mLACP peer
           device";
      }
      enum "bmd-mbr-unknown" {
        value 2;
        description
          "Member's type is unknown";
      }
    }
    description
      "Bmd member type enum";
  }

  typedef Bm-muxreason {
    type enumeration {
      enum "bm-mux-reason-no-reason" {
        value 0;
        description
          "Selection logic has not yet been run for the
           bundle this link is a member of";
      }
      enum "bm-mux-reason-link-down" {
        value 1;
        description
          "Link is down";
      }
      enum "bm-mux-reason-link-deleted" {
        value 2;
        description
          "Link is being removed from the bundle";
      }
      enum "bm-mux-reason-duplex" {
        value 3;
        description
          "Link has wrong duplexity";
      }
      enum "bm-mux-reason-bandwidth" {
        value 4;
        description
          "Link has wrong bandwidth";
      }
      enum "bm-mux-reason-loop-back" {
        value 5;
        description
          "Link is a loopback interface";
      }
      enum "bm-mux-reason-activity-type" {
        value 6;
        description
          "Link has wrong activity type";
      }
      enum "bm-mux-reason-link-limit" {
        value 7;
        description
          "Link's bundle already has maximum number of
           members allowed";
      }
      enum "bm-mux-reason-shared" {
        value 8;
        description
          "Link is attached to a shared medium";
      }
      enum "bm-mux-reason-lagid" {
        value 9;
        description
          "Link has wrong LAG ID";
      }
      enum "bm-mux-reason-no-bundle" {
        value 10;
        description
          "Link's bundle does not exist";
      }
      enum "bm-mux-reason-no-primary" {
        value 11;
        description
          "Link's bundle has no primary link";
      }
      enum "bm-mux-reason-bundle-down" {
        value 12;
        description
          "Link's bundle is shut down";
      }
      enum "bm-mux-reason-individual" {
        value 13;
        description
          "Link is marked individual by partner";
      }
      enum "bm-mux-reason-defaulted" {
        value 14;
        description
          "Link is Defaulted, suggesting it is not
           receiving LACPDUs from the peer";
      }
      enum "bm-mux-reason-in-sync" {
        value 15;
        description
          "Link is in InSync state";
      }
      enum "bm-mux-reason-collecting" {
        value 16;
        description
          "Link is in Collecting state";
      }
      enum "bm-mux-reason-active-link-limit" {
        value 17;
        description
          "Link exceeds maximum active limit";
      }
      enum "bm-mux-reason-distributing" {
        value 18;
        description
          "Link is in Distributing state";
      }
      enum "bm-mux-reason-count" {
        value 19;
        description
          "Enumeration maximum value";
      }
    }
    description
      "Bm muxreason";
  }

  typedef Bmd-member-state {
    type enumeration {
      enum "bmd-mbr-state-configured" {
        value 1;
        description
          "Member is configured";
      }
      enum "bmd-mbr-state-standby" {
        value 2;
        description
          "Member is standby";
      }
      enum "bmd-mbr-state-hot-standby" {
        value 3;
        description
          "Member is hot standby";
      }
      enum "bmd-mbr-state-negotiating" {
        value 4;
        description
          "Member is negotiating";
      }
      enum "bmd-mbr-state-bfd-running" {
        value 5;
        description
          "Member has a BFD session running";
      }
      enum "bmd-mbr-state-active" {
        value 6;
        description
          "Member is active";
      }
    }
    description
      "Bmd member state";
  }

  typedef Bm-severity {
    type enumeration {
      enum "ok" {
        value 0;
        description
          "OK";
      }
      enum "information" {
        value 1;
        description
          "Information";
      }
      enum "misconfiguration" {
        value 2;
        description
          "Misconfiguration";
      }
      enum "warning" {
        value 3;
        description
          "Warning";
      }
      enum "error" {
        value 5;
        description
          "Error";
      }
    }
    description
      "Severity of the member state reason";
  }

  typedef Bm-state-reason-target {
    type enumeration {
      enum "member-reason" {
        description
          "Member applicable reason";
      }
      enum "bundle-reason" {
        description
          "Bundle applicable reason";
      }
    }
    description
      "Scope of the state reason";
  }

  typedef Bm-mbr-state-reason {
    type enumeration {
      enum "bm-mbr-state-reason-unknown" {
        value 0;
        description
          "Reason unavailable (diagnostics error)";
      }
      enum "bm-mbr-state-reason-unselectable-unknown" {
        value 1;
        description
          "Link cannot be used (unknown reason)";
      }
      enum "bm-mbr-state-reason-link-down" {
        value 2;
        description
          "Link is down";
      }
      enum "bm-mbr-state-reason-link-deleting" {
        value 3;
        description
          "Link is being removed from the bundle";
      }
      enum "bm-mbr-state-reason-creating" {
        value 4;
        description
          "Link is in the process of being created";
      }
      enum "bm-mbr-state-reason-bundle-creating" {
        value 5;
        description
          "Bundle is in the process of being created";
      }
      enum "bm-mbr-state-reason-bundle-deleting" {
        value 6;
        description
          "Bundle is in the process of being deleted";
      }
      enum "bm-mbr-state-reason-bundle-admin-down" {
        value 7;
        description
          "Bundle has been shut down";
      }
      enum "bm-mbr-state-reason-replicating" {
        value 8;
        description
          "Bundle is in the process of being replicated to
           this location";
      }
      enum "bm-mbr-state-reason-bandwidth" {
        value 9;
        description
          "Incompatible with other links in the bundle
           (bandwidth out of range)";
      }
      enum "bm-mbr-state-reason-loop-back" {
        value 10;
        description
          "Loopback: Actor and Partner have the same
           System ID and Key";
      }
      enum "bm-mbr-state-reason-activity-type" {
        value 11;
        description
          "Incompatible with other links in the bundle
           (LACP vs non-LACP)";
      }
      enum "bm-mbr-state-reason-bundle-shutdown" {
        value 12;
        description
          "Bundle shutdown is configured for the bundle";
      }
      enum "bm-mbr-state-reason-min-selected" {
        value 13;
        description
          "Not enough links available to meet
           minimum-active threshold";
      }
      enum "bm-mbr-state-reason-max-selected" {
        value 14;
        description
          "Link is Standby due to maximum-active links
           configuration";
      }
      enum "bm-mbr-state-reason-link-limit" {
        value 15;
        description
          "Bundle has too many member links configured";
      }
      enum "bm-mbr-state-reason-active-limit" {
        value 16;
        description
          "Bundle has reached maximum supported number of
           active links";
      }
      enum "bm-mbr-state-reason-standby-unknown" {
        value 17;
        description
          "Link is Standby (unknown reason)";
      }
      enum "bm-mbr-state-reason-expired" {
        value 18;
        description
          "Link is Expired; LACPDUs are not being received
           from the partner";
      }
      enum "bm-mbr-state-reason-defaulted" {
        value 19;
        description
          "Link is Defaulted; LACPDUs are not being
           received from the partner";
      }
      enum "bm-mbr-state-reason-act-or-not-agg" {
        value 20;
        description
          "Link is Not Aggregatable (unknown reason)";
      }
      enum "bm-mbr-state-reason-partner-not-agg" {
        value 21;
        description
          "Partner has marked the link as Not Aggregatable";
      }
      enum "bm-mbr-state-reason-lagid" {
        value 22;
        description
          "Partner System ID/Key do not match that of the
           Selected links";
      }
      enum "bm-mbr-state-reason-bundle-not-cfgd" {
        value 23;
        description
          "Bundle interface is not present in
           configuration";
      }
      enum "bm-mbr-state-reason-bundle-not-ready" {
        value 24;
        description
          "Wait-while timer is running";
      }
      enum "bm-mbr-state-reason-partner-ood" {
        value 25;
        description
          "Partner has not echoed the correct parameters
           for this link";
      }
      enum "bm-mbr-state-reason-partner-not-in-sync" {
        value 26;
        description
          "Partner is not Synchronized (Waiting, Standby,
           or LAG ID mismatch)";
      }
      enum "bm-mbr-state-reason-foreign-partner-oos" {
        value 27;
        description
          "Partner is not Synchronized (Waiting, not
           Selected, or out-of-date)";
      }
      enum "bm-mbr-state-reason-attach-unknown" {
        value 28;
        description
          "Link is Attached and has not gone Collecting
           (unknown reason)";
      }
      enum "bm-mbr-state-reason-partner-not-collecting" {
        value 29;
        description
          "Partner has not advertized that it is
           Collecting";
      }
      enum "bm-mbr-state-reason-collect-unknown" {
        value 30;
        description
          "Link is Collecting and has not gone
           Distributing (unknown reason)";
      }
      enum "bm-mbr-state-reason-standby-foreign" {
        value 31;
        description
          "Link is marked as Standby by mLACP peer";
      }
      enum "bm-mbr-state-reason-bfd-starting" {
        value 32;
        description
          "Link is waiting for BFD session to start";
      }
      enum "bm-mbr-state-reason-bfd-down" {
        value 33;
        description
          "BFD state of this link is Down";
      }
      enum "bm-mbr-state-reason-bfd-nbr-unconfig" {
        value 34;
        description
          "BFD session is unconfigured on the remote end";
      }
      enum "bm-mbr-state-reason-mlacp" {
        value 35;
        description
          "Link is not operational as a result of mLACP
           negotiations";
      }
      enum "bm-mbr-state-reason-pe-isolated" {
        value 36;
        description
          "ICCP group is isolated from the core network";
      }
      enum "bm-mbr-state-reason-forced-switchover" {
        value 37;
        description
          "Forced switchover to the mLACP peer";
      }
      enum "bm-mbr-state-reason-errdis-unknown" {
        value 38;
        description
          "Link is error disabled (unknown reason)";
      }
      enum "bm-mbr-state-reason-mlacp-no-mbr-state-info" {
        value 39;
        description
          "Waiting for member state information from mLACP
           peer";
      }
      enum "bm-mbr-state-reason-active" {
        value 40;
        description
          "Link is Active";
      }
      enum "bm-mbr-state-reason-mlacp-no-bdl-state-info" {
        value 41;
        description
          "Waiting for bundle state information from mLACP
           peer";
      }
      enum "bm-mbr-state-reason-mlacp-no-bdl-config-info" {
        value 42;
        description
          "Waiting for bundle configuration information
           from mLACP peer";
      }
      enum "bm-mbr-state-reason-mlacp-no-bdl-sync" {
        value 43;
        description
          "Waiting for bundle to complete initial
           synchronization with mLACP peer";
      }
      enum "bm-mbr-state-reason-mlacp-bdl-has-no-peer" {
        value 44;
        description
          "mLACP bundle does not have a peer device";
      }
      enum "bm-mbr-state-reason-mlacp-nak" {
        value 45;
        description
          "Link is being ignored due to an inconsistency
           with mLACP peer";
      }
      enum "bm-mbr-state-reason-mlacp-transport-unavailable" {
        value 46;
        description
          "ICCP transport is unavailable";
      }
      enum "bm-mbr-state-reason-mlacp-not-configured" {
        value 47;
        description
          "ICCP Group is not fully configured";
      }
      enum "bm-mbr-state-reason-recovery-timer" {
        value 48;
        description
          "mLACP recovery delay timer is running";
      }
      enum "bm-mbr-state-reason-mlacp-standby" {
        value 49;
        description
          "mLACP peer is active";
      }
      enum "bm-mbr-state-reason-maximized-out" {
        value 50;
        description
          "mLACP peer has more links/bandwidth available";
      }
      enum "bm-mbr-state-reason-mlacp-peer-selected" {
        value 51;
        description
          "mLACP peer has one or more links Selected";
      }
      enum "bm-mbr-state-reason-mlacp-connect-timer-running" {
        value 52;
        description
          "mLACP bundle does not have a peer device
           (connect timer running)";
      }
      enum "bm-mbr-state-reason-bundle-not-mlacp" {
        value 53;
        description
          "Bundle is not configured to run mLACP";
      }
      enum "bm-mbr-state-reason-no-lon" {
        value 54;
        description
          "Bundle has too many working links configured
           (more than the maximum-active limit)";
      }
      enum "bm-mbr-state-reason-cumul-rel-bw-limit" {
        value 55;
        description
          "Additional bandwidth from link would exceed
           load balancing capabilities";
      }
      enum "bm-mbr-state-reason-no-mac" {
        value 56;
        description
          "No MAC address available for the bundle";
      }
      enum "bm-mbr-state-reason-no-system-id" {
        value 57;
        description
          "No system ID available for use by this bundle";
      }
      enum "bm-mbr-state-reason-link-shutdown" {
        value 58;
        description
          "Link is shutdown";
      }
      enum "bm-mbr-state-reason-activity-mlacp" {
        value 59;
        description
          "Non-LACP link in mLACP bundle";
      }
      enum "bm-mbr-state-reason-activity-iccp" {
        value 60;
        description
          "LACP link in inter-chassis bundle";
      }
      enum "bm-mbr-state-reason-bundle-icpe-mlacp" {
        value 61;
        description
          "Parent bundle is both inter-chassis and
           configured for mLACP";
      }
      enum "bm-mbr-state-reason-no-link-num" {
        value 62;
        description
          "Too many bundle members in system; no link
           number available";
      }
      enum "bm-mbr-state-reason-standby-peer-higher-prio" {
        value 63;
        description
          "mLACP peer has a higher priority link";
      }
      enum "bm-mbr-state-reason-red-state-standby" {
        value 64;
        description
          "Link is in standby redundancy state";
      }
      enum "bm-mbr-state-reason-other-red-state-standby" {
        value 65;
        description
          "One or more links in the bundle are in standby
           redundancy state";
      }
      enum "bm-mbr-state-reason-hold-ing" {
        value 66;
        description
          "Holding down temporary to avoid churn after
           restart";
      }
      enum "bm-mbr-state-reason-bundle-error-disabled" {
        value 67;
        description
          "Bundle has been error-disabled";
      }
      enum "bm-mbr-state-reason-bundle-efd-disabled" {
        value 68;
        description
          "Bundle has been disabled by EFD";
      }
      enum "bm-mbr-state-reason-singleton-pe-isolated" {
        value 69;
        description
          "Singleton ICCP group is isolated from the core
           network";
      }
      enum "bm-mbr-state-reason-bfd-ipv6-starting" {
        value 70;
        description
          "Link is waiting for BFDv6 session to start";
      }
      enum "bm-mbr-state-reason-bfd-ipv6-down" {
        value 71;
        description
          "BFDv6 state of this link is Down";
      }
      enum "bm-mbr-state-reason-bfd-ipv6-nbr-unconfig" {
        value 72;
        description
          "BFDv6 session is unconfigured on the remote end";
      }
      enum "bm-mbr-state-reason-timer-running" {
        value 73;
        description
          "LACP delay timer is running";
      }
      enum "bm-mbr-state-reason-client-bundle-ctrl" {
        value 74;
        description
          "Client has configured the bundle state Down";
      }
      enum "bm-mbr-state-reason-lacp-oos" {
        value 75;
        description
          "Link is in standby due to bundle out of service
           state";
      }
      enum "bm-mbr-state-reason-errdis-bundle-oos" {
        value 76;
        description
          "Link is error-disabled due to bundle out of
           service state";
      }
      enum "bm-mbr-state-reason-count" {
        value 77;
        description
          "Enumeration maximum value";
      }
    }
    description
      "Bm mbr state reason";
  }

  typedef Bm-muxstate {
    type enumeration {
      enum "detached" {
        value 1;
        description
          "Port is not attached to a bundle";
      }
      enum "waiting" {
        value 2;
        description
          "Port has chosen bundle and is waiting to join";
      }
      enum "attached" {
        value 3;
        description
          "Port is attached to the bundle but not active";
      }
      enum "collecting" {
        value 4;
        description
          "Port is ready to receive data";
      }
      enum "distributing" {
        value 5;
        description
          "Port is distributing data";
      }
      enum "collecting-distributing" {
        value 6;
        description
          "Port is active and can send and receive data";
      }
    }
    description
      "Bm muxstate";
  }

  typedef Srp-mgmt-srr-failure {
    type enumeration {
      enum "idle-srr-failure" {
        description
          "Idle";
      }
      enum "wait-to-restore-srr-failure" {
        description
          "Wait To Restore";
      }
      enum "signal-fail-srr-failure" {
        description
          "Signal Fail";
      }
      enum "forced-switch-srr-failure" {
        description
          "Forced Switch";
      }
      enum "unknown-srr-failure" {
        description
          "UNKNOWN";
      }
    }
    description
      "SRP SRR failure type";
  }

  typedef Srp-mgmt-srr-node-state {
    type enumeration {
      enum "idle-srr-state" {
        description
          "Idle";
      }
      enum "discovery-srr-state" {
        description
          "Discovery";
      }
      enum "unknown-srr-state" {
        description
          "UNKNOWN";
      }
    }
    description
      "SRP SRR node state";
  }

  typedef Srp-mgmt-ips-path-ind {
    type enumeration {
      enum "short-path" {
        description
          "SHORT";
      }
      enum "long-path" {
        description
          "LONG";
      }
      enum "unknown-path" {
        description
          "UNKNOWN";
      }
    }
    description
      "SRP IPS path indication";
  }

  typedef Srp-mgmt-failure-state-et {
    type enumeration {
      enum "idle-failure-state" {
        description
          "Idle";
      }
      enum "wait-to-restore-failure-state" {
        description
          "Wait To Restore";
      }
      enum "manual-switch-failure-state" {
        description
          "Manual Switch";
      }
      enum "signal-degrade-failure-state" {
        description
          "Signal Degrade";
      }
      enum "signal-fail-failure-state" {
        description
          "Signal Fail";
      }
      enum "forced-switch-failure-state" {
        description
          "Forced Switch";
      }
      enum "shutdown-failure-state" {
        description
          "Shutdown";
      }
      enum "invalid-failure-state" {
        description
          "Invalid";
      }
      enum "unknown-failure-state" {
        description
          "Unknown";
      }
    }
    description
      "SRP failure state type";
  }

  typedef Srp-mgmt-failure-et {
    type enumeration {
      enum "hardware-missing-failure" {
        description
          "Hardware missing";
      }
      enum "layer1-admin-state-failure" {
        description
          "L1 admin state";
      }
      enum "layer1-error-failure" {
        description
          "Layer 1 error";
      }
      enum "keepalive-missed-failure" {
        description
          "Keepalive missed";
      }
      enum "link-quality-degraded-failure" {
        description
          "Link quality degraded";
      }
      enum "mate-problem-failure" {
        description
          "Mate problem";
      }
      enum "side-mismatch-failure" {
        description
          "Side mismatch";
      }
      enum "unknown-failure" {
        description
          "Unknown";
      }
    }
    description
      "SRP failure type";
  }

  typedef Srp-mgmt-ips-req {
    type enumeration {
      enum "idle-ips-request" {
        description
          "Idle";
      }
      enum "wait-to-restore-ips-request" {
        description
          "Wait To Restore";
      }
      enum "manual-switch-ips-request" {
        description
          "Manual Switch";
      }
      enum "signal-degrade-ips-request" {
        description
          "Signal Degrade";
      }
      enum "signal-fail-ips-request" {
        description
          "Signal Fail";
      }
      enum "forced-switch-ips-request" {
        description
          "Forced Switch";
      }
      enum "unknown-ips-request" {
        description
          "UNKNOWN";
      }
    }
    description
      "SRP IPS request type";
  }

  typedef Srp-mgmt-ips-wrap-state {
    type enumeration {
      enum "idle-wrap-state" {
        description
          "Idle";
      }
      enum "wrapped-state" {
        description
          "Wrapped";
      }
      enum "locked-out-wrap-state" {
        description
          "Locked out";
      }
      enum "unknown-wrap-state" {
        description
          "UNKNOWN";
      }
    }
    description
      "SRP IPS side wrap state";
  }

  typedef Im-cmd-intf-type-enum {
    type enumeration {
      enum "srp" {
        description
          "srp";
      }
      enum "tunnel" {
        description
          "tunnel";
      }
      enum "bundle" {
        description
          "bundle";
      }
      enum "serial" {
        description
          "serial";
      }
      enum "sonet-pos" {
        description
          "sonet pos";
      }
      enum "tunnel-gre" {
        description
          "tunnel gre";
      }
      enum "pseudowire-head-end" {
        description
          "pseudowire head end";
      }
      enum "cem" {
        description
          "cem";
      }
      enum "gcc" {
        description
          "gcc";
      }
    }
    description
      "Im cmd intf type enum";
  }

  typedef Ncp-ident {
    type enumeration {
      enum "cdpcp" {
        value 1;
        description
          "CDP control protocol";
      }
      enum "ipcp" {
        value 2;
        description
          "IPv4 control protocol";
      }
      enum "ipcpiw" {
        value 3;
        description
          "IPv4 Interworking control protocol";
      }
      enum "ipv6cp" {
        value 4;
        description
          "IPv6 control protocol";
      }
      enum "mplscp" {
        value 5;
        description
          "MPLS control protocol";
      }
      enum "osicp" {
        value 6;
        description
          "OSI (CLNS) control protocol";
      }
    }
    description
      "Ncp ident";
  }

  typedef Ppp-fsm-state {
    type enumeration {
      enum "ppp-fsm-state-initial-0" {
        value 0;
        description
          "Connection Idle";
      }
      enum "ppp-fsm-state-starting-1" {
        value 1;
        description
          "This layer required, but lower layer down";
      }
      enum "ppp-fsm-state-closed-2" {
        value 2;
        description
          "Lower layer up, but this layer not required";
      }
      enum "ppp-fsm-state-stopped-3" {
        value 3;
        description
          "Listening for a Config Request";
      }
      enum "ppp-fsm-state-closing-4" {
        value 4;
        description
          "Shutting down due to local change";
      }
      enum "ppp-fsm-state-stopping-5" {
        value 5;
        description
          "Shutting down due to peer's actions";
      }
      enum "ppp-fsm-state-req-sent-6" {
        value 6;
        description
          "Config Request Sent";
      }
      enum "ppp-fsm-state-ack-rcvd-7" {
        value 7;
        description
          "Config Ack Received";
      }
      enum "ppp-fsm-state-ack-sent-8" {
        value 8;
        description
          "Config Ack Sent";
      }
      enum "ppp-fsm-state-opened-9" {
        value 9;
        description
          "Connection Open";
      }
    }
    description
      "Ppp fsm state";
  }

  typedef Vlan-switched-mode {
    type enumeration {
      enum "none" {
        value 0;
        description
          "Disabled";
      }
      enum "trunk-port" {
        value 1;
        description
          "Trunk port";
      }
      enum "access-port" {
        value 2;
        description
          "Access port";
      }
    }
    description
      "VLAN-Switched mode";
  }

  typedef Mac-address {
    type yang:mac-address;
    description
      "MAC address type";
  }

  typedef Efp-payload-etype {
    type enumeration {
      enum "payload-ethertype-any" {
        value 0;
        description
          "Any";
      }
      enum "payload-ethertype-ip" {
        value 1;
        description
          "IP";
      }
      enum "payload-ethertype-pppoe" {
        value 2;
        description
          "PPPoE";
      }
    }
    description
      "Payload ethertype match";
  }

  typedef Efp-tag-priority {
    type enumeration {
      enum "priority0" {
        value 0;
        description
          "Priority 0";
      }
      enum "priority1" {
        value 1;
        description
          "Priority 1";
      }
      enum "priority2" {
        value 2;
        description
          "Priority 2";
      }
      enum "priority3" {
        value 3;
        description
          "Priority 3";
      }
      enum "priority4" {
        value 4;
        description
          "Priority 4";
      }
      enum "priority5" {
        value 5;
        description
          "Priority 5";
      }
      enum "priority6" {
        value 6;
        description
          "Priority 6";
      }
      enum "priority7" {
        value 7;
        description
          "Priority 7";
      }
      enum "priority-any" {
        value 8;
        description
          "Any priority";
      }
    }
    description
      "Priority";
  }

  typedef Efp-tag-etype {
    type enumeration {
      enum "untagged" {
        value 0;
        description
          "Untagged";
      }
      enum "dot1q" {
        value 33024;
        description
          "Dot1Q";
      }
      enum "dot1ad" {
        value 34984;
        description
          "Dot1ad";
      }
    }
    description
      "Tag ethertype";
  }

  typedef Vlan-tag-value {
    type uint16;
    description
      "VLAN Tag Value (1 - 4094)";
  }

  typedef Vlan-encaps {
    type enumeration {
      enum "no-encapsulation" {
        value 0;
        description
          "No encapsulation";
      }
      enum "dot1q" {
        value 1;
        description
          "IEEE 802.1Q encapsulation";
      }
      enum "qinq" {
        value 2;
        description
          "Double 802.1Q encapsulation";
      }
      enum "qin-any" {
        value 3;
        description
          "Double 802.1Q wildcarded encapsulation";
      }
      enum "dot1q-native" {
        value 4;
        description
          "IEEE 802.1Q native VLAN encapsulation";
      }
      enum "dot1ad" {
        value 5;
        description
          "IEEE 802.1ad encapsulation";
      }
      enum "dot1ad-native" {
        value 6;
        description
          "IEEE 802.1ad native VLAN encapsulation";
      }
      enum "service-instance" {
        value 7;
        description
          "Ethernet Service Instance";
      }
      enum "dot1ad-dot1q" {
        value 8;
        description
          "IEEE 802.1ad 802.1Q encapsulation";
      }
      enum "dot1ad-any" {
        value 9;
        description
          "IEEE 802.1ad wildcard 802.1Q encapsulation";
      }
    }
    description
      "VLAN encapsulation";
  }

  typedef Im-cmd-lmi-type-enum {
    type enumeration {
      enum "lmi-type-auto" {
        description
          "lmi type auto";
      }
      enum "lmi-type-ansi" {
        description
          "lmi type ansi";
      }
      enum "lmi-type-ccitt" {
        description
          "lmi type ccitt";
      }
      enum "lmi-type-cisco" {
        description
          "lmi type cisco";
      }
    }
    description
      "Im cmd lmi type enum";
  }

  typedef Im-cmd-fr-type-enum {
    type enumeration {
      enum "frame-relay-cisco" {
        description
          "frame relay cisco";
      }
      enum "frame-relay-ietf" {
        description
          "frame relay ietf";
      }
    }
    description
      "Im cmd fr type enum";
  }

  typedef Im-cmd-encaps-enum {
    type enumeration {
      enum "frame-relay" {
        description
          "frame relay";
      }
      enum "vlan" {
        description
          "vlan";
      }
      enum "ppp" {
        description
          "ppp";
      }
    }
    description
      "Im cmd encaps enum";
  }

  typedef Im-attr-transport-mode {
    type enumeration {
      enum "im-attr-transport-mode-unknown" {
        value 0;
        description
          "im attr transport mode unknown";
      }
      enum "im-attr-transport-mode-lan" {
        value 1;
        description
          "im attr transport mode lan";
      }
      enum "im-attr-transport-mode-wan" {
        value 2;
        description
          "im attr transport mode wan";
      }
      enum "im-attr-transport-mode-otn-bt-opu1e" {
        value 3;
        description
          "im attr transport mode otn bt opu1e";
      }
      enum "im-attr-transport-mode-otn-bt-opu2e" {
        value 4;
        description
          "im attr transport mode otn bt opu2e";
      }
      enum "im-attr-transport-mode-otn-opu3" {
        value 5;
        description
          "im attr transport mode otn opu3";
      }
      enum "im-attr-transport-mode-otn-opu4" {
        value 6;
        description
          "im attr transport mode otn opu4";
      }
    }
    description
      "Im attr transport mode";
  }

  typedef Im-cmd-loopback-enum {
    type enumeration {
      enum "no-loopback" {
        description
          "no loopback";
      }
      enum "internal-loopback" {
        description
          "internal loopback";
      }
      enum "external-loopback" {
        description
          "external loopback";
      }
      enum "line-loopback" {
        description
          "line loopback";
      }
    }
    description
      "Im cmd loopback enum";
  }

  typedef Im-attr-flow-control {
    type enumeration {
      enum "im-attr-flow-control-off" {
        value 0;
        description
          "im attr flow control off";
      }
      enum "im-attr-flow-control-on" {
        value 1;
        description
          "im attr flow control on";
      }
      enum "im-attr-flow-control-not-sup" {
        value 2;
        description
          "im attr flow control not sup";
      }
      enum "im-attr-flow-control-priority" {
        value 3;
        description
          "im attr flow control priority";
      }
    }
    description
      "Im attr flow control";
  }

  typedef Im-attr-link {
    type enumeration {
      enum "im-attr-link-type-auto" {
        value 0;
        description
          "im attr link type auto";
      }
      enum "im-attr-link-type-force" {
        value 1;
        description
          "im attr link type force";
      }
    }
    description
      "Im attr link";
  }

  typedef Im-attr-media {
    type enumeration {
      enum "im-attr-media-other" {
        value 0;
        description
          "im attr media other";
      }
      enum "im-attr-media-unknown" {
        value 1;
        description
          "im attr media unknown";
      }
      enum "im-attr-media-aui" {
        value 2;
        description
          "im attr media aui";
      }
      enum "im-attr-media-10base5" {
        value 3;
        description
          "im attr media 10base5";
      }
      enum "im-attr-media-foirl" {
        value 4;
        description
          "im attr media foirl";
      }
      enum "im-attr-media-10base2" {
        value 5;
        description
          "im attr media 10base2";
      }
      enum "im-attr-media-10broad36" {
        value 6;
        description
          "im attr media 10broad36";
      }
      enum "im-attr-media-10base" {
        value 7;
        description
          "im attr media 10base";
      }
      enum "im-attr-media-10base-thd" {
        value 8;
        description
          "im attr media 10base thd";
      }
      enum "im-attr-media-10base-tfd" {
        value 9;
        description
          "im attr media 10base tfd";
      }
      enum "im-attr-media-10base-fp" {
        value 10;
        description
          "im attr media 10base fp";
      }
      enum "im-attr-media-10base-fb" {
        value 11;
        description
          "im attr media 10base fb";
      }
      enum "im-attr-media-10base-fl" {
        value 12;
        description
          "im attr media 10base fl";
      }
      enum "im-attr-media-10base-flhd" {
        value 13;
        description
          "im attr media 10base flhd";
      }
      enum "im-attr-media-10base-flfd" {
        value 14;
        description
          "im attr media 10base flfd";
      }
      enum "im-attr-media-100base-t4" {
        value 15;
        description
          "im attr media 100base t4";
      }
      enum "im-attr-media-100base-tx" {
        value 16;
        description
          "im attr media 100base tx";
      }
      enum "im-attr-media-100base-txhd" {
        value 17;
        description
          "im attr media 100base txhd";
      }
      enum "im-attr-media-100base-txfd" {
        value 18;
        description
          "im attr media 100base txfd";
      }
      enum "im-attr-media-100base-fx" {
        value 19;
        description
          "im attr media 100base fx";
      }
      enum "im-attr-media-100base-fxhd" {
        value 20;
        description
          "im attr media 100base fxhd";
      }
      enum "im-attr-media-100base-fxfd" {
        value 21;
        description
          "im attr media 100base fxfd";
      }
      enum "im-attr-media-100base-ex" {
        value 22;
        description
          "im attr media 100base ex";
      }
      enum "im-attr-media-100base-exhd" {
        value 23;
        description
          "im attr media 100base exhd";
      }
      enum "im-attr-media-100base-exfd" {
        value 24;
        description
          "im attr media 100base exfd";
      }
      enum "im-attr-media-100base-t2" {
        value 25;
        description
          "im attr media 100base t2";
      }
      enum "im-attr-media-100base-t2hd" {
        value 26;
        description
          "im attr media 100base t2hd";
      }
      enum "im-attr-media-100base-t2fd" {
        value 27;
        description
          "im attr media 100base t2fd";
      }
      enum "im-attr-media-1000base-x" {
        value 28;
        description
          "im attr media 1000base x";
      }
      enum "im-attr-media-1000base-xhdx" {
        value 29;
        description
          "im attr media 1000base xhdx";
      }
      enum "im-attr-media-1000base-xfd" {
        value 30;
        description
          "im attr media 1000base xfd";
      }
      enum "im-attr-media-1000base-lx" {
        value 31;
        description
          "im attr media 1000base lx";
      }
      enum "im-attr-media-1000base-lxhd" {
        value 32;
        description
          "im attr media 1000base lxhd";
      }
      enum "im-attr-media-1000base-lxfdx" {
        value 33;
        description
          "im attr media 1000base lxfdx";
      }
      enum "im-attr-media-1000base-sx" {
        value 34;
        description
          "im attr media 1000base sx";
      }
      enum "im-attr-media-1000base-sxhd" {
        value 35;
        description
          "im attr media 1000base sxhd";
      }
      enum "im-attr-media-1000base-sxfd" {
        value 36;
        description
          "im attr media 1000base sxfd";
      }
      enum "im-attr-media-1000base-cx" {
        value 37;
        description
          "im attr media 1000base cx";
      }
      enum "im-attr-media-1000base-cxhdx" {
        value 38;
        description
          "im attr media 1000base cxhdx";
      }
      enum "im-attr-media-1000base-cxfd" {
        value 39;
        description
          "im attr media 1000base cxfd";
      }
      enum "im-attr-media-1000base" {
        value 40;
        description
          "im attr media 1000base";
      }
      enum "im-attr-media-1000base-thd" {
        value 41;
        description
          "im attr media 1000base thd";
      }
      enum "im-attr-media-1000base-tfd" {
        value 42;
        description
          "im attr media 1000base tfd";
      }
      enum "im-attr-media-10gbase-x" {
        value 43;
        description
          "im attr media 10gbase x";
      }
      enum "im-attr-media-10gbase-lx4" {
        value 44;
        description
          "im attr media 10gbase lx4";
      }
      enum "im-attr-media-10gbase-r" {
        value 45;
        description
          "im attr media 10gbase r";
      }
      enum "im-attr-media-10gbase-er" {
        value 46;
        description
          "im attr media 10gbase er";
      }
      enum "im-attr-media-10gbase-lr" {
        value 47;
        description
          "im attr media 10gbase lr";
      }
      enum "im-attr-media-10gbase-sr" {
        value 48;
        description
          "im attr media 10gbase sr";
      }
      enum "im-attr-media-10gbase-w" {
        value 49;
        description
          "im attr media 10gbase w";
      }
      enum "im-attr-media-10gbase-ew" {
        value 50;
        description
          "im attr media 10gbase ew";
      }
      enum "im-attr-media-10gbase-lw" {
        value 51;
        description
          "im attr media 10gbase lw";
      }
      enum "im-attr-media-10gbase-sw" {
        value 52;
        description
          "im attr media 10gbase sw";
      }
      enum "im-attr-media-10gbase-zr" {
        value 53;
        description
          "im attr media 10gbase zr";
      }
      enum "im-attr-media-802-9a" {
        value 54;
        description
          "im attr media 802 9a";
      }
      enum "im-attr-media-rj45" {
        value 55;
        description
          "im attr media rj45";
      }
      enum "im-attr-media-1000base-zx" {
        value 56;
        description
          "im attr media 1000base zx";
      }
      enum "im-attr-media-1000base-cwdm" {
        value 57;
        description
          "im attr media 1000base cwdm";
      }
      enum "im-attr-media-1000base-cwdm-1470" {
        value 58;
        description
          "im attr media 1000base cwdm 1470";
      }
      enum "im-attr-media-1000base-cwdm-1490" {
        value 59;
        description
          "im attr media 1000base cwdm 1490";
      }
      enum "im-attr-media-1000base-cwdm-1510" {
        value 60;
        description
          "im attr media 1000base cwdm 1510";
      }
      enum "im-attr-media-1000base-cwdm-1530" {
        value 61;
        description
          "im attr media 1000base cwdm 1530";
      }
      enum "im-attr-media-1000base-cwdm-1550" {
        value 62;
        description
          "im attr media 1000base cwdm 1550";
      }
      enum "im-attr-media-1000base-cwdm-1570" {
        value 63;
        description
          "im attr media 1000base cwdm 1570";
      }
      enum "im-attr-media-1000base-cwdm-1590" {
        value 64;
        description
          "im attr media 1000base cwdm 1590";
      }
      enum "im-attr-media-1000base-cwdm-1610" {
        value 65;
        description
          "im attr media 1000base cwdm 1610";
      }
      enum "im-attr-media-10gbase-dwdm" {
        value 66;
        description
          "im attr media 10gbase dwdm";
      }
      enum "im-attr-media-100gbase-lr4" {
        value 67;
        description
          "im attr media 100gbase lr4";
      }
      enum "im-attr-media-1000base-dwdm" {
        value 68;
        description
          "im attr media 1000base dwdm";
      }
      enum "im-attr-media-1000base-dwdm-1533" {
        value 69;
        description
          "im attr media 1000base dwdm 1533";
      }
      enum "im-attr-media-1000base-dwdm-1537" {
        value 70;
        description
          "im attr media 1000base dwdm 1537";
      }
      enum "im-attr-media-1000base-dwdm-1541" {
        value 71;
        description
          "im attr media 1000base dwdm 1541";
      }
      enum "im-attr-media-1000base-dwdm-1545" {
        value 72;
        description
          "im attr media 1000base dwdm 1545";
      }
      enum "im-attr-media-1000base-dwdm-1549" {
        value 73;
        description
          "im attr media 1000base dwdm 1549";
      }
      enum "im-attr-media-1000base-dwdm-1553" {
        value 74;
        description
          "im attr media 1000base dwdm 1553";
      }
      enum "im-attr-media-1000base-dwdm-1557" {
        value 75;
        description
          "im attr media 1000base dwdm 1557";
      }
      enum "im-attr-media-1000base-dwdm-1561" {
        value 76;
        description
          "im attr media 1000base dwdm 1561";
      }
      enum "im-attr-media-40gbase-lr4" {
        value 77;
        description
          "im attr media 40gbase lr4";
      }
      enum "im-attr-media-40gbase-er4" {
        value 78;
        description
          "im attr media 40gbase er4";
      }
      enum "im-attr-media-100gbase-er4" {
        value 79;
        description
          "im attr media 100gbase er4";
      }
      enum "im-attr-media-1000base-ex" {
        value 80;
        description
          "im attr media 1000base ex";
      }
      enum "im-attr-media-1000base-bx10-d" {
        value 81;
        description
          "im attr media 1000base bx10 d";
      }
      enum "im-attr-media-1000base-bx10-u" {
        value 82;
        description
          "im attr media 1000base bx10 u";
      }
      enum "im-attr-media-1000base-dwdm-1561-42" {
        value 83;
        description
          "im attr media 1000base dwdm 1561 42";
      }
      enum "im-attr-media-1000base-dwdm-1560-61" {
        value 84;
        description
          "im attr media 1000base dwdm 1560 61";
      }
      enum "im-attr-media-1000base-dwdm-1559-79" {
        value 85;
        description
          "im attr media 1000base dwdm 1559 79";
      }
      enum "im-attr-media-1000base-dwdm-1558-98" {
        value 86;
        description
          "im attr media 1000base dwdm 1558 98";
      }
      enum "im-attr-media-1000base-dwdm-1558-17" {
        value 87;
        description
          "im attr media 1000base dwdm 1558 17";
      }
      enum "im-attr-media-1000base-dwdm-1557-36" {
        value 88;
        description
          "im attr media 1000base dwdm 1557 36";
      }
      enum "im-attr-media-1000base-dwdm-1556-55" {
        value 89;
        description
          "im attr media 1000base dwdm 1556 55";
      }
      enum "im-attr-media-1000base-dwdm-1555-75" {
        value 90;
        description
          "im attr media 1000base dwdm 1555 75";
      }
      enum "im-attr-media-1000base-dwdm-1554-94" {
        value 91;
        description
          "im attr media 1000base dwdm 1554 94";
      }
      enum "im-attr-media-1000base-dwdm-1554-13" {
        value 92;
        description
          "im attr media 1000base dwdm 1554 13";
      }
      enum "im-attr-media-1000base-dwdm-1553-33" {
        value 93;
        description
          "im attr media 1000base dwdm 1553 33";
      }
      enum "im-attr-media-1000base-dwdm-1552-52" {
        value 94;
        description
          "im attr media 1000base dwdm 1552 52";
      }
      enum "im-attr-media-1000base-dwdm-1551-72" {
        value 95;
        description
          "im attr media 1000base dwdm 1551 72";
      }
      enum "im-attr-media-1000base-dwdm-1550-92" {
        value 96;
        description
          "im attr media 1000base dwdm 1550 92";
      }
      enum "im-attr-media-1000base-dwdm-1550-12" {
        value 97;
        description
          "im attr media 1000base dwdm 1550 12";
      }
      enum "im-attr-media-1000base-dwdm-1549-32" {
        value 98;
        description
          "im attr media 1000base dwdm 1549 32";
      }
      enum "im-attr-media-1000base-dwdm-1548-51" {
        value 99;
        description
          "im attr media 1000base dwdm 1548 51";
      }
      enum "im-attr-media-1000base-dwdm-1547-72" {
        value 100;
        description
          "im attr media 1000base dwdm 1547 72";
      }
      enum "im-attr-media-1000base-dwdm-1546-92" {
        value 101;
        description
          "im attr media 1000base dwdm 1546 92";
      }
      enum "im-attr-media-1000base-dwdm-1546-12" {
        value 102;
        description
          "im attr media 1000base dwdm 1546 12";
      }
      enum "im-attr-media-1000base-dwdm-1545-32" {
        value 103;
        description
          "im attr media 1000base dwdm 1545 32";
      }
      enum "im-attr-media-1000base-dwdm-1544-53" {
        value 104;
        description
          "im attr media 1000base dwdm 1544 53";
      }
      enum "im-attr-media-1000base-dwdm-1543-73" {
        value 105;
        description
          "im attr media 1000base dwdm 1543 73";
      }
      enum "im-attr-media-1000base-dwdm-1542-94" {
        value 106;
        description
          "im attr media 1000base dwdm 1542 94";
      }
      enum "im-attr-media-1000base-dwdm-1542-14" {
        value 107;
        description
          "im attr media 1000base dwdm 1542 14";
      }
      enum "im-attr-media-1000base-dwdm-1541-35" {
        value 108;
        description
          "im attr media 1000base dwdm 1541 35";
      }
      enum "im-attr-media-1000base-dwdm-1540-56" {
        value 109;
        description
          "im attr media 1000base dwdm 1540 56";
      }
      enum "im-attr-media-1000base-dwdm-1539-77" {
        value 110;
        description
          "im attr media 1000base dwdm 1539 77";
      }
      enum "im-attr-media-1000base-dwdm-1538-98" {
        value 111;
        description
          "im attr media 1000base dwdm 1538 98";
      }
      enum "im-attr-media-1000base-dwdm-1538-19" {
        value 112;
        description
          "im attr media 1000base dwdm 1538 19";
      }
      enum "im-attr-media-1000base-dwdm-1537-40" {
        value 113;
        description
          "im attr media 1000base dwdm 1537 40";
      }
      enum "im-attr-media-1000base-dwdm-1536-61" {
        value 114;
        description
          "im attr media 1000base dwdm 1536 61";
      }
      enum "im-attr-media-1000base-dwdm-1535-82" {
        value 115;
        description
          "im attr media 1000base dwdm 1535 82";
      }
      enum "im-attr-media-1000base-dwdm-1535-04" {
        value 116;
        description
          "im attr media 1000base dwdm 1535 04";
      }
      enum "im-attr-media-1000base-dwdm-1534-25" {
        value 117;
        description
          "im attr media 1000base dwdm 1534 25";
      }
      enum "im-attr-media-1000base-dwdm-1533-47" {
        value 118;
        description
          "im attr media 1000base dwdm 1533 47";
      }
      enum "im-attr-media-1000base-dwdm-1532-68" {
        value 119;
        description
          "im attr media 1000base dwdm 1532 68";
      }
      enum "im-attr-media-1000base-dwdm-1531-90" {
        value 120;
        description
          "im attr media 1000base dwdm 1531 90";
      }
      enum "im-attr-media-1000base-dwdm-1531-12" {
        value 121;
        description
          "im attr media 1000base dwdm 1531 12";
      }
      enum "im-attr-media-1000base-dwdm-1530-33" {
        value 122;
        description
          "im attr media 1000base dwdm 1530 33";
      }
      enum "im-attr-media-1000base-dwdm-tunable" {
        value 123;
        description
          "im attr media 1000base dwdm tunable";
      }
      enum "im-attr-media-10gbase-dwdm-1561-42" {
        value 124;
        description
          "im attr media 10gbase dwdm 1561 42";
      }
      enum "im-attr-media-10gbase-dwdm-1560-61" {
        value 125;
        description
          "im attr media 10gbase dwdm 1560 61";
      }
      enum "im-attr-media-10gbase-dwdm-1559-79" {
        value 126;
        description
          "im attr media 10gbase dwdm 1559 79";
      }
      enum "im-attr-media-10gbase-dwdm-1558-98" {
        value 127;
        description
          "im attr media 10gbase dwdm 1558 98";
      }
      enum "im-attr-media-10gbase-dwdm-1558-17" {
        value 128;
        description
          "im attr media 10gbase dwdm 1558 17";
      }
      enum "im-attr-media-10gbase-dwdm-1557-36" {
        value 129;
        description
          "im attr media 10gbase dwdm 1557 36";
      }
      enum "im-attr-media-10gbase-dwdm-1556-55" {
        value 130;
        description
          "im attr media 10gbase dwdm 1556 55";
      }
      enum "im-attr-media-10gbase-dwdm-1555-75" {
        value 131;
        description
          "im attr media 10gbase dwdm 1555 75";
      }
      enum "im-attr-media-10gbase-dwdm-1554-94" {
        value 132;
        description
          "im attr media 10gbase dwdm 1554 94";
      }
      enum "im-attr-media-10gbase-dwdm-1554-13" {
        value 133;
        description
          "im attr media 10gbase dwdm 1554 13";
      }
      enum "im-attr-media-10gbase-dwdm-1553-33" {
        value 134;
        description
          "im attr media 10gbase dwdm 1553 33";
      }
      enum "im-attr-media-10gbase-dwdm-1552-52" {
        value 135;
        description
          "im attr media 10gbase dwdm 1552 52";
      }
      enum "im-attr-media-10gbase-dwdm-1551-72" {
        value 136;
        description
          "im attr media 10gbase dwdm 1551 72";
      }
      enum "im-attr-media-10gbase-dwdm-1550-92" {
        value 137;
        description
          "im attr media 10gbase dwdm 1550 92";
      }
      enum "im-attr-media-10gbase-dwdm-1550-12" {
        value 138;
        description
          "im attr media 10gbase dwdm 1550 12";
      }
      enum "im-attr-media-10gbase-dwdm-1549-32" {
        value 139;
        description
          "im attr media 10gbase dwdm 1549 32";
      }
      enum "im-attr-media-10gbase-dwdm-1548-51" {
        value 140;
        description
          "im attr media 10gbase dwdm 1548 51";
      }
      enum "im-attr-media-10gbase-dwdm-1547-72" {
        value 141;
        description
          "im attr media 10gbase dwdm 1547 72";
      }
      enum "im-attr-media-10gbase-dwdm-1546-92" {
        value 142;
        description
          "im attr media 10gbase dwdm 1546 92";
      }
      enum "im-attr-media-10gbase-dwdm-1546-12" {
        value 143;
        description
          "im attr media 10gbase dwdm 1546 12";
      }
      enum "im-attr-media-10gbase-dwdm-1545-32" {
        value 144;
        description
          "im attr media 10gbase dwdm 1545 32";
      }
      enum "im-attr-media-10gbase-dwdm-1544-53" {
        value 145;
        description
          "im attr media 10gbase dwdm 1544 53";
      }
      enum "im-attr-media-10gbase-dwdm-1543-73" {
        value 146;
        description
          "im attr media 10gbase dwdm 1543 73";
      }
      enum "im-attr-media-10gbase-dwdm-1542-94" {
        value 147;
        description
          "im attr media 10gbase dwdm 1542 94";
      }
      enum "im-attr-media-10gbase-dwdm-1542-14" {
        value 148;
        description
          "im attr media 10gbase dwdm 1542 14";
      }
      enum "im-attr-media-10gbase-dwdm-1541-35" {
        value 149;
        description
          "im attr media 10gbase dwdm 1541 35";
      }
      enum "im-attr-media-10gbase-dwdm-1540-56" {
        value 150;
        description
          "im attr media 10gbase dwdm 1540 56";
      }
      enum "im-attr-media-10gbase-dwdm-1539-77" {
        value 151;
        description
          "im attr media 10gbase dwdm 1539 77";
      }
      enum "im-attr-media-10gbase-dwdm-1538-98" {
        value 152;
        description
          "im attr media 10gbase dwdm 1538 98";
      }
      enum "im-attr-media-10gbase-dwdm-1538-19" {
        value 153;
        description
          "im attr media 10gbase dwdm 1538 19";
      }
      enum "im-attr-media-10gbase-dwdm-1537-40" {
        value 154;
        description
          "im attr media 10gbase dwdm 1537 40";
      }
      enum "im-attr-media-10gbase-dwdm-1536-61" {
        value 155;
        description
          "im attr media 10gbase dwdm 1536 61";
      }
      enum "im-attr-media-10gbase-dwdm-1535-82" {
        value 156;
        description
          "im attr media 10gbase dwdm 1535 82";
      }
      enum "im-attr-media-10gbase-dwdm-1535-04" {
        value 157;
        description
          "im attr media 10gbase dwdm 1535 04";
      }
      enum "im-attr-media-10gbase-dwdm-1534-25" {
        value 158;
        description
          "im attr media 10gbase dwdm 1534 25";
      }
      enum "im-attr-media-10gbase-dwdm-1533-47" {
        value 159;
        description
          "im attr media 10gbase dwdm 1533 47";
      }
      enum "im-attr-media-10gbase-dwdm-1532-68" {
        value 160;
        description
          "im attr media 10gbase dwdm 1532 68";
      }
      enum "im-attr-media-10gbase-dwdm-1531-90" {
        value 161;
        description
          "im attr media 10gbase dwdm 1531 90";
      }
      enum "im-attr-media-10gbase-dwdm-1531-12" {
        value 162;
        description
          "im attr media 10gbase dwdm 1531 12";
      }
      enum "im-attr-media-10gbase-dwdm-1530-33" {
        value 163;
        description
          "im attr media 10gbase dwdm 1530 33";
      }
      enum "im-attr-media-10gbase-dwdm-tunable" {
        value 164;
        description
          "im attr media 10gbase dwdm tunable";
      }
      enum "im-attr-media-40gbase-dwdm-1561-42" {
        value 165;
        description
          "im attr media 40gbase dwdm 1561 42";
      }
      enum "im-attr-media-40gbase-dwdm-1560-61" {
        value 166;
        description
          "im attr media 40gbase dwdm 1560 61";
      }
      enum "im-attr-media-40gbase-dwdm-1559-79" {
        value 167;
        description
          "im attr media 40gbase dwdm 1559 79";
      }
      enum "im-attr-media-40gbase-dwdm-1558-98" {
        value 168;
        description
          "im attr media 40gbase dwdm 1558 98";
      }
      enum "im-attr-media-40gbase-dwdm-1558-17" {
        value 169;
        description
          "im attr media 40gbase dwdm 1558 17";
      }
      enum "im-attr-media-40gbase-dwdm-1557-36" {
        value 170;
        description
          "im attr media 40gbase dwdm 1557 36";
      }
      enum "im-attr-media-40gbase-dwdm-1556-55" {
        value 171;
        description
          "im attr media 40gbase dwdm 1556 55";
      }
      enum "im-attr-media-40gbase-dwdm-1555-75" {
        value 172;
        description
          "im attr media 40gbase dwdm 1555 75";
      }
      enum "im-attr-media-40gbase-dwdm-1554-94" {
        value 173;
        description
          "im attr media 40gbase dwdm 1554 94";
      }
      enum "im-attr-media-40gbase-dwdm-1554-13" {
        value 174;
        description
          "im attr media 40gbase dwdm 1554 13";
      }
      enum "im-attr-media-40gbase-dwdm-1553-33" {
        value 175;
        description
          "im attr media 40gbase dwdm 1553 33";
      }
      enum "im-attr-media-40gbase-dwdm-1552-52" {
        value 176;
        description
          "im attr media 40gbase dwdm 1552 52";
      }
      enum "im-attr-media-40gbase-dwdm-1551-72" {
        value 177;
        description
          "im attr media 40gbase dwdm 1551 72";
      }
      enum "im-attr-media-40gbase-dwdm-1550-92" {
        value 178;
        description
          "im attr media 40gbase dwdm 1550 92";
      }
      enum "im-attr-media-40gbase-dwdm-1550-12" {
        value 179;
        description
          "im attr media 40gbase dwdm 1550 12";
      }
      enum "im-attr-media-40gbase-dwdm-1549-32" {
        value 180;
        description
          "im attr media 40gbase dwdm 1549 32";
      }
      enum "im-attr-media-40gbase-dwdm-1548-51" {
        value 181;
        description
          "im attr media 40gbase dwdm 1548 51";
      }
      enum "im-attr-media-40gbase-dwdm-1547-72" {
        value 182;
        description
          "im attr media 40gbase dwdm 1547 72";
      }
      enum "im-attr-media-40gbase-dwdm-1546-92" {
        value 183;
        description
          "im attr media 40gbase dwdm 1546 92";
      }
      enum "im-attr-media-40gbase-dwdm-1546-12" {
        value 184;
        description
          "im attr media 40gbase dwdm 1546 12";
      }
      enum "im-attr-media-40gbase-dwdm-1545-32" {
        value 185;
        description
          "im attr media 40gbase dwdm 1545 32";
      }
      enum "im-attr-media-40gbase-dwdm-1544-53" {
        value 186;
        description
          "im attr media 40gbase dwdm 1544 53";
      }
      enum "im-attr-media-40gbase-dwdm-1543-73" {
        value 187;
        description
          "im attr media 40gbase dwdm 1543 73";
      }
      enum "im-attr-media-40gbase-dwdm-1542-94" {
        value 188;
        description
          "im attr media 40gbase dwdm 1542 94";
      }
      enum "im-attr-media-40gbase-dwdm-1542-14" {
        value 189;
        description
          "im attr media 40gbase dwdm 1542 14";
      }
      enum "im-attr-media-40gbase-dwdm-1541-35" {
        value 190;
        description
          "im attr media 40gbase dwdm 1541 35";
      }
      enum "im-attr-media-40gbase-dwdm-1540-56" {
        value 191;
        description
          "im attr media 40gbase dwdm 1540 56";
      }
      enum "im-attr-media-40gbase-dwdm-1539-77" {
        value 192;
        description
          "im attr media 40gbase dwdm 1539 77";
      }
      enum "im-attr-media-40gbase-dwdm-1538-98" {
        value 193;
        description
          "im attr media 40gbase dwdm 1538 98";
      }
      enum "im-attr-media-40gbase-dwdm-1538-19" {
        value 194;
        description
          "im attr media 40gbase dwdm 1538 19";
      }
      enum "im-attr-media-40gbase-dwdm-1537-40" {
        value 195;
        description
          "im attr media 40gbase dwdm 1537 40";
      }
      enum "im-attr-media-40gbase-dwdm-1536-61" {
        value 196;
        description
          "im attr media 40gbase dwdm 1536 61";
      }
      enum "im-attr-media-40gbase-dwdm-1535-82" {
        value 197;
        description
          "im attr media 40gbase dwdm 1535 82";
      }
      enum "im-attr-media-40gbase-dwdm-1535-04" {
        value 198;
        description
          "im attr media 40gbase dwdm 1535 04";
      }
      enum "im-attr-media-40gbase-dwdm-1534-25" {
        value 199;
        description
          "im attr media 40gbase dwdm 1534 25";
      }
      enum "im-attr-media-40gbase-dwdm-1533-47" {
        value 200;
        description
          "im attr media 40gbase dwdm 1533 47";
      }
      enum "im-attr-media-40gbase-dwdm-1532-68" {
        value 201;
        description
          "im attr media 40gbase dwdm 1532 68";
      }
      enum "im-attr-media-40gbase-dwdm-1531-90" {
        value 202;
        description
          "im attr media 40gbase dwdm 1531 90";
      }
      enum "im-attr-media-40gbase-dwdm-1531-12" {
        value 203;
        description
          "im attr media 40gbase dwdm 1531 12";
      }
      enum "im-attr-media-40gbase-dwdm-1530-33" {
        value 204;
        description
          "im attr media 40gbase dwdm 1530 33";
      }
      enum "im-attr-media-40gbase-dwdm-tunable" {
        value 205;
        description
          "im attr media 40gbase dwdm tunable";
      }
      enum "im-attr-media-100gbase-dwdm-1561-42" {
        value 206;
        description
          "im attr media 100gbase dwdm 1561 42";
      }
      enum "im-attr-media-100gbase-dwdm-1560-61" {
        value 207;
        description
          "im attr media 100gbase dwdm 1560 61";
      }
      enum "im-attr-media-100gbase-dwdm-1559-79" {
        value 208;
        description
          "im attr media 100gbase dwdm 1559 79";
      }
      enum "im-attr-media-100gbase-dwdm-1558-98" {
        value 209;
        description
          "im attr media 100gbase dwdm 1558 98";
      }
      enum "im-attr-media-100gbase-dwdm-1558-17" {
        value 210;
        description
          "im attr media 100gbase dwdm 1558 17";
      }
      enum "im-attr-media-100gbase-dwdm-1557-36" {
        value 211;
        description
          "im attr media 100gbase dwdm 1557 36";
      }
      enum "im-attr-media-100gbase-dwdm-1556-55" {
        value 212;
        description
          "im attr media 100gbase dwdm 1556 55";
      }
      enum "im-attr-media-100gbase-dwdm-1555-75" {
        value 213;
        description
          "im attr media 100gbase dwdm 1555 75";
      }
      enum "im-attr-media-100gbase-dwdm-1554-94" {
        value 214;
        description
          "im attr media 100gbase dwdm 1554 94";
      }
      enum "im-attr-media-100gbase-dwdm-1554-13" {
        value 215;
        description
          "im attr media 100gbase dwdm 1554 13";
      }
      enum "im-attr-media-100gbase-dwdm-1553-33" {
        value 216;
        description
          "im attr media 100gbase dwdm 1553 33";
      }
      enum "im-attr-media-100gbase-dwdm-1552-52" {
        value 217;
        description
          "im attr media 100gbase dwdm 1552 52";
      }
      enum "im-attr-media-100gbase-dwdm-1551-72" {
        value 218;
        description
          "im attr media 100gbase dwdm 1551 72";
      }
      enum "im-attr-media-100gbase-dwdm-1550-92" {
        value 219;
        description
          "im attr media 100gbase dwdm 1550 92";
      }
      enum "im-attr-media-100gbase-dwdm-1550-12" {
        value 220;
        description
          "im attr media 100gbase dwdm 1550 12";
      }
      enum "im-attr-media-100gbase-dwdm-1549-32" {
        value 221;
        description
          "im attr media 100gbase dwdm 1549 32";
      }
      enum "im-attr-media-100gbase-dwdm-1548-51" {
        value 222;
        description
          "im attr media 100gbase dwdm 1548 51";
      }
      enum "im-attr-media-100gbase-dwdm-1547-72" {
        value 223;
        description
          "im attr media 100gbase dwdm 1547 72";
      }
      enum "im-attr-media-100gbase-dwdm-1546-92" {
        value 224;
        description
          "im attr media 100gbase dwdm 1546 92";
      }
      enum "im-attr-media-100gbase-dwdm-1546-12" {
        value 225;
        description
          "im attr media 100gbase dwdm 1546 12";
      }
      enum "im-attr-media-100gbase-dwdm-1545-32" {
        value 226;
        description
          "im attr media 100gbase dwdm 1545 32";
      }
      enum "im-attr-media-100gbase-dwdm-1544-53" {
        value 227;
        description
          "im attr media 100gbase dwdm 1544 53";
      }
      enum "im-attr-media-100gbase-dwdm-1543-73" {
        value 228;
        description
          "im attr media 100gbase dwdm 1543 73";
      }
      enum "im-attr-media-100gbase-dwdm-1542-94" {
        value 229;
        description
          "im attr media 100gbase dwdm 1542 94";
      }
      enum "im-attr-media-100gbase-dwdm-1542-14" {
        value 230;
        description
          "im attr media 100gbase dwdm 1542 14";
      }
      enum "im-attr-media-100gbase-dwdm-1541-35" {
        value 231;
        description
          "im attr media 100gbase dwdm 1541 35";
      }
      enum "im-attr-media-100gbase-dwdm-1540-56" {
        value 232;
        description
          "im attr media 100gbase dwdm 1540 56";
      }
      enum "im-attr-media-100gbase-dwdm-1539-77" {
        value 233;
        description
          "im attr media 100gbase dwdm 1539 77";
      }
      enum "im-attr-media-100gbase-dwdm-1538-98" {
        value 234;
        description
          "im attr media 100gbase dwdm 1538 98";
      }
      enum "im-attr-media-100gbase-dwdm-1538-19" {
        value 235;
        description
          "im attr media 100gbase dwdm 1538 19";
      }
      enum "im-attr-media-100gbase-dwdm-1537-40" {
        value 236;
        description
          "im attr media 100gbase dwdm 1537 40";
      }
      enum "im-attr-media-100gbase-dwdm-1536-61" {
        value 237;
        description
          "im attr media 100gbase dwdm 1536 61";
      }
      enum "im-attr-media-100gbase-dwdm-1535-82" {
        value 238;
        description
          "im attr media 100gbase dwdm 1535 82";
      }
      enum "im-attr-media-100gbase-dwdm-1535-04" {
        value 239;
        description
          "im attr media 100gbase dwdm 1535 04";
      }
      enum "im-attr-media-100gbase-dwdm-1534-25" {
        value 240;
        description
          "im attr media 100gbase dwdm 1534 25";
      }
      enum "im-attr-media-100gbase-dwdm-1533-47" {
        value 241;
        description
          "im attr media 100gbase dwdm 1533 47";
      }
      enum "im-attr-media-100gbase-dwdm-1532-68" {
        value 242;
        description
          "im attr media 100gbase dwdm 1532 68";
      }
      enum "im-attr-media-100gbase-dwdm-1531-90" {
        value 243;
        description
          "im attr media 100gbase dwdm 1531 90";
      }
      enum "im-attr-media-100gbase-dwdm-1531-12" {
        value 244;
        description
          "im attr media 100gbase dwdm 1531 12";
      }
      enum "im-attr-media-100gbase-dwdm-1530-33" {
        value 245;
        description
          "im attr media 100gbase dwdm 1530 33";
      }
      enum "im-attr-media-100gbase-dwdm-tunable" {
        value 246;
        description
          "im attr media 100gbase dwdm tunable";
      }
      enum "im-attr-media-40gbase-kr4" {
        value 247;
        description
          "im attr media 40gbase kr4";
      }
      enum "im-attr-media-40gbase-cr4" {
        value 248;
        description
          "im attr media 40gbase cr4";
      }
      enum "im-attr-media-40gbase-sr4" {
        value 249;
        description
          "im attr media 40gbase sr4";
      }
      enum "im-attr-media-40gbase-fr" {
        value 250;
        description
          "im attr media 40gbase fr";
      }
      enum "im-attr-media-100gbase-cr10" {
        value 251;
        description
          "im attr media 100gbase cr10";
      }
      enum "im-attr-media-100gbase-sr10" {
        value 252;
        description
          "im attr media 100gbase sr10";
      }
      enum "im-attr-media-40gbase-csr4" {
        value 253;
        description
          "im attr media 40gbase csr4";
      }
      enum "im-attr-media-10gbase-cwdm" {
        value 254;
        description
          "im attr media 10gbase cwdm";
      }
      enum "im-attr-media-10gbase-cwdm-tunable" {
        value 255;
        description
          "im attr media 10gbase cwdm tunable";
      }
      enum "im-attr-media-10gbase-cwdm-1470" {
        value 256;
        description
          "im attr media 10gbase cwdm 1470";
      }
      enum "im-attr-media-10gbase-cwdm-1490" {
        value 257;
        description
          "im attr media 10gbase cwdm 1490";
      }
      enum "im-attr-media-10gbase-cwdm-1510" {
        value 258;
        description
          "im attr media 10gbase cwdm 1510";
      }
      enum "im-attr-media-10gbase-cwdm-1530" {
        value 259;
        description
          "im attr media 10gbase cwdm 1530";
      }
      enum "im-attr-media-10gbase-cwdm-1550" {
        value 260;
        description
          "im attr media 10gbase cwdm 1550";
      }
      enum "im-attr-media-10gbase-cwdm-1570" {
        value 261;
        description
          "im attr media 10gbase cwdm 1570";
      }
      enum "im-attr-media-10gbase-cwdm-1590" {
        value 262;
        description
          "im attr media 10gbase cwdm 1590";
      }
      enum "im-attr-media-10gbase-cwdm-1610" {
        value 263;
        description
          "im attr media 10gbase cwdm 1610";
      }
      enum "im-attr-media-40gbase-cwdm" {
        value 264;
        description
          "im attr media 40gbase cwdm";
      }
      enum "im-attr-media-40gbase-cwdm-tunable" {
        value 265;
        description
          "im attr media 40gbase cwdm tunable";
      }
      enum "im-attr-media-40gbase-cwdm-1470" {
        value 266;
        description
          "im attr media 40gbase cwdm 1470";
      }
      enum "im-attr-media-40gbase-cwdm-1490" {
        value 267;
        description
          "im attr media 40gbase cwdm 1490";
      }
      enum "im-attr-media-40gbase-cwdm-1510" {
        value 268;
        description
          "im attr media 40gbase cwdm 1510";
      }
      enum "im-attr-media-40gbase-cwdm-1530" {
        value 269;
        description
          "im attr media 40gbase cwdm 1530";
      }
      enum "im-attr-media-40gbase-cwdm-1550" {
        value 270;
        description
          "im attr media 40gbase cwdm 1550";
      }
      enum "im-attr-media-40gbase-cwdm-1570" {
        value 271;
        description
          "im attr media 40gbase cwdm 1570";
      }
      enum "im-attr-media-40gbase-cwdm-1590" {
        value 272;
        description
          "im attr media 40gbase cwdm 1590";
      }
      enum "im-attr-media-40gbase-cwdm-1610" {
        value 273;
        description
          "im attr media 40gbase cwdm 1610";
      }
      enum "im-attr-media-100gbase-cwdm" {
        value 274;
        description
          "im attr media 100gbase cwdm";
      }
      enum "im-attr-media-100gbase-cwdm-tunable" {
        value 275;
        description
          "im attr media 100gbase cwdm tunable";
      }
      enum "im-attr-media-100gbase-cwdm-1470" {
        value 276;
        description
          "im attr media 100gbase cwdm 1470";
      }
      enum "im-attr-media-100gbase-cwdm-1490" {
        value 277;
        description
          "im attr media 100gbase cwdm 1490";
      }
      enum "im-attr-media-100gbase-cwdm-1510" {
        value 278;
        description
          "im attr media 100gbase cwdm 1510";
      }
      enum "im-attr-media-100gbase-cwdm-1530" {
        value 279;
        description
          "im attr media 100gbase cwdm 1530";
      }
      enum "im-attr-media-100gbase-cwdm-1550" {
        value 280;
        description
          "im attr media 100gbase cwdm 1550";
      }
      enum "im-attr-media-100gbase-cwdm-1570" {
        value 281;
        description
          "im attr media 100gbase cwdm 1570";
      }
      enum "im-attr-media-100gbase-cwdm-1590" {
        value 282;
        description
          "im attr media 100gbase cwdm 1590";
      }
      enum "im-attr-media-100gbase-cwdm-1610" {
        value 283;
        description
          "im attr media 100gbase cwdm 1610";
      }
      enum "im-attr-media-40gbase-elpb" {
        value 284;
        description
          "im attr media 40gbase elpb";
      }
      enum "im-attr-media-100gbase-elpb" {
        value 285;
        description
          "im attr media 100gbase elpb";
      }
      enum "im-attr-media-100gbase-lr10" {
        value 286;
        description
          "im attr media 100gbase lr10";
      }
      enum "im-attr-media-40gbase" {
        value 287;
        description
          "im attr media 40gbase";
      }
      enum "im-attr-media-100gbase-kp4" {
        value 288;
        description
          "im attr media 100gbase kp4";
      }
      enum "im-attr-media-100gbase-kr4" {
        value 289;
        description
          "im attr media 100gbase kr4";
      }
      enum "im-attr-media-10gbase-lrm" {
        value 290;
        description
          "im attr media 10gbase lrm";
      }
      enum "im-attr-media-10gbase-cx4" {
        value 291;
        description
          "im attr media 10gbase cx4";
      }
      enum "im-attr-media-10gbase" {
        value 292;
        description
          "im attr media 10gbase";
      }
      enum "im-attr-media-10gbase-kx4" {
        value 293;
        description
          "im attr media 10gbase kx4";
      }
      enum "im-attr-media-10gbase-kr" {
        value 294;
        description
          "im attr media 10gbase kr";
      }
      enum "im-attr-media-10gbase-pr" {
        value 295;
        description
          "im attr media 10gbase pr";
      }
      enum "im-attr-media-100base-lx" {
        value 296;
        description
          "im attr media 100base lx";
      }
      enum "im-attr-media-100base-zx" {
        value 297;
        description
          "im attr media 100base zx";
      }
      enum "im-attr-media-1000base-bx-d" {
        value 298;
        description
          "im attr media 1000base bx d";
      }
      enum "im-attr-media-1000base-bx-u" {
        value 299;
        description
          "im attr media 1000base bx u";
      }
      enum "im-attr-media-1000base-bx20-d" {
        value 300;
        description
          "im attr media 1000base bx20 d";
      }
      enum "im-attr-media-1000base-bx20-u" {
        value 301;
        description
          "im attr media 1000base bx20 u";
      }
      enum "im-attr-media-1000base-bx40-d" {
        value 302;
        description
          "im attr media 1000base bx40 d";
      }
      enum "im-attr-media-1000base-bx40-da" {
        value 303;
        description
          "im attr media 1000base bx40 da";
      }
      enum "im-attr-media-1000base-bx40-u" {
        value 304;
        description
          "im attr media 1000base bx40 u";
      }
      enum "im-attr-media-1000base-bx80-d" {
        value 305;
        description
          "im attr media 1000base bx80 d";
      }
      enum "im-attr-media-1000base-bx80-u" {
        value 306;
        description
          "im attr media 1000base bx80 u";
      }
      enum "im-attr-media-1000base-bx120-d" {
        value 307;
        description
          "im attr media 1000base bx120 d";
      }
      enum "im-attr-media-1000base-bx120-u" {
        value 308;
        description
          "im attr media 1000base bx120 u";
      }
      enum "im-attr-media-10gbase-bx-d" {
        value 309;
        description
          "im attr media 10gbase bx d";
      }
      enum "im-attr-media-10gbase-bx-u" {
        value 310;
        description
          "im attr media 10gbase bx u";
      }
      enum "im-attr-media-10gbase-bx10-d" {
        value 311;
        description
          "im attr media 10gbase bx10 d";
      }
      enum "im-attr-media-10gbase-bx10-u" {
        value 312;
        description
          "im attr media 10gbase bx10 u";
      }
      enum "im-attr-media-10gbase-bx20-d" {
        value 313;
        description
          "im attr media 10gbase bx20 d";
      }
      enum "im-attr-media-10gbase-bx20-u" {
        value 314;
        description
          "im attr media 10gbase bx20 u";
      }
      enum "im-attr-media-10gbase-bx40-d" {
        value 315;
        description
          "im attr media 10gbase bx40 d";
      }
      enum "im-attr-media-10gbase-bx40-u" {
        value 316;
        description
          "im attr media 10gbase bx40 u";
      }
      enum "im-attr-media-10gbase-bx80-d" {
        value 317;
        description
          "im attr media 10gbase bx80 d";
      }
      enum "im-attr-media-10gbase-bx80-u" {
        value 318;
        description
          "im attr media 10gbase bx80 u";
      }
      enum "im-attr-media-10gbase-bx120-d" {
        value 319;
        description
          "im attr media 10gbase bx120 d";
      }
      enum "im-attr-media-10gbase-bx120-u" {
        value 320;
        description
          "im attr media 10gbase bx120 u";
      }
      enum "im-attr-media-1000base-dr-lx" {
        value 321;
        description
          "im attr media 1000base dr lx";
      }
      enum "im-attr-media-100gbase-er4l" {
        value 322;
        description
          "im attr media 100gbase er4l";
      }
      enum "im-attr-media-100gbase-sr4" {
        value 323;
        description
          "im attr media 100gbase sr4";
      }
      enum "im-attr-media-40gbase-sr-bd" {
        value 324;
        description
          "im attr media 40gbase sr bd";
      }
      enum "im-attr-media-25gbase-cr" {
        value 325;
        description
          "im attr media 25gbase cr";
      }
      enum "im-attr-media-25gbase-cr-s" {
        value 326;
        description
          "im attr media 25gbase cr s";
      }
      enum "im-attr-media-25gbase-kr" {
        value 327;
        description
          "im attr media 25gbase kr";
      }
      enum "im-attr-media-25gbase-kr-s" {
        value 328;
        description
          "im attr media 25gbase kr s";
      }
      enum "im-attr-media-25gbase-r" {
        value 329;
        description
          "im attr media 25gbase r";
      }
      enum "im-attr-media-25gbase-sr" {
        value 330;
        description
          "im attr media 25gbase sr";
      }
      enum "im-attr-media-25gbase-dwdm" {
        value 331;
        description
          "im attr media 25gbase dwdm";
      }
      enum "im-attr-media-25gbase-dwdm-tunable" {
        value 332;
        description
          "im attr media 25gbase dwdm tunable";
      }
      enum "im-attr-media-25gbase-cwdm" {
        value 333;
        description
          "im attr media 25gbase cwdm";
      }
      enum "im-attr-media-25gbase-cwdm-tunable" {
        value 334;
        description
          "im attr media 25gbase cwdm tunable";
      }
      enum "im-attr-media-100gbase-psm4" {
        value 335;
        description
          "im attr media 100gbase psm4";
      }
      enum "im-attr-media-100gbase-er10" {
        value 336;
        description
          "im attr media 100gbase er10";
      }
      enum "im-attr-media-100gbase-er10l" {
        value 337;
        description
          "im attr media 100gbase er10l";
      }
      enum "im-attr-media-100gbase-acc" {
        value 338;
        description
          "im attr media 100gbase acc";
      }
      enum "im-attr-media-100gbase-aoc" {
        value 339;
        description
          "im attr media 100gbase aoc";
      }
      enum "im-attr-media-100gbase-cwdm4" {
        value 340;
        description
          "im attr media 100gbase cwdm4";
      }
      enum "im-attr-media-40gbase-psm4" {
        value 341;
        description
          "im attr media 40gbase psm4";
      }
      enum "im-attr-media-100gbase-cr4" {
        value 342;
        description
          "im attr media 100gbase cr4";
      }
      enum "im-attr-media-100gbase-act-loop" {
        value 343;
        description
          "im attr media 100gbase act loop";
      }
      enum "im-attr-media-100gbase-pas-loop" {
        value 344;
        description
          "im attr media 100gbase pas loop";
      }
      enum "im-attr-media-50gbase-cr2" {
        value 345;
        description
          "im attr media 50gbase cr2";
      }
      enum "im-attr-media-50gbase-sr2" {
        value 346;
        description
          "im attr media 50gbase sr2";
      }
      enum "im-attr-media-50gbase-psm2" {
        value 347;
        description
          "im attr media 50gbase psm2";
      }
      enum "im-attr-media-200gbase-cr4" {
        value 348;
        description
          "im attr media 200gbase cr4";
      }
      enum "im-attr-media-400gbase-fr4" {
        value 349;
        description
          "im attr media 400gbase fr4";
      }
      enum "im-attr-media-400gbase-dr4" {
        value 350;
        description
          "im attr media 400gbase dr4";
      }
      enum "im-attr-media-10gbase-cr" {
        value 351;
        description
          "im attr media 10gbase cr";
      }
      enum "im-attr-media-10gbase-aoc" {
        value 352;
        description
          "im attr media 10gbase aoc";
      }
      enum "im-attr-media-40gbase-aoc" {
        value 353;
        description
          "im attr media 40gbase aoc";
      }
      enum "im-attr-media-40gbase-acu" {
        value 354;
        description
          "im attr media 40gbase acu";
      }
      enum "im-attr-media-100gbase-acu" {
        value 355;
        description
          "im attr media 100gbase acu";
      }
      enum "im-attr-media-10gbase-cu1m" {
        value 356;
        description
          "im attr media 10gbase cu1m";
      }
      enum "im-attr-media-10gbase-cu3m" {
        value 357;
        description
          "im attr media 10gbase cu3m";
      }
      enum "im-attr-media-10gbase-cu5m" {
        value 358;
        description
          "im attr media 10gbase cu5m";
      }
      enum "im-attr-media-10gbase-acu7m" {
        value 359;
        description
          "im attr media 10gbase acu7m";
      }
      enum "im-attr-media-10gbase-acu10m" {
        value 360;
        description
          "im attr media 10gbase acu10m";
      }
      enum "im-attr-media-4x10g-base-lr" {
        value 361;
        description
          "im attr media 4x10g base lr";
      }
      enum "im-attr-media-10gbase-cu1-5m" {
        value 362;
        description
          "im attr media 10gbase cu1 5m";
      }
      enum "im-attr-media-10gbase-cu2m" {
        value 363;
        description
          "im attr media 10gbase cu2m";
      }
      enum "im-attr-media-10gbase-cu2-5m" {
        value 364;
        description
          "im attr media 10gbase cu2 5m";
      }
      enum "im-attr-media-10gbase-aoc1m" {
        value 365;
        description
          "im attr media 10gbase aoc1m";
      }
      enum "im-attr-media-10gbase-aoc2m" {
        value 366;
        description
          "im attr media 10gbase aoc2m";
      }
      enum "im-attr-media-10gbase-aoc3m" {
        value 367;
        description
          "im attr media 10gbase aoc3m";
      }
      enum "im-attr-media-10gbase-aoc5m" {
        value 368;
        description
          "im attr media 10gbase aoc5m";
      }
      enum "im-attr-media-10gbase-aoc7m" {
        value 369;
        description
          "im attr media 10gbase aoc7m";
      }
      enum "im-attr-media-10gbase-aoc10m" {
        value 370;
        description
          "im attr media 10gbase aoc10m";
      }
      enum "im-attr-media-40gbase-acu1m" {
        value 371;
        description
          "im attr media 40gbase acu1m";
      }
      enum "im-attr-media-40gbase-acu3m" {
        value 372;
        description
          "im attr media 40gbase acu3m";
      }
      enum "im-attr-media-40gbase-acu5m" {
        value 373;
        description
          "im attr media 40gbase acu5m";
      }
      enum "im-attr-media-40gbase-acu7m" {
        value 374;
        description
          "im attr media 40gbase acu7m";
      }
      enum "im-attr-media-40gbase-acu10m" {
        value 375;
        description
          "im attr media 40gbase acu10m";
      }
      enum "im-attr-media-25gbase-cu1m" {
        value 376;
        description
          "im attr media 25gbase cu1m";
      }
      enum "im-attr-media-25gbase-cu2m" {
        value 377;
        description
          "im attr media 25gbase cu2m";
      }
      enum "im-attr-media-25gbase-cu3m" {
        value 378;
        description
          "im attr media 25gbase cu3m";
      }
      enum "im-attr-media-25gbase-cu5m" {
        value 379;
        description
          "im attr media 25gbase cu5m";
      }
      enum "im-attr-media-100gbase-sm-sr" {
        value 380;
        description
          "im attr media 100gbase sm sr";
      }
      enum "im-attr-media-1000base-2bx-d" {
        value 381;
        description
          "im attr media 1000base 2bx d";
      }
      enum "im-attr-media-1000base-2bx-d-i" {
        value 382;
        description
          "im attr media 1000base 2bx d i";
      }
      enum "im-attr-media-1000base-2bx-u" {
        value 383;
        description
          "im attr media 1000base 2bx u";
      }
      enum "im-attr-media-1000base-2bx-u-i" {
        value 384;
        description
          "im attr media 1000base 2bx u i";
      }
      enum "im-attr-media-400gbase-cr8" {
        value 385;
        description
          "im attr media 400gbase cr8";
      }
      enum "im-attr-media-100gbase-sr-bd" {
        value 386;
        description
          "im attr media 100gbase sr bd";
      }
      enum "im-attr-media-400gbase-lr8" {
        value 387;
        description
          "im attr media 400gbase lr8";
      }
      enum "im-attr-media-400gbase-aoc" {
        value 388;
        description
          "im attr media 400gbase aoc";
      }
      enum "im-attr-media-400gbase-acc" {
        value 389;
        description
          "im attr media 400gbase acc";
      }
      enum "im-attr-media-400gbase-act-loop" {
        value 390;
        description
          "im attr media 400gbase act loop";
      }
      enum "im-attr-media-400gbase-pas-loop" {
        value 391;
        description
          "im attr media 400gbase pas loop";
      }
      enum "im-attr-media-8x-sfp50gbase-cu" {
        value 392;
        description
          "im attr media 8x sfp50gbase cu";
      }
      enum "im-attr-media-2x100gbase-lr8-s" {
        value 393;
        description
          "im attr media 2x100gbase lr8 s";
      }
      enum "im-attr-media-2x100gbase-sr4" {
        value 394;
        description
          "im attr media 2x100gbase sr4";
      }
      enum "im-attr-media-2x100gbase-psm4" {
        value 395;
        description
          "im attr media 2x100gbase psm4";
      }
      enum "im-attr-media-2x100gbase-cwdm4" {
        value 396;
        description
          "im attr media 2x100gbase cwdm4";
      }
      enum "im-attr-media-2x100gbase-lr4" {
        value 397;
        description
          "im attr media 2x100gbase lr4";
      }
      enum "im-attr-media-100gbase-fr" {
        value 398;
        description
          "im attr media 100gbase fr";
      }
      enum "im-attr-media-100gbase-dwdm2" {
        value 399;
        description
          "im attr media 100gbase dwdm2";
      }
      enum "im-attr-media-25gbase-aoc1m" {
        value 400;
        description
          "im attr media 25gbase aoc1m";
      }
      enum "im-attr-media-25gbase-aoc2m" {
        value 401;
        description
          "im attr media 25gbase aoc2m";
      }
      enum "im-attr-media-25gbase-aoc3m" {
        value 402;
        description
          "im attr media 25gbase aoc3m";
      }
      enum "im-attr-media-25gbase-aoc5m" {
        value 403;
        description
          "im attr media 25gbase aoc5m";
      }
      enum "im-attr-media-25gbase-aoc7m" {
        value 404;
        description
          "im attr media 25gbase aoc7m";
      }
      enum "im-attr-media-25gbase-aoc10m" {
        value 405;
        description
          "im attr media 25gbase aoc10m";
      }
    }
    description
      "Im attr media";
  }

  typedef Im-attr-duplex {
    type enumeration {
      enum "im-attr-duplex-unknown" {
        value 0;
        description
          "im attr duplex unknown";
      }
      enum "im-attr-duplex-half" {
        value 1;
        description
          "im attr duplex half";
      }
      enum "im-attr-duplex-full" {
        value 2;
        description
          "im attr duplex full";
      }
    }
    description
      "Im attr duplex";
  }

  grouping IM-DESC-INFO {
    description
      "Interface description information";
    leaf interface {
      type xr:Interface-name;
      description
        "Interface handle of the Interface";
    }
    leaf state {
      type Im-state-enum;
      description
        "Operational state with no translation of error
         disable or shutdown";
    }
    leaf line-state {
      type Im-state-enum;
      description
        "Line protocol state with no translation of error
         disable or shutdown";
    }
    leaf description {
      type string;
      description
        "Interface description string";
    }
  }

  grouping STATS-BAG-ELEMENT {
    description
      "STATS BAG ELEMENT";
    leaf key {
      type yang:hex-string;
      description
        "key";
    }
    list block-array {
      description
        "block array";
      uses STATS-BAG-BLOCK;
    }
  }

  grouping STATS-BAG-BLOCK {
    description
      "STATS BAG BLOCK";
    leaf type {
      type Stats-counter;
      description
        "type";
    }
    leaf count {
      type uint32;
      description
        "count";
    }
    leaf data {
      type yang:hex-string;
      description
        "data";
    }
  }

  grouping STATS-BAG-ID {
    description
      "STATS BAG ID";
    leaf id-type {
      type Stats-id;
      description
        "id type";
    }
    leaf unused {
      when "../id-type = 'stats-id-type-unknown'" {
        description
          "../id_type = 'STATS_ID_TYPE_UNKNOWN'";
      }
      type uint32;
      description
        "Unused";
    }
    leaf interface-handle {
      when "../id-type = 'stats-id-type-min'" {
        description
          "../id_type = 'STATS_ID_TYPE_MIN'";
      }
      type xr:Interface-name;
      description
        "Interface Handle";
    }
    leaf node-id {
      when "../id-type = 'stats-id-type-node'" {
        description
          "../id_type = 'STATS_ID_TYPE_NODE'";
      }
      type xr:Node-id;
      description
        "Node ID";
    }
    leaf feature-id {
      when "../id-type = 'stats-id-type-feature'" {
        description
          "../id_type = 'STATS_ID_TYPE_FEATURE'";
      }
      type uint32;
      description
        "Feature ID";
    }
    leaf id {
      when "../id-type = 'stats-id-type-other'" {
        description
          "../id_type = 'STATS_ID_TYPE_OTHER'";
      }
      type uint32;
      description
        "ID";
    }
  }

  grouping STATS-DATA {
    description
      "Stats Data";
    container stats-id {
      description
        "Identifier";
      uses STATS-BAG-ID;
    }
    leaf stats-type {
      type Stats-type-val;
      description
        "Stats type value";
    }
    leaf contents {
      type Stats-type-contents;
      description
        "Bag contents";
    }
    list block-array {
      description
        "Block Array";
      uses STATS-BAG-BLOCK;
    }
    list element-array {
      description
        "Element Array";
      uses STATS-BAG-ELEMENT;
    }
  }

  grouping IFSTATSBAG-BASIC {
    description
      "Basic set of interface counters";
    leaf packets-received {
      type uint64;
      description
        "Total no. of Packets received";
    }
    leaf bytes-received {
      type uint64;
      units "byte";
      description
        "Total no. of Bytes received";
    }
    leaf packets-sent {
      type uint64;
      description
        "Total no. of Packets sent";
    }
    leaf bytes-sent {
      type uint64;
      units "byte";
      description
        "Total no. of Bytes sent";
    }
    leaf input-drops {
      type uint32;
      description
        "Total input drops";
    }
    leaf input-queue-drops {
      type uint32;
      description
        "Input queue drops";
    }
    leaf input-errors {
      type uint32;
      description
        "Total input errors";
    }
    leaf unknown-protocol-packets-received {
      type uint32;
      description
        "Unknown protocol packets received";
    }
    leaf output-drops {
      type uint32;
      description
        "Total output drops";
    }
    leaf output-queue-drops {
      type uint32;
      description
        "Output queue drops";
    }
    leaf output-errors {
      type uint32;
      description
        "Total packets dropped due to internal driver
         error";
    }
    leaf last-data-time {
      type uint32;
      units "second";
      description
        "Time when counters were last written (in
         seconds)";
    }
    leaf seconds-since-last-clear-counters {
      type uint32;
      units "second";
      description
        "Time elapsed since last clear command executed
         (in Seconds)";
    }
    leaf last-discontinuity-time {
      type uint32;
      units "second";
      description
        "SysUpTime when counters were last reset (in
         seconds)";
    }
    leaf seconds-since-packet-received {
      type uint32;
      units "second";
      description
        "Time elapsed since packet received (in Seconds)";
    }
    leaf seconds-since-packet-sent {
      type uint32;
      units "second";
      description
        "Time since packet sent (in Seconds)";
    }
  }

  grouping IFSTATSBAG-GENERIC {
    description
      "Generic set of interface counters";
    leaf packets-received {
      type uint64;
      description
        "Total Packets received";
    }
    leaf bytes-received {
      type uint64;
      units "byte";
      description
        "Total Bytes received";
    }
    leaf packets-sent {
      type uint64;
      description
        "Total Packets sent";
    }
    leaf bytes-sent {
      type uint64;
      units "byte";
      description
        "Total Bytes sent";
    }
    leaf multicast-packets-received {
      type uint64;
      description
        "Total no. of multicast packets received";
    }
    leaf broadcast-packets-received {
      type uint64;
      description
        "Total no. of broadcast packets received";
    }
    leaf multicast-packets-sent {
      type uint64;
      description
        "Total no. of multicast packets sent";
    }
    leaf broadcast-packets-sent {
      type uint64;
      description
        "Total no. of broadcast packets sent";
    }
    leaf output-drops {
      type uint32;
      description
        "No. of packet dropped before being transmitted";
    }
    leaf output-queue-drops {
      type uint32;
      description
        "Number of packets dropped due to configured
         output policy";
    }
    leaf input-drops {
      type uint32;
      description
        "Total input drops";
    }
    leaf input-queue-drops {
      type uint32;
      description
        "Placeholder for packets dropped due to configure
         input policy";
    }
    leaf runt-packets-received {
      type uint32;
      description
        "Received packets which are too small to be
         handled";
    }
    leaf giant-packets-received {
      type uint32;
      description
        "Received packets which are too large to be
         handled";
    }
    leaf throttled-packets-received {
      type uint32;
      description
        "No. of times the receiver on the port is was
         disabled";
    }
    leaf parity-packets-received {
      type uint32;
      description
        "No. of parity errors on the interface";
    }
    leaf unknown-protocol-packets-received {
      type uint32;
      description
        "No. of packets dropped because they were
         destined for higher levelprotocols not configure
         or running on the interface";
    }
    leaf input-errors {
      type uint32;
      description
        "Total input errors";
    }
    leaf crc-errors {
      type uint32;
      description
        "Input CRC errors";
    }
    leaf input-overruns {
      type uint32;
      description
        "No. of input packets received with FIFO or DMA
         overrun errors";
    }
    leaf framing-errors-received {
      type uint32;
      description
        "No. of packets received with framing error";
    }
    leaf input-ignored-packets {
      type uint32;
      description
        "Packets dropped due to internal driver error or
         hardware errors ";
    }
    leaf input-aborts {
      type uint32;
      description
        "No. of packets whose reciept was aborted";
    }
    leaf output-errors {
      type uint32;
      description
        "Total packets that could not be transmitted due
         to internal driver error";
    }
    leaf output-underruns {
      type uint32;
      description
        "Transmitted packets with FIFO or DMA underrun
         errors";
    }
    leaf output-buffer-failures {
      type uint32;
      description
        "No. of no resource error received on output";
    }
    leaf output-buffers-swapped-out {
      type uint32;
      description
        "No. of packets swapped to DRAM or main memory";
    }
    leaf applique {
      type uint32;
      description
        "No. of unrecoverable error which have occured on
         the applique";
    }
    leaf resets {
      type uint32;
      description
        "Number of hardware resets";
    }
    leaf carrier-transitions {
      type uint32;
      description
        "No. of times the carrier detect signal of
         interface has changed state";
    }
    leaf availability-flag {
      type uint32;
      description
        "Availability bit mask";
    }
    leaf last-data-time {
      type uint32;
      units "second";
      description
        "Time when counters were last written (in
         Seconds)";
    }
    leaf seconds-since-last-clear-counters {
      type uint32;
      units "second";
      description
        "Time elapsed since last clear command executed
         (in Seconds)";
    }
    leaf last-discontinuity-time {
      type uint32;
      units "second";
      description
        "SysUpTime when counters were last reset (in
         seconds)";
    }
    leaf seconds-since-packet-received {
      type uint32;
      units "second";
      description
        "Time elapsed since packet received (in Seconds)";
    }
    leaf seconds-since-packet-sent {
      type uint32;
      units "second";
      description
        "Time elapsed since packet sent (in Seconds)";
    }
  }

  grouping IM-CMD-IF-STATS {
    description
      "IM CMD IF STATS";
    container full-interface-stats {
      when "../stats-type = 'full'" {
        description
          "../StatsType = 'Full'";
      }
      description
        "Packet, byte and all error counters";
      uses IFSTATSBAG-GENERIC;
    }
    container basic-interface-stats {
      when "../stats-type = 'basic'" {
        description
          "../StatsType = 'Basic'";
      }
      description
        "Packet, byte and selected error counters";
      uses IFSTATSBAG-BASIC;
    }
    leaf stats-type {
      type Im-cmd-stats-enum;
      description
        "StatsType";
    }
  }

  grouping STATSDBAG-DATARATE {
    description
      "Datarate information";
    leaf input-data-rate {
      type uint64;
      units "bit/s";
      description
        "Input data rate in 1000's of bps";
    }
    leaf input-packet-rate {
      type uint64;
      units "packet/s";
      description
        "Input packets per second";
    }
    leaf output-data-rate {
      type uint64;
      units "bit/s";
      description
        "Output data rate in 1000's of bps";
    }
    leaf output-packet-rate {
      type uint64;
      units "packet/s";
      description
        "Output packets per second";
    }
    leaf peak-input-data-rate {
      type uint64;
      description
        "Peak input data rate, highest spike since last
         clear counters";
    }
    leaf peak-input-packet-rate {
      type uint64;
      description
        "Peak input packet rate, highest spike since last
         clear counters";
    }
    leaf peak-output-data-rate {
      type uint64;
      description
        "Peak output data rate, highest spike since last
         clear counters";
    }
    leaf peak-output-packet-rate {
      type uint64;
      description
        "Peak output packet rate, highest spike since
         last clear counters";
    }
    leaf bandwidth {
      type uint32;
      units "kbit/s";
      description
        "Bandwidth (in kbps)";
    }
    leaf load-interval {
      type uint32;
      description
        "Number of 30-sec intervals less one";
    }
    leaf output-load {
      type uint8;
      description
        "Output load as fraction of 255";
    }
    leaf input-load {
      type uint8;
      description
        "Input load as fraction of 255";
    }
    leaf reliability {
      type uint8;
      description
        "Reliability coefficient";
    }
  }

  grouping IM-CMD-GCC-PER-PORT-INFO {
    description
      "GCC";
    leaf derived-mode {
      type Gcc-der-state;
      description
        "Derived State";
    }
    leaf sec-state {
      type Gcc-sec-state;
      description
        "Sec State ";
    }
  }

  grouping CEM-INTERFACE {
    description
      "CEM interface information";
    leaf timeslots {
      type string;
      description
        "Timeslots separated by : or - from 1 to 32. :
         indicates individual timeslot and - represents a
         range. E.g. 1-3:5 represents timeslots 1, 2, 3,
         and 5.";
    }
    leaf payload {
      type uint16;
      units "byte";
      description
        "Payload size in bytes configured on CEM
         interface";
    }
    leaf dejitter-buffer {
      type uint16;
      units "millisecond";
      description
        "Dejitter buffer length configuredin milliseconds";
    }
    leaf framing {
      type int32;
      description
        " If framing is TRUE then the CEM  interface is
         structure aware ; otherwise it is structure
         agnostic";
    }
  }

  grouping PWHE-ETHER-INTERFACE-INFO {
    description
      "PWHE ETHER INTERFACE INFO";
    leaf interface-list-name {
      type string;
      description
        "Interface list Name";
    }
    leaf l2-overhead {
      type uint32;
      description
        "L2 Overhead";
    }
    leaf internal-label {
      type uint32;
      description
        "Internal Label";
    }
  }

  grouping PFI-IP-ADDR-UNION {
    description
      "PFI IP ADDR UNION";
    leaf afi {
      type Tunl-pfi-af-id;
      description
        "AFI";
    }
    leaf ipv4 {
      when "../afi = 'tunl-pfi-af-id-ipv4'" {
        description
          "../AFI = 'TUNL_PFI_AF_ID_IPV4'";
      }
      type Tunl-pfi-in-addr;
      description
        "IPv4 address type";
    }
    leaf ipv6 {
      when "../afi = 'tunl-pfi-af-id-ipv6'" {
        description
          "../AFI = 'TUNL_PFI_AF_ID_IPV6'";
      }
      type Tunl-pfi-in6-addr;
      description
        "IPv6 address type";
    }
  }

  grouping IM-CMD-TUNL-GRE-INFO {
    description
      "Tunnel info ";
    container source-ip-address {
      description
        "Tunnel source IP address";
      uses PFI-IP-ADDR-UNION;
    }
    container destination-ip-address {
      description
        "Tunnel destination IP address";
      uses PFI-IP-ADDR-UNION;
    }
    leaf source-name {
      type string;
      description
        "Tunnel source name";
    }
    leaf destination-ip-address-length {
      type uint8;
      description
        "Tunnel destination IP address length";
    }
    leaf tunnel-tos {
      type uint32;
      description
        "GRE tunnel TOS";
    }
    leaf tunnel-ttl {
      type uint32;
      description
        "GRE tunnel TTL";
    }
    leaf key {
      type uint32;
      description
        "Key value for GRE Packet";
    }
    leaf keepalive-period {
      type uint16;
      units "second";
      description
        "Keepalive period in seconds";
    }
    leaf keepalive-maximum-retry {
      type uint8;
      description
        "Keepalive retry";
    }
    leaf tunnel-mode {
      type Tunnel-gre-mode;
      description
        "Tunnel GRE Mode";
    }
    leaf tunnel-mode-direction {
      type Tunl-ip-mode-dir;
      description
        "Tunnel Mode Direction";
    }
    leaf keepalive-state {
      type Tunnel-ka-df-state;
      description
        "Keepalive State";
    }
    leaf df-bit-state {
      type Tunnel-ka-df-state;
      description
        "DF Bit State";
    }
    leaf key-bit-state {
      type Tunnel-key-state;
      description
        "Key Config State";
    }
  }

  grouping IM-SONET-POS-INFO-INTERFACE {
    description
      "SONET POS interface information";
    leaf aps-state {
      type Sonet-aps-et;
      description
        "APS state";
    }
  }

  grouping SERIAL-INTERFACE {
    description
      "Serial interface information";
    leaf timeslots {
      type string;
      description
        "Timeslots separated by : or - from 1 to 31. :
         indicates individual timeslot and - represents a
         range. E.g. 1-3:5 represents timeslots 1, 2, 3,
         and 5.";
    }
  }

  grouping BM-MAC-ADDR-ST {
    description
      "Data on MAC address allocation";
    leaf address {
      type yang:mac-address;
      description
        "MAC address";
    }
  }

  grouping BM-MBR-STATE-REASON-DATA-TYPE {
    description
      "Additional member state reason data";
    leaf reason-type {
      type Bm-state-reason-target;
      description
        "The item the reason applies to";
    }
    leaf severity {
      type Bm-severity;
      description
        "The severity of the reason";
    }
  }

  grouping BM-MUX-DATA {
    description
      "bm mux information";
    container member-mux-state-reason-data {
      description
        "Data regarding the reason for last Mux state
         change";
      uses BM-MBR-STATE-REASON-DATA-TYPE;
    }
    leaf mux-state {
      type Bm-muxstate;
      description
        "Current state of this bundle member";
    }
    leaf error {
      type uint32;
      description
        "Internal value indicating if an error occurred
         trying to put a link into the desired state";
    }
    leaf member-mux-state-reason {
      type Bm-mbr-state-reason;
      description
        "Reason for last Mux state change";
    }
    leaf member-state {
      type Bmd-member-state;
      description
        "Current internal state of this bundle member";
    }
    leaf mux-state-reason {
      type Bm-muxreason;
      description
        "Reason for last Mux state change (Deprecated)";
    }
  }

  grouping BM-LACP-LINK-DATA {
    description
      "Link properties for a port using LACP ";
    leaf interface-handle {
      type xr:Interface-name;
      description
        "Member's interface handle";
    }
    leaf actor-system-priority {
      type uint16;
      description
        "System priority of actor system";
    }
    leaf actor-system-mac-address {
      type yang:mac-address;
      description
        "MAC Address of the actor system";
    }
    leaf actor-operational-key {
      type uint16;
      description
        "Operational key for this port";
    }
    leaf partner-system-priority {
      type uint16;
      description
        "System priority of partner system";
    }
    leaf partner-system-mac-address {
      type yang:mac-address;
      description
        "MAC Address used to identify the partner system";
    }
    leaf partner-operational-key {
      type uint16;
      description
        "Operational key for partner port";
    }
    leaf selected-aggregator-id {
      type uint32;
      description
        "MIB ifindex of selected bundle";
    }
    leaf attached-aggregator-id {
      type uint32;
      description
        "MIB ifindex of attached bundle";
    }
    leaf actor-port-id {
      type uint16;
      description
        "Port number of this port";
    }
    leaf actor-port-priority {
      type uint16;
      description
        "Priority of this port";
    }
    leaf partner-port-id {
      type uint16;
      description
        "Port number of the partner's port";
    }
    leaf partner-port-priority {
      type uint16;
      description
        "Priority of the partner's port";
    }
    leaf actor-port-state {
      type uint8;
      description
        "LACP state of this port";
    }
    leaf partner-port-state {
      type uint8;
      description
        "LACP state of the partner's port";
    }
  }

  grouping BM-LACP-COUNTERS {
    description
      "Statistics for a port using using LACP";
    leaf lacpd-us-received {
      type uint32;
      description
        "LACPDUs received";
    }
    leaf lacpd-us-transmitted {
      type uint32;
      description
        "LACPDUs transmitted";
    }
    leaf marker-packets-received {
      type uint32;
      description
        "LACP Marker packets received";
    }
    leaf marker-responses-transmitted {
      type uint32;
      description
        "LACP Marker response packets transmitted";
    }
    leaf illegal-packets-received {
      type uint32;
      description
        "Illegal and unknown packets received";
    }
    leaf excess-lacpd-us-received {
      type uint32;
      description
        "LACPDUs received that exceed the rate limit";
    }
    leaf excess-marker-packets-received {
      type uint32;
      description
        "Marker packets received that exceed the rate
         limit";
    }
    leaf defaulted {
      type uint32;
      description
        "State flag set to Defaulted";
    }
    leaf expired {
      type uint32;
      description
        "State flag set to Expired";
    }
    leaf last-cleared-sec {
      type uint32;
      description
        "Last time counters cleared (s) (deprecated)";
    }
    leaf last-cleared-nsec {
      type uint32;
      description
        "Last time counters cleared (nsec) (deprecated)";
    }
  }

  grouping BM-MEMBER-DATA {
    description
      "Bundle member data for any member";
    container counters {
      description
        "Counters data about member link";
      uses BM-LACP-COUNTERS;
    }
    container link-data {
      description
        "Lacp data about member link";
      uses BM-LACP-LINK-DATA;
    }
    container member-mux-data {
      description
        "Mux state machine data";
      uses BM-MUX-DATA;
    }
    container mac-address {
      description
        "MAC address of this member (deprecated)";
      uses BM-MAC-ADDR-ST;
    }
    leaf interface-name {
      type xr:Interface-name;
      description
        "Member's interface name";
      xr:event-telemetry "Subscribe Telemetry Event";
    }
    leaf port-priority {
      type uint16;
      description
        "The priority of this member";
    }
    leaf port-number {
      type uint16;
      description
        "Member's link number";
    }
    leaf underlying-link-id {
      type uint16;
      description
        "Member's underlying link ID";
    }
    leaf link-order-number {
      type uint16;
      description
        "Member's link order number";
    }
    leaf iccp-node {
      type uint32;
      description
        "Location of member";
    }
    leaf bandwidth {
      type uint32;
      units "kbit/s";
      description
        "Bandwidth of this member (kbps)";
    }
    leaf lacp-enabled {
      type string;
      description
        "Boolean indicating LACP enabled or not";
    }
    leaf member-type {
      type Bmd-member-type-enum;
      description
        "Member's type (local/foreign)";
    }
    leaf member-name {
      type string;
      description
        "Member's (short form) name";
    }
    leaf replication-error {
      type uint32;
      description
        "Error from final replication attempt";
    }
  }

  grouping IM-CMD-BUNDLE-INFO {
    description
      "IM CMD BUNDLE INFO";
    list member {
      description
        "List of bundle members and their properties";
      uses BM-MEMBER-DATA;
    }
  }

  grouping IM-CMD-TUNNEL-INFO {
    description
      "IM CMD TUNNEL INFO";
    leaf source-name {
      type string;
      description
        "Tunnel source name";
    }
    leaf source-ipv4-address {
      type inet:ipv4-address;
      description
        "Tunnel source IP address";
    }
    leaf destination-ipv4-address {
      type inet:ipv4-address;
      description
        "Tunnel destination IP address";
    }
    leaf tunnel-type {
      type string;
      description
        "Tunnel protocol/transport";
    }
    leaf key {
      type uint32;
      description
        "GRE tunnel key";
    }
    leaf ttl {
      type uint32;
      description
        "GRE tunnel TTL";
    }
  }

  grouping IFSTATS-SRP-PER-SIDE-ERRORS {
    description
      "IFSTATS SRP PER SIDE ERRORS";
    leaf error-packets-received {
      type uint32;
      description
        "Error packets received";
    }
    leaf crc-errors {
      type uint32;
      description
        "Input CRC errors";
    }
    leaf input-insufficient-resource-events {
      type uint32;
      description
        "Input insufficient resources events";
    }
    leaf mac-aborts-received {
      type uint32;
      description
        "Aborts received at MAC/RAC";
    }
    leaf mac-runt-packets-received {
      type uint32;
      description
        "Too small packets received at MAC/RAC";
    }
    leaf mac-giant-packets-received {
      type uint32;
      description
        "Too large packets received at MAC/RAC";
    }
    leaf framer-runt-packets-received {
      type uint32;
      description
        "Too small packets received at framer";
    }
    leaf framer-giant-packets-received {
      type uint32;
      description
        "Too large packets received at framer";
    }
    leaf framer-aborts-received {
      type uint32;
      description
        "Aborts received at framer";
    }
  }

  grouping IFSTATS-SRP-PER-SIDE-DATA-RATE {
    description
      "IFSTATS SRP PER SIDE DATA RATE";
    leaf bit-rate-sent {
      type uint32;
      description
        "Sent bit rate";
    }
    leaf packet-rate-sent {
      type uint32;
      description
        "Sent packet rate";
    }
    leaf bit-rate-received {
      type uint32;
      description
        "Received bit rate";
    }
    leaf packet-rate-received {
      type uint32;
      description
        "Received packet rate";
    }
  }

  grouping IFSTATSBAG-SRP {
    description
      "SRP interface statistics";
    container side-a-data-rate {
      description
        "Data rates for side A interface";
      uses IFSTATS-SRP-PER-SIDE-DATA-RATE;
    }
    container side-b-data-rate {
      description
        "Data rates for side B interface";
      uses IFSTATS-SRP-PER-SIDE-DATA-RATE;
    }
    container side-a-errors {
      description
        "Errors for side A interface";
      uses IFSTATS-SRP-PER-SIDE-ERRORS;
    }
    container side-b-errors {
      description
        "Errors for side B interface";
      uses IFSTATS-SRP-PER-SIDE-ERRORS;
    }
    leaf data-rate-interval {
      type uint32;
      units "second";
      description
        "Data rate interval (5 mins or 30 seconds)";
    }
  }

  grouping SRP-RATE-LIMIT-DETAIL {
    description
      "Detailed SRP rate limit information";
    leaf min-priority-value {
      type uint16;
      description
        "Minimum SRP priority for high-priority transmit
         queue";
    }
  }

  grouping SRP-RATE-LIMIT-INFO {
    description
      "SRP rate limit information";
    leaf is-admin-down {
      type int32;
      description
        "Is the interfaceadministratively down";
    }
    list rate-limit-detailed-info {
      description
        "SRP rate limit information";
      uses SRP-RATE-LIMIT-DETAIL;
    }
  }

  grouping SRR-NODE-DATA {
    description
      "SRR NODE DATA";
    leaf node-name {
      type string;
      description
        "Node name";
    }
    leaf srr-entry-exits {
      type int32;
      description
        "Does the SRR information exist for this node";
    }
    leaf mac-address {
      type string;
      description
        "node mac address";
    }
    leaf outer-failure {
      type Srp-mgmt-srr-failure;
      description
        "Outer failure";
    }
    leaf inner-failure {
      type Srp-mgmt-srr-failure;
      description
        "Inner failure";
    }
    leaf is-last-announce-received {
      type int32;
      description
        "Announce last received ?";
    }
    leaf last-announce-received-time {
      type uint32;
      description
        "Announce last received";
    }
  }

  grouping SRP-SRR-DETAIL {
    description
      "SRP SRR DETAIL";
    leaf version-number {
      type uint32;
      description
        "Version number";
    }
    leaf is-wrong-version-received {
      type int32;
      description
        "Wrong version recieved";
    }
    leaf last-wrong-version-receive-time {
      type uint32;
      description
        "Time that last wrong version message recieved";
    }
    leaf mac-address {
      type string;
      description
        "SRR node mac address";
    }
    leaf node-state {
      type Srp-mgmt-srr-node-state;
      description
        "SRR node state";
    }
    leaf is-outer-ring-in-use {
      type int32;
      description
        "Is the outer ring in use";
    }
    leaf is-inner-ring-in-use {
      type int32;
      description
        " Is the inner ring in use";
    }
    leaf is-announce {
      type int32;
      description
        "Is announcing enabled";
    }
    leaf outer-fail-type {
      type Srp-mgmt-srr-failure;
      description
        "Outer fail type";
    }
    leaf inner-fail-type {
      type Srp-mgmt-srr-failure;
      description
        "Inner fail type";
    }
    leaf packet-send-timer {
      type uint32;
      units "second";
      description
        "SRR packet send timer interval in seconds";
    }
    leaf next-srr-packet-send-time {
      type uint32;
      units "second";
      description
        "Time remaining in seconds to next SRR packet
         send";
    }
    leaf single-ring-bw {
      type uint32;
      units "Mbit/s";
      description
        "Single ring bandwidth Mbps";
    }
    leaf wtr-time {
      type uint32;
      units "second";
      description
        "SRR Wait To Restore interval delay in seconds";
    }
    leaf wtr-timer-remaining-outer-ring {
      type uint32;
      units "second";
      description
        "Time remaining in seconds until next outer ring
         wrap removal";
    }
    leaf wtr-timer-remaining-inner-ring {
      type uint32;
      units "second";
      description
        "Time remaining in seconds until next inner ring
         wrap removal";
    }
    list nodes-on-ring {
      description
        "List of nodes on the ring info";
      uses SRR-NODE-DATA;
    }
    list nodes-not-on-ring {
      description
        "nodes not in topology map";
      uses SRR-NODE-DATA;
    }
  }

  grouping SRP-SRR-INFO {
    description
      "SRP SRR INFO";
    leaf is-admin-down {
      type int32;
      description
        "Is the interfaceadministratively down";
    }
    leaf is-srr-enabled {
      type int32;
      description
        "SRR enabled";
    }
    list srr-detailed-info {
      description
        "SRP information";
      uses SRP-SRR-DETAIL;
    }
  }

  grouping SRP-TOPOLOGY-NODE-DATA {
    description
      "SRP TOPOLOGY NODE DATA";
    leaf hop-count {
      type uint16;
      description
        "Outer-ring hops to reach this node";
    }
    leaf mac-address {
      type string;
      description
        "MAC address";
    }
    leaf ipv4-address {
      type inet:ipv4-address;
      description
        "IPv4 address";
    }
    leaf is-wrapped {
      type int32;
      description
        "Wrap state";
    }
    leaf is-srr-supported {
      type int32;
      description
        "SRR protocol supported";
    }
    leaf node-name {
      type string;
      description
        "Node name";
    }
  }

  grouping SRP-TOPOLOGY-MAP {
    description
      "SRP TOPOLOGY MAP";
    leaf topology-timer {
      type uint32;
      description
        "How often a topology pkt is sent";
    }
    leaf next-topology-packet-delay {
      type uint32;
      description
        "Time remaining until next topo pkt sent";
    }
    leaf time-since-last-topology-packet-received {
      type uint32;
      description
        "Time since last topo pkt was received";
    }
    leaf time-since-last-topology-change {
      type uint32;
      description
        "Time since last topology change";
    }
    leaf number-of-nodes-on-ring {
      type uint16;
      description
        "Number of nodes on ring";
    }
    list ring-node {
      description
        "List of nodes on the ring info";
      uses SRP-TOPOLOGY-NODE-DATA;
    }
  }

  grouping SRP-TOPOLOGY-INFO {
    description
      "SRP TOPOLOGY INFO";
    leaf is-admin-down {
      type int32;
      description
        "Is the interfaceadministratively down";
    }
    list local-information {
      description
        "Detailed SRP topology information";
      uses SRP-TOPOLOGY-MAP;
    }
  }

  grouping SRP-FAILURE-INFO {
    description
      "SRP failure info";
    leaf type {
      type Srp-mgmt-failure-et;
      description
        "Failure type";
    }
    leaf reported-state {
      type Srp-mgmt-failure-state-et;
      description
        "Reported state";
    }
    leaf debounced-state {
      type Srp-mgmt-failure-state-et;
      description
        "Debounced state";
    }
    leaf current-state {
      type Srp-mgmt-failure-state-et;
      description
        "Current state";
    }
    leaf stable-time {
      type uint64;
      description
        "Stable time";
    }
    leaf debounced-delay {
      type uint32;
      description
        "Debounce delay";
    }
  }

  grouping SRP-IPS-SIDE-DETAIL {
    description
      "SRP IPS SIDE DETAIL";
    leaf mac-address {
      type string;
      description
        "MAC address";
    }
    leaf wrap-state {
      type Srp-mgmt-ips-wrap-state;
      description
        "Wrap state";
    }
    leaf packet-sent-timer {
      type uint32;
      units "second";
      description
        "SRP IPS packet send interval in seconds";
    }
    leaf send-timer-time-remaining {
      type uint32;
      units "second";
      description
        "Time in seconds remaining until next send of an
         IPS request";
    }
    leaf wtr-timer-remaining {
      type uint32;
      units "second";
      description
        "Time in seconds until wrap removal";
    }
    leaf self-detected-request {
      type Srp-mgmt-ips-req;
      description
        "Self Detected Requests";
    }
    leaf remote-request {
      type Srp-mgmt-ips-req;
      description
        "Remote Requests";
    }
    leaf rx-neighbor-mac-address {
      type string;
      description
        "Neighbour mac address for received message";
    }
    leaf rx-message-type {
      type Srp-mgmt-ips-req;
      description
        "Type of message received";
    }
    leaf rx-path-type {
      type Srp-mgmt-ips-path-ind;
      description
        "Short/long path for received message";
    }
    leaf rx-ttl {
      type uint32;
      description
        "Time to live for received message";
    }
    leaf rx-packet-test {
      type int32;
      description
        "Test for existence of an RX packet";
    }
    leaf tx-neighbor-mac-address {
      type string;
      description
        "Mac address of node receiving TXed messages";
    }
    leaf tx-message-type {
      type Srp-mgmt-ips-req;
      description
        "Type of message transmitted";
    }
    leaf tx-path-type {
      type Srp-mgmt-ips-path-ind;
      description
        "Short/long path of transmitted message";
    }
    leaf tx-ttl {
      type uint32;
      description
        "Time to live for transmitted message";
    }
    leaf tx-packet-test {
      type int32;
      description
        "Test for existence of a TX packet";
    }
    leaf delay-keep-alive-trigger {
      type uint32;
      units "millisecond";
      description
        "Number of milliseconds to wait after an L1
         failure is detected before triggering an L2 wrap";
    }
    list asserted-failure {
      description
        "Failures presently asserted";
      uses SRP-FAILURE-INFO;
    }
  }

  grouping SRP-IPS-DETAIL {
    description
      "SRP IPS DETAIL";
    container side-a {
      description
        "Side A IPS details";
      uses SRP-IPS-SIDE-DETAIL;
    }
    container side-b {
      description
        "Side B IPS details";
      uses SRP-IPS-SIDE-DETAIL;
    }
    leaf mac-address {
      type string;
      description
        "MAC address for node";
    }
    leaf is-inter-card-bus-enabled {
      type int32;
      description
        "Inter card bus enabled";
    }
    leaf wtr-timer-period {
      type uint32;
      units "second";
      description
        "IPS Wait To Restore period in seconds";
    }
  }

  grouping SRP-IPS-INFO {
    description
      "SRP IPS INFO";
    leaf is-admin-down {
      type int32;
      description
        "Is the interfaceadministratively down";
    }
    list local-information {
      description
        "IPS information";
      uses SRP-IPS-DETAIL;
    }
  }

  grouping SRP-ALL-INFO {
    description
      "Complete SRP information";
    container ips-info {
      description
        "SRP IPS information";
      uses SRP-IPS-INFO;
    }
    container topology-info {
      description
        "SRP topology information";
      uses SRP-TOPOLOGY-INFO;
    }
    container srr-info {
      description
        "SRP SRR information";
      uses SRP-SRR-INFO;
    }
    container rate-limit-info {
      description
        "SRP rate limit information";
      uses SRP-RATE-LIMIT-INFO;
    }
  }

  grouping IM-CMD-SRP-INFO {
    description
      "IM CMD SRP INFO";
    container srp-information {
      description
        "SRP-specific data";
      uses SRP-ALL-INFO;
    }
    container srp-statistics {
      description
        "SRP-specific packet and byte counters";
      uses IFSTATSBAG-SRP;
    }
  }

  grouping IM-CMD-INTF-TYPE-INFO {
    description
      "Interface-specific information";
    container srp-information {
      when "../interface-type-info = 'srp'" {
        description
          "../InterfaceTypeInfo = 'SRP'";
      }
      description
        "SRP interface information";
      uses IM-CMD-SRP-INFO;
    }
    container tunnel-information {
      when "../interface-type-info = 'tunnel'" {
        description
          "../InterfaceTypeInfo = 'Tunnel'";
      }
      description
        "Tunnel interface information";
      uses IM-CMD-TUNNEL-INFO;
    }
    container bundle-information {
      when "../interface-type-info = 'bundle'" {
        description
          "../InterfaceTypeInfo = 'Bundle'";
      }
      description
        "Bundle interface information";
      uses IM-CMD-BUNDLE-INFO;
    }
    container serial-information {
      when "../interface-type-info = 'serial'" {
        description
          "../InterfaceTypeInfo = 'Serial'";
      }
      description
        "Serial interface information";
      uses SERIAL-INTERFACE;
    }
    container sonet-pos-information {
      when "../interface-type-info = 'sonet-pos'" {
        description
          "../InterfaceTypeInfo = 'SonetPOS'";
      }
      description
        "SONET POS interface information";
      uses IM-SONET-POS-INFO-INTERFACE;
    }
    container tunnel-gre-information {
      when "../interface-type-info = 'tunnel-gre'" {
        description
          "../InterfaceTypeInfo = 'TunnelGRE'";
      }
      description
        "Tunnel GRE interface information";
      uses IM-CMD-TUNL-GRE-INFO;
    }
    container pseudowire-head-end-information {
      when "../interface-type-info = 'pseudowire-head-end'" {
        description
          "../InterfaceTypeInfo = 'PseudowireHeadEnd'";
      }
      description
        "PseudowireHeadEnd interface information";
      uses PWHE-ETHER-INTERFACE-INFO;
    }
    container cem-information {
      when "../interface-type-info = 'cem'" {
        description
          "../InterfaceTypeInfo = 'CEM'";
      }
      description
        "Cem interface information";
      uses CEM-INTERFACE;
    }
    container gcc-information {
      when "../interface-type-info = 'gcc'" {
        description
          "../InterfaceTypeInfo = 'GCC'";
      }
      description
        "GCC interface information";
      uses IM-CMD-GCC-PER-PORT-INFO;
    }
    leaf interface-type-info {
      type Im-cmd-intf-type-enum;
      description
        "InterfaceTypeInfo";
    }
  }

  grouping PPP-SHOW-INT-NCP-INFO {
    description
      "NCP state information";
    leaf ncp-state {
      type Ppp-fsm-state;
      description
        "NCP state value";
    }
    leaf ncp-identifier {
      type Ncp-ident;
      description
        "NCP state identifier";
    }
  }

  grouping PPP-SHOW-INT-INFO {
    description
      "PPP state information";
    leaf lcp-state {
      type Ppp-fsm-state;
      description
        "LCP State";
    }
    leaf is-loopback-detected {
      type int32;
      description
        "Loopback detected";
    }
    leaf keepalive-period {
      type uint32;
      description
        "Keepalive value";
    }
    leaf is-mp-bundle-member {
      type int32;
      description
        "MP Bundle Member";
    }
    leaf is-multilink-open {
      type int32;
      description
        "Is Multilink Open";
    }
    list ncp-info-array {
      description
        "Array of per-NCP data";
      uses PPP-SHOW-INT-NCP-INFO;
    }
  }

  grouping VLAN-SWITCHED-INFO {
    description
      "VLAN-Switched information";
    container trunk-vlan-ranges {
      description
        "VLAN-Switched Trunk VLAN ranges";
      uses EFP-DESCRIPTION;
    }
    leaf mode {
      type Vlan-switched-mode;
      description
        "VLAN-Switched mode";
    }
    leaf access-vlan {
      type Vlan-tag-value;
      description
        "VLAN-Switched Access VLAN";
    }
  }

  grouping EFP-TAG-LOCAL-TRAFFIC-STACK {
    description
      "EFP TAG LOCAL TRAFFIC STACK";
    list local-traffic-tag {
      description
        "VLAN tags for locally-sourced traffic";
      uses EFP-VLAN-TAG;
    }
  }

  grouping EFP-VLAN-TAG {
    description
      "EFP VLAN TAG";
    leaf ethertype {
      type Efp-tag-etype;
      description
        "Ethertype of tag";
    }
    leaf vlan-id {
      type Vlan-tag-value;
      description
        "VLAN Id";
    }
  }

  grouping EFP-RANGE-TYPE {
    description
      "EFP RANGE TYPE";
    leaf vlan-id-low {
      type Vlan-tag-value;
      description
        "VLAN ID Low";
    }
    leaf vlan-id-high {
      type Vlan-tag-value;
      description
        "VLAN ID High";
    }
  }

  grouping EFP-TAG-MATCH {
    description
      "EFP TAG MATCH";
    leaf ethertype {
      type Efp-tag-etype;
      description
        "Ethertype of tag to match";
    }
    leaf priority {
      type Efp-tag-priority;
      description
        "Priority to match";
    }
    list vlan-range {
      description
        "VLAN Ids to match";
      uses EFP-RANGE-TYPE;
    }
  }

  grouping EFP-DESCRIPTION {
    description
      "EFP DESCRIPTION";
    container local-traffic-stack {
      description
        "VLAN tags for locally-sourced traffic";
      uses EFP-TAG-LOCAL-TRAFFIC-STACK;
    }
    leaf payload-ethertype {
      type Efp-payload-etype;
      description
        "Payload Ethertype to match";
    }
    leaf tags-popped {
      type uint16;
      description
        "Number of tags popped on ingress";
    }
    leaf is-exact-match {
      type int32;
      description
        "Whether the packet must match the encapsulation
         exactly, with no further inner tags";
    }
    leaf is-native-vlan {
      type int32;
      description
        "Whether this represents the native VLAN on the
         port";
    }
    leaf is-native-preserving {
      type int32;
      description
        "Whether the native VLAN is customer-tag
         preserving";
    }
    leaf source-mac-match {
      type Mac-address;
      description
        "The source MAC address to match on ingress";
    }
    leaf destination-mac-match {
      type Mac-address;
      description
        "The destination MAC address to match on ingress";
    }
    list tags-to-match {
      description
        "Tags to match on ingress packets";
      uses EFP-TAG-MATCH;
    }
    list pushe {
      description
        "VLAN tags pushed on egress";
      uses EFP-VLAN-TAG;
    }
  }

  grouping VLAN-DOUBLE-TAG-STACK {
    description
      "VLAN double tag stack";
    leaf outer-tag {
      type Vlan-tag-value;
      description
        "Outer tag value";
    }
    leaf second-tag {
      type Vlan-tag-value;
      description
        "Second tag value";
    }
  }

  grouping VLAN-TAG-STACK-TYPE {
    description
      "VLAN encapsulation and tag stack";
    container stack {
      when "../vlan-encapsulation = 'qinq'" {
        description
          "../VLANEncapsulation = 'QinQ'";
      }
      description
        "Stack value";
      uses VLAN-DOUBLE-TAG-STACK;
    }
    container service-instance-details {
      when "../vlan-encapsulation = 'service-instance'" {
        description
          "../VLANEncapsulation = 'ServiceInstance'";
      }
      description
        "Service Instance encapsulation";
      uses EFP-DESCRIPTION;
    }
    container dot1ad-dot1q-stack {
      when "../vlan-encapsulation = 'dot1ad-dot1q'" {
        description
          "../VLANEncapsulation = 'Dot1adDot1Q'";
      }
      description
        "802.1ad 802.1Q stack value";
      uses VLAN-DOUBLE-TAG-STACK;
    }
    leaf vlan-encapsulation {
      type Vlan-encaps;
      description
        "VLANEncapsulation";
    }
    leaf tag {
      when "../vlan-encapsulation = 'dot1q'" {
        description
          "../VLANEncapsulation = 'Dot1Q'";
      }
      type Vlan-tag-value;
      description
        "Tag value";
    }
    leaf outer-tag {
      when "../vlan-encapsulation = 'qin-any'" {
        description
          "../VLANEncapsulation = 'QinAny'";
      }
      type Vlan-tag-value;
      description
        "Outer tag value";
    }
    leaf native-tag {
      when "../vlan-encapsulation = 'dot1q-native'" {
        description
          "../VLANEncapsulation = 'Dot1QNative'";
      }
      type Vlan-tag-value;
      description
        "Native tag value";
    }
    leaf dot1ad-tag {
      when "../vlan-encapsulation = 'dot1ad'" {
        description
          "../VLANEncapsulation = 'Dot1ad'";
      }
      type Vlan-tag-value;
      description
        "802.1ad tag value";
    }
    leaf dot1ad-native-tag {
      when "../vlan-encapsulation = 'dot1ad-native'" {
        description
          "../VLANEncapsulation = 'Dot1adNative'";
      }
      type Vlan-tag-value;
      description
        "802.1ad native tag value";
    }
    leaf dot1ad-outer-tag {
      when "../vlan-encapsulation = 'dot1ad-any'" {
        description
          "../VLANEncapsulation = 'Dot1adAny'";
      }
      type Vlan-tag-value;
      description
        "802.1ad Outer tag value";
    }
  }

  grouping VLAN-INTF-GENERIC {
    description
      "VLAN INTF GENERIC";
    container encapsulation-details {
      description
        "Encapsulation type and tag stack";
      uses VLAN-TAG-STACK-TYPE;
    }
    container vlan-switched {
      description
        "VLAN-Switched information";
      uses VLAN-SWITCHED-INFO;
    }
  }

  grouping IM-CMD-FR-INFO {
    description
      "IM CMD FR INFO";
    leaf fr-encapsulation-type {
      type Im-cmd-fr-type-enum;
      description
        "Frame Relay encapsulation type";
    }
    leaf lmi-type {
      type Im-cmd-lmi-type-enum;
      description
        "The LMI type: Autosense, ANSI, CCITT or CISCO";
    }
    leaf lmidlci {
      type uint32;
      description
        "LMI DLCI";
    }
    leaf is-nni {
      type boolean;
      description
        "The NNI LMI interface type";
    }
    leaf is-dte {
      type boolean;
      description
        "The DTE/DCE LMI interface type";
    }
    leaf is-lmi-up {
      type boolean;
      description
        "Flag indicating whether the LMI  DTE/DCE/NNI-DTE
         state is UP";
    }
    leaf is-lmi-nni-dce-up {
      type boolean;
      description
        "Flag indicating whether the LMI  NNI-DCE state
         is UP";
    }
    leaf is-lmi-enabled {
      type boolean;
      description
        "The status of FR LMI for an interface";
    }
    leaf enquiries-received {
      type uint32;
      description
        "Number of enquiry messages received";
    }
    leaf enquiries-sent {
      type uint32;
      description
        "Number of enquiry messages sent";
    }
    leaf status-received {
      type uint32;
      description
        "Number of status messages received";
    }
    leaf status-sent {
      type uint32;
      description
        "Number of status messages sent";
    }
    leaf update-status-received {
      type uint32;
      description
        "Number of update status messages received";
    }
    leaf update-status-sent {
      type uint32;
      description
        "Number of update status messages sent";
    }
  }

  grouping IM-CMD-ENCAPS-INFO {
    description
      "Encapsulation-specific information";
    container frame-relay-information {
      when "../encapsulation-type = 'frame-relay'" {
        description
          "../EncapsulationType = 'FrameRelay'";
      }
      description
        "Frame Relay information";
      uses IM-CMD-FR-INFO;
    }
    container dot1q-information {
      when "../encapsulation-type = 'vlan'" {
        description
          "../EncapsulationType = 'VLAN'";
      }
      description
        "VLAN 802.1q information";
      uses VLAN-INTF-GENERIC;
    }
    container ppp-information {
      when "../encapsulation-type = 'ppp'" {
        description
          "../EncapsulationType = 'PPP'";
      }
      description
        "PPP information";
      uses PPP-SHOW-INT-INFO;
    }
    leaf encapsulation-type {
      type Im-cmd-encaps-enum;
      description
        "EncapsulationType";
    }
  }

  grouping IM-CMD-IP-INFO-ST {
    description
      "IP information";
    leaf ip-address {
      type inet:ipv4-address;
      description
        "Interface IPv4 address";
      xr:event-telemetry "Subscribe Telemetry Event";
    }
    leaf subnet-mask-length {
      type uint32;
      description
        "Interface subnet mask length";
      xr:event-telemetry "Subscribe Telemetry Event";
    }
  }

  grouping IM-CMD-ARP-INFO-ST {
    description
      "ARP information";
    leaf arp-timeout {
      type uint32;
      units "second";
      description
        "ARP timeout in seconds. Only valid if
         'ARPIsLearningDisabled' is 'false'";
    }
    leaf arp-type-name {
      type string;
      description
        "ARP type name";
    }
    leaf arp-is-learning-disabled {
      type boolean;
      description
        "Whether the interface has dynamic learning
         disabled";
    }
  }

  grouping IM-CMD-CARRIER-DELAY-ST {
    description
      "Carrier Delay Information";
    leaf carrier-delay-up {
      type uint32;
      description
        "Carrier delay on state up (ms)";
    }
    leaf carrier-delay-down {
      type uint32;
      description
        "Carrier delay on state down (ms)";
    }
  }

  grouping IM-CMD-MAC-ADDR-ST {
    description
      "Mac Address";
    leaf address {
      type yang:mac-address;
      description
        "MAC Address";
      xr:event-telemetry "Subscribe Telemetry Event";
    }
  }

  grouping IM-CMD-DAMP-ST {
    description
      "Dampening information";
    leaf penalty {
      type uint32;
      description
        "Dampening penalty of the interface";
    }
    leaf is-suppressed-enabled {
      type boolean;
      description
        "Flag showing if state is suppressed";
    }
    leaf seconds-remaining {
      type uint32;
      units "second";
      description
        "Remaining period of suppression in secs";
    }
    leaf half-life {
      type uint32;
      units "minute";
      description
        "Configured decay half life in mins";
    }
    leaf reuse-threshold {
      type uint32;
      description
        "Configured reuse threshold";
    }
    leaf suppress-threshold {
      type uint32;
      description
        "Value of suppress threshold";
    }
    leaf maximum-suppress-time {
      type uint32;
      units "minute";
      description
        "Maximum suppress time in mins";
    }
    leaf restart-penalty {
      type uint32;
      description
        "Configured restart penalty";
    }
  }

  grouping IM-CMD-INFO {
    description
      "Full interface information";
    container dampening-information {
      description
        "State dampening information of interface";
      uses IM-CMD-DAMP-ST;
    }
    container mac-address {
      description
        "Interface MAC address";
      uses IM-CMD-MAC-ADDR-ST;
    }
    container burned-in-address {
      description
        "Interface burned in address";
      uses IM-CMD-MAC-ADDR-ST;
    }
    container carrier-delay {
      description
        "Carrier Delay of the interface";
      uses IM-CMD-CARRIER-DELAY-ST;
    }
    container arp-information {
      description
        "Interface ARP type and timeout";
      uses IM-CMD-ARP-INFO-ST;
    }
    container ip-information {
      description
        "Interface IP address info";
      uses IM-CMD-IP-INFO-ST;
    }
    container encapsulation-information {
      description
        "Information specific to the encapsulation";
      uses IM-CMD-ENCAPS-INFO;
    }
    container interface-type-information {
      description
        "Information specific to the interface type";
      uses IM-CMD-INTF-TYPE-INFO;
    }
    container data-rates {
      description
        "Packet and byte rates";
      uses STATSDBAG-DATARATE;
    }
    container interface-statistics {
      description
        "Packet, byte and error counters";
      uses IM-CMD-IF-STATS;
    }
    container l2-interface-statistics {
      description
        "L2 Protocol Statistics";
      uses STATS-DATA;
    }
    leaf interface-handle {
      type string;
      description
        "Interface name";
    }
    leaf interface-type {
      type string;
      description
        "Type of Interface";
    }
    leaf hardware-type-string {
      type string {
        length "0..64";
      }
      description
        "Hardware type description string";
    }
    leaf state {
      type Im-state-enum;
      description
        "Interface state";
      xr:event-telemetry "Subscribe Telemetry Event";
    }
    leaf line-state {
      type Im-state-enum;
      description
        "Line protocol state";
      xr:event-telemetry "Subscribe Telemetry Event";
    }
    leaf encapsulation {
      type string;
      description
        "Interface encapsulation";
    }
    leaf encapsulation-type-string {
      type string {
        length "0..32";
      }
      description
        "Interface encapsulation description string";
    }
    leaf mtu {
      type uint32;
      units "byte";
      description
        "MTU in bytes";
      xr:event-telemetry "Subscribe Telemetry Event";
    }
    leaf is-l2-transport-enabled {
      type boolean;
      description
        "L2 transport flag";
    }
    leaf state-transition-count {
      type uint32;
      description
        "The number of times the state has changed";
    }
    leaf last-state-transition-time {
      type uint32;
      description
        "The time elasped after the last state transition";
    }
    leaf is-dampening-enabled {
      type boolean;
      description
        "Dampening enabled flag";
    }
    leaf speed {
      type uint32;
      description
        "Interface speed (Kb/s)";
    }
    leaf crc-length {
      type uint32;
      description
        "Cyclic Redundancy Check length";
    }
    leaf is-scramble-enabled {
      type boolean;
      description
        "Interface scramble config";
    }
    leaf duplexity {
      type Im-attr-duplex;
      description
        "Interface duplexity";
      xr:event-telemetry "Subscribe Telemetry Event";
    }
    leaf media-type {
      type Im-attr-media;
      description
        "Interface media type";
    }
    leaf link-type {
      type Im-attr-link;
      description
        "Interface link type";
    }
    leaf in-flow-control {
      type Im-attr-flow-control;
      description
        "Input flow control configuration";
    }
    leaf out-flow-control {
      type Im-attr-flow-control;
      description
        "Output flow control configuration";
    }
    leaf bandwidth {
      type uint32;
      description
        "Interface bandwidth (Kb/s)";
      xr:event-telemetry "Subscribe Telemetry Event";
    }
    leaf max-bandwidth {
      type uint32;
      description
        "Maximum Interface bandwidth (Kb/s)";
    }
    leaf keepalive {
      type uint32;
      description
        "Interface keepalive time (s)";
    }
    leaf is-l2-looped {
      type boolean;
      description
        "Loopback detected by layer 2";
    }
    leaf parent-interface-name {
      type xr:Interface-name;
      description
        "If handle of Parent interface";
    }
    leaf loopback-configuration {
      type Im-cmd-loopback-enum;
      description
        "Loopback configuration of Interface";
    }
    leaf description {
      type string;
      description
        "Interface description string";
    }
    leaf is-maintenance-enabled {
      type boolean;
      description
        "Maintenance embargo flag";
    }
    leaf is-data-inverted {
      type boolean;
      description
        "Data invert flag";
    }
    leaf transport-mode {
      type Im-attr-transport-mode;
      description
        "Interface transport mode";
    }
    leaf fast-shutdown {
      type boolean;
      description
        "Fast Shutdown flag";
    }
    leaf if-index {
      type uint32;
      description
        "This is not supposed to be used. It is a dummy
         attribute to support ifindex for OC model";
    }
    leaf is-intf-logical {
      type boolean;
      description
        "Flag to check if interface is logical or
         Physical";
    }
  }
}
