module Cisco-IOS-XR-cofo-infra-oper {
  namespace "http://cisco.com/ns/yang/Cisco-IOS-XR-cofo-infra-oper";
  prefix cofo-infra-oper;

  import Cisco-IOS-XR-types {
    prefix xr;
  }
  import cisco-semver {
    prefix semver;
  }
  include Cisco-IOS-XR-cofo-infra-oper-sub1 {
    revision-date 2019-04-05;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR cofo-infra package operational data.
     
     This module contains definitions
     for the following management objects:
       cofo: COFO operational data
     
     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  container cofo {
    config false;
    description
      "COFO operational data";
    container nodes {
      description
        "Node-specific COFO operational data";
      list node {
        key "node-name";
        description
          "COFO operational data for a particular node";
        container client-ids {
          description
            "COFO Client data";
          list client-id {
            key "id";
            description
              "COFO client id";
            leaf id {
              type uint32 {
                range "1..7";
              }
              description
                "Specific Client identifier";
            }
            uses COFO-CLIENT-DATA-BAG;
          }
        }
        container topic-ids {
          description
            "COFO SDR database";
          list topic-id {
            key "id";
            description
              "COFO topic id";
            leaf id {
              type uint32 {
                range "1..8";
              }
              description
                "Specific Topic identifier";
            }
            uses COFO-DATABASE-BAG;
          }
        }
        leaf node-name {
          type xr:Node-id;
          description
            "The node";
        }
      }
    }
  }
}
