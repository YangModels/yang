module zen {
  namespace "http://www.cisco.com/calvados/calvados_controllers/zen";
  prefix zen;

  import Cisco-IOS-XR-sysadmin-show-trace {
    prefix show_trace;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains definitions
     for the Calvados model objects.
     
     Copyright (c) 2012-2019 by Cisco Systems, Inc.
     All rights reserved.";

  revision 2018-04-09 {
    description
      "Required changes for ConfD 6.4.5";
  }

  grouping zen_curr_sensor_data_show {
    container zen_curr_sensor_data {
      list zen_curr_sensor {
        key "zen_curr_sensor";
        leaf zen_curr_sensor {
          type string {
            pattern "all|[0-8]";
          }
        }
        leaf zen_curr_sensor_id {
          type string;
        }
        leaf zen_curr_dev_addr {
          type uint32;
        }
        leaf zen_curr_poll_intvl {
          type uint32;
        }
        leaf zen_curr_delta {
          type uint32;
        }
        leaf zen_curr_raw_data {
          type uint32;
        }
        leaf zen_curr_sensor_value {
          type int32;
        }
        leaf zen_curr_unit {
          type int32;
        }
        leaf zen_curr_last_value {
          type uint32;
        }
        leaf zen_curr_send_update {
          type boolean;
          default "false";
        }
        leaf zen_curr_num_1sec_intervals {
          type int32;
        }
      }
    }
  }

  grouping zen_volt_sensor_data_show {
    container zen_volt_sensor_data {
      list zen_volt_sensor {
        key "zen_volt_sensor";
        leaf zen_volt_sensor {
          type int32 {
            range "0 .. 17";
          }
        }
        leaf zen_volt_sensor_id {
          type string;
        }
        leaf zen_volt_dev_addr {
          type uint32;
        }
        leaf zen_volt_poll_intvl {
          type uint32;
        }
        leaf zen_volt_delta {
          type uint32;
        }
        leaf zen_volt_raw_data {
          type uint32;
        }
        leaf zen_volt_sensor_value {
          type int32;
        }
        leaf zen_volt_unit {
          type int32;
        }
        leaf zen_volt_last_value {
          type uint32;
        }
        leaf zen_volt_send_update {
          type boolean;
          default "false";
        }
        leaf zen_volt_num_1sec_intervals {
          type int32;
        }
      }
    }
  }

  grouping zen_temp_sensor_data_show {
    container zen_temp_sensor_data {
      list zen_temp_sensor {
        key "zen_temp_sensor";
        leaf zen_temp_sensor {
          type string {
            pattern "all|[0-4]";
          }
        }
        leaf zen_temp_sensor_id {
          type string;
        }
        leaf zen_temp_dev_addr {
          type uint32;
        }
        leaf zen_temp_poll_intvl {
          type uint32;
        }
        leaf zen_temp_delta {
          type uint32;
        }
        leaf zen_temp_raw_data {
          type uint32;
        }
        leaf zen_temp_sensor_value {
          type int32;
        }
        leaf zen_temp_unit {
          type int32;
        }
        leaf zen_temp_last_value {
          type uint32;
        }
        leaf zen_temp_send_update {
          type boolean;
          default "false";
        }
        leaf zen_temp_num_1sec_intervals {
          type int32;
        }
      }
    }
  }

  grouping zen_oper_data {
    container zen_oper {
      config false;
      list zen_location {
        key "zen_location";
        leaf zen_location {
          type string;
        }
        leaf zen_pci_base_address {
          type string;
        }
        leaf zen_pci_dev_vendor_id {
          type string;
        }
        leaf zen_pci_dev_device_id {
          type string;
        }
        leaf zen_hp_desc {
          type string;
        }
        leaf zen_handle {
          type string;
        }
        leaf zen_msi {
          type uint32;
        }
        leaf zen_irq {
          type string;
        }
        leaf zen_regs {
          type string;
        }
        leaf zen_trace {
          type string;
        }
        leaf zen_levm {
          type string;
        }
        leaf zen_sensor_poll_timer_tree {
          type string;
        }
        leaf zen_sensor_poll_timer {
          type string;
        }
        leaf zen_sensor_data {
          type string;
        }
        leaf zen_sim {
          type boolean;
          default "false";
        }
        leaf zen_debug {
          type boolean;
          default "false";
        }
        leaf zen_card_type {
          type uint32;
        }
        leaf zen_slot_num {
          type uint32;
        }
        leaf zen_pm_hdl {
          type string;
        }
        leaf zen_hdl {
          type string;
        }
        leaf zen_ccc_hdl {
          type string;
        }
        leaf zen_platform_local_hdl {
          type string;
        }
        leaf zen_cdui_srvr_hdl {
          type string;
        }
        container zen_temp_sensor_default {
          uses zen_temp_sensor_data_show;
        }
        container zen_volt_sensor_default {
          uses zen_volt_sensor_data_show;
        }
        container zen_curr_sensor_default {
          uses zen_curr_sensor_data_show;
        }
      }
    }
  }

  grouping zen-grp {
    container zen {
      uses zen_oper_data;
      uses show_trace:traceable;
    }
  }
}
