module Cisco-IOS-XR-sysadmin-show-trace-cm {
  namespace "http://www.cisco.com/ns/yang/Cisco-IOS-XR-sysadmin-show-trace-cm";
  prefix cm;

  import Cisco-IOS-XR-sysadmin-show-trace {
    prefix show_trace;
  }
  import cisco-semver {
    prefix semver;
  }

  organization
    "Cisco Systems Inc.";
  contact
    "Cisco Systems, Inc.
     Customer Service
     
     Postal: 170 West Tasman Drive
     San Jose, CA 95134
     
     Tel: +1 800 553-NETS
     
     E-mail: cs-yang@cisco.com";
  description
    "This module contains a collection of YANG
     definitions for Cisco IOS-XR SysAdmin configuration.
     
     Copyright (c) 2013-2019 by Cisco Systems, Inc.
     All rights reserved.";

  revision 2019-04-15 {
    description
      "Establish semantic version baseline.";
    semver:module-version "1.0.0";
  }
  revision 2017-04-12 {
    description
      "Changed the namespace and module name";
  }
  revision 2016-05-11 {
    description
      "Initial version.";
  }

  container cm {
    config false;
    uses show_trace:traceable;
  }
}
