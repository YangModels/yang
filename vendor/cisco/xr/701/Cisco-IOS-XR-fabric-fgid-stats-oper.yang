module Cisco-IOS-XR-fabric-fgid-stats-oper {
  namespace "http://cisco.com/ns/yang/Cisco-IOS-XR-fabric-fgid-stats-oper";
  prefix fabric-fgid-stats-oper;

  import Cisco-IOS-XR-types {
    prefix xr;
  }
  import cisco-semver {
    prefix semver;
  }
  include Cisco-IOS-XR-fabric-fgid-stats-oper-sub1 {
    revision-date 2019-04-05;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR fabric-fgid-stats package operational data.
     
     This module contains definitions
     for the following management objects:
       fabric-fgid: Fabric Fgid Data
     
     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  container fabric-fgid {
    config false;
    description
      "Fabric Fgid Data";
    container lr {
      description
        "Fabric Fgid Pool";
      container fgid-lr-ids {
        description
          "Fabric Fgid LR Statistics";
        list fgid-lr-id {
          key "lr-id";
          description
            "Statistics Data";
          leaf lr-id {
            type xr:Cisco-ios-xr-string;
            description
              "LR ID";
          }
          uses FGID-LR-STATS-INFO;
        }
      }
    }
    container system {
      description
        "Fabric Fgid System";
      container system-stats {
        description
          "Fabric Fgid System Statistics";
        container fgid-system-statistics {
          description
            "Statistics Data";
          uses FGID-SYS-STATS-INFO;
        }
      }
    }
    container pool {
      description
        "Fabric Fgid Pool";
      container fgid-pool-ids {
        description
          "Fabric Fgid Pool Statistics";
        list fgid-pool-id {
          key "pool-id";
          description
            "Statistics Data";
          leaf pool-id {
            type xr:Cisco-ios-xr-string;
            description
              "Pool ID";
          }
          uses FGID-POOL-ATTR-INFO;
        }
      }
    }
    container information {
      description
        "Fabric Fgid System";
      container start-fgid {
        description
          "Start FGID";
        container element {
          description
            "Start FGID";
          container filter-options {
            description
              "Num FGID";
            list filter-option {
              key "filter";
              description
                "Detail/Brief/Diag Data";
              leaf filter {
                type xr:Cisco-ios-xr-string;
                description
                  "filter - detail/brief/diag";
              }
              uses FGID-INFO;
            }
          }
        }
      }
    }
  }
}
