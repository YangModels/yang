module Cisco-IOS-XR-manageability-object-tracking-oper {
  namespace "http://cisco.com/ns/yang/Cisco-IOS-XR-manageability-object-tracking-oper";
  prefix manageability-object-tracking-oper;

  import cisco-semver {
    prefix semver;
  }
  import Cisco-IOS-XR-manageability-object-tracking-datatypes {
    prefix dt1;
  }
  include Cisco-IOS-XR-manageability-object-tracking-oper-sub1 {
    revision-date 2019-04-05;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR manageability-object-tracking package operational data.
     
     This module contains definitions
     for the following management objects:
       object-tracking: Object Tracking operational data
     
     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  container object-tracking {
    config false;
    description
      "Object Tracking operational data";
    container track-type-interface {
      description
        "Object Tracking Type interface info";
      uses TRACK-INFO;
    }
    container track-briefs {
      description
        "Object Tracking Track table brief";
      list track-brief {
        key "track-name";
        description
          "Track name - maximum 32 characters";
        leaf track-name {
          type dt1:Object-tracking-name-string;
          description
            "Track name";
        }
        uses TRACK-INFO-BRIEF;
      }
    }
    container track-type-rtr-reachability {
      description
        "Object Tracking Type RTR Reachability info";
      uses TRACK-INFO;
    }
    container track-type-rtr-reachability-brief {
      description
        "Object Tracking Type RTR Reachability brief info";
      uses TRACK-INFO-BRIEF;
    }
    container tracks {
      description
        "Object Tracking Track table";
      list track {
        key "track-name";
        description
          "Track name - maximum 32 characters";
        leaf track-name {
          type dt1:Object-tracking-name-string;
          description
            "Track name";
        }
        uses TRACK-INFO;
      }
    }
    container track-type-ipv4-route-brief {
      description
        "Object Tracking Type Ipv4 Route brief info";
      uses TRACK-INFO-BRIEF;
    }
    container track-type-ipv4-route {
      description
        "Object Tracking Type IPV4 route info";
      uses TRACK-INFO;
    }
    container track-type-interface-brief {
      description
        "Object Tracking Type Interface brief info";
      uses TRACK-INFO-BRIEF;
    }
  }
}
