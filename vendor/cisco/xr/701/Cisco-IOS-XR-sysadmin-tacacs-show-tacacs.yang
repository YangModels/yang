module Cisco-IOS-XR-sysadmin-tacacs-show-tacacs {
  namespace "http://www.cisco.com/ns/yang/Cisco-IOS-XR-sysadmin-tacacs-show-tacacs";
  prefix show_tacacs;

  import tailf-common {
    prefix tailf;
  }
  import ietf-inet-types {
    prefix inet;
  }
  import Cisco-IOS-XR-sysadmin-tacacs-tacacs-server {
    prefix tacacs-server;
  }
  import cisco-semver {
    prefix semver;
  }

  organization
    "Cisco Systems Inc.";
  contact
    "aaa-ng-tacacs-dev@cisco.com";
  description
    "This module defines yang model
     for displaying tacacs+ server host info
     
     Copyright (c) 2012-2019 by Cisco Systems, Inc.
     All rights reserved.";

  revision 2019-04-15 {
    description
      "Establish semantic version baseline.";
    semver:module-version "1.0.0";
  }
  revision 2017-05-10 {
    description
      "Namespace changed from show_tacacs to Cisco-IOS-XR-sysadmin-tacacs-show-tacacs";
  }
  revision 2015-07-07 {
    description
      "Initial revision";
  }

  typedef passwdStr {
    type tailf:md5-digest-string;
  }

  augment "/tacacs-server:tacacs-server" {
    container requests {
      config false;
      list ipv4 {
        key "addr port";
        leaf addr {
          type inet:ip-address;
          description
            "Server IPv4 address";
        }
        leaf port {
          type inet:port-number;
          description
            "Server Port";
        }
        leaf opens {
          type uint32;
          description
            "Socket open count";
        }
        leaf closes {
          type uint32;
          description
            "Socket close count";
        }
        leaf aborts {
          type uint32;
          description
            "Socket abort count";
        }
        leaf errors {
          type uint32;
          description
            "Socket error count";
        }
        leaf packets_in {
          type uint32;
          description
            "Packets received count";
        }
        leaf packets_out {
          type uint32;
          description
            "Packets transmitted count";
        }
      }
    }
  }
}
