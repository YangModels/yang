submodule Cisco-IOS-XR-crypto-macsec-mka-oper-sub1 {
  belongs-to Cisco-IOS-XR-crypto-macsec-mka-oper {
    prefix Cisco-IOS-XR-crypto-macsec-mka-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR crypto-macsec-mka package operational data.
     
     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  typedef Mka-authentication-mode {
    type enumeration {
      enum "auth-mode-invalid" {
        value 0;
        description
          "Invalid authentication mode";
      }
      enum "auth-mode-psk" {
        value 1;
        description
          "Preshared Key";
      }
      enum "auth-mode-eap" {
        value 2;
        description
          "EAP";
      }
    }
    description
      "Mka authentication mode";
  }

  typedef Macsec-service-port {
    type enumeration {
      enum "macsec-service-port-none" {
        value 0;
        description
          "Macsec Service not enabled";
      }
      enum "macsec-service-port-encryption" {
        value 1;
        description
          "Macsec Service Encryption Port";
      }
      enum "macsec-service-port-decryption" {
        value 2;
        description
          "Macsec Service Decryption Port";
      }
    }
    description
      "Macsec service port";
  }

  typedef Macsec-cipher-suite {
    type enumeration {
      enum "cipher-suite-none" {
        value 0;
        description
          "Invalid MACsec cipher";
      }
      enum "cipher-suite-gcm-aes-128" {
        value 1;
        description
          "128 bit GCM_AES MACsec cipher suite";
      }
      enum "cipher-suite-gcm-aes-256" {
        value 2;
        description
          "256 bit GCM_AES MACsec cipher suite";
      }
      enum "cipher-suite-gcm-aes-128-xpn" {
        value 3;
        description
          "128 bit GCM_AES MACsec XPN cipher suite";
      }
      enum "cipher-suite-gcm-aes-256-xpn" {
        value 4;
        description
          "256 bit GCM_AES MACsec XPN cipher suite";
      }
    }
    description
      "Macsec cipher suite";
  }

  grouping MKA-INTERFACE-SUMMARY {
    description
      "MKA INTERFACE SUMMARY";
    leaf interface-name {
      type string;
      description
        "macsec configured interface";
    }
    leaf short-name {
      type string;
      description
        "Short Name String";
    }
    leaf key-chain {
      type string;
      description
        "Name  of the Key chain";
    }
    leaf policy {
      type string;
      description
        "Policy name";
    }
    leaf macsec-svc-port {
      type boolean;
      description
        "Is macsec-service port or not";
    }
    leaf macsec-svc-port-type {
      type Macsec-service-port;
      description
        "Macsec-service Encryption / Decryption port";
    }
    leaf svcport-short-name {
      type string;
      description
        "Macsec Service paired port Short Name String";
    }
    leaf mka-mode {
      type Mka-authentication-mode;
      description
        "MKA authentication mode";
    }
    leaf fallback-keychain {
      type string;
      description
        "fallback Keychain name";
    }
    leaf macsec-shutdown {
      type boolean;
      description
        "MacsecShutdown";
    }
  }

  grouping MKA-INTERFACE-INFO {
    description
      "MKA INTERFACE INFO";
    container interface-summary {
      description
        "MKA Interface Summary";
      uses MKA-INTERFACE-SUMMARY;
    }
  }

  grouping PEER-DATA {
    description
      "PEER DATA";
    leaf mi {
      type string;
      description
        "Member ID";
    }
    leaf sci {
      type string;
      description
        "Rx SCI";
    }
    leaf mn {
      type uint32;
      description
        "Message Number";
    }
    leaf priority {
      type uint32;
      description
        "KS Priority";
    }
    leaf ssci {
      type uint32;
      description
        "Peer SSCI";
    }
  }

  grouping CA-DATA {
    description
      "CA DATA";
    container peers-status {
      description
        "Peers Status";
      uses PEERS-STATUS-DATA;
    }
    leaf is-key-server {
      type boolean;
      description
        "Is Key Server";
    }
    leaf status {
      type string;
      description
        "Session Status [Secured/Not Secured]";
    }
    leaf num-live-peers {
      type uint32;
      description
        "Number of Live Peers";
    }
    leaf first-ca {
      type boolean;
      description
        "Is First CA";
    }
    leaf peer-sci {
      type string;
      description
        "Peer SCI(MAC)";
    }
    leaf num-live-peers-responded {
      type uint32;
      description
        "Number of Live Peers responded";
    }
    leaf ckn {
      type string;
      description
        "CKN";
    }
    leaf my-mi {
      type string;
      description
        "Member Identifier";
    }
    leaf my-mn {
      type uint32;
      description
        "Message Number";
    }
    leaf authenticator {
      type boolean;
      description
        "authenticator";
    }
    leaf status-description {
      type string;
      description
        "Status Description";
    }
    leaf authentication-mode {
      type string;
      description
        "CA Authentication Mode
         :PRIMARY-PSK/FALLBACK-PSK/EAP";
    }
    leaf key-chain {
      type string;
      description
        "Key Chain name";
    }
    list live-peer {
      description
        "Live Peer List";
      uses PEER-DATA;
    }
    list potential-peer {
      description
        "Potential Peer List";
      uses PEER-DATA;
    }
    list dormant-peer {
      description
        "Dormant Peer List";
      uses PEER-DATA;
    }
  }

  grouping PEER-STATUS-DATA-INTERNAL {
    description
      "PEER STATUS DATA INTERNAL";
    leaf mi {
      type string {
        length "0..25";
      }
      description
        "Member ID";
    }
    leaf icv-status {
      type string {
        length "0..10";
      }
      description
        "ICV Status";
    }
    leaf icv-check-timestamp {
      type string {
        length "0..128";
      }
      description
        "ICV Check Timestamp";
    }
  }

  grouping PEER-STATUS-DATA {
    description
      "PEER STATUS DATA";
    container peer-data {
      description
        "Peer Status Data";
      uses PEER-STATUS-DATA-INTERNAL;
    }
    leaf sci {
      type string {
        length "0..17";
      }
      description
        "Rx SCI";
    }
  }

  grouping PEERS-STATUS-DATA {
    description
      "PEERS STATUS DATA";
    leaf tx-mkpdu-timestamp {
      type string {
        length "0..128";
      }
      description
        "Tx MKPDU Timestamp";
    }
    leaf peer-count {
      type uint32;
      description
        "Peer Count";
    }
    list peer {
      description
        "Peer List";
      uses PEER-STATUS-DATA;
    }
  }

  grouping FALLBACK-KEEPALIVE-DATA {
    description
      "FALLBACK KEEPALIVE DATA";
    container peers-status {
      description
        "Peers Status";
      uses PEERS-STATUS-DATA;
    }
    leaf ckn {
      type string {
        length "0..65";
      }
      description
        "CKN";
    }
    leaf mi {
      type string {
        length "0..25";
      }
      description
        "Member Identifier";
    }
    leaf mn {
      type uint32;
      description
        "Message Number";
    }
  }

  grouping VP-DATA {
    description
      "VP DATA";
    leaf my-sci {
      type string;
      description
        "Local SCI(MAC)";
    }
    leaf virtual-port-id {
      type uint32;
      description
        "Virtual Port ID";
    }
    leaf latest-rx {
      type boolean;
      description
        "Latest Rx status";
    }
    leaf latest-tx {
      type boolean;
      description
        "Latest Tx status";
    }
    leaf latest-an {
      type uint32;
      description
        "Latest SAK AN";
    }
    leaf latest-ki {
      type string;
      description
        "Latest SAK KI";
    }
    leaf latest-kn {
      type uint32;
      description
        "Latest SAK KN";
    }
    leaf old-rx {
      type boolean;
      description
        "Old Rx status";
    }
    leaf old-tx {
      type boolean;
      description
        "Old Tx status";
    }
    leaf old-an {
      type uint32;
      description
        "Old SAK AN";
    }
    leaf old-ki {
      type string;
      description
        "Old SAK KI";
    }
    leaf old-kn {
      type uint32;
      description
        "Old SAK KN";
    }
    leaf wait-time {
      type uint32;
      description
        "SAK Transmit Wait Time";
    }
    leaf retire-time {
      type uint32;
      description
        "SAK Retire time";
    }
    leaf macsec-cipher-suite {
      type Macsec-cipher-suite;
      description
        "SAK Cipher Suite";
    }
    leaf ssci {
      type uint32;
      description
        "SSCI of the Local TxSC";
    }
    leaf time-to-sak-rekey {
      type string;
      description
        "Next SAK Rekey time in Sec";
    }
    list fallback-keepalive {
      description
        "Fallback Keepalive";
      uses FALLBACK-KEEPALIVE-DATA;
    }
  }

  grouping MKA-VLAN-TAG {
    description
      "MKA VLAN TAG";
    leaf ether-type {
      type uint16;
      description
        "EtherType";
    }
    leaf priority {
      type uint8;
      description
        "Priority";
    }
    leaf cfi {
      type uint8;
      description
        "Cannonical Format Identifier";
    }
    leaf vlan-id {
      type uint16;
      description
        "Vlan Id";
    }
  }

  grouping MKA-SESSION-SUMMARY {
    description
      "MKA SESSION SUMMARY";
    container outer-tag {
      description
        "VLAN Outer TAG";
      uses MKA-VLAN-TAG;
    }
    container inner-tag {
      description
        "VLAN Inner TAG";
      uses MKA-VLAN-TAG;
    }
    leaf interface-name {
      type string;
      description
        "macsec configured interface";
    }
    leaf inherited-policy {
      type boolean;
      description
        "Is Inherited Policy";
    }
    leaf policy {
      type string;
      description
        "Policy Name";
    }
    leaf priority {
      type uint32;
      description
        "Key Server Priority";
    }
    leaf my-mac {
      type string;
      description
        "My MAC";
    }
    leaf delay-protection {
      type boolean;
      description
        "Delay Protect";
    }
    leaf replay-protect {
      type boolean;
      description
        "Replay Protect";
    }
    leaf window-size {
      type uint32;
      description
        "Replay Window Size";
    }
    leaf include-icv-indicator {
      type boolean;
      description
        "IncludeICVIndicator";
    }
    leaf confidentiality-offset {
      type uint32;
      description
        "Confidentiality Offset";
    }
    leaf algo-agility {
      type uint32;
      description
        "Alogorithm Agility";
    }
    leaf capability {
      type uint32;
      description
        "MACSec Capability";
    }
    leaf mka-cipher-suite {
      type string;
      description
        "MKA Cipher Suite";
    }
    leaf configured-mac-sec-cipher-suite {
      type string;
      description
        "configured cipher suite";
    }
    leaf mac-sec-desired {
      type boolean;
      description
        "MACSec Desired";
    }
  }

  grouping MKA-SESSION {
    description
      "MKA SESSION";
    container session-summary {
      description
        "Session summary";
      uses MKA-SESSION-SUMMARY;
    }
    container vp {
      description
        "Virtual Pointer Info";
      uses VP-DATA;
    }
    list ca {
      description
        "CA List for a Session";
      uses CA-DATA;
    }
  }
}
