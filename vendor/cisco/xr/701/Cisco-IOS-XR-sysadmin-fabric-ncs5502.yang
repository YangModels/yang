module Cisco-IOS-XR-sysadmin-fabric-ncs5502 {
  namespace "http://www.cisco.com/ns/yang/Cisco-IOS-XR-sysadmin-fabric-ncs5502";
  prefix fabric;

  import Cisco-IOS-XR-sysadmin-fabric-mgr-fgid {
    prefix fabric-fgid;
  }
  import Cisco-IOS-XR-sysadmin-fabric-mgr-fsdb-server-ncs5502 {
    prefix fabric-fsdb;
  }
  import Cisco-IOS-XR-sysadmin-fabric-mgr-fsdb-aggregator-ncs5502 {
    prefix fabric-fsdb-aggr;
  }
  import Cisco-IOS-XR-sysadmin-fabric-driver-sfe {
    prefix fabric-sfe;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains definitions
     for the Calvados model objects.
     
     Copyright (c) 2012-2019 by Cisco Systems, Inc.
     All rights reserved.";

  revision 2019-04-15 {
    description
      "Establish semantic version baseline.";
    semver:module-version "1.0.0";
  }
  revision 2017-05-01 {
    description
      "Namespace change to comply with Cisco guidelines on namespace";
  }

  grouping fabric_action_cmds {
    container fabric_action {
      container fabric {
        description
          "Fabric resource commands";
        uses fabric-fsdb-aggr:fsdb_aggr_ppu;
      }
    }
  }

  grouping fabric_clear {
    container fabric {
      description
        "Fabric resource commands";
      uses fabric-fsdb-aggr:fsdb_aggr_clear;
    }
  }

  grouping fabric {
    container fabric {
      description
        "Fabric resource commands";
      container fabric {
        description
          "Fabric configuration";
        container fsdbagg {
          uses fabric-fsdb-aggr:fsdb_agg_conf_plane;
        }
        uses fabric-fgid:fgid_conf_resource;
      }
      container oper {
        config false;
        uses fabric-fgid:fgid;
        uses fabric-fsdb-aggr:fsdb_aggr;
        uses fabric-fsdb:fsdb_svr;
      }
    }
    container sfe_oper {
      config false;
      uses fabric-sfe:sfe;
    }
  }
}
