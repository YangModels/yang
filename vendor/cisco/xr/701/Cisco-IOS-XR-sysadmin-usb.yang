module Cisco-IOS-XR-sysadmin-usb {
  namespace "http://www.cisco.com/ns/yang/Cisco-IOS-XR-sysadmin-usb";
  prefix usb;

  import tailf-common {
    prefix tailf;
  }
  import cisco-semver {
    prefix semver;
  }

  organization
    "Cisco Systems Inc.";
  contact
    "Cisco Systems, Inc.
     Customer Service
     
     Postal: 170 West Tasman Drive
     San Jose, CA 95134
     
     Tel: +1 800 553-NETS
     
     E-mail: cs-yang@cisco.com";
  description
    "This module contains a collection of YANG
     definitions for Cisco IOS-XR SysAdmin configuration.
     
     This module defines the top level container for
     all 'usb' commands for Sysadmin.
     
     Copyright (c) 2018-2019 by Cisco Systems, Inc.
     All rights reserved.";

  revision 2019-04-15 {
    description
      "Establish semantic version baseline.";
    semver:module-version "1.0.0";
  }
  revision 2018-05-23 {
    description
      "Created initial 'usb mount unmount' implementation";
  }

  container usb {
    config false;
    tailf:action "device" {
      input {
        leaf operation {
          type string;
          description
            "mount unmount";
        }
      }
      output {
        leaf success {
          type string;
        }
      }
    }
  }
}
