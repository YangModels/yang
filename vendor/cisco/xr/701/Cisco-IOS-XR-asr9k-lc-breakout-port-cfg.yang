module Cisco-IOS-XR-asr9k-lc-breakout-port-cfg {
  namespace "http://cisco.com/ns/yang/Cisco-IOS-XR-asr9k-lc-breakout-port-cfg";
  prefix asr9k-lc-breakout-port-cfg;

  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR asr9k-lc-breakout-port package configuration.
     
     This module contains definitions
     for the following management objects:
       hardware-module-breakout: HW module breakout config
     
     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  typedef Hw-module-breakout-if {
    type enumeration {
      enum "10x-ten-gig-e" {
        value 1;
        description
          "TenGigE interfaces";
      }
      enum "2x-forty-gig-e" {
        value 2;
        description
          "FortyGigE interfaces";
      }
      enum "1x-forty-gig-e" {
        value 3;
        description
          "FortyGigE interfaces";
      }
      enum "4x-ten-gig-e" {
        value 4;
        description
          "TenGigE interfaces";
      }
      enum "4x-twenty-five-gig-e" {
        value 5;
        description
          "TwentyFiveGigE interfaces";
      }
      enum "1x-four-hundred-gig-e" {
        value 6;
        description
          "FourHundredGigE interfaces";
      }
      enum "8x-fifty-gig-e" {
        value 7;
        description
          "FiftyGigE interfaces";
      }
    }
    description
      "Hw module breakout if";
  }

  container hardware-module-breakout {
    description
      "HW module breakout config";
    list config-mode {
      key "id1";
      description
        "Active or pre configuration";
      leaf id1 {
        type xr:Cisco-ios-xr-string;
        description
          "act- or pre-config";
      }
      list node {
        key "id2";
        description
          "none";
        container ports {
          description
            "Optics port configuration";
          list port {
            key "id4";
            description
              "Optics port number";
            leaf iftype {
              type Hw-module-breakout-if;
              description
                "Breakout iftype";
            }
            leaf id4 {
              type xr:Cisco-ios-xr-string;
              description
                "Optics port number";
            }
          }
        }
        leaf id2 {
          type xr:Cisco-ios-xr-string;
          description
            "Fully qualified line card specification";
        }
      }
    }
  }
}
