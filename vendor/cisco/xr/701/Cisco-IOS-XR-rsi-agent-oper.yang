module Cisco-IOS-XR-rsi-agent-oper {
  namespace "http://cisco.com/ns/yang/Cisco-IOS-XR-rsi-agent-oper";
  prefix rsi-agent-oper;

  import Cisco-IOS-XR-types {
    prefix xr;
  }
  import cisco-semver {
    prefix semver;
  }
  include Cisco-IOS-XR-rsi-agent-oper-sub1 {
    revision-date 2019-04-05;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR rsi-agent package operational data.
     
     This module contains definitions
     for the following management objects:
       rsi-agent: RSI operational data
     
     Copyright (c) 2013-2019 by Cisco Systems, Inc.
     All rights reserved.";

  revision 2019-04-05 {
    description
      "Establish semantic version baseline.";
    semver:module-version "1.0.0";
  }
  revision 2019-02-13 {
    description
      "Fixing yang oper coverage.";
  }
  revision 2018-11-26 {
    description
      "Fixing yang usability issues.";
  }
  revision 2018-01-24 {
    description
      "Fixed datatype issues";
  }
  revision 2018-01-11 {
    description
      "Add rsip node into schema.";
  }
  revision 2017-09-07 {
    description
      "Fixed type translation error.";
  }
  revision 2015-11-09 {
    description
      "IOS XR 6.0 revision.";
  }

  grouping VIRTUAL-ROUTING-FORWARDING-ID {
    description
      "Common node of virtual-router-id-info,
       virtual-router-name-info";
    container virtual-routing-forwarding-id-infos {
      description
        "Virtual Routing and Forwarding ID";
      list virtual-routing-forwarding-id-info {
        key "vrfid";
        description
          "Virtual Router and Forwarding ID details";
        leaf vrfid {
          type xr:Cisco-ios-xr-string;
          description
            "Virtual Router Forwarding ID";
        }
        uses TABLE-NAME-DB-FILTER;
        uses TABLE-ID-DB-FILTER;
        uses INTERFACE-HANDLE-DB-TABLE;
        uses GLOBAL-INTERFACE-HANDLE-DB-TABLE;
      }
    }
  }

  grouping TABLE-NAME-DB-FILTER {
    description
      "Common node of virtual-routing-forwarding-id-info
       , virtual-routing-forwarding-name-info";
    container table-name-db-filter-infos {
      description
        "Table Name database";
      list table-name-db-filter-info {
        description
          "Table name List";
        leaf table-name {
          type xr:Cisco-ios-xr-string;
          description
            "Table Name";
        }
        leaf afi {
          type uint32;
          description
            "Address Family Indicator";
        }
        leaf safi {
          type uint32;
          description
            "Subsequent Address Family Indicator";
        }
        list table-name-db-filter-info-table {
          description
            "Table name details";
          leaf table-name {
            type xr:Cisco-ios-xr-string;
            description
              "Table Name";
          }
          leaf afi {
            type uint32;
            description
              "Address Family Indicator";
          }
          leaf safi {
            type uint32;
            description
              "Subsequent Address Family Indicator";
          }
          uses RSI-AGENT-TBL;
        }
      }
    }
  }

  grouping VRF-NAME-TABLE {
    description
      "Common node of virtual-router-name-info,
       virtual-router-id-info";
    container vrf-names {
      description
        "List of Virtual Router";
      list vrf-name {
        key "name";
        description
          "VRF details by name";
        leaf name {
          type xr:Cisco-ios-xr-string {
            length "1..32";
          }
          description
            "vrf name";
        }
        uses RSI-AGENT-VRF;
      }
    }
  }

  grouping VRFID-TABLE {
    description
      "Common node of node, virtual-router-name-info,
       virtual-router-id-info";
    container vrfids {
      description
        "List of Virtual Router Forwarding ID";
      list vrfid {
        key "id";
        description
          "VRF details by ID";
        leaf id {
          type xr:Cisco-ios-xr-string;
          description
            "vrf id";
        }
        uses RSI-AGENT-VRF;
      }
    }
  }

  grouping INTERFACE-HANDLE-DB-TABLE {
    description
      "Common node of node,
       virtual-routing-forwarding-id-info,
       virtual-routing-forwarding-name-info";
    container interfaces {
      description
        "Interface handle database";
      list interface {
        key "interface";
        description
          "Client details";
        leaf interface {
          type xr:Interface-name;
          description
            "Interface handle";
        }
        uses RSI-AGENT-INTF;
      }
    }
  }

  grouping VIRTUAL-ROUTING-FORWARDING-NAME {
    description
      "Common node of virtual-router-id-info,
       virtual-router-name-info";
    container virtual-routing-forwarding-name-infos {
      description
        "Virtual Routing and Forwarding Name";
      list virtual-routing-forwarding-name-info {
        key "vrf-name";
        description
          "Virtual Router and Forwarding Name details";
        leaf vrf-name {
          type xr:Cisco-ios-xr-string;
          description
            "Virtual Router Forwarding Name";
        }
        uses TABLE-NAME-DB-FILTER;
        uses TABLE-ID-DB-FILTER;
        uses INTERFACE-HANDLE-DB-TABLE;
        uses GLOBAL-INTERFACE-HANDLE-DB-TABLE;
      }
    }
  }

  grouping TABLE-ID-DB-FILTER {
    description
      "Common node of node,
       virtual-routing-forwarding-id-info,
       virtual-routing-forwarding-name-info";
    container table-id-db-filter-infos {
      description
        "Table ID database";
      list table-id-db-filter-info {
        description
          "Table id filters";
        leaf table-name {
          type xr:Cisco-ios-xr-string;
          description
            "Table Name";
        }
        leaf afi {
          type uint32;
          description
            "Address Family Indicator";
        }
        leaf safi {
          type uint32;
          description
            "Subsequent Address Family Indicator";
        }
        list table-id-db-filter-info-table-id {
          key "table-id";
          description
            "Table id details";
          leaf table-id {
            type uint32;
            description
              "Table ID";
          }
          uses RSI-AGENT-TBL;
        }
      }
    }
  }

  grouping GLOBAL-INTERFACE-HANDLE-DB-TABLE {
    description
      "Common node of node,
       virtual-routing-forwarding-id-info,
       virtual-routing-forwarding-name-info";
    container global-interface-handles {
      description
        "Global Interface handle database";
      list global-interface-handle {
        key "interface";
        description
          "Interface handle details";
        leaf interface {
          type xr:Interface-name;
          description
            "Interface handle";
        }
        uses RSI-AGENT-INTF;
      }
    }
  }

  container rsi-agent {
    config false;
    description
      "RSI operational data";
    container nodes {
      description
        "Node operational data";
      list node {
        key "node-name";
        description
          "Node details";
        container virtual-routers {
          description
            "List of Virtual Router Name";
          list virtual-router {
            key "vr-name";
            description
              "Producer details";
            leaf vr-name {
              type xr:Cisco-ios-xr-string;
              description
                "virtual router name";
            }
            uses RSI-AGENT-VR;
          }
        }
        container rsi-agent-role {
          description
            "RSI Agent role database";
          uses RSI-AGENT-ROLE;
        }
        container virtual-router-ids {
          description
            "List of Virtual Router";
          list virtual-router-id {
            key "vrid";
            description
              "Producer details";
            leaf vrid {
              type xr:Cisco-ios-xr-string;
              description
                "virtual router ID";
            }
            uses RSI-AGENT-VR;
          }
        }
        container producers {
          description
            "List of Producers";
          list producer {
            key "producer-name";
            description
              "Producer details";
            leaf producer-name {
              type uint32 {
                range "1..4294967295";
              }
              description
                "producer name";
            }
            uses RSI-AGENT-PROD;
          }
        }
        container table-id-db-dependent-infos {
          description
            "Table ID Dependent database";
          list table-id-db-dependent-info {
            key "table-id";
            description
              "Table id details";
            leaf table-id {
              type uint32;
              description
                "Table ID";
            }
            uses RSI-AGENT-TBL-REQ-DEP;
          }
        }
        container interface-names {
          description
            "Interface name database";
          list interface-name {
            key "interface";
            description
              "Interface name details";
            leaf interface {
              type xr:Cisco-ios-xr-string;
              description
                "Interface name";
            }
            uses RSI-AGENT-INTF;
          }
        }
        container virtual-router-name-infos {
          description
            "Virtual Router Name";
          list virtual-router-name-info {
            key "vr-name";
            description
              "Virtual Router Name details";
            leaf vr-name {
              type xr:Cisco-ios-xr-string;
              description
                "Virtual Router Name";
            }
            uses VIRTUAL-ROUTING-FORWARDING-ID;
            uses VIRTUAL-ROUTING-FORWARDING-NAME;
            uses VRF-NAME-TABLE;
            uses VRFID-TABLE;
          }
        }
        container state {
          description
            "SVD state details";
          uses RSI-AGENT-STATE;
        }
        container virtual-router-id-infos {
          description
            "Virtual Router ID";
          list virtual-router-id-info {
            key "vrid";
            description
              "Virtual Router ID details";
            leaf vrid {
              type xr:Cisco-ios-xr-string;
              description
                "Virtual Router ID";
            }
            uses VIRTUAL-ROUTING-FORWARDING-ID;
            uses VIRTUAL-ROUTING-FORWARDING-NAME;
            uses VRF-NAME-TABLE;
            uses VRFID-TABLE;
          }
        }
        container clients {
          description
            "RSI Clients table";
          list client {
            key "client-name";
            description
              "Client details";
            leaf client-name {
              type xr:Cisco-ios-xr-string;
              description
                "Client name";
            }
            uses RSI-AGENT-CLIENT;
          }
        }
        container stale-producer-infos {
          description
            "RSI Stale Producer database";
          list stale-producer-info {
            key "index";
            description
              "Stale producer details";
            leaf index {
              type uint32;
              description
                "Producer Index";
            }
            uses RSI-AGENT-PROD;
          }
        }
        leaf node-name {
          type xr:Node-id;
          description
            "Node";
        }
        uses TABLE-ID-DB-FILTER;
        uses VRFID-TABLE;
        uses INTERFACE-HANDLE-DB-TABLE;
        uses GLOBAL-INTERFACE-HANDLE-DB-TABLE;
      }
    }
  }
}
