module Cisco-IOS-XR-sysadmin-fabric-cxp-ncs6k {
  namespace "http://www.cisco.com/ns/yang/Cisco-IOS-XR-sysadmin-fabric-cxp-ncs6k";
  prefix fabric_cxp;

  import Cisco-IOS-XR-sysadmin-fabric-types {
    prefix fabric-types;
  }
  import tailf-xsd-types {
    prefix xs;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains definitions
     for the Calvados model objects.
     
     Copyright (c) 2012-2019 by Cisco Systems, Inc.
     All rights reserved.";

  revision 2019-04-15 {
    description
      "Establish semantic version baseline.";
    semver:module-version "1.0.0";
  }
  revision 2018-04-09 {
    description
      "Required changes for ConfD 6.4.5";
  }
  revision 2017-08-01 {
    description
      "Updated to display cxp2 firmware and eeprom version";
  }
  revision 2017-06-19 {
    description
      "Namespace change to comply with Cisco guidelines on namespace";
  }

  grouping dom_output {
    list port {
      key "cxp_port";
      leaf show_port {
        type boolean;
      }
      leaf cxp2_display {
        type boolean;
      }
      leaf rack_num {
        type uint32;
      }
      leaf slot_num {
        type uint32;
      }
      leaf cxp_port {
        type fabric-types:cxp_port_type;
      }
      leaf cur_loc_str {
        type string;
      }
      leaf vendorname {
        type string;
      }
      leaf partnumber {
        type string;
      }
      leaf serialnumber {
        type string;
      }
      leaf vid {
        type string;
      }
      leaf pid {
        type string;
      }
      leaf vendor_rev_num {
        type uint32;
      }
      leaf vendor_pn {
        type string;
      }
      leaf vendor_sn {
        type string;
      }
      leaf dev_description {
        type string;
      }
      leaf clei_code_num {
        type string;
      }
      leaf ven_date_code {
        type string;
      }
      leaf ven_lot_code {
        type string;
      }
      leaf vendor_oui_ieee_company_id {
        type uint32;
      }
      leaf eeprom_rev_num {
        type uint32;
      }
      leaf firmware_rev_num {
        type uint32;
      }
      leaf current_speed {
        type string;
      }
      leaf TX_temp_rd {
        type xs:float;
      }
      leaf TX_temp_sts {
        type string;
      }
      leaf TX_volt_sts {
        type string;
      }
      leaf TX_volt_rd {
        type xs:float;
      }
      leaf tx_chn_sts0 {
        type string;
      }
      leaf tx_chn_sts1 {
        type string;
      }
      leaf tx_chn_sts2 {
        type string;
      }
      leaf tx_chn_sts3 {
        type string;
      }
      leaf tx_chn_sts4 {
        type string;
      }
      leaf tx_chn_sts5 {
        type string;
      }
      leaf tx_chn_sts6 {
        type string;
      }
      leaf tx_chn_sts7 {
        type string;
      }
      leaf tx_chn_sts8 {
        type string;
      }
      leaf tx_chn_sts9 {
        type string;
      }
      leaf tx_chn_sts10 {
        type string;
      }
      leaf tx_chn_sts11 {
        type string;
      }
      leaf tx_fault0 {
        type string;
      }
      leaf tx_fault1 {
        type string;
      }
      leaf tx_fault2 {
        type string;
      }
      leaf tx_fault3 {
        type string;
      }
      leaf tx_fault4 {
        type string;
      }
      leaf tx_fault5 {
        type string;
      }
      leaf tx_fault6 {
        type string;
      }
      leaf tx_fault7 {
        type string;
      }
      leaf tx_fault8 {
        type string;
      }
      leaf tx_fault9 {
        type string;
      }
      leaf tx_fault10 {
        type string;
      }
      leaf tx_fault11 {
        type string;
      }
      leaf tx_bias_cur0 {
        type xs:float;
      }
      leaf tx_bias_cur1 {
        type xs:float;
      }
      leaf tx_bias_cur2 {
        type xs:float;
      }
      leaf tx_bias_cur3 {
        type xs:float;
      }
      leaf tx_bias_cur4 {
        type xs:float;
      }
      leaf tx_bias_cur5 {
        type xs:float;
      }
      leaf tx_bias_cur6 {
        type xs:float;
      }
      leaf tx_bias_cur7 {
        type xs:float;
      }
      leaf tx_bias_cur8 {
        type xs:float;
      }
      leaf tx_bias_cur9 {
        type xs:float;
      }
      leaf tx_bias_cur10 {
        type xs:float;
      }
      leaf tx_bias_cur11 {
        type xs:float;
      }
      leaf tx_los0 {
        type string;
      }
      leaf tx_los1 {
        type string;
      }
      leaf tx_los2 {
        type string;
      }
      leaf tx_los3 {
        type string;
      }
      leaf tx_los4 {
        type string;
      }
      leaf tx_los5 {
        type string;
      }
      leaf tx_los6 {
        type string;
      }
      leaf tx_los7 {
        type string;
      }
      leaf tx_los8 {
        type string;
      }
      leaf tx_los9 {
        type string;
      }
      leaf tx_los10 {
        type string;
      }
      leaf tx_los11 {
        type string;
      }
      leaf tx_opt_pw_alm0 {
        type string;
      }
      leaf tx_opt_pw_alm1 {
        type string;
      }
      leaf tx_opt_pw_alm2 {
        type string;
      }
      leaf tx_opt_pw_alm3 {
        type string;
      }
      leaf tx_opt_pw_alm4 {
        type string;
      }
      leaf tx_opt_pw_alm5 {
        type string;
      }
      leaf tx_opt_pw_alm6 {
        type string;
      }
      leaf tx_opt_pw_alm7 {
        type string;
      }
      leaf tx_opt_pw_alm8 {
        type string;
      }
      leaf tx_opt_pw_alm9 {
        type string;
      }
      leaf tx_opt_pw_alm10 {
        type string;
      }
      leaf tx_opt_pw_alm11 {
        type string;
      }
      leaf tx_cdr_lock0 {
        type string;
      }
      leaf tx_cdr_lock1 {
        type string;
      }
      leaf tx_cdr_lock2 {
        type string;
      }
      leaf tx_cdr_lock3 {
        type string;
      }
      leaf tx_cdr_lock4 {
        type string;
      }
      leaf tx_cdr_lock5 {
        type string;
      }
      leaf tx_cdr_lock6 {
        type string;
      }
      leaf tx_cdr_lock7 {
        type string;
      }
      leaf tx_cdr_lock8 {
        type string;
      }
      leaf tx_cdr_lock9 {
        type string;
      }
      leaf tx_cdr_lock10 {
        type string;
      }
      leaf tx_cdr_lock11 {
        type string;
      }
      leaf tx_opt_bs_alm0 {
        type string;
      }
      leaf tx_opt_bs_alm1 {
        type string;
      }
      leaf tx_opt_bs_alm2 {
        type string;
      }
      leaf tx_opt_bs_alm3 {
        type string;
      }
      leaf tx_opt_bs_alm4 {
        type string;
      }
      leaf tx_opt_bs_alm5 {
        type string;
      }
      leaf tx_opt_bs_alm6 {
        type string;
      }
      leaf tx_opt_bs_alm7 {
        type string;
      }
      leaf tx_opt_bs_alm8 {
        type string;
      }
      leaf tx_opt_bs_alm9 {
        type string;
      }
      leaf tx_opt_bs_alm10 {
        type string;
      }
      leaf tx_opt_bs_alm11 {
        type string;
      }
      leaf tx_light_op_dBm0 {
        type string;
      }
      leaf tx_light_op_dBm1 {
        type string;
      }
      leaf tx_light_op_dBm2 {
        type string;
      }
      leaf tx_light_op_dBm3 {
        type string;
      }
      leaf tx_light_op_dBm4 {
        type string;
      }
      leaf tx_light_op_dBm5 {
        type string;
      }
      leaf tx_light_op_dBm6 {
        type string;
      }
      leaf tx_light_op_dBm7 {
        type string;
      }
      leaf tx_light_op_dBm8 {
        type string;
      }
      leaf tx_light_op_dBm9 {
        type string;
      }
      leaf tx_light_op_dBm10 {
        type string;
      }
      leaf tx_light_op_dBm11 {
        type string;
      }
      leaf RX_temp_rd {
        type xs:float;
      }
      leaf RX_temp_sts {
        type string;
      }
      leaf RX_volt_sts {
        type string;
      }
      leaf RX_volt_rd {
        type xs:float;
      }
      leaf rx_chn_sts0 {
        type string;
      }
      leaf rx_chn_sts1 {
        type string;
      }
      leaf rx_chn_sts2 {
        type string;
      }
      leaf rx_chn_sts3 {
        type string;
      }
      leaf rx_chn_sts4 {
        type string;
      }
      leaf rx_chn_sts5 {
        type string;
      }
      leaf rx_chn_sts6 {
        type string;
      }
      leaf rx_chn_sts7 {
        type string;
      }
      leaf rx_chn_sts8 {
        type string;
      }
      leaf rx_chn_sts9 {
        type string;
      }
      leaf rx_chn_sts10 {
        type string;
      }
      leaf rx_chn_sts11 {
        type string;
      }
      leaf rx_los0 {
        type string;
      }
      leaf rx_los1 {
        type string;
      }
      leaf rx_los2 {
        type string;
      }
      leaf rx_los3 {
        type string;
      }
      leaf rx_los4 {
        type string;
      }
      leaf rx_los5 {
        type string;
      }
      leaf rx_los6 {
        type string;
      }
      leaf rx_los7 {
        type string;
      }
      leaf rx_los8 {
        type string;
      }
      leaf rx_los9 {
        type string;
      }
      leaf rx_los10 {
        type string;
      }
      leaf rx_los11 {
        type string;
      }
      leaf rx_opt_pw_alm0 {
        type string;
      }
      leaf rx_opt_pw_alm1 {
        type string;
      }
      leaf rx_opt_pw_alm2 {
        type string;
      }
      leaf rx_opt_pw_alm3 {
        type string;
      }
      leaf rx_opt_pw_alm4 {
        type string;
      }
      leaf rx_opt_pw_alm5 {
        type string;
      }
      leaf rx_opt_pw_alm6 {
        type string;
      }
      leaf rx_opt_pw_alm7 {
        type string;
      }
      leaf rx_opt_pw_alm8 {
        type string;
      }
      leaf rx_opt_pw_alm9 {
        type string;
      }
      leaf rx_opt_pw_alm10 {
        type string;
      }
      leaf rx_opt_pw_alm11 {
        type string;
      }
      leaf rx_light_in_dBm0 {
        type string;
      }
      leaf rx_light_in_dBm1 {
        type string;
      }
      leaf rx_light_in_dBm2 {
        type string;
      }
      leaf rx_light_in_dBm3 {
        type string;
      }
      leaf rx_light_in_dBm4 {
        type string;
      }
      leaf rx_light_in_dBm5 {
        type string;
      }
      leaf rx_light_in_dBm6 {
        type string;
      }
      leaf rx_light_in_dBm7 {
        type string;
      }
      leaf rx_light_in_dBm8 {
        type string;
      }
      leaf rx_light_in_dBm9 {
        type string;
      }
      leaf rx_light_in_dBm10 {
        type string;
      }
      leaf rx_light_in_dBm11 {
        type string;
      }
    }
  }

  grouping fc_cxp_port_rack_summary {
    list split_tbl_flag {
      key "tbl_splt";
      leaf tbl_splt {
        type uint32;
      }
      list smry_per_slot {
        key "slot_no";
        leaf func_rack_name {
          type string;
        }
        leaf max_cxp {
          type uint32;
        }
        leaf row_cxp_1 {
          type boolean;
          default "false";
        }
        leaf row_cxp_2 {
          type boolean;
          default "false";
        }
        leaf slot_row {
          type boolean;
          default "false";
        }
        leaf tbl_splt_flag {
          type boolean;
        }
        leaf slot_no {
          type uint32;
        }
        leaf cxp_port_no {
          type uint32;
        }
        leaf fc_loc_str {
          type string;
        }
        leaf cxp_sts_0 {
          type string;
        }
        leaf cxp_sts_1 {
          type string;
        }
        leaf cxp_sts_2 {
          type string;
        }
        leaf cxp_sts_3 {
          type string;
        }
        leaf cxp_sts_4 {
          type string;
        }
        leaf cxp_sts_5 {
          type string;
        }
        leaf cxp_sts_6 {
          type string;
        }
        leaf cxp_sts_7 {
          type string;
        }
        leaf cxp_sts_8 {
          type string;
        }
        leaf cxp_sts_9 {
          type string;
        }
        leaf cxp_sts_10 {
          type string;
        }
        leaf cxp_sts_11 {
          type string;
        }
        leaf cxp_sts_12 {
          type string;
        }
        leaf cxp_sts_13 {
          type string;
        }
        leaf cxp_sts_14 {
          type string;
        }
        leaf cxp_sts_15 {
          type string;
        }
      }
    }
  }

  grouping fc_cxp_dom {
    container cxp {
      container dom {
        list location {
          key "loc_str";
          leaf loc_str {
            type string;
          }
          leaf description {
            type string;
            default "location (R/S)";
          }
          uses dom_output;
        }
      }
      container summary {
        list rack {
          key "rack_str";
          leaf rack_str {
            type string;
          }
          leaf description {
            type string;
            default "Rack No.";
          }
          uses fc_cxp_port_rack_summary;
        }
      }
    }
  }
}
