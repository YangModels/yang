module Cisco-IOS-XR-icpe-sdacp-oper {
  namespace "http://cisco.com/ns/yang/Cisco-IOS-XR-icpe-sdacp-oper";
  prefix icpe-sdacp-oper;

  import Cisco-IOS-XR-types {
    prefix xr;
  }
  import cisco-semver {
    prefix semver;
  }
  import Cisco-IOS-XR-icpe-infra-oper {
    prefix a1;
  }
  include Cisco-IOS-XR-icpe-sdacp-oper-sub3 {
    revision-date 2019-04-05;
  }
  include Cisco-IOS-XR-icpe-sdacp-oper-sub2 {
    revision-date 2019-04-05;
  }
  include Cisco-IOS-XR-icpe-sdacp-oper-sub1 {
    revision-date 2019-04-05;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR icpe-sdacp package operational data.
     
     This YANG module augments the
       Cisco-IOS-XR-icpe-infra-oper
     module with state data.
     
     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  typedef Icpe-sat-id {
    type uint32 {
      range "100..65534";
    }
    description
      "Icpe sat id";
  }

  augment "/a1:nv-satellite" {
    description
      "This augment extends the operational data of
       'Cisco-IOS-XR-icpe-infra-oper'";
    container sdacp-discovery2s {
      description
        "ICPE Configured interface state information
         table";
      list sdacp-discovery2 {
        key "interface-name";
        description
          "ICPE Configured interface state information";
        leaf interface-name {
          type xr:Interface-name;
          description
            "Interface name";
        }
        uses ICPE-SDACP-CFG-SFL;
      }
    }
  }
  augment "/a1:nv-satellite" {
    description
      "This augment extends the operational data of
       'Cisco-IOS-XR-icpe-infra-oper'";
    container icpe-dpms {
      description
        "ICPE DPM operational information table";
      list icpe-dpm {
        key "discovery-interface";
        description
          "ICPE DPM operational information";
        leaf discovery-interface {
          type xr:Interface-name;
          description
            "Discovery interface";
        }
        uses DPM-OPER-IF;
      }
    }
  }
  augment "/a1:nv-satellite" {
    description
      "This augment extends the operational data of
       'Cisco-IOS-XR-icpe-infra-oper'";
    container sdacp-controls {
      description
        "SDAC Protocol Discovery information table";
      list sdacp-control {
        key "satellite-id";
        description
          "SDAC Protocol Discovery information";
        leaf satellite-id {
          type Icpe-sat-id;
          description
            "Satellite ID";
        }
        uses ICPE-CPM-OPER-SAT;
      }
    }
  }
}
