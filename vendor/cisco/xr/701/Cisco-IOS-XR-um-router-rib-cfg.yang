module Cisco-IOS-XR-um-router-rib-cfg {
  namespace "http://cisco.com/ns/yang/Cisco-IOS-XR-um-router-rib-cfg";
  prefix um-router-rib-cfg;

  import cisco-semver {
    prefix semver;
  }
  import Cisco-IOS-XR-um-vrf-cfg {
    prefix a1;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR router-rib package configuration.
     
     This YANG module augments the
     modules with configuration data.
     
     Copyright (c) 2019 by Cisco Systems, Inc.
     All rights reserved.";

  revision 2019-06-10 {
    description
      "Establish semantic version baseline.";
    semver:module-version "1.0.0";
  }
  revision 2019-03-30 {
    description
      "Initial version";
  }

  augment "/a1:address-family/a1:ipv4/a1:unicast" {
    container maximum {
      description
        "Set maximum prefix limit";
      container prefix {
        presence "Indicates a prefix node is configured.";
        description
          "Set table's maximum prefix limit";
        leaf prefix-limit {
          type uint32 {
            range "32..10000000" {
              description
                "Maximum table's prefix limit";
            }
          }
          mandatory true;
          description
            "Set table's maximum prefix limit";
        }
        leaf mid-thresh {
          type uint32 {
            range "1..100" {
              description
                "mid-thresh (% of max)";
            }
          }
          description
            "mid-thresh (% of max)";
        }
      }
    }
  }
  augment "/a1:address-family/a1:ipv4/a1:multicast/a1:topologies/a1:topology" {
    container maximum {
      description
        "Set maximum prefix limit";
      container prefix {
        presence "Indicates a prefix node is configured.";
        description
          "Set table's maximum prefix limit";
        leaf prefix-limit {
          type uint32 {
            range "32..10000000" {
              description
                "Maximum table's prefix limit";
            }
          }
          mandatory true;
          description
            "Set table's maximum prefix limit";
        }
        leaf mid-thresh {
          type uint32 {
            range "1..100" {
              description
                "mid-thresh (% of max)";
            }
          }
          description
            "mid-thresh (% of max)";
        }
      }
    }
  }
  augment "/a1:address-family/a1:ipv6/a1:unicast" {
    container maximum {
      description
        "Set maximum prefix limit";
      container prefix {
        presence "Indicates a prefix node is configured.";
        description
          "Set table's maximum prefix limit";
        leaf prefix-limit {
          type uint32 {
            range "32..10000000" {
              description
                "Maximum table's prefix limit";
            }
          }
          mandatory true;
          description
            "Set table's maximum prefix limit";
        }
        leaf mid-thresh {
          type uint32 {
            range "1..100" {
              description
                "mid-thresh (% of max)";
            }
          }
          description
            "mid-thresh (% of max)";
        }
      }
    }
  }
  augment "/a1:address-family/a1:ipv6/a1:multicast/a1:topologies/a1:topology" {
    container maximum {
      description
        "Set maximum prefix limit";
      container prefix {
        presence "Indicates a prefix node is configured.";
        description
          "Set table's maximum prefix limit";
        leaf prefix-limit {
          type uint32 {
            range "32..10000000" {
              description
                "Maximum table's prefix limit";
            }
          }
          mandatory true;
          description
            "Set table's maximum prefix limit";
        }
        leaf mid-thresh {
          type uint32 {
            range "1..100" {
              description
                "mid-thresh (% of max)";
            }
          }
          description
            "mid-thresh (% of max)";
        }
      }
    }
  }
  augment "/a1:vrfs/a1:vrf/a1:address-family/a1:ipv4/a1:unicast" {
    container maximum {
      description
        "Set maximum prefix limit";
      container prefix {
        presence "Indicates a prefix node is configured.";
        description
          "Set table's maximum prefix limit";
        leaf prefix-limit {
          type uint32 {
            range "32..10000000" {
              description
                "Maximum table's prefix limit";
            }
          }
          mandatory true;
          description
            "Set table's maximum prefix limit";
        }
        leaf mid-thresh {
          type uint32 {
            range "1..100" {
              description
                "mid-thresh (% of max)";
            }
          }
          description
            "mid-thresh (% of max)";
        }
      }
    }
  }
  augment "/a1:vrfs/a1:vrf/a1:address-family/a1:ipv4/a1:multicast" {
    container maximum {
      description
        "Set maximum prefix limit";
      container prefix {
        presence "Indicates a prefix node is configured.";
        description
          "Set table's maximum prefix limit";
        leaf prefix-limit {
          type uint32 {
            range "32..10000000" {
              description
                "Maximum table's prefix limit";
            }
          }
          mandatory true;
          description
            "Set table's maximum prefix limit";
        }
        leaf mid-thresh {
          type uint32 {
            range "1..100" {
              description
                "mid-thresh (% of max)";
            }
          }
          description
            "mid-thresh (% of max)";
        }
      }
    }
  }
  augment "/a1:vrfs/a1:vrf/a1:address-family/a1:ipv6/a1:unicast" {
    container maximum {
      description
        "Set maximum prefix limit";
      container prefix {
        presence "Indicates a prefix node is configured.";
        description
          "Set table's maximum prefix limit";
        leaf prefix-limit {
          type uint32 {
            range "32..10000000" {
              description
                "Maximum table's prefix limit";
            }
          }
          mandatory true;
          description
            "Set table's maximum prefix limit";
        }
        leaf mid-thresh {
          type uint32 {
            range "1..100" {
              description
                "mid-thresh (% of max)";
            }
          }
          description
            "mid-thresh (% of max)";
        }
      }
    }
  }
  augment "/a1:vrfs/a1:vrf/a1:address-family/a1:ipv6/a1:multicast" {
    container maximum {
      description
        "Set maximum prefix limit";
      container prefix {
        presence "Indicates a prefix node is configured.";
        description
          "Set table's maximum prefix limit";
        leaf prefix-limit {
          type uint32 {
            range "32..10000000" {
              description
                "Maximum table's prefix limit";
            }
          }
          mandatory true;
          description
            "Set table's maximum prefix limit";
        }
        leaf mid-thresh {
          type uint32 {
            range "1..100" {
              description
                "mid-thresh (% of max)";
            }
          }
          description
            "mid-thresh (% of max)";
        }
      }
    }
  }
  container router {
    description
      "Enable a routing process";
    container rib {
      description
        "RIB configuration subcommands";
      container address-family {
        description
          "RIB address family configuration subcommands";
        container ipv4 {
          description
            "IPv4 commands";
          container next-hop {
            description
              "Set next-hop configuration";
            container dampening {
              description
                "Set next-hop dampening";
              container disable {
                presence "Indicates a disable node is configured.";
                description
                  "Disable next-hop dampening";
              }
            }
          }
          container redistribution-history {
            description
              "Redistribution history related commands.";
            container size {
              description
                "Number of routes to store in history.";
              leaf bcdl {
                type uint32 {
                  range "10..2000000" {
                    description
                      "Maximum BCDL redistribution history size.";
                  }
                }
                description
                  "BCDL clients only";
              }
              leaf protocols {
                type uint32 {
                  range "10..250000" {
                    description
                      "Maximum protocol redistribution history size.";
                  }
                }
                description
                  "Protocol clients only";
              }
            }
          }
        }
        container ipv6 {
          description
            "IPv6 commands";
          container next-hop {
            description
              "Set next-hop configuration";
            container dampening {
              description
                "Set next-hop dampening";
              container disable {
                presence "Indicates a disable node is configured.";
                description
                  "Disable next-hop dampening";
              }
            }
          }
          container redistribution-history {
            description
              "Redistribution history related commands.";
            container size {
              description
                "Number of routes to store in history.";
              leaf bcdl {
                type uint32 {
                  range "10..2000000" {
                    description
                      "Maximum BCDL redistribution history size.";
                  }
                }
                description
                  "BCDL clients only";
              }
              leaf protocols {
                type uint32 {
                  range "10..250000" {
                    description
                      "Maximum protocol redistribution history size.";
                  }
                }
                description
                  "Protocol clients only";
              }
            }
          }
        }
      }
      leaf recursion-depth-max {
        type uint32 {
          range "5..16" {
            description
              "Maximum depth for route recursion check.";
          }
        }
        description
          "Set maximum depth for route recursion check.";
      }
    }
  }
}
