module Cisco-IOS-XR-sysmgr-act {
  namespace "http://cisco.com/ns/yang/Cisco-IOS-XR-sysmgr-act";
  prefix sysmgr-act;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR sysmgr action package configuration.
     
     Copyright (c) 2016-2019 by Cisco Systems, Inc.
     All rights reserved.";

  revision 2019-04-05 {
    description
      "Establish semantic version baseline.";
    semver:module-version "1.0.0";
  }
  revision 2017-03-03 {
    description
      "IOS XR 6.3.1 revision.";
  }

  rpc sysmgr-process-restart {
    description
      "Restart an XR process";
    input {
      leaf process-name {
        type string;
        mandatory true;
        description
          "XR process name or Job Id e.g. bgp, ospf";
      }
      leaf location {
        type string;
        description
          "XR node identifier e.g. 0/RP0/CPU0, 0/0/CPU0";
      }
    }
  }
}
