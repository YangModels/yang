module Cisco-IOS-XR-hw-module-cfg {
  namespace "http://cisco.com/ns/yang/Cisco-IOS-XR-hw-module-cfg";
  prefix hw-module-cfg;

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR hw-module package configuration.
     
     This module contains definitions
     for the following management objects:
       hw-module: HW module configuration
     
     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  grouping LOCATION-TABLE {
    description
      "Common node of shutdown, auto-reset-disable";
    container locations {
      description
        "Location of HW module";
      list location {
        key "location";
        description
          "Location of HW module";
        leaf location {
          type string;
          description
            "Location String";
        }
      }
    }
  }

  container hw-module {
    description
      "HW module configuration";
    container auto-reset-disable {
      description
        "Do not reset HW module on fault";
      uses LOCATION-TABLE;
    }
    container shutdown {
      description
        "Shutdown HW module";
      uses LOCATION-TABLE;
    }
  }
}
