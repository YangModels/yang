module Cisco-IOS-XR-spi-invmgr-oper {
  namespace "http://cisco.com/ns/yang/Cisco-IOS-XR-spi-invmgr-oper";
  prefix spi-invmgr-oper;

  import Cisco-IOS-XR-types {
    prefix xr;
  }
  import cisco-semver {
    prefix semver;
  }
  include Cisco-IOS-XR-spi-invmgr-oper-sub1 {
    revision-date 2019-04-05;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR spi-invmgr package operational data.
     
     This module contains definitions
     for the following management objects:
       inventory: Inventory Operational data space
     
     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  container inventory {
    config false;
    description
      "Inventory Operational data space";
    container racks {
      description
        "Entities";
      list rack {
        key "name";
        description
          "Rack Number";
        leaf name {
          type xr:Cisco-ios-xr-string;
          description
            "Rack name";
        }
        list entity {
          key "name";
          description
            "Entity name";
          container subentities {
            description
              "SubEntities Table";
            list subentity {
              key "name";
              description
                "Subentity";
              leaf name {
                type string;
                description
                  "Subentity name";
              }
              uses INV-PHY-ENTITY-BASIC-INFO;
            }
          }
          container attributes {
            description
              "Attributes";
            container inv-asset-bag {
              description
                "Inventory Asset Bag";
              uses INV-PHY-ENTITY-ASSET-INFO;
            }
            container inv-basic-bag {
              description
                "Inventory Basic Bag";
              uses INV-PHY-ENTITY-BASIC-INFO;
            }
            leaf pi-card-type {
              type uint32 {
                range "0..4294967295";
              }
              description
                "PI Card Type";
            }
            leaf node-id {
              type uint32 {
                range "0..4294967295";
              }
              description
                "Node ID Tuple";
            }
            leaf pd-card-type {
              type uint32 {
                range "0..4294967295";
              }
              description
                "PD Card Type";
            }
          }
          leaf name {
            type string;
            description
              "Entity name";
          }
        }
      }
    }
  }
}
