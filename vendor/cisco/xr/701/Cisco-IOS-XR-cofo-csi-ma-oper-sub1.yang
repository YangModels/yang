submodule Cisco-IOS-XR-cofo-csi-ma-oper-sub1 {
  belongs-to Cisco-IOS-XR-cofo-csi-ma-oper {
    prefix Cisco-IOS-XR-cofo-csi-ma-oper;
  }

  import ietf-inet-types {
    prefix inet;
  }
  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR cofo-csi-ma package operational data.
     
     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  typedef Csi-ma-fo-timer-state {
    type enumeration {
      enum "csi-ma-fo-default" {
        value 1;
        description
          "Default state";
      }
      enum "csi-ma-fo-push-self-data" {
        value 2;
        description
          "Push self data";
      }
      enum "csi-ma-fo-sync-rem-data" {
        value 3;
        description
          "Sync remote data";
      }
      enum "csi-ma-fo-synced" {
        value 4;
        description
          "Synced";
      }
      enum "csi-ma-fo-max" {
        value 5;
        description
          "Max state";
      }
    }
    description
      "Fail Over Timer state";
  }

  typedef Csi-ma-conn-state {
    type enumeration {
      enum "csi-ma-conn-default" {
        description
          "Default connection state";
      }
      enum "csi-ma-conn-closed" {
        description
          "Connection closed";
      }
      enum "csi-ma-conn-opened" {
        description
          "Connection opened";
      }
      enum "csi-ma-conn-synced" {
        description
          "Connection synced";
      }
      enum "csi-ma-conn-max" {
        description
          "Unknown connection state";
      }
    }
    description
      "CSI-MA connection state enum type";
  }

  typedef Csi-ipv6 {
    type inet:ipv6-address;
    description
      "Csi ipv6";
  }

  typedef Csi-ipv4 {
    type inet:ipv4-address;
    description
      "Csi ipv4";
  }

  typedef Csi-ma-afi {
    type enumeration {
      enum "csi-afi-ipv4" {
        value 1;
        description
          "IPv4 address family";
      }
      enum "csi-afi-ipv6" {
        value 2;
        description
          "IPv6 address family";
      }
      enum "csi-afi-invalid" {
        value 3;
        description
          "Invalid address family";
      }
    }
    description
      "CSI MA Address family enum type";
  }

  typedef Im-state {
    type uint32;
    description
      "Im state";
  }

  typedef Csi-ma-item-state {
    type enumeration {
      enum "csi-ma-item-create-req" {
        description
          "Interface create requested, wating for ack";
      }
      enum "csi-ma-item-attr-req" {
        description
          "Requested attributes passed from pub-sub admin";
      }
      enum "csi-ma-item-valid" {
        description
          "Valid entry";
      }
      enum "csi-ma-item-synced" {
        description
          "Replicated and synced to all nodes";
      }
      enum "csi-ma-item-mark-ed" {
        description
          "Marked for sweep at EOD";
      }
      enum "csi-ma-item-invalid" {
        description
          "Marked for delete in IM and then purge entry";
      }
      enum "csi-ma-item-delete-req" {
        description
          "Interface delete requested, wating for ack";
      }
      enum "csi-ma-item-max-states" {
        description
          "Invalid state";
      }
    }
    description
      "CSI MA item state enum type";
  }

  typedef Im-pic {
    type uint64;
    description
      "Im pic";
  }

  grouping CSI-MA-ADMIN-INFO {
    description
      "CSI-MA Admin information";
    leaf csi-index-xr {
      type uint32;
      description
        "CSI Index";
    }
    leaf sdr-id {
      type uint32;
      description
        "Local SDR ID";
    }
    leaf peer-sdr-id {
      type uint32;
      description
        "Peer SDR ID";
    }
    leaf peer-sdr-name {
      type string;
      description
        "Peer SDR name";
    }
    leaf state {
      type Csi-ma-item-state;
      description
        "Item State";
    }
    leaf csi-helper-reg {
      type boolean;
      description
        "CSI Helper reg flag";
    }
  }

  grouping CSI-MA-REMOTE-INFO {
    description
      "CSI-MA Remote information";
    container pub-data {
      description
        "Published data";
      uses CSI-HELPER-PUB;
    }
    leaf sdr-id-xr {
      type uint32;
      description
        "SDR ID";
    }
    leaf state {
      type Csi-ma-item-state;
      description
        "Remote data entry state";
    }
  }

  grouping CSI-MA-GLOBAL-INFO {
    description
      "CSI-MA global information";
    leaf invmgr-conn-state {
      type Csi-ma-conn-state;
      description
        "Inventory manager connection state";
    }
    leaf fail-over-timer-state {
      type Csi-ma-fo-timer-state;
      description
        "Fail Over Timer state for remote data";
    }
    leaf own-im-conn-state {
      type Csi-ma-conn-state;
      description
        "Owner channel IM connection state";
    }
    leaf gdp-im-conn-state {
      type Csi-ma-conn-state;
      description
        "GDP IM connection state";
    }
    leaf l3p-im-conn-state {
      type Csi-ma-conn-state;
      description
        "L3P IM connection state";
    }
  }

  grouping CSI-MA-ETHER-INTERFACE-INFO {
    description
      "CSI-Ether Interface information";
    leaf name {
      type string;
      description
        "Interface name";
    }
    leaf handle {
      type xr:Interface-name;
      description
        "Interface handle";
    }
    leaf csi-index {
      type uint32;
      description
        "CSI Index";
    }
    leaf state {
      type Csi-ma-item-state;
      description
        "Item state";
    }
    leaf if-state {
      type Im-state;
      description
        "Interface state";
    }
  }

  grouping CSI-INDEX-INFO {
    description
      "CSI Index and IP information type";
    leaf csi-index {
      type uint32;
      description
        "CSI Index";
    }
    list ip-arr {
      description
        "CSI IP Array";
      uses CSI-IPADDR;
    }
  }

  grouping CSI-HELPER-PUB {
    description
      "CSI Helper publish data";
    leaf-list csi-pic-arr {
      type uint64;
      description
        "CSI PIC Array";
    }
    list csi-info-arr {
      description
        "CSI Index - IP Array";
      uses CSI-INDEX-INFO;
    }
  }

  grouping CSI-IPADDR {
    description
      "IP Address";
    leaf af {
      type Csi-ma-afi;
      description
        "AF";
    }
    leaf ipv4 {
      when "../af = 'csi-afi-ipv4'" {
        description
          "../AF = 'CSI_AFI_IPV4'";
      }
      type Csi-ipv4;
      description
        "IPv4";
    }
    leaf ipv6 {
      when "../af = 'csi-afi-ipv6'" {
        description
          "../AF = 'CSI_AFI_IPV6'";
      }
      type Csi-ipv6;
      description
        "IPv6";
    }
  }

  grouping CSI-MA-INTERFACE-INFO {
    description
      "CSI-MA Interface information";
    container pub-data {
      description
        "Remote published data";
      uses CSI-HELPER-PUB;
    }
    container csi-ether-info {
      description
        "CSI-Ether Interface information";
      uses CSI-MA-ETHER-INTERFACE-INFO;
    }
    leaf name {
      type string;
      description
        "Interface name";
    }
    leaf handle {
      type xr:Interface-name;
      description
        "Interface handle";
    }
    leaf csi-index-xr {
      type uint32;
      description
        "CSI Index";
    }
    leaf sdr-id {
      type uint32;
      description
        "SDR ID";
    }
    leaf peer-sdr-id {
      type uint32;
      description
        "Peer SDR ID";
    }
    leaf repl-handle {
      type uint32;
      description
        "Replication handle";
    }
    leaf repl-fail-count {
      type uint32;
      description
        "Replication fail count";
    }
    leaf state {
      type Csi-ma-item-state;
      description
        "Item state";
    }
    leaf if-state {
      type Im-state;
      description
        "Interface state";
    }
    leaf rem-slice-attr {
      type boolean;
      description
        "Rem slice attribute";
    }
    leaf rem-ip-attr {
      type boolean;
      description
        "Rem IP attribute";
    }
    list local-ip-arr {
      description
        "Local IP addresses";
      uses CSI-IPADDR;
    }
    list peer-ip-arr {
      description
        "Peer IP addresses";
      uses CSI-IPADDR;
    }
  }

  grouping CSI-MA-SLICE {
    description
      "CSI-MA slice information type";
    leaf slice-node-id {
      type uint32;
      description
        "Slice Node ID";
    }
    leaf admin-up {
      type boolean;
      description
        "Admin state UP flag";
    }
    leaf oper-up {
      type boolean;
      description
        "Oper state UP flag";
    }
    leaf pic {
      type Im-pic;
      description
        "PIC value";
    }
    leaf-list csi-pic-arr {
      type Im-pic;
      description
        "CSI PIC array";
    }
  }

  grouping CSI-MA-NODE-INFO {
    description
      "CSI-MA Node information";
    leaf rack-slot-id {
      type uint64;
      description
        "Rack slot ID";
    }
    leaf node-id {
      type uint32;
      description
        "Node id";
    }
    leaf node-up {
      type boolean;
      description
        "Node up flag";
    }
    list slice-arr {
      description
        "Slice array associated with node";
      uses CSI-MA-SLICE;
    }
  }
}
