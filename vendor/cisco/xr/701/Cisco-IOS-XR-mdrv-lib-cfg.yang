module Cisco-IOS-XR-mdrv-lib-cfg {
  namespace "http://cisco.com/ns/yang/Cisco-IOS-XR-mdrv-lib-cfg";
  prefix mdrv-lib-cfg;

  import ietf-yang-types {
    prefix yang;
  }
  import cisco-semver {
    prefix semver;
  }
  import Cisco-IOS-XR-ifmgr-cfg {
    prefix a1;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR mdrv-lib package configuration.
     
     This module contains definitions
     for the following management objects:
       fast-shutdown: Fast Shutdown configuration
     
     This YANG module augments the
       Cisco-IOS-XR-ifmgr-cfg
     module with configuration data.
     
     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  augment "/a1:interface-configurations/a1:interface-configuration" {
    description
      "This augment extends the configuration data of
       'Cisco-IOS-XR-ifmgr-cfg'";
    leaf fast-shutdown {
      type empty;
      description
        "Enable Fast Shutdown for this interface";
    }
  }
  augment "/a1:interface-configurations/a1:interface-configuration" {
    description
      "This augment extends the configuration data of
       'Cisco-IOS-XR-ifmgr-cfg'";
    leaf mac-addr {
      type yang:mac-address;
      description
        "Set the Mac address on an interface";
    }
  }
  container fast-shutdown {
    description
      "Fast Shutdown configuration";
    leaf ethernet {
      type empty;
      description
        "Enable Fast Shutdown for all Ethernet interfaces";
    }
  }
}
