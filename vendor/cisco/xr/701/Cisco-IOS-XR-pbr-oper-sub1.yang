submodule Cisco-IOS-XR-pbr-oper-sub1 {
  belongs-to Cisco-IOS-XR-pbr-oper {
    prefix Cisco-IOS-XR-pbr-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR pbr package operational data.
     
     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  typedef Policy-state {
    type enumeration {
      enum "active" {
        value 0;
        description
          "active";
      }
      enum "suspended" {
        value 1;
        description
          "suspended";
      }
    }
    description
      "Different Interface states";
  }

  grouping HTTP-ENRICH-STATS-ST {
    description
      "HTTP Enrichment Stats";
    leaf rqst-rcvd-packets {
      type uint64;
      description
        "TotalNum of pkts HTTP request received";
    }
    leaf rqst-rcvd-bytes {
      type uint64;
      units "byte";
      description
        "TotalNum of Bytes HTTP request received";
    }
    leaf drop-packets {
      type uint64;
      description
        "Dropped  packets";
    }
    leaf drop-bytes {
      type uint64;
      units "byte";
      description
        "Dropped bytes";
    }
    leaf resp-sent-packets {
      type uint64;
      description
        "TotalNum of pkts HTTP Enrichment response sent";
    }
    leaf resp-sent-bytes {
      type uint64;
      units "byte";
      description
        "TotalNum of Bytes HTTP Enrichment response sent";
    }
    leaf req-sent-packets {
      type uint64;
      description
        "TotalNum of pkts HTTP Enrichment request sent";
    }
    leaf tcp-sent-packets {
      type uint64;
      description
        "TotalNum of pkts HTTP Enrichment TCP packet sent";
    }
  }

  grouping HTTPR-STATS-ST {
    description
      "HTTPR Stats";
    leaf rqst-rcvd-packets {
      type uint64;
      description
        "TotalNum of pkts HTTP request received";
    }
    leaf rqst-rcvd-bytes {
      type uint64;
      units "byte";
      description
        "TotalNum of Bytes HTTP request received";
    }
    leaf drop-packets {
      type uint64;
      description
        "Dropped  packets";
    }
    leaf drop-bytes {
      type uint64;
      units "byte";
      description
        "Dropped bytes";
    }
    leaf resp-sent-packets {
      type uint64;
      description
        "TotalNum of pkts HTTPR response sent";
    }
    leaf resp-sent-bytes {
      type uint64;
      units "byte";
      description
        "TotalNum of Bytes HTTPR response sent";
    }
  }

  grouping GEN-STATS-ST {
    description
      "Counters common to all features";
    leaf transmit-packets {
      type uint64;
      units "byte";
      description
        "Transmitted packets (packets/bytes)";
    }
    leaf transmit-bytes {
      type uint64;
      units "byte";
      description
        "Transmitted bytes (packets/bytes)";
    }
    leaf total-drop-packets {
      type uint64;
      units "byte";
      description
        "Dropped packets (packets/bytes)";
    }
    leaf total-drop-bytes {
      type uint64;
      units "byte";
      description
        "Dropped bytes (packets/bytes)";
    }
    leaf total-drop-rate {
      type uint32;
      units "byte";
      description
        "Total drop rate (packets/bytes)";
    }
    leaf match-data-rate {
      type uint32;
      units "kbit/s";
      description
        "Incoming matched data rate in kbps";
    }
    leaf total-transmit-rate {
      type uint32;
      units "kbit/s";
      description
        "Total transmit rate in kbps";
    }
    leaf pre-policy-matched-packets {
      type uint64;
      description
        "Matched pkts before applying policy";
    }
    leaf pre-policy-matched-bytes {
      type uint64;
      units "byte";
      description
        "Matched bytes before applying policy";
    }
  }

  grouping CLASS-STATS {
    description
      "CLASS STATS";
    container general-stats {
      description
        "general stats";
      uses GEN-STATS-ST;
    }
    container httpr-stats {
      description
        "HTTPR stats";
      uses HTTPR-STATS-ST;
    }
    container http-enrich-stats {
      description
        "HTTP Enrichment stats";
      uses HTTP-ENRICH-STATS-ST;
    }
    leaf counter-validity-bitmask {
      type uint64;
      units "byte";
      description
        " Bitmask to indicate which counter or counters
         are undetermined. Counters will be marked
         undetermined when one or more classes share
         queues with class-default because in such cases
         the value of counters for each class is invalid.
         Based on the flag(s) set, the following counters
         will be marked undetermined. For example, if
         value of this object returned is 0x00000101,
         counters
         TransmitPackets/TransmitBytes/TotalTransmitRate
         and DropPackets/DropBytes are undetermined
         .0x00000001 - Transmit
         (TransmitPackets/TransmitBytes/TotalTransmitRate
         ), 0x00000002 - Drop
         (TotalDropPackets/TotalDropBytes/TotalDropRate),
         0x00000004 - Httpr
         (HttprTransmitPackets/HttprTransmitBytes),
         0x00000020 - HttpErich
         (HttpErichTransmitPackets
         /HttpEnrichTransmitBytes), ";
    }
    leaf class-name {
      type string {
        length "0..65";
      }
      description
        "ClassName";
    }
    leaf class-id {
      type uint32;
      description
        "ClassId";
    }
  }

  grouping PBR-STATS {
    description
      "policy map statistics";
    leaf node-name {
      type string {
        length "0..42";
      }
      description
        "NodeName";
    }
    leaf policy-name {
      type string {
        length "0..65";
      }
      description
        "PolicyName";
    }
    leaf state {
      type Policy-state;
      description
        "State";
    }
    leaf state-description {
      type string {
        length "0..128";
      }
      description
        "StateDescription";
    }
    list class-stat {
      description
        "Array of classes contained in policy";
      uses CLASS-STATS;
    }
  }
}
