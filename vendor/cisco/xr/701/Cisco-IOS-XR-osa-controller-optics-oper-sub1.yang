submodule Cisco-IOS-XR-osa-controller-optics-oper-sub1 {
  belongs-to Cisco-IOS-XR-osa-controller-optics-oper {
    prefix Cisco-IOS-XR-osa-controller-optics-oper;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This submodule contains a collection of YANG definitions
     for Cisco IOS-XR osa-controller-optics package operational data.
     
     Copyright (c) 2013-2019 by Cisco Systems, Inc.
     All rights reserved.";

  revision 2019-04-05 {
    description
      "Establish semantic version baseline.";
    semver:module-version "1.0.0";
  }
  revision 2019-02-16 {
    description
      "Initial Revision.";
  }
  revision 2015-11-09 {
    description
      "IOS XR 6.0 revision.";
  }

  typedef Osa-edm-fec {
    type enumeration {
      enum "none" {
        value 0;
        description
          "None";
      }
      enum "standard" {
        value 1;
        description
          "Standard";
      }
      enum "sd7" {
        value 2;
        description
          "SD7";
      }
      enum "sd15" {
        value 3;
        description
          "SD15";
      }
      enum "sd20" {
        value 4;
        description
          "SD20";
      }
      enum "sd27" {
        value 5;
        description
          "SD27";
      }
      enum "sd29" {
        value 6;
        description
          "SD29";
      }
      enum "staircase" {
        value 7;
        description
          "Staircase";
      }
      enum "sd15-de" {
        value 8;
        description
          "SD15 DE";
      }
      enum "staircase-de" {
        value 9;
        description
          "Staircase DE";
      }
    }
    description
      "Osa edm fec";
  }

  typedef Osa-edm-trunk-bitrate {
    type enumeration {
      enum "none" {
        value 0;
        description
          "No Trunk Config";
      }
      enum "fifty-gig" {
        value 1;
        description
          "Fifty Gig";
      }
      enum "hundred-gig" {
        value 2;
        description
          "Hundred Gig";
      }
      enum "one-fifty-gig" {
        value 3;
        description
          "One Fifty Gig";
      }
      enum "two-hundred-gig" {
        value 4;
        description
          "Two Hundred Gig";
      }
      enum "two-fifty-gig" {
        value 5;
        description
          "Two Fifty Gig";
      }
      enum "three-hundred-gig" {
        value 6;
        description
          "Three Hundred Gig";
      }
      enum "three-fifty-gig" {
        value 7;
        description
          "Three Fifty Gig";
      }
      enum "four-hundred-gig" {
        value 8;
        description
          "Four Hundred Gig";
      }
      enum "four-fifty-gig" {
        value 9;
        description
          "Four Fifty Gig";
      }
      enum "five-hundred-gig" {
        value 10;
        description
          "Five Hundred Gig";
      }
      enum "five-fifty-gig" {
        value 11;
        description
          "Five Fifty Gig";
      }
      enum "six-hundred-gig" {
        value 12;
        description
          "Six Hundred Gig";
      }
    }
    description
      "Osa edm trunk bitrate";
  }

  grouping OSA-OPTICS-BPS-GBD-CAPAB-INFO-B {
    description
      "OSA OPTICS BPS GBD CAPAB INFO B";
    leaf trunk-rate {
      type Osa-edm-trunk-bitrate;
      description
        "Trunk Rate";
    }
    leaf fec-type {
      type Osa-edm-fec;
      description
        "Fec Type";
    }
    leaf bps {
      type string {
        length "0..10";
      }
      units "bit/s";
      description
        "BPS";
    }
    leaf baud-rate-approx {
      type string {
        length "0..11";
      }
      description
        "Approximated Baudrate";
    }
  }

  grouping OSA-OPTICS-BPS-GBD-CAPAB-B {
    description
      "OSA Optics bps-gbd capab entries";
    list bps-baud-rate-capab-info {
      description
        "bps baud rate capab info";
      uses OSA-OPTICS-BPS-GBD-CAPAB-INFO-B;
    }
  }
}
