module Cisco-IOS-XR-dnx-driver-oper {
  namespace "http://cisco.com/ns/yang/Cisco-IOS-XR-dnx-driver-oper";
  prefix dnx-driver-oper;

  import Cisco-IOS-XR-types {
    prefix xr;
  }
  import cisco-semver {
    prefix semver;
  }
  include Cisco-IOS-XR-dnx-driver-oper-sub1 {
    revision-date 2019-04-05;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR dnx-driver package operational data.
     
     This module contains definitions
     for the following management objects:
       fia: FIA driver operational data
     
     Copyright (c) 2013-2019 by Cisco Systems, Inc.
     All rights reserved.";

  revision 2019-04-05 {
    description
      "Establish semantic version baseline.";
    semver:module-version "1.0.0";
  }
  revision 2017-08-29 {
    description
      "Changed blk and field info to be dynamic.";
  }
  revision 2015-11-09 {
    description
      "IOS XR 6.0 revision.";
  }

  typedef Link-option-string {
    type string {
      pattern "(flap)|(topo)";
    }
    description
      "flap:Display link flap info, topo:Display link
       topo info";
  }

  typedef Fia-has-phy-location {
    type uint32 {
      range "0..1";
    }
    description
      "Fia has phy location";
  }

  typedef Fia-max-lc-slot {
    type uint32 {
      range "0..16";
    }
    description
      "Fia max lc slot";
  }

  typedef Fia-max-asic-instances {
    type uint32 {
      range "0..255";
    }
    description
      "Fia max asic instances";
  }

  typedef Link-info-max-number {
    type uint32 {
      range "0..111";
    }
    description
      "Link info max number";
  }

  typedef Diag-shell-unit-number {
    type uint32 {
      range "0..63";
    }
    description
      "Diag shell unit number";
  }

  container fia {
    config false;
    description
      "FIA driver operational data";
    container nodes {
      description
        "FIA driver operational data for available nodes";
      list node {
        key "node-name";
        description
          "FIA operational data for a particular node";
        container rx-link-information {
          description
            "FIA RX link related information";
          container link-options {
            description
              "Option table for link rx information";
            list link-option {
              key "option";
              description
                "Option : topo , flag , stats";
              container rx-asic-instances {
                description
                  "Instance table for rx information";
                list rx-asic-instance {
                  key "instance";
                  description
                    "Instance number for rx link information";
                  container rx-links {
                    description
                      "Link table class for rx information";
                    list rx-link {
                      description
                        "Link number for rx link information";
                      leaf start-number {
                        type Link-info-max-number;
                        description
                          "Link Starting number";
                      }
                      leaf end-number {
                        type Link-info-max-number;
                        description
                          "Link Ending number";
                      }
                      leaf status-option {
                        type xr:Cisco-ios-xr-string;
                        description
                          "RX link status option";
                      }
                      list rx-link {
                        key "link";
                        description
                          "Single link information";
                        leaf link {
                          type Link-info-max-number;
                          description
                            "Single link";
                        }
                        uses FIA-EDM-RXLINK;
                      }
                    }
                  }
                  leaf instance {
                    type Fia-max-asic-instances;
                    description
                      "Receive instance";
                  }
                }
              }
              leaf option {
                type Link-option-string;
                description
                  "Link option";
              }
            }
          }
        }
        container driver-information {
          description
            "FIA Driver Related Information";
          uses FIA-EDM-DRIVER-INFO;
        }
        container clear-statistics {
          description
            "Clear statistics information";
          container asic-instances {
            description
              "Instance table for clear statistics
               information";
            list asic-instance {
              key "asic-instance";
              description
                "Asic instance to be cleared";
              leaf asic-instance {
                type Fia-max-asic-instances;
                description
                  "Asic instance";
              }
              leaf instance {
                type Fia-max-asic-instances;
                mandatory true;
                description
                  "Clear value";
              }
            }
          }
        }
        container event-history {
          description
            "FIA event history information";
          container event-history-asic-instances {
            description
              "Instance table for event history";
            list event-history-asic-instance {
              key "instance";
              description
                "Asic instance to be displayed";
              leaf instance {
                type Fia-max-asic-instances;
                description
                  "Asic instance";
              }
              uses FIA-EDM-EVENT-HISTORY-INFO;
            }
          }
        }
        container tx-link-information {
          description
            "FIA TX link related information";
          container tx-status-option-table {
            description
              "Link table for tx information";
            container tx-status-option {
              description
                "Option: data, ctrl, all- for now none";
              container tx-asic-instances {
                description
                  "Instance table for tx information";
                list tx-asic-instance {
                  key "instance";
                  description
                    "Instance number for tx link information";
                  container tx-links {
                    description
                      "Link table for tx information";
                    list tx-link {
                      description
                        "Link number for tx link information";
                      leaf start-number {
                        type Link-info-max-number;
                        description
                          "Link Starting Number";
                      }
                      leaf end-number {
                        type Link-info-max-number;
                        description
                          "Link Ending Number";
                      }
                      list tx-link {
                        key "link";
                        description
                          "Single link information";
                        leaf link {
                          type Link-info-max-number;
                          description
                            "Single Link";
                        }
                        uses FIA-EDM-TXLINK;
                      }
                    }
                  }
                  leaf instance {
                    type Fia-max-asic-instances;
                    description
                      "Transmit instance";
                  }
                }
              }
            }
          }
        }
        container diag-shell {
          description
            "FIA diag shell information";
          container diag-shell-units {
            description
              "Unit table for diag shell";
            list diag-shell-unit {
              key "unit";
              description
                "Unit number for diag shell statistics";
              container commands {
                description
                  "Command table for diag shell";
                list command {
                  key "cmd";
                  description
                    "Command for diag shell statistics";
                  leaf cmd {
                    type string {
                      length "1..256";
                    }
                    description
                      "Shell command";
                  }
                  list output {
                    key "output";
                    description
                      "Added to support datalist";
                    leaf output {
                      type xr:Cisco-ios-xr-string;
                      description
                        "First line";
                    }
                    uses FIA-EDM-DIAG-SHELL-OUTPUT;
                  }
                }
              }
              leaf unit {
                type Diag-shell-unit-number;
                description
                  "Unit number";
              }
            }
          }
        }
        container oir-history {
          description
            "FIA operational data of oir history";
          container flags {
            description
              "Flag table for history";
            list flag {
              key "flag";
              description
                "Flag value for physical location";
              container slots {
                description
                  "Slot table for history";
                list slot {
                  key "slot";
                  description
                    "Slot number for getting history";
                  leaf slot {
                    type Fia-max-lc-slot;
                    description
                      "Slot number";
                  }
                  uses FIA-EDM-DRIVER-INFO;
                }
              }
              leaf flag {
                type Fia-has-phy-location;
                description
                  "Flag value";
              }
            }
          }
        }
        container asic-statistics {
          description
            "FIA asic statistics information";
          container statistics-asic-instances {
            description
              "Instance table for statistics";
            list statistics-asic-instance {
              key "instance";
              description
                "Asic instance for statistics";
              container pbc-statistics {
                description
                  "Packet Byte Counter for a Asic";
                container pbc-stats {
                  description
                    "PBC stats bag";
                  uses FIA-EDM-STATS-ASIC-PBC-INFO;
                }
              }
              container fmac-statistics {
                description
                  "Statistics of FMAC";
                container fmac-links {
                  description
                    "Link table for statistics";
                  list fmac-link {
                    key "link";
                    description
                      "Link number for statistics";
                    leaf link {
                      type Link-info-max-number;
                      description
                        "Link number";
                    }
                    list fmac-asic {
                      key "asic";
                      description
                        "Single aisc information";
                      leaf asic {
                        type Fia-max-asic-instances;
                        description
                          "Single asic";
                      }
                      uses FIA-EDM-STATS-ASIC-FMAC-INFO;
                    }
                  }
                }
              }
              leaf instance {
                type Fia-max-asic-instances;
                description
                  "Asic instance";
              }
            }
          }
        }
        leaf node-name {
          type xr:Node-id;
          description
            "Node ID";
        }
      }
    }
  }
}
