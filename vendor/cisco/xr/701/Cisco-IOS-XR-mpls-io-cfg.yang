module Cisco-IOS-XR-mpls-io-cfg {
  namespace "http://cisco.com/ns/yang/Cisco-IOS-XR-mpls-io-cfg";
  prefix mpls-io-cfg;

  import cisco-semver {
    prefix semver;
  }
  import Cisco-IOS-XR-ifmgr-cfg {
    prefix a1;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR mpls-io package configuration.
     
     This model is deprecated and is replaced by
     Cisco-IOS-XR-um-if-mpls-cfg.yang which will provide the
     compatible functionalities.
     
     This YANG module augments the
       Cisco-IOS-XR-ifmgr-cfg
     module with configuration data.
     
     Copyright (c) 2013-2019 by Cisco Systems, Inc.
     All rights reserved.";

  revision 2019-05-12 {
    description
      "Deprecated the native model, replaced by UM model.";
    semver:module-version "1.0.0";
  }
  revision 2019-04-05 {
    description
      "Establish semantic version baseline.";
  }
  revision 2017-05-18 {
    description
      "IOS XR 6.2.2 revision.";
  }
  revision 2015-11-09 {
    description
      "IOS XR 6.0 revision.";
  }

  augment "/a1:interface-configurations/a1:interface-configuration" {
    description
      "This augment extends the configuration data of
       'Cisco-IOS-XR-ifmgr-cfg'";
    container mpls {
      status deprecated;
      description
        "This model is deprecated and is replaced by
         Cisco-IOS-XR-um-if-mpls-cfg.yang which will
         provide the compatible functionalities.  MPLS
         configuration under an interface";
      container label-security {
        description
          "MPLS label security";
        leaf multi-label-drop {
          type empty;
          description
            "Enable drop of multi-labelled incoming packets
             on a Interface";
        }
        leaf rpf {
          type empty;
          description
            "Enable MPLS RPF for incoming packets on a
             Interface";
        }
      }
      leaf mtu {
        type uint32 {
          range "68..65535";
        }
        description
          "Set the MPLS MTU for the interface";
      }
    }
  }
}
