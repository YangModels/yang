module Cisco-IOS-XR-crypto-sam-oper {
  namespace "http://cisco.com/ns/yang/Cisco-IOS-XR-crypto-sam-oper";
  prefix crypto-sam-oper;

  import Cisco-IOS-XR-types {
    prefix xr;
  }
  import cisco-semver {
    prefix semver;
  }
  include Cisco-IOS-XR-crypto-sam-oper-sub1 {
    revision-date 2019-04-05;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR crypto-sam package operational data.
     
     This module contains definitions
     for the following management objects:
       sam: Software authentication manager certificate information
     
     Copyright (c) 2013-2019 by Cisco Systems, Inc.
     All rights reserved.";

  revision 2019-04-05 {
    description
      "Establish semantic version baseline.";
    semver:module-version "1.0.0";
  }
  revision 2017-09-07 {
    description
      "Fixed type translation error.";
  }
  revision 2015-01-07 {
    description
      "IOS XR 5.3.1 revision.";
  }

  container sam {
    config false;
    description
      "Software authentication manager certificate
       information";
    container system-information {
      description
        "SAM system information";
      uses CRYPTO-SAM-SYSINFO;
    }
    container log-contents {
      description
        "SAM log content table information";
      list log-content {
        key "number-of-lines";
        description
          "Number of lines for SAM log message";
        leaf number-of-lines {
          type uint32;
          description
            "Number of lines";
        }
        uses CRYPTO-LOG;
      }
    }
    container devices {
      description
        "Certificate device table information";
      list device {
        key "device-name";
        description
          "Certificate table device information";
        container certificate {
          description
            "Certificate table information";
          container brief {
            description
              "Certificate table brief information";
            uses CRYPTO-SAM-CERTIFICATE-COMMON;
          }
          container certificate-indexes {
            description
              "Certificate detail index table information";
            list certificate-index {
              key "index";
              description
                "Certificate detail index information";
              container detail {
                description
                  "Certificate table detail information";
                uses CRYPTO-SAM-CERTIFICATE-COMMON;
              }
              leaf index {
                type uint32;
                description
                  "Specify certificate index";
              }
            }
          }
        }
        leaf device-name {
          type xr:Cisco-ios-xr-string;
          description
            "Specify device name";
        }
      }
    }
    container packages {
      description
        "SAM certificate information  package";
      list package {
        key "package-name";
        description
          "SAM certificate information for a specific
           package";
        leaf package-name {
          type string;
          description
            "Specify package name";
        }
        uses CRYPTO-SAM-CERTIFICATE-COMMON;
      }
    }
    container certificate-revocations {
      description
        "Certificate revocation list index table
         information";
      list certificate-revocation {
        key "crl-index";
        description
          "Certificate revocation list index information";
        container certificate-revocation-list-detail {
          description
            "Certificate revocation list detail information";
          uses CRYPTO-SAM-CRL-INFO;
        }
        leaf crl-index {
          type uint32;
          description
            "CRL index";
        }
      }
    }
    container certificate-revocation-list-summary {
      description
        "Certificate revocation list summary information ";
      uses CRYPTO-SAM-CRL-INFO;
    }
  }
}
