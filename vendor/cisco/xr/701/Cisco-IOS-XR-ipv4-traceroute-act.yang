submodule Cisco-IOS-XR-ipv4-traceroute-act {
  belongs-to Cisco-IOS-XR-traceroute-act {
    prefix traceroute-act;
  }

  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR IPv4 traceroute action package configuration.
     
     Copyright (c) 2016-2019 by Cisco Systems, Inc.
     All rights reserved.";

  revision 2019-04-05 {
    description
      "Establish semantic version baseline.";
    semver:module-version "1.0.0";
  }
  revision 2016-09-17 {
    description
      "IOS XR 6.2.1 revision.";
  }

  grouping TRACEROUTE-OPTIONS {
    leaf destination {
      type string;
      mandatory true;
      description
        "Destination address or hostname";
    }
    leaf source {
      type string;
      description
        "Source address or interface";
    }
    leaf timeout {
      type uint32 {
        range "0..36";
      }
      default "3";
      description
        "Timeout in seconds";
    }
    leaf probe {
      type uint16 {
        range "1..64";
      }
      default "3";
      description
        "Probe count";
    }
    leaf numeric {
      type boolean;
      description
        "Numeric display only";
    }
    leaf vrf-name {
      type string;
      description
        "VRF name";
    }
    leaf min-ttl {
      type uint16 {
        range "0..255";
      }
      default "1";
      description
        "minimum time to live";
    }
    leaf max-ttl {
      type uint16 {
        range "0..255";
      }
      default "30";
      description
        "maximum time to live";
    }
    leaf port {
      type uint32 {
        range "0..65535";
      }
      description
        "Port numbe";
    }
    leaf verbose {
      type boolean;
      description
        "verbose output";
    }
  }

  grouping TRACEROUTE-OUTPUT {
    leaf destination {
      type string;
      description
        "Destination address or hostname";
    }
    container hops {
      list hop {
        key "hop-index";
        leaf hop-index {
          type uint32;
          description
            "Index of the hop";
        }
        leaf hop-address {
          type string;
          description
            "Address of the hop";
        }
        leaf hop-hostname {
          type string;
          description
            "Hostname of the hop";
        }
        container probes {
          list probe {
            key "probe-index";
            leaf probe-index {
              type uint32;
              description
                "Index of the probe";
            }
            leaf result {
              type string;
              description
                "Response for each probe";
            }
            leaf delta-time {
              type uint32;
              description
                "Delta time in seconds";
            }
            leaf hop-address {
              type string;
              description
                "Address of the hop";
            }
            leaf hop-hostname {
              type string;
              description
                "Hostname of the hop";
            }
            container srv6-header {
              leaf destination-address {
                type uint32;
                description
                  "Destination address for srv6 header";
              }
              leaf segments-left {
                type uint32;
                description
                  "Number of segments left";
              }
              container segments {
                leaf-list segment {
                  type string;
                  description
                    "sid in sidlist";
                }
              }
            }
          }
        }
      }
    }
    leaf verbose-output {
      type string;
      description
        "Verbose output";
    }
  }
}
