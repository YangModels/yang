module Cisco-IOS-XR-lib-mpp-cfg {
  namespace "http://cisco.com/ns/yang/Cisco-IOS-XR-lib-mpp-cfg";
  prefix lib-mpp-cfg;

  import ietf-inet-types {
    prefix inet;
  }
  import Cisco-IOS-XR-types {
    prefix xr;
  }
  import cisco-semver {
    prefix semver;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR lib-mpp package configuration.
     
     This module contains definitions
     for the following management objects:
       control-plane: Configure control Plane
     
     Copyright (c) 2013-2019 by Cisco Systems, Inc.
     All rights reserved.";

  revision 2019-04-05 {
    description
      "Establish semantic version baseline.";
    semver:module-version "1.0.0";
  }
  revision 2018-07-23 {
    description
      "Removing Third Party Applications schema.";
  }
  revision 2017-09-07 {
    description
      "Fixed type translation error.";
  }
  revision 2017-07-28 {
    description
      "Fixing Third Party Applications schema.";
  }
  revision 2015-07-30 {
    description
      "Descriptions updated.";
  }
  revision 2015-01-07 {
    description
      "IOS XR 5.3.1 revision.";
  }

  grouping HTTP-PROTOCOL {
    description
      "Common node of interface, all-interfaces";
    container http-protocol {
      description
        "Configure HTTP on this interface";
      uses PEER-CLASS;
    }
  }

  grouping SNMP-PROTOCOL {
    description
      "Common node of interface, all-interfaces";
    container snmp-protocol {
      description
        "Configure SNMP for this interface";
      uses PEER-CLASS;
    }
  }

  grouping TFTP-PROTOCOL {
    description
      "Common node of interface, all-interfaces";
    container tftp-protocol {
      description
        "Configure TFTP on this interface";
      uses PEER-CLASS;
    }
  }

  grouping INTERFACE-SELECTION {
    description
      "Common node of inband, outband";
    container interface-selection {
      description
        "Configure interfaces";
      container interfaces {
        description
          "Configure a specific interface";
        list interface {
          key "interface-name";
          description
            "Specific interface";
          leaf interface-name {
            type xr:Interface-name;
            description
              "Name of the Interface";
          }
          uses HTTP-PROTOCOL;
          uses TFTP-PROTOCOL;
          uses NETCONF-PROTOCOL;
          uses XR-XML;
          uses SSH-PROTOCOL;
          uses SNMP-PROTOCOL;
          uses TELNET-PROTOCOL;
          uses ALL-PROTOCOLS;
        }
      }
      container all-interfaces {
        description
          "Configure all Inband interfaces";
        uses HTTP-PROTOCOL;
        uses TFTP-PROTOCOL;
        uses NETCONF-PROTOCOL;
        uses XR-XML;
        uses SSH-PROTOCOL;
        uses SNMP-PROTOCOL;
        uses TELNET-PROTOCOL;
        uses ALL-PROTOCOLS;
      }
    }
  }

  grouping NETCONF-PROTOCOL {
    description
      "Common node of interface, all-interfaces";
    container netconf-protocol {
      description
        "Configure NETCONF protocol and peer addresses";
      uses PEER-CLASS;
    }
  }

  grouping PEER-PREFIX-CLASS {
    description
      "Common node of peer-v4, peer-v6";
    container peer-prefixes {
      description
        "Configure peer addresses with prefix";
      list peer-prefix {
        key "address-prefix";
        description
          "Peer address (with prefix)";
        leaf address-prefix {
          type inet:ip-prefix;
          description
            "prefix/length";
        }
      }
    }
  }

  grouping PEER-NO-PREFIX-CLASS {
    description
      "Common node of peer-v4, peer-v6";
    container peers {
      description
        "Configure peer addresses";
      list peer {
        key "address";
        description
          "Configure peer on the interface";
        leaf address {
          type inet:ip-address-no-zone;
          description
            "prefix";
        }
      }
    }
  }

  grouping XR-XML {
    description
      "Common node of interface, all-interfaces";
    container xr-xml {
      description
        "Configure XML and peer addresses";
      uses PEER-CLASS;
    }
  }

  grouping PEER-CLASS {
    description
      "Common node of snmp-protocol, http-protocol,
       ssh-protocol, telnet-protocol, tftp-protocol, xml
       , netconf-protocol, all-protocols";
    container peer-class {
      description
        "Configure peer addresses";
      container peer-v4 {
        description
          "Configure v4 peer addresses";
        uses PEER-NO-PREFIX-CLASS;
        uses PEER-PREFIX-CLASS;
      }
      container peer-v6 {
        description
          "Configure v6 peer addresses";
        uses PEER-NO-PREFIX-CLASS;
        uses PEER-PREFIX-CLASS;
      }
      leaf peer-all {
        type empty;
        description
          "Only takes 'True'";
      }
    }
  }

  grouping TELNET-PROTOCOL {
    description
      "Common node of interface, all-interfaces";
    container telnet-protocol {
      description
        "Configure Telnet for this interface";
      uses PEER-CLASS;
    }
  }

  grouping ALL-PROTOCOLS {
    description
      "Common node of interface, all-interfaces";
    container all-protocols {
      description
        "Configure all protocols on this interface";
      uses PEER-CLASS;
    }
  }

  grouping SSH-PROTOCOL {
    description
      "Common node of interface, all-interfaces";
    container ssh-protocol {
      description
        "Configure SSH protocol and peer addresses";
      uses PEER-CLASS;
    }
  }

  container control-plane {
    description
      "Configure control Plane";
    container management-plane-protection {
      description
        "Configure management plane protection";
      container outband {
        description
          "Outband Configuration";
        leaf outband-vrf {
          type string;
          description
            "Configure outband VRF";
        }
        uses INTERFACE-SELECTION;
      }
      container inband {
        description
          "Inband Configuration";
        uses INTERFACE-SELECTION;
      }
    }
  }
}
