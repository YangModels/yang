module Cisco-IOS-XR-sysadmin-tacacs-tacacs-server {
  namespace "http://www.cisco.com/ns/yang/Cisco-IOS-XR-sysadmin-tacacs-tacacs-server";
  prefix tacacs-server;

  import tailf-common {
    prefix tailf;
  }
  import ietf-inet-types {
    prefix inet;
  }
  import cisco-semver {
    prefix semver;
  }

  organization
    "Cisco Systems";
  contact
    "aaa-ng-tacacs-dev@cisco.com";
  description
    "This module defines the TACACS+ data model.
     
     Copyright (c) 2012-2019 by Cisco Systems, Inc.
     All rights reserved.";

  revision 2019-04-15 {
    description
      "Establish semantic version baseline.";
    semver:module-version "1.0.0";
  }
  revision 2017-05-10 {
    description
      "Namespace changed from tacacs to Cisco-IOS-XR-sysadmin-tacacs-tacacs-server";
  }
  revision 2015-06-06 {
    description
      "Initial creation";
  }

  typedef passwdStr {
    type tailf:aes-cfb-128-encrypted-string;
  }

  container tacacs-server {
    list host {
      key "ip port";
      max-elements "10";
      ordered-by user;
      leaf ip {
        type inet:ip-address;
      }
      leaf port {
        type inet:port-number {
          range "1 .. 65535";
        }
      }
      leaf timeout {
        type uint32 {
          range "1 .. 1000";
        }
      }
      leaf key {
        type passwdStr;
      }
    }
    leaf timeout {
      type uint32 {
        range "1 .. 1000";
      }
    }
    leaf key {
      type passwdStr;
    }
  }
}
