module Cisco-IOS-XR-gnss-oper {
  namespace "http://cisco.com/ns/yang/Cisco-IOS-XR-gnss-oper";
  prefix gnss-oper;

  import Cisco-IOS-XR-types {
    prefix xr;
  }
  import cisco-semver {
    prefix semver;
  }
  include Cisco-IOS-XR-gnss-oper-sub1 {
    revision-date 2019-04-05;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR gnss package operational data.
     
     This module contains definitions
     for the following management objects:
       gnss-receiver: GNSS receiver operational data
     
     Copyright (c) 2013-2019 by Cisco Systems, Inc.
     All rights reserved.";

  revision 2019-04-05 {
    description
      "Establish semantic version baseline.";
    semver:module-version "1.0.0";
  }
  revision 2017-09-07 {
    description
      "Fixed type translation error.";
  }
  revision 2015-11-09 {
    description
      "IOS XR 6.0 revision.";
  }

  container gnss-receiver {
    config false;
    description
      "GNSS receiver operational data";
    container nodes {
      description
        "Table for node-specific operational data";
      list node {
        key "node";
        description
          "Node-specific data for a particular node";
        container receivers {
          description
            "Table for node-specific operational data";
          list receiver {
            key "number";
            description
              "Operational data for a GNSS receiver";
            leaf number {
              type uint32;
              description
                "Number";
            }
            uses GNSSMGR-RX-INFO;
          }
        }
        leaf node {
          type xr:Node-id;
          description
            "Node";
        }
      }
    }
  }
}
