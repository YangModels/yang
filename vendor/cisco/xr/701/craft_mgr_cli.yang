module craft_mgr_cli {
  namespace "http://www.cisco.com/panini/calvados/craft_mgr";
  prefix crmgr;

  import Cisco-IOS-XR-sysadmin-show-trace {
    prefix show_trace;
  }
  import Cisco-IOS-XR-sysadmin-types {
    prefix calvados;
  }

  organization
    "Cisco Systems Inc.";
  contact
    "Cisco Systems, Inc.
     Customer Service
     
     Postal: 170 West Tasman Drive
     San Jose, CA 95134
     
     Tel: +1 800 553-NETS
     
     E-mail: cs-yang@cisco.com";
  description
    "This module holds Craft Mgr data.
     
     Copyright (c) 2012-2019 by Cisco Systems, Inc.
     All rights reserved.";

  revision 2015-08-30 {
    description
      "Initial version.";
  }

  grouping lcd-group {
    container message {
      container all {
        leaf op_message {
          type string {
            length "0..512";
          }
        }
      }
      container rack_loc {
        list location {
          key "rackId";
          leaf rackId {
            type calvados:rack-id;
          }
          leaf op_message {
            type string {
              length "0..512";
            }
          }
        }
      }
    }
    container name {
      container all {
        leaf lcd_name {
          type string {
            length "0..15";
          }
        }
      }
      container rack_loc {
        list location {
          key "rackId";
          leaf rackId {
            type calvados:rack-id;
          }
          leaf lcd_name {
            type string {
              length "0..15";
            }
          }
        }
      }
    }
    container alarm_category {
      container all {
        leaf lcd_alarm_category {
          type uint32 {
            range "0..3";
          }
        }
      }
      container rack_loc {
        list location {
          key "rackId";
          leaf rackId {
            type calvados:rack-id;
          }
          leaf lcd_alarm_category {
            type uint32 {
              range "0..3";
            }
          }
        }
      }
    }
  }

  container lcd {
    container config {
      description
        "Lcd configurational data";
      uses lcd-group;
    }
  }
  container craft_mgr {
    config false;
    uses show_trace:traceable;
  }
}
