module Cisco-IOS-XR-ncs4k-freqsync-cfg {
  namespace "http://cisco.com/ns/yang/Cisco-IOS-XR-ncs4k-freqsync-cfg";
  prefix ncs4k-freqsync-cfg;

  import ietf-yang-types {
    prefix yang;
  }
  import cisco-semver {
    prefix semver;
  }
  import Cisco-IOS-XR-freqsync-datatypes {
    prefix dt1;
  }
  import Cisco-IOS-XR-snmp-agent-cfg {
    prefix a1;
  }
  import Cisco-IOS-XR-ifmgr-cfg {
    prefix a2;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR ncs4k-freqsync package configuration.
     
     This module contains definitions
     for the following management objects:
       clock-interface: Configuration for a clock interface
       frequency-synchronization: Frequency Synchronization global
         configuration
     
     This YANG module augments the
       Cisco-IOS-XR-snmp-agent-cfg,
       Cisco-IOS-XR-ifmgr-cfg
     modules with configuration data.
     
     Copyright (c) 2013-2019 by Cisco Systems, Inc.
     All rights reserved.";

  revision 2019-04-05 {
    description
      "Establish semantic version baseline.";
    semver:module-version "1.0.0";
  }
  revision 2017-09-30 {
    description
      "Ensure propagation of MDA mandatory state to YANG model.";
  }
  revision 2015-11-09 {
    description
      "IOS XR 6.0 revision.";
  }

  typedef Fsync-system-timing-mode {
    type enumeration {
      enum "line-only" {
        value 2;
        description
          "Line-interfaces only";
      }
      enum "clock-only" {
        value 3;
        description
          "Clock-interfaces only";
      }
    }
    description
      "Fsync system timing mode";
  }

  typedef Fsync-clock-source {
    type enumeration {
      enum "system" {
        value 1;
        description
          "System";
      }
      enum "independent" {
        value 3;
        description
          "Independent";
      }
    }
    description
      "Fsync clock source";
  }

  typedef Fsync-source-selection-logging {
    type enumeration {
      enum "changes" {
        value 1;
        description
          "Log both selection changes and errors";
      }
      enum "errors" {
        value 2;
        description
          "Log selection errors";
      }
    }
    description
      "Fsync source selection logging";
  }

  augment "/a2:interface-configurations/a2:interface-configuration" {
    description
      "This augment extends the configuration data of
       'Cisco-IOS-XR-ifmgr-cfg'";
    container frequency-synchronization {
      description
        "Frequency Synchronization interface
         configuration";
      container input-quality-level {
        description
          "Set the input quality level";
        leaf quality-level-option {
          type dt1:Fsync-ql-option;
          must "../exact-quality-level-value or ../min-quality-level-value or ../max-quality-level-value";
          description
            "Quality level option";
        }
        leaf exact-quality-level-value {
          type dt1:Fsync-ql-value;
          must "../quality-level-option and not(../min-quality-level-value or ../max-quality-level-value)";
          description
            "Exact quality level value";
        }
        leaf min-quality-level-value {
          type dt1:Fsync-ql-value;
          must "../quality-level-option and not(../exact-quality-level-value)";
          description
            "Minimum quality level value";
        }
        leaf max-quality-level-value {
          type dt1:Fsync-ql-value;
          must "../quality-level-option and not(../exact-quality-level-value)";
          description
            "Maximum quality level value";
        }
      }
      container output-quality-level {
        description
          "Set the output quality level";
        leaf quality-level-option {
          type dt1:Fsync-ql-option;
          must "../exact-quality-level-value or ../min-quality-level-value or ../max-quality-level-value";
          description
            "Quality level option";
        }
        leaf exact-quality-level-value {
          type dt1:Fsync-ql-value;
          must "../quality-level-option and not(../min-quality-level-value or ../max-quality-level-value)";
          description
            "Exact quality level value";
        }
        leaf min-quality-level-value {
          type dt1:Fsync-ql-value;
          must "../quality-level-option and not(../exact-quality-level-value)";
          description
            "Minimum quality level value";
        }
        leaf max-quality-level-value {
          type dt1:Fsync-ql-value;
          must "../quality-level-option and not(../exact-quality-level-value)";
          description
            "Maximum quality level value";
        }
      }
      leaf ssm-disable {
        type empty;
        description
          "Disable SSM on this source";
      }
      leaf time-of-day-priority {
        type uint32 {
          range "1..254";
        }
        default "100";
        description
          "Set the time-of-day priority of this source";
      }
      leaf selection-input {
        type empty;
        description
          "Assign this source as a selection input";
      }
      leaf enable {
        type empty;
        description
          "Enable Frequency Synchronization";
      }
      leaf priority {
        type uint32 {
          range "1..254";
        }
        default "100";
        description
          "Set the priority of this source";
      }
      leaf wait-to-restore-time {
        type uint32 {
          range "0..12";
        }
        default "5";
        description
          "Set the wait-to-restore time for this source";
      }
    }
  }
  augment "/a1:snmp/a1:notification" {
    description
      "This augment extends the configuration data of
       'Cisco-IOS-XR-snmp-agent-cfg'";
    container frequency-synchronization {
      description
        "Frequency Synchronization trap configuration";
      leaf enable {
        type empty;
        description
          "Enable Frequency Synchronization traps";
      }
    }
  }
  container clock-interface {
    description
      "Configuration for a clock interface";
    container clocks {
      description
        "Configuration for a clock interface";
      list clock {
        key "clock-name";
        description
          "Configuration for a clock interface";
        container frequency-synchronization {
          description
            "Frequency Synchronization clock configuraiton";
          container input-quality-level {
            description
              "Set the input quality level";
            leaf quality-level-option {
              type dt1:Fsync-ql-option;
              must "../exact-quality-level-value or ../min-quality-level-value or ../max-quality-level-value";
              description
                "Quality level option";
            }
            leaf exact-quality-level-value {
              type dt1:Fsync-ql-value;
              must "../quality-level-option and not(../min-quality-level-value or ../max-quality-level-value)";
              description
                "Exact quality level value";
            }
            leaf min-quality-level-value {
              type dt1:Fsync-ql-value;
              must "../quality-level-option and not(../exact-quality-level-value)";
              description
                "Minimum quality level value";
            }
            leaf max-quality-level-value {
              type dt1:Fsync-ql-value;
              must "../quality-level-option and not(../exact-quality-level-value)";
              description
                "Maximum quality level value";
            }
          }
          container output-quality-level {
            description
              "Set the output quality level";
            leaf quality-level-option {
              type dt1:Fsync-ql-option;
              must "../exact-quality-level-value or ../min-quality-level-value or ../max-quality-level-value";
              description
                "Quality level option";
            }
            leaf exact-quality-level-value {
              type dt1:Fsync-ql-value;
              must "../quality-level-option and not(../min-quality-level-value or ../max-quality-level-value)";
              description
                "Exact quality level value";
            }
            leaf min-quality-level-value {
              type dt1:Fsync-ql-value;
              must "../quality-level-option and not(../exact-quality-level-value)";
              description
                "Minimum quality level value";
            }
            leaf max-quality-level-value {
              type dt1:Fsync-ql-value;
              must "../quality-level-option and not(../exact-quality-level-value)";
              description
                "Maximum quality level value";
            }
          }
          leaf ssm-disable {
            type empty;
            description
              "Disable SSM on this source";
          }
          leaf wait-to-restore-time {
            type uint32 {
              range "0..12";
            }
            default "5";
            description
              "Set the wait-to-restore time for this source";
          }
          leaf time-of-day-priority {
            type uint32 {
              range "1..254";
            }
            default "100";
            description
              "Set the time-of-day priority of this source";
          }
          leaf priority {
            type uint32 {
              range "1..254";
            }
            default "100";
            description
              "Set the priority of this source";
          }
          leaf selection-input {
            type empty;
            description
              "Assign this source as a selection input";
          }
        }
        leaf clock-name {
          type string;
          description
            "Clock Name";
        }
      }
    }
  }
  container frequency-synchronization {
    description
      "Frequency Synchronization global configuration";
    leaf clock-identity {
      type yang:mac-address;
      description
        "Local clock ID";
    }
    leaf quality-level-option {
      type dt1:Fsync-ql-option;
      default "option-1";
      description
        "Quality level option";
    }
    leaf enable {
      type empty;
      description
        "Enable Frequency Synchronization";
    }
    leaf source-selection-logging {
      type Fsync-source-selection-logging;
      description
        "Source selection logging option";
    }
    leaf clock-interface-source-type {
      type Fsync-clock-source;
      description
        "Clock interface source type";
    }
    leaf system-timing-mode {
      type Fsync-system-timing-mode;
      description
        "System timing mode";
    }
  }
}
