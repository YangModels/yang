module Cisco-IOS-XR-dwdm-ui-oper {
  namespace "http://cisco.com/ns/yang/Cisco-IOS-XR-dwdm-ui-oper";
  prefix dwdm-ui-oper;

  import Cisco-IOS-XR-types {
    prefix xr;
  }
  import cisco-semver {
    prefix semver;
  }
  include Cisco-IOS-XR-dwdm-ui-oper-sub1 {
    revision-date 2019-04-05;
  }

  organization
    "Cisco Systems, Inc.";
  contact
    "Cisco Systems, Inc.
     Customer Service
     
     Postal: 170 West Tasman Drive
     San Jose, CA 95134
     
     Tel: +1 800 553-NETS
     
     E-mail: cs-yang@cisco.com";
  description
    "This module contains a collection of YANG definitions
     for Cisco IOS-XR dwdm-ui package operational data.
     
     This module contains definitions
     for the following management objects:
       dwdm: DWDM operational data
       vtxp: VTXP specific operational data
     
     Copyright (c) 2013-2019 by Cisco Systems, Inc.
     All rights reserved.";

  revision 2019-04-05 {
    description
      "Establish semantic version baseline.";
    semver:module-version "1.0.0";
  }
  revision 2015-11-09 {
    description
      "IOS XR 6.0 revision.";
  }

  container dwdm {
    config false;
    description
      "DWDM operational data";
    container ports {
      description
        "All DWDM Port operational data";
      list port {
        key "name";
        description
          "DWDM Port operational data";
        container prbs {
          description
            "DWDM Port PRBS related data";
          container twenty-four-hours-bucket {
            description
              "Port 24-hour PRBS statistics table";
            container twenty-four-hours-statistics {
              description
                "Port 24-hour PRBS statistics data";
              uses DWDM-EDM-PRBS-INFO;
            }
          }
          container fifteen-minutes-bucket {
            description
              "Port 15-minute PRBS statistics table";
            container fifteen-minutes-statistics {
              description
                "Port 15-minute PRBS statistics data";
              uses DWDM-EDM-PRBS-INFO;
            }
          }
        }
        container optics {
          description
            "DWDM Port optics operational data";
          container wave-info {
            description
              "DWDM port wavelength information data";
            uses DWDM-EDM-WAVE-INFO;
          }
        }
        container info {
          description
            "DWDM port operational data";
          uses DWDM-EDM-PORT-INFO;
        }
        leaf name {
          type xr:Interface-name;
          description
            "Port name";
        }
      }
    }
  }
  container vtxp {
    config false;
    description
      "VTXP specific operational data";
    container dwdm-vtxp {
      description
        "DWDM operational data";
      container port-vtxps {
        description
          "All DWDM Port operational data";
        list port-vtxp {
          key "name";
          description
            "DWDM Port operational data";
          container info {
            description
              "DWDM port operational data";
            uses DWDM-EDM-VTXP-INFO;
          }
          leaf name {
            type xr:Interface-name;
            description
              "Port name";
          }
        }
      }
    }
  }
}
