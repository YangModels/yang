submodule Cisco-IOS-XR-asr9k-netflow-oper-sub3 {

  belongs-to Cisco-IOS-XR-asr9k-netflow-oper {
    prefix Cisco-IOS-XR-asr9k-netflow-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR asr9k-netflow package operational data.

     Copyright (c) 2013-2015 by Cisco Systems, Inc.
     All rights reserved.";

  revision "2015-11-09" {
    description
      "IOS XR 6.0 revision.";
  }


  grouping NFMGR-FSM-EDM-INFO {
    description "Netflow flow sampler data";
    leaf id {
      xr:xr-xml-map "netflow_sampler_types:ID";
      type uint32;
      description "Unique ID in the global flow sampler ID space";
    }
    leaf name {
      xr:xr-xml-map "netflow_sampler_types:Name";
      type string;
      description "Name of the flow sampler map";
    }
    leaf sampling-mode {
      xr:xr-xml-map "netflow_sampler_types:SamplingMode";
      type string;
      description "Sampling mode and parameters";
    }
  }
}
