module Cisco-IOS-XR-pfi-im-cmd-oper {

  /*** NAMESPACE / PREFIX DEFINITION ***/

  namespace "http://cisco.com/ns/yang/Cisco-IOS-XR-pfi-im-cmd-oper";


  prefix "pfi-im-cmd-oper";

  /*** LINKAGE (IMPORTS / INCLUDES) ***/

  import Cisco-IOS-XR-types { prefix "xr"; }

  include Cisco-IOS-XR-pfi-im-cmd-oper-sub2 {
    revision-date 2015-11-09;
  }

  include Cisco-IOS-XR-pfi-im-cmd-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR pfi-im-cmd package operational data.

     This module contains definitions
     for the following management objects:
       interfaces: Interface operational data

     Copyright (c) 2013-2015 by Cisco Systems, Inc.
     All rights reserved.";

  revision "2015-11-09" {
    description
      "IOS XR 6.0 revision.";
  }

  typedef Interface-type-set {
    type enumeration {
      enum hardware-interfaces {
        value 0;
        description
          "Restrict the output to hardware interfaces only";
      }
    }
    description "Interface type set";
  }

  grouping INTERFACE-SUMMARY {
    description "Common node of node-type-set, interfaces";

    container interface-summary {
      xr:xr-xml-map "pfi_im_cmd_oper:InterfaceSummary";
      description "Interface summary information";
      uses IM-IF-SUMMARY-INFO;
    }
  }

  container interfaces {
    xr:xr-xml-map "pfi_im_cmd_oper:Interfaces";
    config false;
    description "Interface operational data";

    container interface-xr {
      xr:xr-xml-map "pfi_im_cmd_oper:InterfaceTable";
      description
        "Detailed operational data for interfaces and
        configured features";

      list interface {
        xr:xr-xml-map "pfi_im_cmd_oper:Interface";
        key "interface-name";
        description
          "Detailed operational data for a particular
          interface";
        leaf interface-name {
          xr:xr-xml-map "pfi_im_cmd_oper:InterfaceName";
          type xr:Interface-name;
          description "The name of the interface";
        }
        uses IM-CMD-INFO;
      }
    }

    container node-type-sets {
      xr:xr-xml-map "pfi_im_cmd_oper:NodeTypeSetTable";
      description
        "Node and/or interface type specific view of
        interface summary data";

      list node-type-set {
        xr:xr-xml-map "pfi_im_cmd_oper:NodeTypeSet";
        description
          "Summary data for all interfaces on a particular
          node";
        leaf node-name {
          xr:xr-xml-map "pfi_im_cmd_oper:NodeName";
          type xr:Node-id;
          description "The location to filter on";
        }
        leaf type-set-name {
          xr:xr-xml-map "pfi_im_cmd_oper:TypeSetName";
          type Interface-type-set;
          description "The interface type to filter on";
        }
        uses INTERFACE-SUMMARY;
      }
    }

    container interface-briefs {
      xr:xr-xml-map "pfi_im_cmd_oper:InterfaceBriefTable";
      description "Brief operational data for interfaces";

      list interface-brief {
        xr:xr-xml-map "pfi_im_cmd_oper:InterfaceBrief";
        key "interface-name";
        description
          "Brief operational attributes for a particular
          interface";
        leaf interface-name {
          xr:xr-xml-map "pfi_im_cmd_oper:InterfaceName";
          type xr:Interface-name;
          description "The name of the interface";
        }
        uses IMDS-IFATTR-BASE-INFO;
      }
    }

    container inventory-summary {
      xr:xr-xml-map "pfi_im_cmd_oper:InventorySummary";
      description "Inventory summary information";
      uses IM-IF-SUMMARY-INFO;
    }

    container interfaces {
      xr:xr-xml-map "pfi_im_cmd_oper:InterfaceDescriptionTable";
      description "Descriptions for interfaces";

      list interface {
        xr:xr-xml-map "pfi_im_cmd_oper:Interface";
        key "interface-name";
        description "Description for a particular interface";
        leaf interface-name {
          xr:xr-xml-map "pfi_im_cmd_oper:InterfaceName";
          type xr:Interface-name;
          description "The name of the interface";
        }
        uses IM-DESC-INFO;
      }
    }
    uses INTERFACE-SUMMARY;
  }
}
