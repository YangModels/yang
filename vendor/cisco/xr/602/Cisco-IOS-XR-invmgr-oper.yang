module Cisco-IOS-XR-invmgr-oper {

  /*** NAMESPACE / PREFIX DEFINITION ***/

  namespace "http://cisco.com/ns/yang/Cisco-IOS-XR-invmgr-oper";


  prefix "invmgr-oper";

  /*** LINKAGE (IMPORTS / INCLUDES) ***/

  import Cisco-IOS-XR-types { prefix "xr"; }

  include Cisco-IOS-XR-invmgr-oper-sub4 {
    revision-date 2015-11-09;
  }

  include Cisco-IOS-XR-invmgr-oper-sub3 {
    revision-date 2015-11-09;
  }

  include Cisco-IOS-XR-invmgr-oper-sub2 {
    revision-date 2015-11-09;
  }

  include Cisco-IOS-XR-invmgr-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR invmgr package operational data.

     This module contains definitions
     for the following management objects:
       inventory: Inventory information

     Copyright (c) 2013-2015 by Cisco Systems, Inc.
     All rights reserved.";

  revision "2015-11-09" {
    description
      "IOS XR 6.0 revision.";
  }


  grouping THRESH-BAG {
    description
      "Common node of minor-lo, minor-hi, major-lo,
      major-hi, critical-lo, critical-hi";

    container thresh-bag {
      xr:xr-xml-map "invmgr_oper:ThreshBag";
      description "Environment threshold info";
      uses ENVMON-THRESHOLD-INFO;
    }
  }

  grouping ATTRIBUTES {
    description
      "Common node of rack, slot, tsi1, tsi2, tsi3, tsi4
      , tsi5, tsi6, tsi7, tsi8, tsi9, tsi10, tsi11";

    container attributes {
      xr:xr-xml-map "invmgr_oper:Attributes";
      description "Attributes";

      container node-state-info {
        xr:xr-xml-map "invmgr_oper:NodeStateInfo";
        description "Inventory Node State info";
        uses INV-NODE-STATE-INFO;
      }

      container env-sensor-info {
        xr:xr-xml-map "invmgr_oper:EnvSensorInfo";
        description "Environment sensor info";
        uses ENVMON-SENSOR-INFO;
      }

      container pwg-info {
        xr:xr-xml-map "invmgr_oper:PWGInfo";
        description "Inventory EDM PWG info";
        uses INV-PWG-INFO;
      }

      container env-sensor-info-xml {
        xr:xr-xml-map "invmgr_oper:EnvSensorInfoXML";
        description "Environment sensor info XML";
        uses ENVMON-SENSOR-INFO-XML;
      }

      container inv-asset-bag {
        xr:xr-xml-map "invmgr_oper:InvAssetBag";
        description "Inventory Asset Bag";
        uses INV-PHY-ENTITY-ASSET-INFO;
      }

      container threshold {
        xr:xr-xml-map "invmgr_oper:Threshold";
        description "Threshold";

        container major-lo {
          xr:xr-xml-map "invmgr_oper:MajorLo";
          description "Major Low";
          uses THRESH-BAG;
        }

        container critical-hi {
          xr:xr-xml-map "invmgr_oper:CriticalHi";
          description "Critical High";
          uses THRESH-BAG;
        }

        container minor-hi {
          xr:xr-xml-map "invmgr_oper:MinorHi";
          description "Minor High";
          uses THRESH-BAG;
        }

        container major-hi {
          xr:xr-xml-map "invmgr_oper:MajorHi";
          description "Major High";
          uses THRESH-BAG;
        }

        container critical-lo {
          xr:xr-xml-map "invmgr_oper:CriticalLo";
          description "Critical Low";
          uses THRESH-BAG;
        }

        container minor-lo {
          xr:xr-xml-map "invmgr_oper:MinorLo";
          description "Minor Low";
          uses THRESH-BAG;
        }
      }

      container fru-info {
        xr:xr-xml-map "invmgr_oper:FRUInfo";
        description "Inventory EDM FRU info";
        uses INV-CARD-FRU-INFO;
      }

      container inv-basic-bag {
        xr:xr-xml-map "invmgr_oper:InvBasicBag";
        description "Inventory Basic Bag";
        uses INV-PHY-ENTITY-BASIC-INFO;
      }

      container inv-eeprom-info {
        xr:xr-xml-map "invmgr_oper:InvEEPROMInfo";
        description "Inventory EDM EEPROM Information Bag";
        uses INVMGR-EEPROM-OPAQUE-DATA;
      }
      leaf module-done {
        xr:xr-xml-map "invmgr_oper:ModuleDone";
        type int32;
        default "1";
        description "Inventory EDM Module Done Tuple";
      }
      leaf vm-node-id {
        xr:xr-xml-map "invmgr_oper:VMNodeID";
        type int32;
        description "VM Node ID Tuple";
      }
      leaf vm-done {
        xr:xr-xml-map "invmgr_oper:VMDone";
        type int32;
        description "VM Done Tuple";
      }
      leaf node-id {
        xr:xr-xml-map "invmgr_oper:NodeID";
        type int32;
        description "Node ID Tuple";
      }
    }
  }

  grouping SLOT {
    description "Common node of powershelf, fantray, entity";

    list slot {
      xr:xr-xml-map "invmgr_oper:Slot";
      key "name";
      description "Slot number";

      container tsi1s {
        xr:xr-xml-map "invmgr_oper:EntityLevel1";
        description "Entity Level 1";

        list tsi1 {
          xr:xr-xml-map "invmgr_oper:TSI1";
          key "name";
          description "TSI1";

          container tsi2s {
            xr:xr-xml-map "invmgr_oper:EntityLevel2";
            description "Entity Level 2";

            list tsi2 {
              xr:xr-xml-map "invmgr_oper:TSI2";
              key "name";
              description "TSI2";

              container tsi3s {
                xr:xr-xml-map "invmgr_oper:EntityLevel3";
                description "Entity Level 3";

                list tsi3 {
                  xr:xr-xml-map "invmgr_oper:TSI3";
                  key "name";
                  description "TSI3";

                  container tsi4s {
                    xr:xr-xml-map "invmgr_oper:EntityLevel4";
                    description "Entity Level 4";

                    list tsi4 {
                      xr:xr-xml-map "invmgr_oper:TSI4";
                      key "name";
                      description "TSI4";

                      container tsi5s {
                        xr:xr-xml-map "invmgr_oper:EntityLevel5";
                        description "Entity Level 5";

                        list tsi5 {
                          xr:xr-xml-map "invmgr_oper:TSI5";
                          key "name";
                          description "TSI5";

                          container tsi6s {
                            xr:xr-xml-map "invmgr_oper:EntityLevel6";
                            description "Entity Level 6";

                            list tsi6 {
                              xr:xr-xml-map "invmgr_oper:TSI6";
                              key "name";
                              description "TSI6";

                              container tsi7s {
                                xr:xr-xml-map "invmgr_oper:EntityLe"+
                                  "vel7";
                                description "Entity Level 7";

                                list tsi7 {
                                  xr:xr-xml-map "invmgr_oper:TSI7";
                                  key "name";
                                  description "TSI7";

                                  container tsi8s {
                                    xr:xr-xml-map "invmgr_oper:Enti"+
                                      "tyLevel8";
                                    description "Entity Level 8";

                                    list tsi8 {
                                      xr:xr-xml-map "invmgr_oper:TS"+
                                        "I8";
                                      key "name";
                                      description "TSI8";

                                      container tsi9s {
                                        xr:xr-xml-map "invmgr_oper:"+
                                          "EntityLevel9";
                                        description
                                          "Entity Level 9";

                                        list tsi9 {
                                          xr:xr-xml-map "invmgr_ope"+
                                            "r:TSI9";
                                          key "name";
                                          description "TSI9";

                                          container tsi10s {
                                            xr:xr-xml-map "invmgr_o"+
                                              "per:EntityLevel10";
                                            description
                                              "Entity Level 10";

                                            list tsi10 {
                                              xr:xr-xml-map "invmgr"+
                                                "_oper:TSI10";
                                              key "name";
                                              description "TSI10";

                                              container tsi11s {
                                                xr:xr-xml-map "invm"+
                                                  "gr_oper:EntityLe"+
                                                  "vel11";
                                                description
                                                  "Entity Level 11";

                                                list tsi11 {
                                                  xr:xr-xml-map "in"+
                                                    "vmgr_oper:TSI1"+
                                                    "1";
                                                  key "name";
                                                  description
                                                    "TSI11";
                                                  leaf name {
                                                    xr:xr-xml-map "invmgr_oper:Name";
                                                    type xr:Cisco-ios-xr-string;
                                                    description
                                                      "TSI11";
                                                  }
                                                  uses ATTRIBUTES;
                                                }
                                              }
                                              leaf name {
                                                xr:xr-xml-map "invm"+
                                                  "gr_oper:Name";
                                                type xr:Cisco-ios-xr-string;
                                                description "TSI10";
                                              }
                                              uses ATTRIBUTES;
                                            }
                                          }
                                          leaf name {
                                            xr:xr-xml-map "invmgr_o"+
                                              "per:Name";
                                            type xr:Cisco-ios-xr-string;
                                            description "TSI9";
                                          }
                                          uses ATTRIBUTES;
                                        }
                                      }
                                      leaf name {
                                        xr:xr-xml-map "invmgr_oper:"+
                                          "Name";
                                        type xr:Cisco-ios-xr-string;
                                        description "TSI8";
                                      }
                                      uses ATTRIBUTES;
                                    }
                                  }
                                  leaf name {
                                    xr:xr-xml-map "invmgr_oper:Name";
                                    type xr:Cisco-ios-xr-string;
                                    description "TSI7";
                                  }
                                  uses ATTRIBUTES;
                                }
                              }
                              leaf name {
                                xr:xr-xml-map "invmgr_oper:Name";
                                type xr:Cisco-ios-xr-string;
                                description "TSI6";
                              }
                              uses ATTRIBUTES;
                            }
                          }
                          leaf name {
                            xr:xr-xml-map "invmgr_oper:Name";
                            type xr:Cisco-ios-xr-string;
                            description "TSI5";
                          }
                          uses ATTRIBUTES;
                        }
                      }
                      leaf name {
                        xr:xr-xml-map "invmgr_oper:Name";
                        type xr:Cisco-ios-xr-string;
                        description "TSI4";
                      }
                      uses ATTRIBUTES;
                    }
                  }
                  leaf name {
                    xr:xr-xml-map "invmgr_oper:Name";
                    type xr:Cisco-ios-xr-string;
                    description "TSI3";
                  }
                  uses ATTRIBUTES;
                }
              }
              leaf name {
                xr:xr-xml-map "invmgr_oper:Name";
                type xr:Cisco-ios-xr-string;
                description "TSI2";
              }
              uses ATTRIBUTES;
            }
          }
          leaf name {
            xr:xr-xml-map "invmgr_oper:Name";
            type xr:Cisco-ios-xr-string;
            description "TSI1";
          }
          uses ATTRIBUTES;
        }
      }
      leaf name {
        xr:xr-xml-map "invmgr_oper:Name";
        type xr:Cisco-ios-xr-string;
        description "Slot name";
      }
      uses ATTRIBUTES;
    }
  }

  container inventory {
    xr:xr-xml-map "invmgr_oper:Inventory";
    config false;
    description "Inventory information";

    container racks {
      xr:xr-xml-map "invmgr_oper:RackTable";
      description "RackTable";

      list rack {
        xr:xr-xml-map "invmgr_oper:Rack";
        key "name";
        description "Rack name";

        container entity {
          xr:xr-xml-map "invmgr_oper:Entity";
          description "Entity information";
          uses SLOT;
        }

        container powershelf {
          xr:xr-xml-map "invmgr_oper:Powershelf";
          description "Powershelf information";
          uses SLOT;
        }

        container fantray {
          xr:xr-xml-map "invmgr_oper:Fantray";
          description "Fantray information";
          uses SLOT;
        }
        leaf name {
          xr:xr-xml-map "invmgr_oper:Name";
          type xr:Cisco-ios-xr-string;
          description "Rack name";
        }
        uses ATTRIBUTES;
      }
    }
  }
}
