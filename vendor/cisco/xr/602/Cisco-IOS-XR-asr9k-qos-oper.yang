module Cisco-IOS-XR-asr9k-qos-oper {

  /*** NAMESPACE / PREFIX DEFINITION ***/

  namespace "http://cisco.com/ns/yang/Cisco-IOS-XR-asr9k-qos-oper";


  prefix "asr9k-qos-oper";

  /*** LINKAGE (IMPORTS / INCLUDES) ***/

  import Cisco-IOS-XR-types { prefix "xr"; }

  include Cisco-IOS-XR-asr9k-qos-oper-sub2 {
    revision-date 2015-11-09;
  }

  include Cisco-IOS-XR-asr9k-qos-oper-sub1 {
    revision-date 2015-11-09;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR asr9k-qos package operational data.

     This module contains definitions
     for the following management objects:
       platform-qos: QoS ASR9K platform operational data 

     Copyright (c) 2013-2015 by Cisco Systems, Inc.
     All rights reserved.";

  revision "2015-11-09" {
    description
      "IOS XR 6.0 revision.";
  }


  grouping DETAILS {
    description "Common node of output, input, member-interface";

    container details {
      xr:xr-xml-map "qos_asr9k_oper:Details";
      description "QoS policy direction egress";
      uses QOS-SHOW-EA-POLICY;
    }
  }

  grouping STATISTICS {
    description "Common node of input, output";

    container statistics {
      xr:xr-xml-map "qos_pi_asr9k_oper:Statistics";
      description
        "Policy-map statistics operational data for an
        interface";
      uses QOS-STATS;
    }
  }

  grouping INTERFACE {
    description
      "Common node of interface-table,
      nv-interface-table";

    list interface {
      xr:xr-xml-map "qos_pi_asr9k_oper:Interface";
      key "interface-name";
      description
        "QoS policy-map operational data for a particular
        interface";
      leaf interface-name {
        xr:xr-xml-map "qos_pi_asr9k_oper:InterfaceName";
        type xr:Interface-name;
        description "Name of the interface";
      }
      uses MEMBER-INTERFACE-TABLE;
      uses SATELLITE-ID-TABLE;
      uses INPUT;
      uses OUTPUT;
    }
  }

  grouping INPUT {
    description
      "Common node of shared-policy-instance,
      member-interface, interface,
      nv-satellite-interface, satellite-id";

    container input {
      xr:xr-xml-map "qos_pi_asr9k_oper:Input";
      description
        "A piece of QoS policy-map operational data for
        an interface";
      uses STATISTICS;
    }
  }

  grouping MEMBER-INTERFACE-TABLE {
    description
      "Common node of interface, nv-satellite-interface,
      shared-policy-instance";

    container member-interfaces {
      xr:xr-xml-map "qos_pi_asr9k_oper:MemberInterfaceTable";
      description "QoS policy-map member interface table";

      list member-interface {
        xr:xr-xml-map "qos_pi_asr9k_oper:MemberInterface";
        key "interface-name";
        description "QoS policy-map member interface statistics";
        leaf interface-name {
          xr:xr-xml-map "qos_pi_asr9k_oper:InterfaceName";
          type xr:Interface-name;
          description "Name of member interface";
        }
        uses SATELLITE-ID-TABLE;
        uses INPUT;
        uses OUTPUT;
      }
    }
  }

  grouping QOS-ASR9K-OPER-MEMBER-INTERFACE-TABLE {
    description "Common node of bundle-output, bundle-input";

    container member-interfaces {
      xr:xr-xml-map "qos_asr9k_oper:MemberInterfaceTable";
      description "QoS list of member interfaces";

      list member-interface {
        xr:xr-xml-map "qos_asr9k_oper:MemberInterface";
        key "interface-name";
        description "QoS interface name";
        leaf interface-name {
          xr:xr-xml-map "qos_asr9k_oper:InterfaceName";
          type xr:Interface-name;
          description "Memeber interface";
        }
        uses DETAILS;
      }
    }
  }

  grouping OUTPUT {
    description
      "Common node of shared-policy-instance,
      member-interface, interface,
      nv-satellite-interface, satellite-id";

    container output {
      xr:xr-xml-map "qos_pi_asr9k_oper:Output";
      description
        "A piece of QoS policy-map operational data for
        an interface";
      uses STATISTICS;
    }
  }

  grouping SATELLITE-ID-TABLE {
    description "Common node of interface, member-interface";

    container satellite-ids {
      xr:xr-xml-map "qos_pi_asr9k_oper:SatelliteIDTable";
      description "Satellite ID information";

      list satellite-id {
        xr:xr-xml-map "qos_pi_asr9k_oper:SatelliteID";
        key "nv-satellite-id";
        description "Satellite ID information";
        leaf nv-satellite-id {
          xr:xr-xml-map "qos_pi_asr9k_oper:nVSatelliteID";
          type int32;
          description "Satellite ID";
        }
        uses INPUT;
        uses OUTPUT;
      }
    }
  }

  container platform-qos {
    xr:xr-xml-map "qos_asr9k_oper:PlatformQoS";
    config false;
    description "QoS ASR9K platform operational data ";

    container nodes {
      xr:xr-xml-map "qos_asr9k_oper:NodeTable";
      description
        "List of nodes with platform specific QoS
        configuration";

      list node {
        xr:xr-xml-map "qos_asr9k_oper:Node";
        key "node-name";
        description "Node with platform specific QoS configuration";

        container capability {
          xr:xr-xml-map "qos_asr9k_oper:Capability";
          description "QoS system capability";
          uses QOS-EA-CAPABILITY;
        }

        container interfaces {
          xr:xr-xml-map "qos_asr9k_oper:InterfaceTable";
          description "QoS list of interfaces";

          list interface {
            xr:xr-xml-map "qos_asr9k_oper:Interface";
            key "interface-name";
            description "QoS interface name";

            container input {
              xr:xr-xml-map "qos_asr9k_oper:Input";
              description "QoS policy direction ingress";
              uses DETAILS;
            }

            container output {
              xr:xr-xml-map "qos_asr9k_oper:Output";
              description "QoS policy direction egress";
              uses DETAILS;
            }
            leaf interface-name {
              xr:xr-xml-map "qos_asr9k_oper:InterfaceName";
              type xr:Interface-name;
              description "The name of the interface";
            }
          }
        }

        container bundle-interfaces {
          xr:xr-xml-map "qos_asr9k_oper:BundleInterfaceTable";
          description "QoS list of bundle interfaces";

          list bundle-interface {
            xr:xr-xml-map "qos_asr9k_oper:BundleInterface";
            key "interface-name";
            description "QoS interface name";

            container bundle-output {
              xr:xr-xml-map "qos_asr9k_oper:BundleOutput";
              description "QoS policy direction output";
              uses QOS-ASR9K-OPER-MEMBER-INTERFACE-TABLE;
            }

            container bundle-input {
              xr:xr-xml-map "qos_asr9k_oper:BundleInput";
              description "QoS policy direction output";
              uses QOS-ASR9K-OPER-MEMBER-INTERFACE-TABLE;
            }
            leaf interface-name {
              xr:xr-xml-map "qos_asr9k_oper:InterfaceName";
              type xr:Interface-name;
              description "Bundle interface name";
            }
          }
        }
        leaf node-name {
          xr:xr-xml-map "qos_asr9k_oper:NodeName";
          type xr:Node-id;
          description "Node name";
        }
      }
    }
  }
}
