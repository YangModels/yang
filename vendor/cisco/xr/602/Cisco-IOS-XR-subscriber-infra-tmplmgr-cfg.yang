module Cisco-IOS-XR-subscriber-infra-tmplmgr-cfg {

  /*** NAMESPACE / PREFIX DEFINITION ***/

  namespace "http://cisco.com/ns/yang"+
    "/Cisco-IOS-XR-subscriber-infra-tmplmgr-cfg";


  prefix "subscriber-infra-tmplmgr-cfg";

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR subscriber-infra-tmplmgr package configuration.

     This module contains definitions
     for the following management objects:
       dynamic-template: All dynamic template configurations

     Copyright (c) 2013-2015 by Cisco Systems, Inc.
     All rights reserved.";

  revision "2015-01-07" {
    description
      "IOS XR 5.3.1 revision.";
  }


  container dynamic-template {
    xr:xr-xml-map "subscriber_infra_subdb_cfg:DynamicTemplate";
    description "All dynamic template configurations";

    container ppps {
      xr:xr-xml-map "subscriber_infra_subdb_cfg:PPPTable";
      description "Templates of the PPP Type";

      list ppp {
        xr:xr-xml-map "subscriber_infra_subdb_cfg:PPP";
        key "template-name";
        description "A Template of the PPP Type";
        leaf template-name {
          xr:xr-xml-map "subscriber_infra_subdb_cfg:TemplateName";
          type xr:Cisco-ios-xr-string;
          description "The name of the template";
        }
      }
    }

    container ip-subscribers {
      xr:xr-xml-map "subscriber_infra_subdb_cfg:IPSubscriberTable";
      description "The IP Subscriber Template Table";

      list ip-subscriber {
        xr:xr-xml-map "subscriber_infra_subdb_cfg:IPSubscriber";
        key "template-name";
        description "A IP Subscriber Type Template ";
        leaf template-name {
          xr:xr-xml-map "subscriber_infra_subdb_cfg:TemplateName";
          type xr:Cisco-ios-xr-string;
          description "The name of the template";
        }
      }
    }

    container subscriber-services {
      xr:xr-xml-map "subscriber_infra_subdb_cfg:SubscriberServiceTa"+
        "ble";
      description "The Service Type Template Table";

      list subscriber-service {
        xr:xr-xml-map "subscriber_infra_subdb_cfg:SubscriberService";
        key "template-name";
        description "A Service Type Template ";
        leaf template-name {
          xr:xr-xml-map "subscriber_infra_subdb_cfg:TemplateName";
          type xr:Cisco-ios-xr-string;
          description "The name of the template";
        }
      }
    }
  }
}
