submodule Cisco-IOS-XR-nto-misc-oper-sub1 {

  belongs-to Cisco-IOS-XR-nto-misc-oper {
    prefix Cisco-IOS-XR-nto-misc-oper;
  }

  /*** LINKAGE (IMPORTS / INCLUDES) ***/

  import Cisco-IOS-XR-types { prefix "xr"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This submodule contains a collection of YANG definitions
     for Cisco IOS-XR nto-misc package operational data.

     Copyright (c) 2013-2015 by Cisco Systems, Inc.
     All rights reserved.";

  revision "2015-11-09" {
    description
      "IOS XR 6.0 revision.";
  }


  grouping NODE-MEM-INFO-DETAIL-NG {
    description "Detail Node memory information";
    leaf page-size {
      xr:xr-xml-map "shellutil_meminfo:PageSize";
      type uint32;
      units "byte";
      description "Page size in bytes";
    }
    leaf ram-memory {
      xr:xr-xml-map "shellutil_meminfo:RAMMemory";
      type uint64;
      units "byte";
      description "Physical memory size in bytes";
    }
    leaf free-physical-memory {
      xr:xr-xml-map "shellutil_meminfo:FreePhysicalMemory";
      type uint64;
      units "byte";
      description "Physical memory available in bytes";
    }
    leaf system-ram-memory {
      xr:xr-xml-map "shellutil_meminfo:SystemRAMMemory";
      type uint64;
      units "byte";
      description "Application memory size in bytes";
    }
    leaf free-application-memory {
      xr:xr-xml-map "shellutil_meminfo:FreeApplicationMemory";
      type uint64;
      units "byte";
      description "Application memory available in bytes";
    }
    leaf image-memory {
      xr:xr-xml-map "shellutil_meminfo:ImageMemory";
      type uint64;
      units "byte";
      description "Image memory size in bytes";
    }
    leaf boot-ram-size {
      xr:xr-xml-map "shellutil_meminfo:BootRAMSize";
      type uint64;
      units "byte";
      description "Boot RAM size in bytes";
    }
    leaf reserved-memory {
      xr:xr-xml-map "shellutil_meminfo:ReservedMemory";
      type uint64;
      units "byte";
      description "Reserved memory size in bytes";
    }
    leaf io-memory {
      xr:xr-xml-map "shellutil_meminfo:IOMemory";
      type uint64;
      units "byte";
      description "IO memory size in bytes";
    }
    leaf flash-system {
      xr:xr-xml-map "shellutil_meminfo:FlashSystem";
      type uint64;
      units "byte";
      description "Flash System size in bytes";
    }
  }

  grouping NODE-MEM-INFO {
    description "Node memory information";
    leaf page-size {
      xr:xr-xml-map "shellutil_meminfo:PageSize";
      type uint32;
      units "byte";
      description "Page size in bytes";
    }
    leaf ram-memory {
      xr:xr-xml-map "shellutil_meminfo:RAMMemory";
      type uint64;
      units "byte";
      description "Physical memory size in bytes";
    }
    leaf free-physical-memory {
      xr:xr-xml-map "shellutil_meminfo:FreePhysicalMemory";
      type uint64;
      units "byte";
      description "Physical memory available in bytes";
    }
    leaf system-ram-memory {
      xr:xr-xml-map "shellutil_meminfo:SystemRAMMemory";
      type uint64;
      units "byte";
      description "Application memory size in bytes";
    }
    leaf free-application-memory {
      xr:xr-xml-map "shellutil_meminfo:FreeApplicationMemory";
      type uint64;
      units "byte";
      description "Application memory available in bytes";
    }
    leaf image-memory {
      xr:xr-xml-map "shellutil_meminfo:ImageMemory";
      type uint64;
      units "byte";
      description "Image memory size in bytes";
    }
    leaf boot-ram-size {
      xr:xr-xml-map "shellutil_meminfo:BootRAMSize";
      type uint64;
      units "byte";
      description "Boot RAM size in bytes";
    }
    leaf reserved-memory {
      xr:xr-xml-map "shellutil_meminfo:ReservedMemory";
      type uint64;
      units "byte";
      description "Reserved memory size in bytes";
    }
    leaf io-memory {
      xr:xr-xml-map "shellutil_meminfo:IOMemory";
      type uint64;
      units "byte";
      description "IO memory size in bytes";
    }
    leaf flash-system {
      xr:xr-xml-map "shellutil_meminfo:FlashSystem";
      type uint64;
      units "byte";
      description "Flash System size in bytes";
    }
  }
}
