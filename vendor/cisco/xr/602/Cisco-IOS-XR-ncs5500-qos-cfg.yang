module Cisco-IOS-XR-ncs5500-qos-cfg {

  /*** NAMESPACE / PREFIX DEFINITION ***/

  namespace "http://cisco.com/ns/yang/Cisco-IOS-XR-ncs5500-qos-cfg";


  prefix "ncs5500-qos-cfg";

  /*** LINKAGE (IMPORTS / INCLUDES) ***/

  import Cisco-IOS-XR-types { prefix "xr"; }

  import Cisco-IOS-XR-ifmgr-cfg { prefix "a1"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR ncs5500-qos package configuration.

     This YANG module augments the
       Cisco-IOS-XR-ifmgr-cfg
     module with configuration data.

     Copyright (c) 2013-2015 by Cisco Systems, Inc.
     All rights reserved.";

  revision "2015-11-09" {
    description
      "IOS XR 6.0 revision.";
  }

  typedef Qos-field-not-supported {
    type enumeration {
      enum not-supported {
        value 0;
        description "Dummy data type leave unspecified";
      }
    }
    description "Qos field not supported";
  }
  typedef Qos-policy-account {
    type enumeration {
      enum no-preference {
        value 0;
        description "No account turn off preference";
      }
      enum layer2 {
        value 1;
        description "Turn on layer 2 accounting";
      }
      enum no-layer2 {
        value 2;
        description "Turn off layer 2 accounting";
      }
      enum user-defined {
        value 4;
        description "User defined accounting";
      }
      enum layer1 {
        value 8;
        description "Turn on layer 1 accounting";
      }
    }
    description "Qos policy account";
  }

  grouping QOS {
    description
      "Common node of interface-configuration, cac, pvp,
      pac, pvc-mode";

    container qos {
      xr:xr-xml-map "qos_ea_fretta_interface_cfg:QOS";
      description "Interface QOS configuration";

      container input {
        xr:xr-xml-map "qos_ea_fretta_interface_cfg:Input";
        description "Ingress service policy";
        uses SERVICE-POLICY;
      }

      container output {
        xr:xr-xml-map "qos_ea_fretta_interface_cfg:Output";
        description "Egress service policy";
        uses SERVICE-POLICY;
      }
      leaf actual-rate-up {
        xr:xr-xml-map "qos_ea_fretta_interface_cfg:ActualRateUp";
        type uint32 {
          range "1..4294967295";
        }
        description "Minimum bandwidth guaranteed for a subscriber";
      }
      leaf actual-rate-down {
        xr:xr-xml-map "qos_ea_fretta_interface_cfg:ActualRateDown";
        type uint32 {
          range "1..4294967295";
        }
        description "Minimum bandwidth guaranteed for a subscriber";
      }
    }
  }

  grouping SERVICE-POLICY {
    description "Common node of input, output";

    list service-policy {
      xr:xr-xml-map "qos_ea_fretta_interface_cfg:ServicePolicy";
      key "service-policy-name";
      description "Service policy details";
      leaf service-policy-name {
        xr:xr-xml-map "qos_ea_fretta_interface_cfg:ServicePolicyNam"+
          "e";
        type string {
          length "0..64";
        }
        description "Name of policy-map";
      }
      leaf account-type {
        xr:xr-xml-map "qos_ea_fretta_interface_cfg:AccountType";
        type Qos-policy-account;
        description "Turn off L2 or L3 accounting.";
      }
      leaf l1-user-defined {
        xr:xr-xml-map "qos_ea_fretta_interface_cfg:L1UserDefined";
        type int32 {
          range "-63..63";
        }
        description "User specified value";
      }
      leaf spi-name {
        xr:xr-xml-map "qos_ea_fretta_interface_cfg:SPIName";
        type string;
        description "Not supported (Leave unspecified).";
      }
      leaf policy-merge {
        xr:xr-xml-map "qos_ea_fretta_interface_cfg:PolicyMerge";
        type Qos-field-not-supported;
        description "Not supported (Leave unspecified).";
      }
      leaf subscriber-parent-policy {
        xr:xr-xml-map "qos_ea_fretta_interface_cfg:SubscriberParent"+
          "Policy";
        type Qos-field-not-supported;
        description "Not supported (Leave unspecified).";
      }
      leaf resource-id {
        xr:xr-xml-map "qos_ea_fretta_interface_cfg:ResourceID";
        type Qos-field-not-supported;
        description "Not supported (Leave unspecified).";
      }
      leaf service-fragment-parent-policy {
        xr:xr-xml-map "qos_ea_fretta_interface_cfg:ServiceFragmentP"+
          "arentPolicy";
        type Qos-field-not-supported;
        description "Not supported (Leave unspecified).";
      }
    }
  }

  augment "/a1:interface-configurations/a1:interface-configuration" {
    description
      "This augment extends the configuration data of
      'Cisco-IOS-XR-ifmgr-cfg'";
    uses QOS;
  }
}
