module Cisco-IOS-XR-snmp-ifmib-oper {

  /*** NAMESPACE / PREFIX DEFINITION ***/

  namespace "http://cisco.com/ns/yang/Cisco-IOS-XR-snmp-ifmib-oper";


  prefix "snmp-ifmib-oper";

  /*** LINKAGE (IMPORTS / INCLUDES) ***/

  import Cisco-IOS-XR-types { prefix "xr"; }

  import Cisco-IOS-XR-snmp-agent-oper { prefix "a1"; }

  include Cisco-IOS-XR-snmp-ifmib-oper-sub1 {
    revision-date 2015-01-07;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description 
    "This module contains a collection of YANG definitions
     for Cisco IOS-XR snmp-ifmib package operational data.

     This YANG module augments the
       Cisco-IOS-XR-snmp-agent-oper
     module with state data.

     Copyright (c) 2013-2015 by Cisco Systems, Inc.
     All rights reserved.";

  revision "2015-01-07" {
    description
      "IOS XR 5.3.1 revision.";
  }


  augment "/a1:snmp" {

    container interface-mib {
      xr:xr-xml-map "snmp_mibs_ifmib_oper:InterfaceMIB";
      description "SNMP IF-MIB information";

      container interfaces {
        xr:xr-xml-map "snmp_mibs_ifmib_oper:InterfaceTable";
        description "Interfaces ifIndex information";

        list interface {
          xr:xr-xml-map "snmp_mibs_ifmib_oper:Interface";
          key "interface-name";
          description "ifIndex for a specific Interface Name";
          leaf interface-name {
            xr:xr-xml-map "snmp_mibs_ifmib_oper:InterfaceName";
            type xr:Interface-name;
            description "Interface Name";
          }
          uses IFMIB-IFNAME-IFINDEX-ENTRY;
        }
      }

      container interface-connectors {
        xr:xr-xml-map "snmp_mibs_ifmib_oper:InterfaceConnectorTable";
        description "Interfaces ifConnectorPresent information";

        list interface-connector {
          xr:xr-xml-map "snmp_mibs_ifmib_oper:InterfaceConnector";
          key "interface-name";
          description
            "ifConnectorPresent for a specific Interface
            Name";
          leaf interface-name {
            xr:xr-xml-map "snmp_mibs_ifmib_oper:InterfaceName";
            type xr:Interface-name;
            description "Interface Name";
          }
          uses IFMIB-IFCONNECTORPRESENT-ENTRY;
        }
      }

      container interface-aliases {
        xr:xr-xml-map "snmp_mibs_ifmib_oper:InterfaceAliasTable";
        description "Interfaces ifAlias information";

        list interface-alias {
          xr:xr-xml-map "snmp_mibs_ifmib_oper:InterfaceAlias";
          key "interface-name";
          description "ifAlias for a specific Interface Name";
          leaf interface-name {
            xr:xr-xml-map "snmp_mibs_ifmib_oper:InterfaceName";
            type xr:Interface-name;
            description "Interface Name";
          }
          uses IFMIB-IFALIAS-ENTRY;
        }
      }

      container notification-interfaces {
        xr:xr-xml-map "snmp_mibs_ifmib_oper:NotificationInterfaceTa"+
          "ble";
        description "Interfaces Notification information";

        list notification-interface {
          xr:xr-xml-map "snmp_mibs_ifmib_oper:NotificationInterface";
          key "interface-name";
          description "Notification for specific Interface Name";
          leaf interface-name {
            xr:xr-xml-map "snmp_mibs_ifmib_oper:InterfaceName";
            type xr:Interface-name;
            description "Interface Name";
          }
          uses IFMIB-NOTIF-STATUS-ENTRY;
        }
      }

      container interface-stack-statuses {
        xr:xr-xml-map "snmp_mibs_ifmib_oper:InterfaceStackStatusTab"+
          "le";
        description "Interfaces ifstackstatus information";

        list interface-stack-status {
          xr:xr-xml-map "snmp_mibs_ifmib_oper:InterfaceStackStatus";
          key "interface-stack-status";
          description "ifstatus for a pair of Interface";
          leaf interface-stack-status {
            xr:xr-xml-map "snmp_mibs_ifmib_oper:InterfaceStackStatu"+
              "s";
            type xr:Cisco-ios-xr-string;
            description "StackHigherLayer.StackLowerLayer";
          }
          uses IFMIB-IFSTACKSTATUS-ENTRY;
        }
      }
    }
    description
      "This augment extends the operational data of
      'Cisco-IOS-XR-snmp-agent-oper'";
  }
}
